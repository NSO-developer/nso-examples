module my-alarms {
  namespace "http://examples.com/ma";
  prefix ma;

  import tailf-ncs-alarms {
    prefix al;
  }

  identity website-alarm {
    base al:alarm-type;
  }


  // This alarm is generated by explicit test Java code

  identity webserver-on-fire {
    base website-alarm;
  }


  // The webserver devices generate linkDown, linkUp NETCONF notifications
  // This alarmtype is used to illustrate the whole chain of events
  // where:
  // 1. ConfD device generates a NETCONF notification, and NCS subscribes to
  //    those notifs
  // 2. NCS writes the Notif into the notif table
  // 3. Usercode in
  //    src/main/java/com/tailf/examples/website/NcNotifSubscriber.java
  //    picks up the Notif
  // 4. That code creates the link-down/link-up alarm using AlarmSink.java
  // 5. An SNMP trap, is generated by
  //    NCS and sent northbound
  // 6. A user of the alarmSource also picks up a copy of the Alarm

  identity link-down {
    base website-alarm;
  }

  identity link-up {
    base website-alarm;
  }



}
