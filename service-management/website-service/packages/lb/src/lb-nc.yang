module lb-nc {
  yang-version 1.1;
  namespace "http://tail-f.com/ns/ned-id/lb-nc";
  prefix lb-nc;

  import tailf-common {
    prefix tailf;
  }

  import tailf-ncs-ned {
    prefix ned;
  }

  identity lb-nc {
    tailf:abstract;
    base ned:netconf-ned-id;
  }
}
