module webserver-nc-1.2 {
  yang-version 1.1;
  namespace "http://tail-f.com/ns/ned-id/webserver-nc-1.2";
  prefix webserver-nc-1.2;

  import webserver-nc {
    prefix family;
  }

  identity webserver-nc-1.2 {
    base family:webserver-nc;
  }
}
