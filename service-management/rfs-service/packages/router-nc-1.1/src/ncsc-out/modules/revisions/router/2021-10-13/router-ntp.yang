submodule router-ntp {
  // Generated by yanger -t ncs
  tailf:mount-id "router-nc-1.1:router-nc-1.1";

  yang-version 1.1;
  belongs-to router {
    prefix r;
  }

  import ietf-inet-types {
    prefix inet;
  }
  include router-types;
  import tailf-common {
    prefix tailf;
  }
  import tailf-ncs {
    prefix ncs;
  }

  description
    "The 'ntp' component provides support for configuring
     the ntpd daemon from the reference NTP implementation. It
     also provides status information pertaining to the configured
     servers.

     The set of configurable parameters has been limited to
     those that may be generally useful on a network device,
     including

         - remote servers/peers
         - local-clock server
         - access control
         - symmetric-key based authentication";

  revision 2021-10-13 {
    description
      "YANG 1.1 compatible.";
  }
  revision 2008-11-04 {
    description
      "draft-ietf-netmod-yang-02 compatible.";
  }
  revision 2007-08-29 {
    description
      "Syntax fixes after pyang validation.";
  }
  revision 2007-06-08 {
    description
      "Initial revision.";
  }

  typedef ncs_rpc_notif_ntpState {
    type enumeration {
      enum "reject" {
        tailf:code-name "ns_reject";
      }
      enum "falsetick";
      enum "excess";
      enum "outlyer";
      enum "candidate";
      enum "selected";
      enum "syspeer";
      enum "ppspeer";
      enum "unknown";
    }
  }

  typedef ncs_rpc_notif_ntpStratum {
    type uint8 {
      range "0..15";
    }
  }

  typedef ncs_rpc_notif_ntpDecimal {
    type int32;
    units "milliseconds";
  }

  typedef ncs_rpc_notif_ntpRestrictName {
    type union {
      type enumeration {
        enum "default";
      }
      type inet:host;
    }
  }

  typedef ncs_rpc_notif_ntpRestrictMask {
    type union {
      type enumeration {
        enum "default";
      }
      type inet:ip-address;
    }
  }

  typedef ncs_rpc_notif_ntpRestrictFlag {
    type enumeration {
      enum "ignore";
      enum "kod";
      enum "limited";
      enum "lowpriotrap";
      enum "nomodify";
      enum "nopeer";
      enum "noquery";
      enum "noserve";
      enum "notrap";
      enum "notrust";
      enum "ntpport";
      enum "version" {
        tailf:code-name "nr_version";
      }
    }
  }

  typedef ncs_rpc_notif_ntpKeyValue {
    type string {
      pattern '[!-~]{1,32}';
    }
  }

  typedef live_ncs_ntpState {
    type enumeration {
      enum "reject" {
        tailf:code-name "ns_reject";
      }
      enum "falsetick";
      enum "excess";
      enum "outlyer";
      enum "candidate";
      enum "selected";
      enum "syspeer";
      enum "ppspeer";
      enum "unknown";
    }
  }

  typedef live_ncs_ntpStratum {
    type uint8 {
      range "0..15";
    }
  }

  typedef live_ncs_ntpDecimal {
    type int32;
    units "milliseconds";
  }

  typedef live_ncs_ntpRestrictName {
    type union {
      type enumeration {
        enum "default";
      }
      type inet:host;
    }
  }

  typedef live_ncs_ntpRestrictMask {
    type union {
      type enumeration {
        enum "default";
      }
      type inet:ip-address;
    }
  }

  typedef live_ncs_ntpRestrictFlag {
    type enumeration {
      enum "ignore";
      enum "kod";
      enum "limited";
      enum "lowpriotrap";
      enum "nomodify";
      enum "nopeer";
      enum "noquery";
      enum "noserve";
      enum "notrap";
      enum "notrust";
      enum "ntpport";
      enum "version" {
        tailf:code-name "nr_version";
      }
    }
  }

  typedef live_ncs_ntpKeyValue {
    type string {
      pattern '[!-~]{1,32}';
    }
  }

  typedef ntpState {
    type enumeration {
      enum "reject" {
        tailf:code-name "ns_reject";
      }
      enum "falsetick";
      enum "excess";
      enum "outlyer";
      enum "candidate";
      enum "selected";
      enum "syspeer";
      enum "ppspeer";
      enum "unknown";
    }
  }

  typedef ntpStratum {
    type uint8 {
      range "0..15";
    }
  }

  typedef ntpDecimal {
    type int32;
    units "milliseconds";
  }

  typedef ntpRestrictName {
    type union {
      type enumeration {
        enum "default";
      }
      type inet:host;
    }
  }

  typedef ntpRestrictMask {
    type union {
      type enumeration {
        enum "default";
      }
      type inet:ip-address;
    }
  }

  typedef ntpRestrictFlag {
    type enumeration {
      enum "ignore";
      enum "kod";
      enum "limited";
      enum "lowpriotrap";
      enum "nomodify";
      enum "nopeer";
      enum "noquery";
      enum "noserve";
      enum "notrap";
      enum "notrust";
      enum "ntpport";
      enum "version" {
        tailf:code-name "nr_version";
      }
    }
  }

  typedef ntpKeyValue {
    type string {
      pattern '[!-~]{1,32}';
    }
  }

  grouping ncs_rpc_notif_ntpStatus {
    leaf state {
      type ncs_rpc_notif_ntpState;
    }
    leaf stratum {
      type ncs_rpc_notif_ntpStratum;
    }
    leaf reach {
      type string;
    }
    leaf delay {
      type ncs_rpc_notif_ntpDecimal;
    }
    leaf offset {
      type ncs_rpc_notif_ntpDecimal;
    }
    leaf jitter {
      type ncs_rpc_notif_ntpDecimal;
    }
  }

  grouping ncs_rpc_notif_ntp {
    list server {
      key "name";
      max-elements 16;
      leaf name {
        type inet:host;
      }
      leaf enabled {
        type boolean;
        default "true";
      }
      leaf peer {
        type boolean;
        default "false";
      }
      leaf iburst {
        type empty;
      }
      leaf version {
        type int8 {
          range "1..4";
        }
        default "4";
      }
      leaf key {
        type leafref {
          path "../../key/name";
        }
      }
      container status {
        config false;
        uses ncs_rpc_notif_ntpStatus;
      }
    }
    container local-clock {
      leaf enabled {
        type boolean;
        default "true";
      }
      leaf stratum {
        type ncs_rpc_notif_ntpStratum;
        default "10";
      }
      container status {
        uses ncs_rpc_notif_ntpStatus;
      }
    }
    list restrict {
      key "name mask";
      max-elements 64;
      leaf name {
        type ncs_rpc_notif_ntpRestrictName;
      }
      leaf mask {
        type ncs_rpc_notif_ntpRestrictMask;
      }
      leaf-list flag {
        type ncs_rpc_notif_ntpRestrictFlag;
      }
    }
    list key {
      key "name";
      max-elements 64;
      leaf name {
        type uint8 {
          range "1..max";
        }
      }
      leaf value {
        type ncs_rpc_notif_ntpKeyValue;
      }
      leaf trusted {
        type boolean;
        default "true";
      }
    }
    leaf requestkey {
      type leafref {
        path "../key/name";
      }
    }
    leaf controlkey {
      type leafref {
        path "../key/name";
      }
    }
  }

  grouping live_ncs_ntpStatus {
    leaf state {
      type live_ncs_ntpState;
    }
    leaf stratum {
      type live_ncs_ntpStratum;
    }
    leaf reach {
      type string;
    }
    leaf delay {
      type live_ncs_ntpDecimal;
    }
    leaf offset {
      type live_ncs_ntpDecimal;
    }
    leaf jitter {
      type live_ncs_ntpDecimal;
    }
  }

  grouping live_ncs_ntp {
    list server {
      key "name";
      // NCS drop max-elements statement
      leaf name {
        type inet:host;
      }
      leaf enabled {
        type boolean;
        // NCS drop default statement
      }
      leaf peer {
        type boolean;
        // NCS drop default statement
      }
      leaf iburst {
        type empty;
      }
      leaf version {
        type int8 {
          range "1..4";
        }
        // NCS drop default statement
      }
      leaf key {
        type leafref {
          path "../../key/name";
        }
      }
      container status {
        uses live_ncs_ntpStatus;
      }
    }
    container local-clock {
      leaf enabled {
        type boolean;
        // NCS drop default statement
      }
      leaf stratum {
        type live_ncs_ntpStratum;
        // NCS drop default statement
      }
      container status {
        uses live_ncs_ntpStatus;
      }
    }
    list restrict {
      key "name mask";
      // NCS drop max-elements statement
      leaf name {
        type live_ncs_ntpRestrictName;
      }
      leaf mask {
        type live_ncs_ntpRestrictMask;
      }
      leaf-list flag {
        type live_ncs_ntpRestrictFlag;
      }
    }
    list key {
      key "name";
      // NCS drop max-elements statement
      leaf name {
        type uint8 {
          range "1..max";
        }
      }
      leaf value {
        type live_ncs_ntpKeyValue;
      }
      leaf trusted {
        type boolean;
        // NCS drop default statement
      }
    }
    leaf requestkey {
      type leafref {
        path "../key/name";
      }
    }
    leaf controlkey {
      type leafref {
        path "../key/name";
      }
    }
  }

  grouping ntpStatus {
    leaf state {
      type ntpState;
    }
    leaf stratum {
      type ntpStratum;
    }
    leaf reach {
      type string;
    }
    leaf delay {
      type ntpDecimal;
    }
    leaf offset {
      type ntpDecimal;
    }
    leaf jitter {
      type ntpDecimal;
    }
  }

  grouping ntp {
    list server {
      key "name";
      max-elements 16;
      leaf name {
        type inet:host;
      }
      leaf enabled {
        type boolean;
        default "true";
      }
      leaf peer {
        type boolean;
        default "false";
      }
      leaf iburst {
        type empty;
      }
      leaf version {
        type int8 {
          range "1..4";
        }
        default "4";
      }
      leaf key {
        type leafref {
          path "../../key/name";
        }
      }
      // NCS drop config false container status
    }
    container local-clock {
      leaf enabled {
        type boolean;
        default "true";
      }
      leaf stratum {
        type ntpStratum;
        default "10";
      }
      container status {
        uses ntpStatus;
      }
    }
    list restrict {
      key "name mask";
      max-elements 64;
      leaf name {
        type ntpRestrictName;
      }
      leaf mask {
        type ntpRestrictMask;
      }
      leaf-list flag {
        type ntpRestrictFlag;
      }
    }
    list key {
      key "name";
      max-elements 64;
      leaf name {
        type uint8 {
          range "1..max";
        }
      }
      leaf value {
        type ntpKeyValue;
      }
      leaf trusted {
        type boolean;
        default "true";
      }
    }
    leaf requestkey {
      type leafref {
        path "../key/name";
      }
    }
    leaf controlkey {
      type leafref {
        path "../key/name";
      }
    }
  }
}
