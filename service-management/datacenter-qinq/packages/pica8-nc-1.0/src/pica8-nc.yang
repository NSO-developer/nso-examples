module pica8-nc {
  yang-version 1.1;
  namespace "http://tail-f.com/ns/ned-id/pica8-nc";
  prefix pica8-nc;

  import tailf-common {
    prefix tailf;
  }

  import tailf-ncs-ned {
    prefix ned;
  }

  identity pica8-nc {
    tailf:abstract;
    base ned:netconf-ned-id;
  }
}
