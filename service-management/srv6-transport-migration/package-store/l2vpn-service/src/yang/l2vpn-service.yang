module l2vpn-service {
  namespace "http://tail-f.com/srlab/l2vpn-service";
  prefix l2vpn;
  yang-version 1.1;

  import tailf-common {
    prefix tailf;
  }
  import tailf-ncs {
    prefix ncs;
  }
  import inventory {
    prefix inv;
  }

  revision 2026-05-07 {
    description
      "Initial revision.";
  }



  identity l2vpn {
    base inv:service-kind;
  }

  list l2vpn {
    description "Ethernet multi-point service (EVPN).";

    uses ncs:service-data;
    ncs:servicepoint l2vpn-service;

    key name;
    leaf name {
      description "Service instance name";
      type string {
        pattern "[A-Za-z0-9-]{3,24}";
      }
      tailf:cli-allow-range;
    }

    leaf customer {
      mandatory true;
      type leafref {
        path "/inv:inventory/inv:customer/inv:name";
      }
    }

    leaf-list ports {
      type leafref {
        path "/inv:inventory/inv:port/inv:pid";
      }
    }

    leaf vni {
      description "Manually assigned VNI (EVI); optional.";
      type leafref {
        path "/inv:inventory/inv:vni/inv:vnid";
      }
    }

    leaf force {
      description
       "Provision port to this service even if it is already in use.";
      type boolean;
      default false;
    }
  }
}
