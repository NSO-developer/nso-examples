module ietf-te-ann {
  yang-version 1.1;
  namespace "urn:dummy";
  prefix dummy;

  import tailf-common {
    prefix tailf;
  }

  description
    "Tail-f annotations for the IETF TE module used by the
     srv6-transport-migration example.";

  revision 2026-05-07 {
    description
      "Initial revision.";
  }

  tailf:annotate-module "ietf-te" {
    tailf:annotate-statement "container[name='te']" {
      tailf:info "IETF TE tunnel model";
      tailf:annotate-statement "container[name='tunnels']" {
        tailf:info "IETF TE tunnels";
        tailf:annotate-statement "list[name='tunnel']" {
          tailf:info "IETF TE tunnel";
        }
      }
    }
  }
}
