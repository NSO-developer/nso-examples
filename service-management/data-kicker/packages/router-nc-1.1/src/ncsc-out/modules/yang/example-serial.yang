module example-serial {
  // Generated by yanger -t ncs
  tailf:mount-id "router-nc-1.1:router-nc-1.1";
  tailf:ncs-device-type "netconf";

  yang-version 1.1;
  namespace "http://example.com/example-serial";
  prefix ex;

  import router {
    prefix r;
  }
  import ietf-yang-types {
    prefix yang;
  }
  import ietf-inet-types {
    prefix inet;
  }
  import tailf-common {
    prefix tailf;
  }
  import tailf-ncs {
    prefix ncs;
  }

  revision 2021-10-13 {
    description
      "YANG 1.1 compatible.";
  }

  augment "/ncs:compliance/ncs:template/ncs:ned-id/ncs:config/r:sys/r:interfaces" {
    list serial {
      // NCS patched for predictable order
      ordered-by user;
      key "name";
      leaf name {
        type string;
      }
      container ppp {
        leaf accounting {
          type string;
        }
      }
      container authentication {
        leaf method {
          type string;
        }
        leaf list-name {
          type string;
        }
        leaf one-time {
          type empty;
        }
        leaf optional {
          type empty;
        }
      }
      leaf authorization {
        type string;
      }
      container ipcp {
        container dns {
          leaf primary {
            type string;
          }
        }
      }
      container multilink {
        presence "true";
        container links {
          container minimum {
            leaf minimum-value {
              type string;
            }
            leaf mandatory {
              type empty;
            }
          }
        }
        leaf group {
          type string;
        }
        container fragment {
          container delay {
            leaf delay-value {
              type string;
            }
            leaf additional-delay-value {
              type string;
            }
          }
        }
      }
    }
  }
  augment "/ncs:devices/ncs:template/ncs:ned-id/ncs:config/r:sys/r:interfaces" {
    list serial {
      // NCS patched for predictable order
      ordered-by user;
      key "name";
      leaf name {
        type string;
      }
      container ppp {
        leaf accounting {
          type string;
        }
      }
      container authentication {
        leaf method {
          type string;
        }
        leaf list-name {
          type string;
        }
        leaf one-time {
          type empty;
        }
        leaf optional {
          type empty;
        }
      }
      leaf authorization {
        type string;
      }
      container ipcp {
        container dns {
          leaf primary {
            type string;
          }
        }
      }
      container multilink {
        presence "true";
        container links {
          container minimum {
            leaf minimum-value {
              type string;
            }
            leaf mandatory {
              type empty;
            }
          }
        }
        leaf group {
          type string;
        }
        container fragment {
          container delay {
            leaf delay-value {
              type string;
            }
            leaf additional-delay-value {
              type string;
            }
          }
        }
      }
    }
  }
  augment "/ncs:devices/ncs:device/ncs:live-status/r:sys/r:interfaces" {
    list serial {
      tailf:ncs-device-type "netconf";
      tailf:display-when "not(../../../ncs:module) or ../../../ncs:module[ncs:name='example-serial'] or (../../../ncs:live-status-protocol[not(ncs:capability)]) or (../../../ncs:live-status-protocol/ncs:capability/ncs:module[.='example-serial'])";
      key "name";
      leaf name {
        type string;
      }
      container ppp {
        leaf accounting {
          type string;
        }
      }
      container authentication {
        leaf method {
          type enumeration {
            enum "chap";
            enum "eap";
            enum "ms-chap";
            enum "ms-chap-v2";
            enum "pap";
          }
        }
        leaf list-name {
          type string;
        }
        leaf one-time {
          type empty;
        }
        leaf optional {
          type empty;
        }
      }
      leaf authorization {
        type string;
      }
      container ipcp {
        container dns {
          leaf primary {
            type inet:ipv4-address;
          }
        }
      }
      container multilink {
        presence "true";
        container links {
          container minimum {
            leaf minimum-value {
              type uint8;
            }
            leaf mandatory {
              type empty;
            }
          }
        }
        leaf group {
          type uint32;
        }
        container fragment {
          container delay {
            leaf delay-value {
              type uint16;
            }
            leaf additional-delay-value {
              type uint16;
            }
          }
        }
      }
    }
  }
  augment "/ncs:devices/ncs:device/ncs:config/r:sys/r:interfaces" {
    list serial {
      tailf:ncs-device-type "netconf";
      tailf:display-when "not(../../../ncs:module) or ../../../ncs:module[ncs:name='example-serial']";
      key "name";
      leaf name {
        type string;
      }
      container ppp {
        leaf accounting {
          type string;
        }
      }
      container authentication {
        leaf method {
          type enumeration {
            enum "chap";
            enum "eap";
            enum "ms-chap";
            enum "ms-chap-v2";
            enum "pap";
          }
        }
        leaf list-name {
          type string;
        }
        leaf one-time {
          type empty;
        }
        leaf optional {
          type empty;
        }
      }
      leaf authorization {
        type string;
      }
      container ipcp {
        container dns {
          leaf primary {
            type inet:ipv4-address;
          }
        }
      }
      container multilink {
        presence "true";
        container links {
          container minimum {
            leaf minimum-value {
              type uint8;
            }
            leaf mandatory {
              type empty;
            }
          }
        }
        leaf group {
          type uint32;
        }
        container fragment {
          container delay {
            leaf delay-value {
              type uint16;
            }
            leaf additional-delay-value {
              type uint16;
            }
          }
        }
      }
    }
  }
}
