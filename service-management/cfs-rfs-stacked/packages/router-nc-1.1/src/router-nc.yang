module router-nc {
  yang-version 1.1;
  namespace "http://tail-f.com/ns/ned-id/router-nc";
  prefix router-nc;

  import tailf-common {
    prefix tailf;
  }

  import tailf-ncs-ned {
    prefix ned;
  }

  identity router-nc {
    tailf:abstract;
    base ned:netconf-ned-id;
  }
}
