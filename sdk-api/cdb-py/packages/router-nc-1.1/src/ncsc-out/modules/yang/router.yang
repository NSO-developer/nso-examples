module router {
  // Generated by yanger -t ncs
  tailf:mount-id "router-nc-1.1:router-nc-1.1";
  tailf:ncs-device-type "netconf";

  yang-version 1.1;
  namespace "http://example.com/router";
  prefix r;

  include router-types;
  include router-interfaces;
  include router-syslog;
  include router-dns;
  include router-ntp;
  include router-routes;
  import tailf-common {
    prefix tailf;
  }
  import tailf-ncs {
    prefix ncs;
  }

  organization
    "tail-f";
  description
    "An example module describing some common components typically found
     on routers

      interfaces - configuration and status of network interfaces
      routes     - configuration of static routes
      syslog     - configuration of logging to remote syslog servers
      dns        - configuration of the DNS resolver
      ntp        - configuration and status of the NTP daemon

     This module is the main YANG module, and each component has its
     own YANG submodule.";

  revision 2021-10-13 {
    description
      "YANG 1.1 compatible.Added a link-status notification and an admin-state.";
  }
  revision 2008-11-04 {
    description
      "draft-ietf-netmod-yang-02 compatible.";
  }
  revision 2007-08-29 {
    description
      "Syntax fixes after pyang validation.";
  }
  revision 2007-06-08 {
    description
      "Initial revision.";
  }

  typedef ncs_rpc_notif_admin-state {
    type enumeration {
      enum "locked";
      enum "unlocked";
    }
    default "unlocked";
  }

  typedef live_ncs_admin-state {
    type enumeration {
      enum "locked";
      enum "unlocked";
    }
    // NCS drop default statement
  }

  typedef admin-state {
    type enumeration {
      enum "locked";
      enum "unlocked";
    }
    default "unlocked";
  }

  augment "/ncs:devices/ncs:device/ncs:notifications/ncs:received-notifications/ncs:notification/ncs:data" {
    container link-status {
      presence "";
      config false;
      leaf name {
        type string;
      }
      leaf status {
        type enumeration {
          enum "up";
          enum "down";
        }
        // NCS drop mandatory statement
      }
    }
  }
  augment "/ncs:devices/ncs:device/ncs:config" {
    container sys {
      tailf:ncs-device-type "netconf";
      tailf:display-when "not(../../ncs:module) or ../../ncs:module[ncs:name='router']";
      container interfaces {
        uses interfaces;
      }
      container routes {
        uses routes;
      }
      container syslog {
        uses syslog;
      }
      container ntp {
        uses ntp;
      }
      container dns {
        uses dns;
      }
      // NCS drop config false container state
    }
  }
  augment "/ncs:devices/ncs:device/ncs:live-status" {
    container sys {
      tailf:ncs-device-type "netconf";
      tailf:display-when "not(../../ncs:module) or ../../ncs:module[ncs:name='router'] or (../../ncs:live-status-protocol[not(ncs:capability)]) or (../../ncs:live-status-protocol/ncs:capability/ncs:module[.='router'])";
      container interfaces {
        uses live_ncs_interfaces;
      }
      container routes {
        uses live_ncs_routes;
      }
      container syslog {
        uses live_ncs_syslog;
      }
      container ntp {
        uses live_ncs_ntp;
      }
      container dns {
        uses live_ncs_dns;
      }
      container state {
        leaf admin-state {
          type live_ncs_admin-state;
        }
      }
    }
  }
}
