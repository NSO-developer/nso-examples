submodule router-routes {
  // Generated by yanger -t ncs
  tailf:mount-id "router-nc-1.1:router-nc-1.1";

  yang-version 1.1;
  belongs-to router {
    prefix r;
  }

  import ietf-inet-types {
    prefix inet;
  }
  include router-types;
  import tailf-common {
    prefix tailf;
  }
  import tailf-ncs {
    prefix ncs;
  }

  description
    "The 'routes' component provides support for configuring static routes
     (IPv4 and IPv6).

     The data model is loosely based on (a subset of) Juniper's, there
     is support for two 'conceptual' routing tables named 'inet' and
     'inet6' (in the actual Linux implementation, these both map to
     the 'main' routing table).";

  revision 2021-10-13 {
    description
      "YANG 1.1 compatible.";
  }
  revision 2008-11-04 {
    description
      "draft-ietf-netmod-yang-02 compatible.";
  }

  grouping ncs_rpc_notif_routes {
    container inet {
      list route {
        key "name prefix-length";
        leaf name {
          type inet:ipv4-address;
        }
        leaf prefix-length {
          type ncs_rpc_notif_prefixLengthIPv4;
        }
        leaf description {
          type string;
        }
        leaf enabled {
          type boolean;
          default "true";
        }
        leaf type {
          type enumeration {
            enum "next-hop" {
              tailf:code-name "inet_next_hop";
            }
            enum "reject" {
              tailf:code-name "inet_reject";
            }
            enum "discard";
            enum "prohibit";
          }
          default "next-hop";
        }
        list next-hop {
          key "name";
          unique "metric";
          max-elements 16;
          leaf name {
            type inet:ipv4-address;
            description
              "must not be a multicast address";
          }
          leaf metric {
            type int32;
            default "0";
          }
        }
      }
    }
    container inet6 {
      list route {
        key "name prefix-length";
        leaf name {
          type inet:ipv6-address;
        }
        leaf prefix-length {
          type ncs_rpc_notif_prefixLengthIPv6;
        }
        leaf description {
          type string;
        }
        leaf enabled {
          type boolean;
          default "true";
        }
        leaf type {
          type enumeration {
            enum "next-hop" {
              tailf:code-name "inet6_next_hop";
            }
            enum "reject" {
              tailf:code-name "inet6_reject";
            }
          }
          default "next-hop";
        }
        list next-hop {
          key "name";
          unique "metric";
          max-elements 16;
          leaf name {
            type inet:ipv6-address;
            description
              "must not be a multicast address";
          }
          leaf metric {
            type int32;
            default "1024";
          }
          leaf interface {
            type ncs_rpc_notif_interfaceName;
          }
          leaf unit {
            type ncs_rpc_notif_interfaceLogicalUnit;
          }
        }
      }
    }
  }

  grouping live_ncs_routes {
    container inet {
      list route {
        key "name prefix-length";
        leaf name {
          type inet:ipv4-address;
        }
        leaf prefix-length {
          type live_ncs_prefixLengthIPv4;
        }
        leaf description {
          type string;
        }
        leaf enabled {
          type boolean;
          // NCS drop default statement
        }
        leaf type {
          type enumeration {
            enum "next-hop" {
              tailf:code-name "inet_next_hop";
            }
            enum "reject" {
              tailf:code-name "inet_reject";
            }
            enum "discard";
            enum "prohibit";
          }
          // NCS drop default statement
        }
        list next-hop {
          key "name";
          unique "metric";
          // NCS drop max-elements statement
          leaf name {
            type inet:ipv4-address;
            description
              "must not be a multicast address";
          }
          leaf metric {
            type int32;
            // NCS drop default statement
          }
        }
      }
    }
    container inet6 {
      list route {
        key "name prefix-length";
        leaf name {
          type inet:ipv6-address;
        }
        leaf prefix-length {
          type live_ncs_prefixLengthIPv6;
        }
        leaf description {
          type string;
        }
        leaf enabled {
          type boolean;
          // NCS drop default statement
        }
        leaf type {
          type enumeration {
            enum "next-hop" {
              tailf:code-name "inet6_next_hop";
            }
            enum "reject" {
              tailf:code-name "inet6_reject";
            }
          }
          // NCS drop default statement
        }
        list next-hop {
          key "name";
          unique "metric";
          // NCS drop max-elements statement
          leaf name {
            type inet:ipv6-address;
            description
              "must not be a multicast address";
          }
          leaf metric {
            type int32;
            // NCS drop default statement
          }
          leaf interface {
            type live_ncs_interfaceName;
          }
          leaf unit {
            type live_ncs_interfaceLogicalUnit;
          }
        }
      }
    }
  }

  grouping routes {
    container inet {
      list route {
        key "name prefix-length";
        leaf name {
          type inet:ipv4-address;
        }
        leaf prefix-length {
          type prefixLengthIPv4;
        }
        leaf description {
          type string;
        }
        leaf enabled {
          type boolean;
          default "true";
        }
        leaf type {
          type enumeration {
            enum "next-hop" {
              tailf:code-name "inet_next_hop";
            }
            enum "reject" {
              tailf:code-name "inet_reject";
            }
            enum "discard";
            enum "prohibit";
          }
          default "next-hop";
        }
        list next-hop {
          key "name";
          unique "metric";
          max-elements 16;
          leaf name {
            type inet:ipv4-address;
            description
              "must not be a multicast address";
          }
          leaf metric {
            type int32;
            default "0";
          }
        }
      }
    }
    container inet6 {
      list route {
        key "name prefix-length";
        leaf name {
          type inet:ipv6-address;
        }
        leaf prefix-length {
          type prefixLengthIPv6;
        }
        leaf description {
          type string;
        }
        leaf enabled {
          type boolean;
          default "true";
        }
        leaf type {
          type enumeration {
            enum "next-hop" {
              tailf:code-name "inet6_next_hop";
            }
            enum "reject" {
              tailf:code-name "inet6_reject";
            }
          }
          default "next-hop";
        }
        list next-hop {
          key "name";
          unique "metric";
          max-elements 16;
          leaf name {
            type inet:ipv6-address;
            description
              "must not be a multicast address";
          }
          leaf metric {
            type int32;
            default "1024";
          }
          leaf interface {
            type interfaceName;
          }
          leaf unit {
            type interfaceLogicalUnit;
          }
        }
      }
    }
  }
}
