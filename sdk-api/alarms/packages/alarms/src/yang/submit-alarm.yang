module submit-alarm {
  namespace "http://example.com/submit-alarm";
  prefix submit-al;

  import tailf-common {
    prefix tailf;
  }

  import tailf-ncs-alarms {
    prefix al;
  }

  import link-alarm {
    prefix link-al;
  }

  container example {
    description "A small module to generate alarms from inside the cli.
                 Normally the alarm would be generated by some external
                 producer.";
    tailf:action generate {
      tailf:actionpoint generate-alarm;
      input {
        container alarm {
          leaf device {
            description "The name of the device the alarm should occur on.
                         The device is one of the devices: /ncs:devices/device.
                         In this example it would be one of ex0, ex1 or ex2.";
            type string;
          }
          leaf object {
            description "The specific interface on the device which generated
                         the alarm. In this example it could be one of eth0,
                         eth1. The alarming object within the device.";
              type string;
          }
          leaf alarm-type {
            description "Alarm type correspond to the X.733 alarm standard
                         triplet, event type, probable cause, specific
                         problem.";
            type identityref {
              base link-al:link-alarm;
            }
          }
          leaf perceived-severity {
              type al:severity-t;
          }
          leaf specific-problem {
            description "The specific problem on the managed object.";
            type string;
          }
          leaf alarm-text {
            description "Text to be presented to the operator.";
            type string;
          }
        }
      }
      output {
        leaf result {
          type boolean;
        }
        leaf info {
          type string;
          description
            "contains additional information about the result";
        }
      }
    }
  }
}
