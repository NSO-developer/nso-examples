submodule router-types {
  // Generated by yanger -t ncs
  tailf:mount-id "router-nc-1.0:router-nc-1.0";

  belongs-to router {
    prefix r;
  }

  import tailf-common {
    prefix tailf;
  }
  import tailf-ncs {
    prefix ncs;
  }

  description
    "Common types used within router.";

  revision 2008-11-04 {
    description
      "draft-ietf-netmod-yang-02 compatible.";
  }
  revision 2007-08-29 {
    description
      "Syntax fixes after pyang validation.";
  }
  revision 2007-06-08 {
    description
      "Initial revision.";
  }

  typedef ncs_compliance_template_prefixLengthIPv4 {
    type string;
  }

  typedef ncs_compliance_template_prefixLengthIPv6 {
    type string;
  }

  typedef ncs_compliance_template_interfaceName {
    type string;
  }

  typedef ncs_compliance_template_interfaceLogicalUnit {
    type string;
  }

  typedef ncs_template_prefixLengthIPv4 {
    type string;
  }

  typedef ncs_template_prefixLengthIPv6 {
    type string;
  }

  typedef ncs_template_interfaceName {
    type string;
  }

  typedef ncs_template_interfaceLogicalUnit {
    type string;
  }

  typedef ncs_rpc_notif_prefixLengthIPv4 {
    type int32 {
      range "0..32";
    }
  }

  typedef ncs_rpc_notif_prefixLengthIPv6 {
    type int32 {
      range "0..128";
    }
  }

  typedef ncs_rpc_notif_interfaceName {
    type string {
      length "1..30";
      pattern '[A-Za-z][^/:.]*';
    }
  }

  typedef ncs_rpc_notif_interfaceLogicalUnit {
    type int32 {
      range "0..9999";
    }
  }

  typedef live_ncs_prefixLengthIPv4 {
    type int32 {
      range "0..32";
    }
  }

  typedef live_ncs_prefixLengthIPv6 {
    type int32 {
      range "0..128";
    }
  }

  typedef live_ncs_interfaceName {
    type string {
      length "1..30";
      pattern '[A-Za-z][^/:.]*';
    }
  }

  typedef live_ncs_interfaceLogicalUnit {
    type int32 {
      range "0..9999";
    }
  }

  typedef prefixLengthIPv4 {
    type int32 {
      range "0..32";
    }
  }

  typedef prefixLengthIPv6 {
    type int32 {
      range "0..128";
    }
  }

  typedef interfaceName {
    type string {
      length "1..30";
      pattern '[A-Za-z][^/:.]*';
    }
  }

  typedef interfaceLogicalUnit {
    type int32 {
      range "0..9999";
    }
  }
}
