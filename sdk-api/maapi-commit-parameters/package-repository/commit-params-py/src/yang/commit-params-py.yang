module commit-params-py {

  namespace "http://example.com/commit-params-py";
  prefix commit-params-py;
  yang-version 1.1;

  import ietf-yang-structure-ext {
    prefix sx;
  }
  import tailf-common {
    prefix tailf;
  }
  import tailf-ncs-commit-params {
    prefix ncp;
  }
  import tailf-ncs {
    prefix ncs;
  }

  sx:augment-structure "/ncp:commit-params" {
    container audit-context {
      presence "Attach extra audit information to the commit";
      leaf ticket-id {
        type string;
      }
    }
  }

  container commit-params-py {
    list commit-params-py-instances {

      key name;
      leaf name {
        tailf:info "Unique service id";
        tailf:cli-allow-range;
        type string;
      }

      uses ncs:service-data;
      ncs:servicepoint commit-params-py-servicepoint;

      leaf device {
        type leafref {
          path "/ncs:devices/ncs:device/ncs:name";
        }
      }

      leaf if {
        type string;
      }

      leaf if-speed {
        type string;
      }

      tailf:action showcase-py {
        tailf:actionpoint showcase-py;
      }
    }
  }
}
