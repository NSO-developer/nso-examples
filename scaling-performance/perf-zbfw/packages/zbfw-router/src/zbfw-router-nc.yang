module zbfw-router-nc {
  yang-version 1.1;
  namespace "http://tail-f.com/ns/ned-id/zbfw-router-nc";
  prefix zbfw-router-nc;

  import tailf-common {
    prefix tailf;
  }

  import tailf-ncs-ned {
    prefix ned;
  }

  identity zbfw-router-nc {
    tailf:abstract;
    base ned:netconf-ned-id;
  }
}
