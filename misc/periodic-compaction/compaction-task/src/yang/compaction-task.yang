module compaction-task {

  yang-version 1.1;
  namespace "http://example.com/compaction-task";
  prefix compaction-task;

  import tailf-common {
    prefix tailf;
  }

  description
    "Compaction task to be used in combination with ncs scheduler";

  revision 2023-03-15 {
    description
      "Initial revision.";
  }

  container compaction-task {
    action compact {
      tailf:actionpoint compact;
    }
  }
}
