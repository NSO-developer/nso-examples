module hw-nc-1.0 {
  yang-version 1.1;
  namespace "http://tail-f.com/ns/ned-id/hw-nc-1.0";
  prefix hw-nc-1.0;

  import hw-nc {
    prefix family;
  }

  identity hw-nc-1.0 {
    base family:hw-nc;
  }
}
