module webserver-nc-1.0 {
  yang-version 1.1;
  namespace "http://tail-f.com/ns/ned-id/webserver-nc-1.0";
  prefix webserver-nc-1.0;

  import webserver-nc {
    prefix family;
  }

  identity webserver-nc-1.0 {
    base family:webserver-nc;
  }
}
