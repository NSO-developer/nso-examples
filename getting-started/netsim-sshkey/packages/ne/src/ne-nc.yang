module ne-nc {
  yang-version 1.1;
  namespace "http://tail-f.com/ns/ned-id/ne-nc";
  prefix ne-nc;

  import tailf-common {
    prefix tailf;
  }

  import tailf-ncs-ned {
    prefix ned;
  }

  identity ne-nc {
    tailf:abstract;
    base ned:netconf-ned-id;
  }
}
