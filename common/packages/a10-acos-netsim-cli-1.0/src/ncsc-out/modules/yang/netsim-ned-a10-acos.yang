module netsim-ned-a10-acos {
  // Generated by yanger -t ncs
  tailf:mount-id "a10-acos-netsim-cli-1.0:a10-acos-netsim-cli-1.0";
  tailf:ncs-device-type "cli-ned";

  namespace "http://tail-f.com/ned/a10-acos";
  prefix a10-acos;

  import tailf-common {
    prefix tailf;
  }
  import ietf-inet-types {
    prefix inet;
  }
  import tailf-ncs {
    prefix ncs;
  }

  revision 2026-01-29;

  typedef ncs_compliance_template_ipv4-mask {
    type string;
  }

  typedef ncs_compliance_template_ipv6-prefix {
    type string;
  }

  typedef ncs_compliance_template_ethernet-index {
    type string;
  }

  typedef ncs_compliance_template_vlan-index {
    type string;
  }

  typedef ncs_compliance_template_cipher {
    type string;
  }

  typedef ncs_template_ipv4-mask {
    type string;
  }

  typedef ncs_template_ipv6-prefix {
    type string;
  }

  typedef ncs_template_ethernet-index {
    type string;
  }

  typedef ncs_template_vlan-index {
    type string;
  }

  typedef ncs_template_cipher {
    type string;
  }

  typedef ncs_rpc_notif_ipv4-mask {
    type inet:ipv4-address;
  }

  typedef ncs_rpc_notif_ipv6-prefix {
    type string;
  }

  typedef ncs_rpc_notif_ethernet-index {
    type union {
      type uint16;
      type string;
    }
  }

  typedef ncs_rpc_notif_vlan-index {
    type union {
      type uint16;
      type string;
    }
  }

  typedef ncs_rpc_notif_cipher {
    type union {
      type enumeration {
        enum "SSL3_RSA_DES_192_CBC3_SHA";
        enum "SSL3_RSA_DES_40_CBC_SHA";
        enum "SSL3_RSA_DES_64_CBC_SHA";
        enum "SSL3_RSA_RC4_128_MD5";
        enum "SSL3_RSA_RC4_128_SHA";
        enum "SSL3_RSA_RC4_40_MD5";
        enum "TLS1_DHE_RSA_AES_128_GCM_SHA256";
        enum "TLS1_DHE_RSA_AES_128_SHA";
        enum "TLS1_DHE_RSA_AES_128_SHA256";
        enum "TLS1_DHE_RSA_AES_256_GCM_SHA384";
        enum "TLS1_DHE_RSA_AES_256_SHA";
        enum "TLS1_DHE_RSA_AES_256_SHA256";
        enum "TLS1_ECDHE_ECDSA_AES_128_GCM_SHA256";
        enum "TLS1_ECDHE_ECDSA_AES_128_SHA";
        enum "TLS1_ECDHE_ECDSA_AES_128_SHA256";
        enum "TLS1_ECDHE_ECDSA_AES_256_GCM_SHA384";
        enum "TLS1_ECDHE_ECDSA_AES_256_SHA";
        enum "TLS1_ECDHE_RSA_AES_128_GCM_SHA256";
        enum "TLS1_ECDHE_RSA_AES_128_SHA";
        enum "TLS1_ECDHE_RSA_AES_128_SHA256";
        enum "TLS1_ECDHE_RSA_AES_256_GCM_SHA384";
        enum "TLS1_ECDHE_RSA_AES_256_SHA";
        enum "TLS1_RSA_AES_128_GCM_SHA256";
        enum "TLS1_RSA_AES_128_SHA";
        enum "TLS1_RSA_AES_128_SHA256";
        enum "TLS1_RSA_AES_256_GCM_SHA384";
        enum "TLS1_RSA_AES_256_SHA";
        enum "TLS1_RSA_AES_256_SHA256";
        enum "TLS1_RSA_EXPORT1024_RC4_56_MD5";
        enum "TLS1_RSA_EXPORT1024_RC4_56_SHA";
      }
      type string;
    }
  }

  typedef ipv4-mask {
    type inet:ipv4-address;
  }

  typedef ipv6-prefix {
    type string;
  }

  typedef ethernet-index {
    type union {
      type uint16;
      type string;
    }
  }

  typedef vlan-index {
    type union {
      type uint16;
      type string;
    }
  }

  typedef cipher {
    type union {
      type enumeration {
        enum "SSL3_RSA_DES_192_CBC3_SHA";
        enum "SSL3_RSA_DES_40_CBC_SHA";
        enum "SSL3_RSA_DES_64_CBC_SHA";
        enum "SSL3_RSA_RC4_128_MD5";
        enum "SSL3_RSA_RC4_128_SHA";
        enum "SSL3_RSA_RC4_40_MD5";
        enum "TLS1_DHE_RSA_AES_128_GCM_SHA256";
        enum "TLS1_DHE_RSA_AES_128_SHA";
        enum "TLS1_DHE_RSA_AES_128_SHA256";
        enum "TLS1_DHE_RSA_AES_256_GCM_SHA384";
        enum "TLS1_DHE_RSA_AES_256_SHA";
        enum "TLS1_DHE_RSA_AES_256_SHA256";
        enum "TLS1_ECDHE_ECDSA_AES_128_GCM_SHA256";
        enum "TLS1_ECDHE_ECDSA_AES_128_SHA";
        enum "TLS1_ECDHE_ECDSA_AES_128_SHA256";
        enum "TLS1_ECDHE_ECDSA_AES_256_GCM_SHA384";
        enum "TLS1_ECDHE_ECDSA_AES_256_SHA";
        enum "TLS1_ECDHE_RSA_AES_128_GCM_SHA256";
        enum "TLS1_ECDHE_RSA_AES_128_SHA";
        enum "TLS1_ECDHE_RSA_AES_128_SHA256";
        enum "TLS1_ECDHE_RSA_AES_256_GCM_SHA384";
        enum "TLS1_ECDHE_RSA_AES_256_SHA";
        enum "TLS1_RSA_AES_128_GCM_SHA256";
        enum "TLS1_RSA_AES_128_SHA";
        enum "TLS1_RSA_AES_128_SHA256";
        enum "TLS1_RSA_AES_256_GCM_SHA384";
        enum "TLS1_RSA_AES_256_SHA";
        enum "TLS1_RSA_AES_256_SHA256";
        enum "TLS1_RSA_EXPORT1024_RC4_56_MD5";
        enum "TLS1_RSA_EXPORT1024_RC4_56_SHA";
      }
      type string;
    }
  }

  grouping ncs_compliance_template_slb-template-version-grouping {
    container version {
      leaf current {
        tailf:cli-drop-node-name;
        type string;
      }
      leaf lower {
        tailf:cli-drop-node-name;
        type string;
      }
    }
  }

  grouping ncs_compliance_template_ip-list-grouping {
    list ip-list {
      // NCS patched for predictable order
      ordered-by user;
      key "name";
      leaf name {
        type string;
      }
    }
  }

  grouping ncs_compliance_template_cgnv6-grouping {
    container cgnv6 {
      container logging {
        container nat-quota-exceeded {
          leaf level {
            type string;
          }
        }
        container sampling-enable {
          leaf all {
            type empty;
          }
        }
      }
      list server {
        // NCS patched for predictable order
        ordered-by user;
        key "name";
        unique "address";
        leaf name {
          type string;
        }
        leaf address {
          tailf:cli-drop-node-name;
          // NCS drop mandatory statement
          type string;
        }
        leaf health-check-disable {
          type empty;
        }
        list port {
          // NCS patched for predictable order
          ordered-by user;
          key "number tcpudp";
          leaf number {
            type string;
          }
          leaf tcpudp {
            type string;
          }
          leaf health-check-disable {
            type empty;
          }
        }
      }
      list service-group {
        // NCS patched for predictable order
        ordered-by user;
        key "name tcpudp";
        unique "name";
        leaf name {
          type string;
        }
        leaf tcpudp {
          type string;
        }
        container sampling-enable {
          leaf all {
            type empty;
          }
        }
        list member {
          // NCS patched for predictable order
          ordered-by user;
          key "host port";
          leaf host {
            type string;
          }
          leaf port {
            type string;
          }
          container sampling-enable {
            leaf all {
              type empty;
            }
          }
        }
        container shared {
          choice group-partition {
            leaf group {
              type string;
            }
            leaf partition {
              type string;
            }
          }
        }
      }
      container translation {
        leaf udp-timeout {
          type string;
        }
        leaf tcp-timeout {
          type string;
        }
        leaf icmp-timeout {
          type string;
        }
        container service-timeout {
          list tcp {
            // NCS patched for predictable order
            ordered-by user;
            tailf:cli-suppress-mode;
            key "port-id";
            leaf port-id {
              type string;
            }
            leaf to {
              type string;
            }
            leaf timeout {
              tailf:cli-drop-node-name;
              type string;
            }
          }
          list udp {
            // NCS patched for predictable order
            ordered-by user;
            tailf:cli-suppress-mode;
            key "port-id";
            leaf port-id {
              type string;
            }
            leaf timeout {
              tailf:cli-drop-node-name;
              type string;
            }
          }
        }
      }
      container lsn {
        list alg {
          // NCS patched for predictable order
          ordered-by user;
          tailf:cli-suppress-mode;
          key "alg-id";
          leaf alg-id {
            type string;
          }
          leaf enable {
            type empty;
          }
        }
        leaf hairpinning {
          type string;
        }
        leaf half-close-timeout {
          type string;
        }
        container logging {
          leaf default-template {
            type string;
          }
        }
        list endpoint-independent-mapping {
          // NCS patched for predictable order
          ordered-by user;
          key "proto";
          leaf proto {
            type string;
          }
          container port {
            leaf from {
              tailf:cli-drop-node-name;
              type string;
            }
            leaf to {
              type string;
            }
          }
        }
        list endpoint-independent-filtering {
          // NCS patched for predictable order
          ordered-by user;
          key "proto";
          leaf proto {
            type string;
          }
          container port {
            leaf from {
              tailf:cli-drop-node-name;
              type string;
            }
            leaf to {
              type string;
            }
          }
        }
        leaf ip-selection {
          type string;
        }
        container inside {
          container source {
            leaf class-list {
              type string;
            }
          }
        }
      }
      list lsn-rule-list {
        // NCS patched for predictable order
        ordered-by user;
        key "name";
        leaf name {
          type string;
        }
        container default {
          container tcp {
            uses ncs_compliance_template_port-grouping;
          }
          container udp {
            uses ncs_compliance_template_port-grouping;
          }
          container icmp {
            // NCS expand uses statement
            list action {
              // NCS patched for predictable order
              ordered-by user;
              tailf:cli-suppress-mode;
              key "type";
              leaf type {
                type string;
              }
              leaf pool {
                type string;
              }
              leaf domain {
                type string;
              }
            }
            leaf no-action {
              type empty;
            }
          }
          container others {
            // NCS expand uses statement
            list action {
              // NCS patched for predictable order
              ordered-by user;
              tailf:cli-suppress-mode;
              key "type";
              leaf type {
                type string;
              }
              leaf pool {
                type string;
              }
              leaf domain {
                type string;
              }
            }
            leaf no-action {
              type empty;
            }
          }
        }
        list ip {
          // NCS patched for predictable order
          ordered-by user;
          key "address";
          leaf address {
            type string;
          }
          container tcp {
            uses ncs_compliance_template_port-grouping;
          }
          container udp {
            uses ncs_compliance_template_port-grouping;
          }
          container icmp {
            // NCS expand uses statement
            list action {
              // NCS patched for predictable order
              ordered-by user;
              tailf:cli-suppress-mode;
              key "type";
              leaf type {
                type string;
              }
              leaf pool {
                type string;
              }
              leaf domain {
                type string;
              }
            }
            leaf no-action {
              type empty;
            }
          }
          container others {
            // NCS expand uses statement
            list action {
              // NCS patched for predictable order
              ordered-by user;
              tailf:cli-suppress-mode;
              key "type";
              leaf type {
                type string;
              }
              leaf pool {
                type string;
              }
              leaf domain {
                type string;
              }
            }
            leaf no-action {
              type empty;
            }
          }
        }
      }
      container fixed-nat {
        leaf create-port-mapping-file {
          type empty;
        }
      }
      container nat {
        list pool {
          // NCS patched for predictable order
          ordered-by user;
          tailf:cli-suppress-mode;
          key "name";
          leaf name {
            type string;
          }
          leaf address {
            tailf:cli-drop-node-name;
            type string;
          }
          leaf address-end {
            tailf:cli-drop-node-name;
            type string;
          }
          leaf netmask {
            type string;
          }
          leaf vrid {
            type string;
          }
          leaf port-batch-v2-size {
            type string;
          }
          leaf simultaneous-batch-allocation {
            type empty;
          }
          leaf tcp-time-wait-interval {
            type string;
          }
          container usable-nat-ports {
            leaf start {
              tailf:cli-drop-node-name;
              type string;
            }
            leaf end {
              tailf:cli-drop-node-name;
              type string;
            }
          }
        }
        list pool-group {
          // NCS patched for predictable order
          ordered-by user;
          key "name";
          leaf name {
            type string;
          }
          leaf vrid {
            type string;
          }
          list member {
            // NCS patched for predictable order
            ordered-by user;
            tailf:cli-suppress-mode;
            key "name";
            leaf name {
              type string;
            }
          }
        }
      }
      container resource-usage {
        leaf lsn-nat-addr-count {
          type string;
        }
      }
      list lsn-lid {
        // NCS patched for predictable order
        ordered-by user;
        key "lid";
        leaf lid {
          type string;
        }
        leaf name {
          type string;
        }
        container lsn-rule-list {
          leaf destination {
            type string;
          }
        }
        list user-quota {
          // NCS patched for predictable order
          ordered-by user;
          tailf:cli-suppress-mode;
          key "protocol";
          leaf protocol {
            type string;
          }
          leaf quota {
            tailf:cli-drop-node-name;
            type string;
          }
          leaf reserve {
            type string;
          }
        }
        leaf source-nat-pool {
          type string;
        }
      }
      container template {
        list logging {
          // NCS patched for predictable order
          ordered-by user;
          key "name";
          leaf name {
            type string;
          }
          container log {
            container fixed-nat {
              leaf port-mappings {
                type string;
              }
              container sessions {
                presence "true";
                leaf merged-style {
                  type empty;
                }
              }
            }
            leaf port-mappings {
              type string;
            }
            container sessions {
              presence "true";
              leaf merged-style {
                type empty;
              }
            }
          }
          leaf facility {
            type string;
          }
          leaf severity {
            type string;
          }
          container service-group {
            leaf name {
              tailf:cli-drop-node-name;
              type string;
            }
            leaf shared {
              type empty;
            }
          }
          container disable-log-by-destination {
            presence "true";
            leaf icmp {
              type empty;
            }
          }
          leaf include-destination {
            type empty;
          }
          leaf format {
            type string;
          }
          leaf batched-logging-disable {
            type empty;
          }
        }
      }
    }
  }

  grouping ncs_compliance_template_sflow-grouping {
    container sflow {
      container agent {
        leaf address {
          type string;
        }
      }
      container setting {
        leaf local-collection {
          type empty;
        }
        leaf source-ip-use-mgmt {
          type empty;
        }
      }
      list collector {
        // NCS patched for predictable order
        ordered-by user;
        tailf:cli-suppress-mode;
        key "ip port";
        leaf ip {
          type string;
        }
        leaf port {
          type string;
        }
      }
      list collector-alt {
        // NCS patched for predictable order
        ordered-by user;
        tailf:cli-suppress-mode;
        tailf:alt-name "collector";
        key "ip port";
        leaf ip {
          type string;
        }
        leaf port {
          type string;
        }
      }
      container polling {
        leaf cpu-usage {
          type empty;
        }
        leaf-list ve {
          // NCS patched for predictable order
          ordered-by user;
          tailf:cli-range-list-syntax;
          type string;
        }
      }
      container sampling {
        leaf-list ve {
          // NCS patched for predictable order
          ordered-by user;
          tailf:cli-range-list-syntax;
          type string;
        }
      }
      container source-address {
        leaf ip {
          type string;
        }
        leaf ipv6 {
          type string;
        }
      }
    }
  }

  grouping ncs_compliance_template_ip-address {
    list address {
      // NCS patched for predictable order
      ordered-by user;
      tailf:cli-suppress-mode;
      key "address mask";
      leaf address {
        type string;
      }
      leaf mask {
        type string;
      }
    }
  }

  grouping ncs_compliance_template_algs {
    container alg {
      uses ncs_compliance_template_pptp_alg;
      uses ncs_compliance_template_tftp_alg;
      uses ncs_compliance_template_rtsp_alg;
      uses ncs_compliance_template_esp_alg;
    }
  }

  grouping ncs_compliance_template_pptp_alg {
    leaf pptp {
      type string;
    }
  }

  grouping ncs_compliance_template_tftp_alg {
    leaf tftp {
      type string;
    }
  }

  grouping ncs_compliance_template_rtsp_alg {
    leaf rtsp {
      type string;
    }
  }

  grouping ncs_compliance_template_esp_alg {
    leaf esp {
      type string;
    }
  }

  grouping ncs_compliance_template_lid-grouping {
    choice lid-choice {
      leaf glid {
        type string;
      }
      leaf lid {
        type string;
      }
      leaf lsn-lid {
        type string;
      }
      leaf lsn-radius-profile {
        type string;
      }
    }
  }

  grouping ncs_compliance_template_mgmt-source-interface-grouping {
    container source-interface {
      leaf loopback {
        type string;
      }
    }
  }

  grouping ncs_compliance_template_priority-cost {
    leaf priority-cost {
      // NCS drop mandatory statement
      type string;
    }
  }

  grouping ncs_compliance_template_hostname-grouping {
    leaf hostname {
      type string;
    }
  }

  grouping ncs_compliance_template_password-grouping {
    leaf username {
      type string;
    }
    leaf password {
      type string;
    }
  }

  grouping ncs_compliance_template_interface-grouping {
    container interface {

      grouping lldp-interface-grouping {
        container lldp {
          container enable {
            leaf rx {
              type empty;
            }
            leaf tx {
              type empty;
            }
          }
          leaf notification {
            type string;
          }
          leaf tx-dot1-tlvs {
            type string;
          }
        }
      }
      container management {
        container bcast-rate-limit {
          presence "present";
          leaf rate {
            type string;
          }
        }
        container ip {
          uses ncs_compliance_template_ip-address;
          leaf control-apps-use-mgmt-port {
            type empty;
          }
          leaf default-gateway {
            type string;
          }
        }
        container ipv6 {
          list address {
            // NCS patched for predictable order
            ordered-by user;
            key "ip";
            tailf:cli-suppress-mode;
            leaf ip {
              tailf:cli-drop-node-name;
              type ncs_compliance_template_ipv6-prefix;
            }
            leaf link-local {
              type empty;
            }
          }
          leaf default-gateway {
            type string;
          }
        }
        uses lldp-interface-grouping;
        leaf flow-control {
          type empty;
        }
        container access-list {
          leaf id {
            tailf:cli-drop-node-name;
            type string;
          }
          leaf in {
            // NCS drop must statement
            type empty;
          }
        }
        leaf enabled-disabled {
          tailf:cli-drop-node-name;
          type string;
        }
        leaf duplexity {
          type string;
        }
        leaf mtu {
          type string;
        }
        leaf speed {
          type string;
        }
      }
      list ethernet {
        // NCS patched for predictable order
        ordered-by user;
        key "nr";
        leaf nr {
          type ncs_compliance_template_ethernet-index;
        }
        leaf name {
          type string;
        }
        container ip {
          uses ncs_compliance_template_ip-address;
          leaf cache-spoofing-port {
            type empty;
          }
          leaf helper-address {
            type string;
          }
          container nat {
            leaf inside {
              type empty;
            }
            leaf outside {
              type empty;
            }
          }
          container ospf;
          container router {
            container isis {
              presence "true";
              leaf cmds {
                tailf:cli-drop-node-name;
                type string;
              }
            }
          }
          leaf allow-promiscuous-vip {
            type empty;
          }
          container tcp {
            leaf syn-cookie {
              type empty;
            }
          }
        }
        container ipv6 {
          container access-list {
            leaf id {
              tailf:cli-drop-node-name;
              type string;
            }
            leaf in {
              // NCS drop must statement
              type empty;
            }
          }
          list address {
            // NCS patched for predictable order
            ordered-by user;
            key "ip";
            tailf:cli-suppress-mode;
            leaf ip {
              tailf:cli-drop-node-name;
              type ncs_compliance_template_ipv6-prefix;
            }
            leaf link-local {
              type empty;
            }
            leaf anycast {
              type empty;
            }
          }
          container nat {
            leaf inside {
              type empty;
            }
            leaf outside {
              type empty;
            }
          }
          container ndisc {
            container router-advertisement;
          }
          container ospf;
          container router {
            container isis {
              presence "true";
              leaf cmds {
                tailf:cli-drop-node-name;
                type string;
              }
            }
          }
        }
        leaf load-interval {
          type string;
        }
        container access-list {
          leaf id {
            tailf:cli-drop-node-name;
            type string;
          }
          leaf in {
            // NCS drop must statement
            type empty;
          }
        }
        leaf state {
          tailf:cli-drop-node-name;
          type string;
        }
        leaf state-alt {
          tailf:cli-drop-node-name;
          type string;
        }
        leaf duplexity {
          type string;
        }
        leaf cpu-process {
          type empty;
        }
        leaf flow-control {
          type empty;
        }
        container icmp-rate-limit {
          leaf rate {
            tailf:cli-drop-node-name;
            type string;
          }
          leaf lockup {
            // NCS drop must statement
            type string;
          }
          leaf lockup-period {
            // NCS drop must statement
            tailf:cli-drop-node-name;
            type string;
          }
        }
        container ospf;
        container isis;
        leaf l3-vlan-fwd-disable {
          type empty;
        }
        container lacp {
          leaf port-priority {
            type string;
          }
          leaf timeout {
            type string;
          }
          container trunk {
            leaf number {
              tailf:cli-drop-node-name;
              type string;
            }
            leaf admin-key {
              // NCS drop must statement
              type string;
            }
            leaf mode {
              // NCS drop must statement
              type string;
            }
            leaf unidirectional-detection {
              // NCS drop must statement
              type empty;
            }
          }
          container udld-timeout {
            leaf timeout-type {
              tailf:cli-drop-node-name;
              type string;
            }
            leaf milli {
              tailf:cli-drop-node-name;
              type string;
            }
            leaf secs {
              tailf:cli-drop-node-name;
              type string;
            }
          }
        }
        uses lldp-interface-grouping;
        leaf mtu {
          type string;
        }
        leaf speed {
          type string;
        }
        list trunk-group-list {
          // NCS patched for predictable order
          ordered-by user;
          key "trunk-group-key";
          tailf:cli-drop-node-name;
          leaf trunk-group-key {
            type string;
          }
          leaf trunk-group-id {
            tailf:cli-drop-node-name;
            // NCS drop mandatory statement
            type string;
          }
          leaf trunk-group-type {
            tailf:cli-drop-node-name;
            type string;
          }
        }
      }
      list trunk {
        // NCS patched for predictable order
        ordered-by user;
        key "nr";
        leaf nr {
          type ncs_compliance_template_ethernet-index;
        }
        leaf name {
          type string;
        }
        leaf state {
          tailf:cli-drop-node-name;
          type string;
        }
        container icmp-rate-limit {
          leaf rate {
            tailf:cli-drop-node-name;
            type string;
          }
          leaf lockup {
            // NCS drop must statement
            type string;
          }
          leaf lockup-period {
            // NCS drop must statement
            tailf:cli-drop-node-name;
            type string;
          }
        }
        list access-list {
          // NCS patched for predictable order
          ordered-by user;
          tailf:cli-suppress-mode;
          key "id in-type";
          leaf id {
            type string;
          }
          leaf in-type {
            type string;
          }
        }
        container ip {
          list address {
            // NCS patched for predictable order
            ordered-by user;
            key "ip mask";
            tailf:cli-suppress-mode;
            leaf ip {
              type string;
            }
            leaf mask {
              type ncs_compliance_template_ipv4-mask;
            }
          }
          leaf allow-promiscuous-vip {
            type empty;
          }
          leaf cache-spoofing-port {
            type empty;
          }
          container nat {
            leaf inside {
              type empty;
            }
            leaf outside {
              type empty;
            }
          }
        }
      }
      list loopback {
        // NCS patched for predictable order
        ordered-by user;
        key "nr";
        leaf nr {
          type ncs_compliance_template_ethernet-index;
        }
        container ip {
          uses ncs_compliance_template_ip-address;
          container router {
            choice isis-choice {
              container isis-alt {
                tailf:cli-drop-node-name;
                leaf isis {
                  type string;
                }
              }
              leaf isis {
                type empty;
              }
            }
          }
        }
        container icmp-rate-limit {
          leaf rate {
            tailf:cli-drop-node-name;
            type string;
          }
          leaf lockup {
            // NCS drop must statement
            type string;
          }
          leaf lockup-period {
            tailf:cli-drop-node-name;
            // NCS drop must statement
            type string;
          }
        }
        leaf state {
          tailf:cli-drop-node-name;
          type string;
        }
      }
      list ve {
        // NCS patched for predictable order
        ordered-by user;
        key "id";
        leaf id {
          type ncs_compliance_template_vlan-index;
        }
        leaf name {
          type string;
        }
        container bfd {
          container echo {
            presence "true";
          }
        }
        container icmp-rate-limit {
          leaf rate {
            tailf:cli-drop-node-name;
            type string;
          }
          leaf lockup {
            // NCS drop must statement
            type string;
          }
          leaf lockup-period {
            tailf:cli-drop-node-name;
            // NCS drop must statement
            type string;
          }
        }
        container access-list {
          leaf id {
            tailf:cli-drop-node-name;
            type string;
          }
          leaf in {
            // NCS drop must statement
            type empty;
          }
        }
        leaf l3-vlan-fwd-disable {
          type empty;
        }
        container ip {
          leaf allow-promiscuous-vip {
            type empty;
          }
          leaf cache-spoofing-port {
            type empty;
          }
          leaf helper-address {
            type string;
          }
          container nat {
            leaf inside {
              type empty;
            }
            leaf outside {
              type empty;
            }
          }
          container ospf;
          container router {
            container isis {
              presence "true";
              leaf cmds {
                tailf:cli-drop-node-name;
                type string;
              }
            }
          }
          container tcp {
            leaf syn-cookie {
              type empty;
            }
          }
          uses ncs_compliance_template_ip-address;
        }
        container ipv6 {
          container access-list {
            leaf id {
              tailf:cli-drop-node-name;
              type string;
            }
            leaf in {
              // NCS drop must statement
              type empty;
            }
          }
          container nat {
            leaf inside {
              type empty;
            }
            leaf outside {
              type empty;
            }
          }
          container ndisc {
            container router-advertisement;
          }
          container ospf;
          container router {
            container isis {
              presence "true";
              leaf cmds {
                tailf:cli-drop-node-name;
                type string;
              }
            }
          }
          list address {
            // NCS patched for predictable order
            ordered-by user;
            key "ip";
            tailf:cli-suppress-mode;
            leaf ip {
              tailf:cli-drop-node-name;
              type ncs_compliance_template_ipv6-prefix;
            }
            leaf link-local {
              type empty;
            }
            leaf anycast {
              type empty;
            }
          }
        }
        leaf mtu {
          type string;
        }
        leaf state {
          tailf:cli-drop-node-name;
          type string;
        }
        container isis;
        container ospf;
      }
    }
  }

  grouping ncs_compliance_template_ip-route-grouping {
    list route {
      // NCS patched for predictable order
      ordered-by user;
      tailf:cli-suppress-mode;
      key "ip mask forwarding-router";
      leaf ip {
        type string;
      }
      leaf mask {
        type string;
      }
      leaf forwarding-router {
        type string;
      }
      leaf distance {
        tailf:cli-drop-node-name;
        type string;
      }
      leaf cpu-process {
        tailf:cli-drop-node-name;
        type string;
      }
    }
  }

  grouping ncs_compliance_template_ip-prefix-list-grouping {
    list prefix-list {
      // NCS patched for predictable order
      ordered-by user;
      tailf:cli-suppress-mode;
      key "name seq";
      leaf name {
        type string;
      }
      leaf seq {
        type string;
      }
      choice permit-deny {
        leaf permit {
          type string;
        }
        leaf deny {
          type string;
        }
      }
      leaf ge {
        type string;
      }
      leaf le {
        type string;
      }
    }
  }

  grouping ncs_compliance_template_ip-grouping {
    container ip {
      list access-list {
        // NCS patched for predictable order
        ordered-by user;
        key "name";
        leaf name {
          type string;
        }
        list access-list-rule {
          // NCS patched for predictable order
          ordered-by user;
          tailf:cli-suppress-mode;
          tailf:cli-drop-node-name;
          key "rule";
          leaf rule {
            type string;
          }
        }
      }
      list address {
        // NCS patched for predictable order
        ordered-by user;
        key "ip";
        tailf:cli-suppress-mode;
        leaf ip {
          tailf:cli-drop-node-name;
          type string;
        }
        leaf mask {
          tailf:cli-drop-node-name;
          type ncs_compliance_template_ipv4-mask;
        }
      }
      container anomaly-drop {
        leaf bad-content {
          type string;
        }
        leaf drop-all {
          type empty;
        }
        leaf frag {
          type empty;
        }
        leaf ip-option {
          type string;
        }
        leaf land-attack {
          type empty;
        }
        leaf out-of-sequence {
          type string;
        }
        leaf ping-of-death {
          type empty;
        }
        leaf tcp-no-flag {
          type empty;
        }
        leaf tcp-syn-fin {
          type empty;
        }
        leaf tcp-syn-frag {
          type empty;
        }
        leaf zero-window {
          type string;
        }
        container security-attack {
          leaf layer-3 {
            type empty;
          }
          leaf layer-4 {
            type empty;
          }
        }
        list packet-deformity {
          // NCS patched for predictable order
          ordered-by user;
          tailf:cli-suppress-mode;
          key "layer";
          leaf layer {
            type string;
          }
        }
      }
      container as-path {
        list access-list {
          // NCS patched for predictable order
          ordered-by user;
          tailf:cli-suppress-mode;
          key "name action path";
          leaf name {
            type string;
          }
          leaf action {
            type string;
          }
          leaf path {
            type string;
          }
        }
      }
      container community-list {
        list standard-number {
          // NCS patched for predictable order
          ordered-by user;
          tailf:cli-drop-node-name;
          tailf:cli-suppress-mode;
          key "nr";
          leaf nr {
            type string;
          }
          list rules {
            // NCS patched for predictable order
            ordered-by user;
            tailf:cli-drop-node-name;
            tailf:cli-suppress-mode;
            key "action expr";
            leaf action {
              type string;
            }
            leaf expr {
              type string;
            }
          }
        }
        list expanded-number {
          // NCS patched for predictable order
          ordered-by user;
          tailf:cli-drop-node-name;
          tailf:cli-suppress-mode;
          key "nr";
          leaf nr {
            type string;
          }
          list rules {
            // NCS patched for predictable order
            ordered-by user;
            tailf:cli-drop-node-name;
            tailf:cli-suppress-mode;
            key "action expr";
            leaf action {
              type string;
            }
            leaf expr {
              type string;
            }
          }
        }
        list word {
          // NCS patched for predictable order
          ordered-by user;
          tailf:cli-drop-node-name;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
        list expanded {
          // NCS patched for predictable order
          ordered-by user;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
        list standard {
          // NCS patched for predictable order
          ordered-by user;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
      }
      leaf default-gateway {
        type string;
      }
      container dns {
        leaf primary {
          type string;
        }
        leaf secondary {
          type string;
        }
        leaf suffix {
          type string;
        }
      }
      container extcommunity-list {
        list standard-number {
          // NCS patched for predictable order
          ordered-by user;
          tailf:cli-drop-node-name;
          tailf:cli-suppress-mode;
          key "nr";
          leaf nr {
            type string;
          }
          list rules {
            // NCS patched for predictable order
            ordered-by user;
            tailf:cli-drop-node-name;
            tailf:cli-suppress-mode;
            key "action expr";
            leaf action {
              type string;
            }
            leaf expr {
              type string;
            }
          }
        }
        list expanded-number {
          // NCS patched for predictable order
          ordered-by user;
          tailf:cli-drop-node-name;
          tailf:cli-suppress-mode;
          key "nr";
          leaf nr {
            type string;
          }
          list rules {
            // NCS patched for predictable order
            ordered-by user;
            tailf:cli-drop-node-name;
            tailf:cli-suppress-mode;
            key "action expr";
            leaf action {
              type string;
            }
            leaf expr {
              type string;
            }
          }
        }
        list expanded {
          // NCS patched for predictable order
          ordered-by user;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
        list standard {
          // NCS patched for predictable order
          ordered-by user;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
      }
      container frag {
        leaf buff {
          type string;
        }
        container cpu-threshold {
          leaf high {
            type string;
          }
          leaf low {
            type string;
          }
        }
        leaf max-reassembly-sessions {
          type string;
        }
        leaf timeout {
          type string;
        }
      }
      container icmp {
        container disable {
          leaf redirect {
            type empty;
          }
          leaf unreachable {
            type empty;
          }
        }
      }
      container mgmt-traffic {
        container snmp {
          uses ncs_compliance_template_mgmt-source-interface-grouping;
        }
        container ntp {
          uses ncs_compliance_template_mgmt-source-interface-grouping;
        }
        container syslog {
          uses ncs_compliance_template_mgmt-source-interface-grouping;
        }
        container ssh {
          uses ncs_compliance_template_mgmt-source-interface-grouping;
        }
        container telnet {
          uses ncs_compliance_template_mgmt-source-interface-grouping;
        }
        container ftp {
          uses ncs_compliance_template_mgmt-source-interface-grouping;
        }
        container tftp {
          uses ncs_compliance_template_mgmt-source-interface-grouping;
        }
        container rcp {
          uses ncs_compliance_template_mgmt-source-interface-grouping;
        }
        container web {
          uses ncs_compliance_template_mgmt-source-interface-grouping;
        }
        container all {
          uses ncs_compliance_template_mgmt-source-interface-grouping;
        }
      }
      container nat {
        uses ncs_compliance_template_algs;
        leaf allow-static-host {
          type empty;
        }
        container inside {
          container source {
            list list {
              // NCS patched for predictable order
              ordered-by user;
              tailf:cli-suppress-mode;
              key "id";
              leaf id {
                type string;
              }
              leaf pool {
                // NCS drop mandatory statement
                type string;
              }
            }
            leaf class-list {
              type string;
            }
            list static {
              // NCS patched for predictable order
              ordered-by user;
              tailf:cli-suppress-mode;
              key "source nat";
              leaf source {
                type string;
              }
              leaf nat {
                type string;
              }
              leaf vrid {
                type string;
              }
            }
          }
        }
        list pool {
          // NCS patched for predictable order
          ordered-by user;
          tailf:cli-suppress-mode;
          key "name";
          leaf name {
            type string;
          }
          leaf ipstart {
            // NCS drop mandatory statement
            tailf:cli-drop-node-name;
            type string;
          }
          leaf ipend {
            // NCS drop mandatory statement
            tailf:cli-drop-node-name;
            type string;
          }
          leaf netmask {
            // NCS drop mandatory statement
            type string;
          }
          leaf gateway {
            type string;
          }
          leaf ha-group-id {
            type string;
          }
          leaf ha-use-all-ports {
            type empty;
          }
          leaf vrid {
            type string;
          }
          leaf ip-rr {
            type empty;
          }
          leaf lsn {
            type empty;
          }
          leaf max-users-per-ip {
            type string;
          }
        }
        list pool-group {
          // NCS patched for predictable order
          ordered-by user;
          key "name";
          leaf name {
            type string;
          }
          leaf ha-group-id {
            type string;
          }
          list member {
            // NCS patched for predictable order
            ordered-by user;
            key "member-id";
            tailf:cli-suppress-mode;
            leaf member-id {
              type string;
            }
          }
        }
        container range-list;
        leaf reset-idle-tcp-conn {
          type empty;
        }
        container template {
          list logging {
            // NCS patched for predictable order
            ordered-by user;
            key "name";
            leaf name {
              type string;
            }
          }
        }
        container translation {
          leaf icmp-timeout {
            type string;
          }
          leaf tcp-timeout {
            type string;
          }
          leaf udp-timeout {
            type string;
          }
          leaf syn-timeout {
            type string;
          }
          list service-timeout {
            // NCS patched for predictable order
            ordered-by user;
            tailf:cli-suppress-mode;
            key "protocol from";
            leaf protocol {
              type string;
            }
            leaf from {
              type string;
            }
            leaf to {
              type string;
            }
            leaf timeout {
              tailf:cli-drop-node-name;
              type string;
            }
          }
        }
        container lsn {
          container endpoint-independent-mapping {
            container tcp {
              container enable {
                leaf ephemeral {
                  type empty;
                }
                leaf well-known {
                  type empty;
                }
              }
            }
            container udp {
              container enable {
                leaf ephemeral {
                  type empty;
                }
                leaf well-known {
                  type empty;
                }
              }
            }
          }
          container endpoint-independent-filtering {
            container tcp {
              container enable {
                leaf ephemeral {
                  type empty;
                  // NCS drop must statement
                }
                leaf well-known {
                  type empty;
                  // NCS drop must statement
                }
              }
            }
            container udp {
              container enable {
                leaf ephemeral {
                  type empty;
                  // NCS drop must statement
                }
                leaf well-known {
                  type empty;
                  // NCS drop must statement
                }
              }
            }
          }
          leaf ip-selection {
            type string;
          }
          leaf attempt-port-preservation {
            type string;
          }
          uses ncs_compliance_template_algs;
        }
      }
      uses ncs_compliance_template_ip-prefix-list-grouping;
      uses ncs_compliance_template_ip-route-grouping;
      container tcp {
        container syn-cookie {
          leaf threshold {
            type string;
          }
        }
      }
    }
  }

  grouping ncs_compliance_template_resource-usage-grouping {
    leaf class-list-ipv6-addr-count {
      type string;
    }
    leaf client-ssl-template-count {
      type string;
    }
    leaf conn-reuse-template-count {
      type string;
    }
    leaf fast-tcp-template-count {
      type string;
    }
    leaf fast-udp-template-count {
      type string;
    }
    leaf http-template-count {
      type string;
    }
    leaf l4-session-count {
      type string;
    }
    leaf nat-pool-addr-count {
      type string;
    }
    leaf persist-cookie-template-count {
      type string;
    }
    leaf persist-srcip-template-count {
      type string;
    }
    leaf proxy-template-count {
      type string;
    }
    leaf real-port-count {
      type string;
    }
    leaf real-server-count {
      type string;
    }
    leaf server-ssl-template-count {
      type string;
    }
    leaf service-group-count {
      type string;
    }
    leaf stream-template-count {
      type string;
    }
    leaf virtual-port-count {
      type string;
    }
    leaf virtual-server-count {
      type string;
    }
  }

  grouping ncs_compliance_template_snmp-remote-grouping {
    list remote {
      // NCS patched for predictable order
      ordered-by user;
      tailf:cli-suppress-mode;
      key "host";
      leaf host {
        type string;
      }
      leaf mask {
        tailf:cli-drop-node-name;
        type string;
      }
    }
  }

  grouping ncs_compliance_template_health-grouping {
    container health {
      list monitor {
        // NCS patched for predictable order
        ordered-by user;
        key "name";
        leaf name {
          type string;
        }
        container interval {
          leaf interval {
            tailf:cli-drop-node-name;
            type string;
          }
          leaf timeout {
            type string;
          }
        }
        leaf interval-alt {
          tailf:alt-name "interval";
          type string;
        }
        leaf timeout-alt {
          tailf:alt-name "timeout";
          type string;
        }
        leaf retry {
          type string;
        }
        leaf retry-alt {
          tailf:alt-name "retry";
          type string;
        }
        leaf up-retry {
          type string;
        }
        leaf up-retry-alt {
          tailf:alt-name "up-retry";
          type string;
        }
        leaf strictly-retry-on-server-error-response {
          type empty;
        }
        leaf disable-after-down {
          type empty;
        }
        leaf override-port {
          type string;
        }
        leaf override-ipv4 {
          type string;
        }
        leaf override-ipv6 {
          type string;
        }
        container method {
          choice method-choice {
            container icmp {
              leaf transparent {
                type string;
              }
            }
            container http {
              presence "true";
              leaf port {
                type string;
              }
              // NCS expand uses statement
              leaf username {
                type string;
              }
              leaf password {
                type string;
              }
              leaf url {
                type empty;
              }
              leaf method {
                tailf:cli-drop-node-name;
                type string;
              }
              leaf path {
                tailf:cli-drop-node-name;
                type string;
              }
              leaf postdata {
                type string;
              }
              leaf postfile {
                type string;
              }
              container expect {
                choice expect-choice {
                  leaf response-code {
                    type string;
                  }
                  leaf text {
                    tailf:cli-drop-node-name;
                    type string;
                  }
                }
              }
              leaf maintenance-code {
                type string;
              }
              leaf host {
                type string;
              }
            }
            container https {
              presence "true";
              leaf port {
                type string;
              }
              leaf disable-sslv2hello {
                type empty;
              }
              uses ncs_compliance_template_password-grouping;
              leaf url {
                type empty;
              }
              leaf method {
                tailf:cli-drop-node-name;
                type string;
              }
              leaf path {
                tailf:cli-drop-node-name;
                type string;
              }
              container expect {
                choice expect-choice {
                  leaf response-code {
                    type string;
                  }
                  leaf text {
                    tailf:cli-drop-node-name;
                    type string;
                  }
                }
              }
              leaf maintenance-code {
                type string;
              }
              leaf host {
                type string;
              }
              container cert {
                leaf cert {
                  tailf:cli-drop-node-name;
                  type string;
                }
                leaf key {
                  type string;
                }
              }
            }
            container tcp {
              leaf port {
                type string;
              }
              leaf method {
                tailf:cli-drop-node-name;
                type string;
              }
              leaf sendcontent {
                tailf:cli-drop-node-name;
                type string;
              }
              leaf response {
                type empty;
              }
              leaf contains {
                type string;
              }
            }
            container udp {
              leaf port {
                type string;
              }
            }
            container ftp {
              presence "present";
              leaf port {
                type string;
              }
              uses ncs_compliance_template_password-grouping;
            }
            container snmp {
              presence "present";
              leaf community {
                type string;
              }
              leaf oid {
                type string;
              }
              leaf operation {
                type string;
              }
              leaf port {
                type string;
              }
            }
            container smtp {
              leaf domain {
                type string;
              }
              leaf port {
                type string;
              }
            }
            container dns {
              choice dns-health-choice {
                leaf domain {
                  type string;
                }
                leaf ipaddress {
                  type string;
                }
              }
              leaf port {
                type string;
              }
              leaf expect {
                type empty;
              }
              leaf response-code {
                type string;
              }
              leaf recurse {
                type string;
              }
              leaf tcp {
                type empty;
              }
              leaf type {
                type string;
              }
            }
            container pop3 {
              uses ncs_compliance_template_password-grouping;
              leaf port {
                type string;
              }
            }
            container imap {
              leaf port {
                type string;
              }
              uses ncs_compliance_template_password-grouping;
              leaf-list auth {
                // NCS patched for predictable order
                ordered-by user;
                type string;
              }
            }
            container sip {
              leaf port {
                type string;
              }
              leaf register {
                type empty;
              }
              leaf tcp {
                type empty;
              }
              leaf expect-response-code {
                type string;
              }
            }
            container radius {
              uses ncs_compliance_template_password-grouping;
              leaf secret {
                // NCS drop mandatory statement
                type string;
              }
              leaf port {
                type string;
              }
            }
            container tacplus {
              uses ncs_compliance_template_password-grouping;
              leaf secret {
                type string;
              }
              leaf port {
                type string;
              }
            }
            container ldap {
              leaf port {
                type string;
              }
              leaf overssl {
                type empty;
              }
              leaf binddn {
                type string;
              }
              leaf password {
                // NCS drop mandatory statement
                type string;
              }
            }
            container rtsp {
              leaf port {
                type string;
              }
              leaf rtspurl {
                type string;
              }
            }
            container database {
              leaf dbtype {
                tailf:cli-drop-node-name;
                type string;
              }
              leaf db-name {
                type string;
              }
              uses ncs_compliance_template_password-grouping;
              leaf send {
                type string;
              }
              leaf receive {
                type string;
              }
              leaf row {
                type string;
              }
              leaf column {
                type string;
              }
            }
            container external {
              leaf program {
                type string;
              }
            }
            container ntp;
            container compound {
              leaf name {
                tailf:cli-drop-node-name;
                type string;
              }
            }
          }
        }
      }
    }
  }

  grouping ncs_compliance_template_accounting-grouping {
    container accounting {
      container commands {
        leaf level {
          tailf:cli-drop-node-name;
          type string;
        }
        leaf stop-only {
          type empty;
        }
        leaf tacplus {
          type empty;
        }
      }
      leaf debug {
        type string;
      }
      container exec {
        choice st-st {
          leaf start-stop {
            type empty;
          }
          leaf stop-only {
            type empty;
          }
        }
        choice service {
          leaf tacplus {
            type empty;
          }
          leaf radius {
            type empty;
          }
        }
      }
    }
  }

  grouping ncs_compliance_template_acos-events-grouping {
    container acos-events {
      container logdb {
        leaf enable-all {
          type empty;
        }
        leaf enable-cgn {
          type empty;
        }
        leaf enable-http-forward-proxy {
          type empty;
        }
        leaf enable-smtp {
          type empty;
        }
      }
    }
  }

  grouping ncs_compliance_template_authorization-grouping {
    container authorization {
      container commands {
        leaf level {
          tailf:cli-drop-node-name;
          type string;
        }
        leaf-list method {
          // NCS patched for predictable order
          ordered-by user;
          type string;
        }
      }
    }
  }

  grouping ncs_compliance_template_bgp-grouping {
    container bgp {
      leaf extended-asn-cap {
        type empty;
      }
    }
  }

  grouping ncs_compliance_template_lacp-grouping {
    container lacp {
      leaf system-priority {
        type string;
      }
    }
  }

  grouping ncs_compliance_template_slb-grouping {
    container slb {
      container graceful-shutdown {
        leaf timeout {
          tailf:cli-drop-node-name;
          type string;
        }
        leaf when {
          // NCS drop must statement
          tailf:cli-drop-node-name;
          type string;
        }
      }
      leaf disable-server-auto-reselect {
        type empty;
      }
      container buff-thresh {
        leaf hw-buff {
          type string;
        }
        leaf relieve-thresh {
          type string;
        }
        leaf sys-buff-low {
          type string;
        }
        leaf sys-buff-high {
          type string;
        }
      }
      container template {
        list server {
          // NCS patched for predictable order
          ordered-by user;
          key "name";
          leaf name {
            type string;
          }
          leaf health-check {
            type string;
          }
          container conn-limit {
            leaf limit {
              tailf:cli-drop-node-name;
              type string;
            }
            leaf resume {
              // NCS drop must statement
              type string;
            }
            leaf no-logging {
              type empty;
            }
          }
          container conn-rate-limit {
            leaf limit {
              tailf:cli-drop-node-name;
              type string;
            }
            leaf per {
              // NCS drop must statement
              type string;
            }
            leaf no-logging {
              type empty;
            }
          }
          leaf dns-query-interval {
            type string;
          }
          leaf dynamic-server-prefix {
            type string;
          }
          leaf max-dynamic-server {
            type string;
          }
          leaf min-ttl-ratio {
            type string;
          }
          container slow-start {
            presence "present";
            leaf from {
              type string;
            }
            choice slow-start-choice {
              leaf add {
                type string;
              }
              leaf times {
                type string;
              }
            }
            leaf every {
              type string;
            }
            leaf till {
              type string;
            }
          }
        }
        list port {
          // NCS patched for predictable order
          ordered-by user;
          key "name";
          leaf name {
            type string;
          }
          container health-check {
            presence "true";
            choice mon-choice {
              leaf monitor {
                tailf:cli-drop-node-name;
                type string;
              }
              leaf ping {
                type empty;
              }
            }
          }
          container conn-limit {
            leaf limit {
              tailf:cli-drop-node-name;
              type string;
            }
            leaf resume {
              // NCS drop must statement
              type string;
            }
            leaf no-logging {
              type empty;
            }
          }
          container conn-rate-limit {
            leaf limit {
              tailf:cli-drop-node-name;
              type string;
            }
            leaf per {
              // NCS drop must statement
              type string;
            }
            leaf no-logging {
              type empty;
            }
          }
          leaf dest-nat {
            type empty;
          }
          leaf down-grace-period {
            type string;
          }
          leaf dscp {
            type string;
          }
          container dynamic-member-priority {
            leaf priority {
              tailf:cli-drop-node-name;
              type string;
            }
            leaf decrement {
              // NCS drop must statement
              type string;
            }
          }
          container inband-health-check {
            presence "true";
            leaf retry {
              type string;
            }
            leaf reassign {
              type string;
            }
          }
          leaf no-ssl {
            type empty;
          }
          container slow-start {
            presence "present";
            leaf from {
              type string;
            }
            choice slow-start-choice {
              leaf add {
                type string;
              }
              leaf times {
                type string;
              }
            }
            leaf every {
              type string;
            }
            leaf till {
              type string;
            }
          }
          leaf source-nat {
            type string;
          }
          leaf weight {
            type string;
          }
        }
        container cache;
        list client-ssl {
          // NCS patched for predictable order
          ordered-by user;
          key "name";
          leaf name {
            type string;
          }
          container cert {
            leaf cert {
              tailf:cli-drop-node-name;
              type string;
            }
            leaf partition {
              type string;
            }
          }
          container chain-cert {
            leaf chain-cert {
              tailf:cli-drop-node-name;
              type string;
            }
            leaf partition {
              type string;
            }
          }
          list ca-cert {
            // NCS patched for predictable order
            ordered-by user;
            tailf:cli-suppress-mode;
            key "name";
            leaf name {
              type string;
            }
            leaf partition {
              type string;
            }
          }
          container key {
            leaf key-name {
              tailf:cli-drop-node-name;
              type string;
            }
            leaf partition {
              type string;
            }
            leaf pass-phrase {
              type empty;
            }
            leaf pass-phrase-value {
              tailf:cli-drop-node-name;
              type string;
            }
          }
          list cipher {
            // NCS patched for predictable order
            ordered-by user;
            tailf:cli-suppress-mode;
            key "name";
            leaf name {
              type ncs_compliance_template_cipher;
            }
          }
          container template {
            container cipher {
              leaf name {
                tailf:cli-drop-node-name;
                type string;
              }
            }
          }
          leaf close-notify {
            type empty;
          }
          leaf renegotiation-disable {
            type empty;
          }
          leaf session-cache-size {
            type string;
          }
          leaf session-cache-timeout {
            type string;
          }
          leaf session-ticket-lifetime {
            type string;
          }
          uses ncs_compliance_template_slb-template-version-grouping;
          leaf auth-username-attribute {
            type string;
          }
          container certificate {
            leaf name {
              tailf:cli-drop-node-name;
              type string;
            }
            leaf key {
              type string;
            }
            leaf pass-phrase {
              type string;
            }
            leaf chain-cert {
              type string;
            }
          }
          leaf disable-sslv3 {
            type empty;
          }
        }
        list connection-reuse {
          // NCS patched for predictable order
          ordered-by user;
          key "name";
          leaf name {
            type string;
          }
          leaf timeout {
            type string;
          }
          leaf limit-per-server {
            type string;
          }
          container keep-alive-conn {
            presence "present";
            leaf preopen {
              type empty;
            }
            leaf connections {
              tailf:cli-drop-node-name;
              type string;
            }
          }
        }
        container diameter;
        list dns {
          // NCS patched for predictable order
          ordered-by user;
          key "name";
          leaf name {
            type string;
          }
          leaf max-query-length {
            type string;
          }
          leaf max-cache-size {
            type string;
          }
          leaf max-cache-entry-size {
            type string;
          }
          container dns-log-enable {
            leaf period {
              type string;
            }
          }
          leaf query-id-switch {
            type empty;
          }
        }
        list dynamic-service {
          // NCS patched for predictable order
          ordered-by user;
          key "name";
          leaf name {
            type string;
          }
          container dns {
            list server {
              // NCS patched for predictable order
              ordered-by user;
              tailf:cli-suppress-mode;
              key "ip";
              leaf ip {
                type string;
              }
            }
          }
        }
        list http {
          // NCS patched for predictable order
          ordered-by user;
          key "name";
          leaf name {
            type string;
          }
          container insert-client-ip {
            presence "true";
            leaf header-name {
              tailf:cli-drop-node-name;
              type string;
            }
            leaf replace {
              type empty;
            }
          }
          container non-http-bypass {
            leaf service-group {
              type string;
            }
          }
          container url-hash-persist {
            leaf offset {
              type string;
            }
            choice hash-choice {
              leaf first {
                type string;
              }
              leaf last {
                type string;
              }
            }
            leaf use-server-status {
              type empty;
            }
          }
          list host-switching {
            // NCS patched for predictable order
            ordered-by user;
            tailf:cli-suppress-mode;
            key "match-type identifier";
            leaf match-type {
              type string;
            }
            leaf identifier {
              type string;
            }
            leaf service-group {
              // NCS drop mandatory statement
              type string;
            }
          }
          list url-switching {
            // NCS patched for predictable order
            ordered-by user;
            tailf:cli-suppress-mode;
            key "match-type identifier";
            leaf match-type {
              type string;
            }
            leaf identifier {
              type string;
            }
            leaf service-group {
              // NCS drop mandatory statement
              type string;
            }
          }
          leaf request-line-case-insensitive {
            type empty;
          }
          container redirect-rewrite {
            leaf secure {
              type empty;
            }
          }
          list request-header-insert {
            // NCS patched for predictable order
            ordered-by user;
            tailf:cli-suppress-mode;
            key "header";
            leaf header {
              type string;
            }
            leaf insert-mode {
              tailf:cli-drop-node-name;
              type string;
            }
          }
          list response-header-insert {
            // NCS patched for predictable order
            ordered-by user;
            tailf:cli-suppress-mode;
            key "header";
            leaf header {
              type string;
            }
            leaf insert-mode {
              tailf:cli-drop-node-name;
              type string;
            }
          }
          leaf keep-client-alive {
            type empty;
          }
        }
        container persist {
          list source-ip {
            // NCS patched for predictable order
            ordered-by user;
            key "name";
            leaf name {
              type string;
            }
            leaf dont-honor-conn-rules {
              type empty;
            }
            leaf enforce-higher-priority {
              type empty;
            }
            leaf incl-sport {
              type empty;
            }
            container match-type {
              choice match-choice {
                leaf server {
                  type empty;
                }
                leaf service-group {
                  type empty;
                }
              }
              leaf scan-all-members {
                type empty;
              }
            }
            leaf netmask {
              type string;
            }
            leaf netmask6 {
              type string;
            }
            leaf timeout {
              type string;
            }
          }
          list cookie {
            // NCS patched for predictable order
            ordered-by user;
            key "id";
            leaf id {
              type string;
            }
            leaf name {
              type string;
            }
            leaf expire {
              type string;
            }
            container match-type {
              leaf server {
                type empty;
              }
              leaf service-group {
                type empty;
              }
              leaf scan-all-members {
                type empty;
              }
            }
            leaf insert-always {
              type empty;
            }
            leaf pass-thru {
              type empty;
            }
          }
          list destination-ip {
            // NCS patched for predictable order
            ordered-by user;
            key "name";
            leaf name {
              type string;
            }
          }
          list ssl-sid {
            // NCS patched for predictable order
            ordered-by user;
            key "name";
            leaf name {
              type string;
            }
            leaf timeout {
              type string;
            }
          }
        }
        list policy {
          // NCS patched for predictable order
          ordered-by user;
          key "name";
          leaf name {
            type string;
          }
          leaf proxy-keep-alive {
            type empty;
          }

          grouping stp-class-list-grouping {
            list lid {
              // NCS patched for predictable order
              ordered-by user;
              key "limit-id";
              leaf limit-id {
                type string;
              }
              leaf class-list-group {
                type string;
              }
              container action {
                choice action-choice {
                  leaf drop {
                    type empty;
                  }
                  leaf forward-to-internet {
                    type string;
                  }
                  leaf forward-to-service-group {
                    type string;
                  }
                }
                leaf log {
                  type empty;
                }
              }
              leaf conn-limit {
                type string;
              }
              container conn-rate-limit {
                leaf limit {
                  tailf:cli-drop-node-name;
                  type string;
                }
                leaf per {
                  // NCS drop must statement
                  type string;
                }
              }
              leaf request-limit {
                type string;
              }
              container request-rate-limit {
                leaf limit {
                  tailf:cli-drop-node-name;
                  type string;
                }
                leaf per {
                  // NCS drop must statement
                  type string;
                }
              }
              container over-limit-action {
                leaf over-limit-action-choice {
                  tailf:cli-drop-node-name;
                  type string;
                }
                leaf lockout {
                  type string;
                }
                leaf lockout-val {
                  tailf:cli-drop-node-name;
                  type string;
                }
                leaf log {
                  type empty;
                }
                leaf log-val {
                  tailf:cli-drop-node-name;
                  type string;
                }
              }
            }
            container client-ip {
              choice client-ip-choice {
                leaf l3-dest {
                  type empty;
                }
                leaf l7-header {
                  type empty;
                }
              }
              leaf l7-header-string {
                tailf:cli-drop-node-name;
                type string;
              }
            }
          }
          container class-list {
            leaf name {
              type string;
            }
            uses stp-class-list-grouping;
          }
          container class-list-alt {
            tailf:alt-name "class-list";
            leaf name {
              tailf:cli-drop-node-name;
              type string;
            }
            uses stp-class-list-grouping;
          }
          leaf class-list-group {
            type string;
          }
          container bw-list {
            leaf name {
              type string;
            }
            list id {
              // NCS patched for predictable order
              ordered-by user;
              tailf:cli-suppress-mode;
              key "id";
              leaf id {
                type string;
              }
              leaf service-group {
                type string;
              }
            }
          }
        }
        list server-ssl {
          // NCS patched for predictable order
          ordered-by user;
          key "name";
          leaf name {
            type string;
          }
          leaf cert {
            type string;
          }
          leaf ca-cert {
            type string;
          }
          list cipher {
            // NCS patched for predictable order
            ordered-by user;
            tailf:cli-suppress-mode;
            key "name";
            leaf name {
              type ncs_compliance_template_cipher;
            }
          }
          container server-certificate-error {
            leaf trap {
              type empty;
            }
            leaf email {
              type empty;
            }
            leaf logging {
              type empty;
            }
            leaf ignore {
              type empty;
            }
          }
          leaf close-notify {
            type empty;
          }
          container key {
            leaf key-name {
              tailf:cli-drop-node-name;
              type string;
            }
            leaf partition {
              type string;
            }
            leaf pass-phrase {
              type empty;
            }
            leaf pass-phrase-value {
              tailf:cli-drop-node-name;
              type string;
            }
          }
          container template {
            container cipher {
              leaf name {
                tailf:cli-drop-node-name;
                type string;
              }
            }
          }
          uses ncs_compliance_template_slb-template-version-grouping;
        }
        list sip {
          // NCS patched for predictable order
          ordered-by user;
          key "name";
          leaf name {
            type string;
          }
          leaf timeout {
            type string;
          }
          leaf call-id-persist-disable {
            type empty;
          }
          leaf insert-client-ip {
            type empty;
          }
        }
        container smtp;
        container streaming-media;
        list tcp {
          // NCS patched for predictable order
          ordered-by user;
          key "name";
          leaf name {
            type string;
          }
          leaf idle-timeout {
            type string;
          }
          container force-delete-timeout {
            leaf timeout {
              tailf:cli-drop-node-name;
              type string;
            }
            leaf alive-if-active {
              // NCS drop must statement
              type empty;
            }
          }
          leaf half-close-idle-timeout {
            type string;
          }
          leaf initial-window-size {
            type string;
          }
          leaf lan-fast-ack {
            type empty;
          }
          leaf reset-fwd {
            type empty;
          }
          leaf reset-rev {
            type empty;
          }
        }
        list tcp-proxy {
          // NCS patched for predictable order
          ordered-by user;
          key "name";
          leaf name {
            type string;
          }
          leaf idle-timeout {
            type string;
          }
          leaf syn-retries {
            type string;
          }
          leaf retransmit-retries {
            type string;
          }
          leaf half-close-idle-timeout {
            type string;
          }
          leaf backend-wscale {
            type string;
          }
          leaf reset-fwd {
            type empty;
          }
          leaf reset-rev {
            type empty;
          }
          leaf receive-buffer {
            type string;
          }
          leaf transmit-buffer {
            type string;
          }
          leaf nagle {
            type empty;
          }
          leaf timewait {
            type string;
          }
          leaf reno {
            type empty;
          }
        }
        list udp {
          // NCS patched for predictable order
          ordered-by user;
          key "name";
          leaf name {
            type string;
          }
          leaf idle-timeout {
            type string;
          }
          container aging {
            choice aging-choice {
              leaf immediate {
                type empty;
              }
              container short {
                presence "present";
                leaf short-value {
                  tailf:cli-drop-node-name;
                  type string;
                }
              }
            }
          }
          leaf re-select-if-server-down {
            type empty;
          }
        }
        list virtual-port {
          // NCS patched for predictable order
          ordered-by user;
          key "name";
          leaf name {
            type string;
          }
          leaf reset-unknown-conn {
            type empty;
          }
          leaf ignore-tcp-msl {
            type empty;
          }
          leaf allow-syn-otherflags {
            type empty;
          }
          leaf snat-port-preserve {
            type empty;
          }
        }
        list external-service {
          // NCS patched for predictable order
          ordered-by user;
          key "name";
          leaf name {
            type string;
          }
          container timeout {
            leaf time {
              tailf:cli-drop-node-name;
              type string;
            }
            leaf action {
              type string;
            }
          }
          leaf service-group {
            type string;
          }
          container template {
            leaf tcp-proxy {
              type string;
            }
          }
        }
        list virtual-server {
          // NCS patched for predictable order
          ordered-by user;
          key "name";
          leaf name {
            type string;
          }
          container conn-limit {
            leaf limit {
              tailf:cli-drop-node-name;
              type string;
            }
            leaf reset {
              // NCS drop must statement
              type empty;
            }
            leaf no-logging {
              type empty;
            }
          }
          container conn-rate-limit {
            leaf limit {
              tailf:cli-drop-node-name;
              type string;
            }
            leaf per {
              // NCS drop must statement
              type string;
            }
            leaf reset {
              // NCS drop must statement
              type empty;
            }
            leaf no-logging {
              type empty;
            }
          }
          container icmp-rate-limit {
            leaf rate {
              tailf:cli-drop-node-name;
              type string;
            }
            leaf lockup {
              // NCS drop must statement
              type string;
            }
            leaf lockup-period {
              tailf:cli-drop-node-name;
              // NCS drop must statement
              type string;
            }
          }
          leaf subnet-gratuitous-arp {
            type empty;
          }
        }
        list cipher {
          // NCS patched for predictable order
          ordered-by user;
          key "name";
          leaf name {
            type string;
          }

          grouping cipher-prio-grouping {
            leaf priority {
              type string;
            }
          }
          container SSL3_RSA_DES_192_CBC3_SHA {
            presence "present";
            uses cipher-prio-grouping;
          }
          container SSL3_RSA_DES_40_CBC_SHA {
            presence "present";
            uses cipher-prio-grouping;
          }
          container SSL3_RSA_DES_64_CBC_SHA {
            presence "present";
            uses cipher-prio-grouping;
          }
          container SSL3_RSA_RC4_128_MD5 {
            presence "present";
            uses cipher-prio-grouping;
          }
          container SSL3_RSA_RC4_128_SHA {
            presence "present";
            uses cipher-prio-grouping;
          }
          container SSL3_RSA_RC4_40_MD5 {
            presence "present";
            uses cipher-prio-grouping;
          }
          container TLS1_RSA_AES_128_SHA {
            presence "present";
            uses cipher-prio-grouping;
          }
          container TLS1_RSA_AES_256_SHA {
            presence "present";
            uses cipher-prio-grouping;
          }
          container TLS1_RSA_EXPORT1024_RC4_56_MD5 {
            presence "present";
            uses cipher-prio-grouping;
          }
          container TLS1_RSA_EXPORT1024_RC4_56_SHA {
            presence "present";
            uses cipher-prio-grouping;
          }
          container TLS1_RSA_AES_128_SHA256 {
            presence "present";
            uses cipher-prio-grouping;
          }
          container TLS1_RSA_AES_256_SHA256 {
            presence "present";
            uses cipher-prio-grouping;
          }
          container TLS1_DHE_RSA_AES_128_GCM_SHA256 {
            presence "present";
            uses cipher-prio-grouping;
          }
          container TLS1_DHE_RSA_AES_128_SHA {
            presence "present";
            uses cipher-prio-grouping;
          }
          container TLS1_DHE_RSA_AES_128_SHA256 {
            presence "present";
            uses cipher-prio-grouping;
          }
          container TLS1_DHE_RSA_AES_256_GCM_SHA384 {
            presence "present";
            uses cipher-prio-grouping;
          }
          container TLS1_DHE_RSA_AES_256_SHA {
            presence "present";
            uses cipher-prio-grouping;
          }
          container TLS1_DHE_RSA_AES_256_SHA256 {
            presence "present";
            uses cipher-prio-grouping;
          }
          container TLS1_ECDHE_ECDSA_AES_128_GCM_SHA256 {
            presence "present";
            uses cipher-prio-grouping;
          }
          container TLS1_ECDHE_ECDSA_AES_128_SHA {
            presence "present";
            uses cipher-prio-grouping;
          }
          container TLS1_ECDHE_ECDSA_AES_128_SHA256 {
            presence "present";
            uses cipher-prio-grouping;
          }
          container TLS1_ECDHE_ECDSA_AES_256_GCM_SHA384 {
            presence "present";
            uses cipher-prio-grouping;
          }
          container TLS1_ECDHE_ECDSA_AES_256_SHA {
            presence "present";
            uses cipher-prio-grouping;
          }
          container TLS1_ECDHE_RSA_AES_128_GCM_SHA256 {
            presence "present";
            uses cipher-prio-grouping;
          }
          container TLS1_ECDHE_RSA_AES_128_SHA {
            presence "present";
            uses cipher-prio-grouping;
          }
          container TLS1_ECDHE_RSA_AES_128_SHA256 {
            presence "present";
            uses cipher-prio-grouping;
          }
          container TLS1_ECDHE_RSA_AES_256_GCM_SHA384 {
            presence "present";
            uses cipher-prio-grouping;
          }
          container TLS1_ECDHE_RSA_AES_256_SHA {
            presence "present";
            uses cipher-prio-grouping;
          }
          container TLS1_RSA_AES_128_GCM_SHA256 {
            presence "present";
            uses cipher-prio-grouping;
          }
          container TLS1_RSA_AES_256_GCM_SHA384 {
            presence "present";
            uses cipher-prio-grouping;
          }
        }
      }
      list server {
        // NCS patched for predictable order
        ordered-by user;
        key "name";
        unique "address";
        leaf name {
          type string;
        }
        leaf address {
          tailf:cli-drop-node-name;
          // NCS drop mandatory statement
          type string;
        }
        leaf disable {
          type empty;
        }
        choice hc-choice {
          leaf health-check {
            type string;
          }
          container health-check-conf {
            tailf:cli-drop-node-name;
            container health-check {
              choice monitor-choice {
                leaf ping {
                  type empty;
                }
                leaf host {
                  tailf:cli-drop-node-name;
                  type string;
                }
              }
            }
          }
          leaf health-check-disable {
            type empty;
          }
        }
        container conn-limit {
          leaf limit {
            tailf:cli-drop-node-name;
            type string;
          }
          leaf resume {
            // NCS drop must statement
            type string;
          }
          leaf no-logging {
            type empty;
          }
        }
        leaf conn-resume {
          type string;
        }
        leaf extended-stats {
          type empty;
        }
        leaf external-ip {
          type string;
        }
        container ha-priority-cost {
          leaf cost {
            tailf:cli-drop-node-name;
            type string;
          }
          leaf ha-group {
            type string;
          }
        }
        leaf ipv6 {
          type string;
        }
        leaf slow-start {
          type empty;
        }
        leaf spoofing-cache {
          type empty;
        }
        leaf stats-data-disable {
          type empty;
        }
        leaf weight {
          type string;
        }
        list port {
          // NCS patched for predictable order
          ordered-by user;
          key "number tcpudp";
          leaf number {
            type string;
          }
          leaf tcpudp {
            type string;
          }
          container conn-limit {
            leaf limit {
              tailf:cli-drop-node-name;
              type string;
            }
            leaf resume {
              // NCS drop must statement
              type string;
            }
            leaf no-logging {
              type empty;
            }
          }
          leaf conn-resume {
            type string;
          }
          leaf extended-stats {
            type empty;
          }
          container ha-priority-cost {
            leaf cost {
              tailf:cli-drop-node-name;
              type string;
            }
            leaf ha-group {
              // NCS drop must statement
              type string;
            }
          }
          leaf health-check-disable {
            type empty;
          }
          container template {
            leaf port {
              type string;
            }
          }
          choice hc-choice {
            leaf health-check {
              type string;
            }
            container health-check-conf {
              tailf:cli-drop-node-name;
              container health-check {
                choice monitor-choice {
                  leaf ping {
                    type empty;
                  }
                  leaf host {
                    tailf:cli-drop-node-name;
                    type string;
                  }
                  container follow-port {
                    leaf port {
                      tailf:cli-drop-node-name;
                      type string;
                    }
                    leaf tcpudp {
                      tailf:cli-drop-node-name;
                      type string;
                    }
                  }
                }
              }
            }
          }
          leaf no-ssl {
            type empty;
          }
          leaf stats-data-disable {
            type empty;
          }
          leaf state {
            tailf:cli-drop-node-name;
            type string;
          }
        }
        container template {
          leaf server {
            type string;
          }
        }
        leaf state {
          tailf:cli-drop-node-name;
          type string;
        }
      }
      list service-group {
        // NCS patched for predictable order
        ordered-by user;
        key "name tcpudp";
        unique "name";
        leaf name {
          type string;
        }
        leaf tcpudp {
          type string;
        }
        leaf backup-server-event-log {
          type empty;
        }
        leaf extended-stats {
          type empty;
        }
        container health-check {
          choice monitor-choice {
            leaf ping {
              type empty;
            }
            leaf host {
              tailf:cli-drop-node-name;
              type string;
            }
          }
          leaf partition {
            type string;
          }
        }
        list member1 {
          // NCS patched for predictable order
          ordered-by user;
          tailf:cli-suppress-mode;
          tailf:alt-name "member";
          key "host port";
          leaf host {
            type string;
          }
          leaf port {
            type string;
          }
          leaf partition {
            type string;
          }
          leaf state {
            tailf:cli-drop-node-name;
            type string;
          }
          leaf priority {
            type string;
          }
        }
        list member2 {
          // NCS patched for predictable order
          ordered-by user;
          tailf:alt-name "member";
          key "host port";
          leaf host {
            type string;
          }
          leaf port {
            type string;
          }
          leaf partition {
            type string;
          }
          leaf state {
            tailf:cli-drop-node-name;
            type string;
          }
          leaf priority {
            type string;
          }
          leaf template {
            type string;
          }
        }
        container method {
          choice method-choice {
            leaf fastest-response {
              type empty;
            }
            container least-connection {
              presence "true";
              leaf pseudo-round-robin {
                type empty;
              }
            }
            leaf least-request {
              type empty;
            }
            leaf round-robin {
              type empty;
            }
            leaf round-robin-strict {
              type empty;
            }
            container service-least-connection {
              presence "true";
              leaf pseudo-round-robin {
                type empty;
              }
            }
            container service-weighted-least-connection {
              presence "true";
              leaf pseudo-round-robin {
                type empty;
              }
            }
            leaf stateless-dst-ip-hash {
              type empty;
            }
            leaf stateless-per-pkt-round-robin {
              type empty;
            }
            leaf stateless-src-dst-ip-hash {
              type empty;
            }
            leaf stateless-src-ip-hash {
              type empty;
            }
            leaf stateless-src-ip-only-hash {
              type empty;
            }
            container weighted-least-connection {
              presence "true";
              leaf pseudo-round-robin {
                type empty;
              }
            }
            leaf weighted-rr {
              type empty;
            }
          }
        }
        container min-active-member {
          leaf min {
            tailf:cli-drop-node-name;
            type string;
          }
          leaf method {
            // NCS drop must statement
            tailf:cli-drop-node-name;
            type string;
          }
        }
        list priority {
          // NCS patched for predictable order
          ordered-by user;
          tailf:cli-suppress-mode;
          key "prio";
          leaf prio {
            type string;
          }
          leaf action {
            tailf:cli-drop-node-name;
            type string;
          }
        }
        container priority-affinity {
          presence "true";
        }
        leaf reset-on-server-selection-fail {
          type empty;
        }
        leaf stats-data-disable {
          type empty;
        }
      }
      list virtual-server {
        // NCS patched for predictable order
        ordered-by user;
        key "name";
        leaf name {
          type string;
        }
        leaf address {
          tailf:cli-drop-node-name;
          // NCS drop mandatory statement
          type string;
        }
        leaf netmask {
          tailf:cli-drop-node-name;
          type string;
        }
        leaf acl {
          type string;
        }
        leaf arp-disable {
          type empty;
        }
        leaf disable {
          type empty;
        }
        leaf extended-stats {
          type empty;
        }
        leaf ha-dynamic {
          type string;
        }
        choice disable-choice {
          leaf disable-when-any-port-down {
            type empty;
          }
          leaf disable-when-all-ports-down {
            type empty;
          }
        }
        leaf ha-group {
          type string;
        }
        leaf redistribution-flagged {
          type empty;
        }
        leaf stats-data-disable {
          type empty;
        }
        leaf vrid {
          type string;
        }
        list port {
          // NCS patched for predictable order
          ordered-by user;
          key "id type";
          leaf id {
            type string;
          }
          leaf type {
            // NCS drop must statement
            type string;
          }
          container access-list {
            choice access-list-id {
              leaf acl-id {
                tailf:cli-drop-node-name;
                type string;
              }
              leaf name {
                type string;
              }
            }
            choice nat-choice {
              leaf source-nat-pool-alt1 {
                tailf:alt-name "source-nat-pool";
                type string;
              }
              leaf source-nat-pool-alt2 {
                tailf:alt-name "source-nat-pool";
                type string;
              }
              leaf source-nat-pool-alt3 {
                tailf:alt-name "source-nat-pool";
                type string;
              }
            }
            leaf sequence-number {
              type string;
            }
          }
          list aflex {
            // NCS patched for predictable order
            ordered-by user;
            tailf:cli-suppress-mode;
            key "id";
            leaf id {
              type string;
            }
          }
          container conn-limit {
            leaf limit {
              tailf:cli-drop-node-name;
              type string;
            }
            leaf reset {
              // NCS drop must statement
              type empty;
            }
            leaf no-logging {
              type empty;
            }
          }
          leaf def-selection-if-pref-failed-disable {
            type empty;
          }
          leaf disable {
            type empty;
          }
          leaf extended-stats {
            type empty;
          }
          leaf ha-conn-mirror {
            type empty;
            // NCS drop must statement
          }
          leaf message-switching {
            type empty;
          }
          leaf name {
            type string;
          }
          container no-dest-nat {
            presence "true";
            leaf port-translation {
              type empty;
            }
          }
          leaf pbslb {
            type empty;
          }
          leaf reset-on-server-selection-fail {
            type empty;
          }
          leaf redirect-to-https {
            type empty;
          }
          leaf support-http2 {
            type empty;
          }
          leaf service-group {
            type string;
          }
          leaf snat-on-vip {
            type empty;
          }
          container source-nat {
            choice source-nat-choice {
              container auto {
                presence "true";
                leaf precedence {
                  type empty;
                }
              }
              leaf class-list {
                type string;
              }
              list pool {
                // NCS patched for predictable order
                ordered-by user;
                tailf:cli-suppress-mode;
                // NCS drop tailf-common:cli-diff-create-before statement
                key "name";
                leaf name {
                  type string;
                }
              }
            }
          }
          leaf stats-data-disable {
            type empty;
          }
          leaf syn-cookie {
            type empty;
          }
          container use-default-if-no-server {
            presence "true";
            leaf sack {
              type empty;
            }
          }
          leaf use-rcv-hop-for-resp {
            type empty;
          }
          list template {
            // NCS patched for predictable order
            ordered-by user;
            tailf:cli-suppress-mode;
            key "template-type";
            leaf template-type {
              type string;
            }
            leaf udp {
              tailf:cli-drop-node-name;
              type string;
            }
            leaf sip {
              tailf:cli-drop-node-name;
              type string;
            }
            leaf diameter {
              tailf:cli-drop-node-name;
              type string;
            }
            container persist {
              tailf:cli-drop-node-name;
              leaf source-ip {
                type string;
              }
              leaf destination-ip {
                type string;
              }
              leaf ssl-sid {
                type string;
              }
              leaf cookie {
                type string;
              }
            }
            leaf policy {
              tailf:cli-drop-node-name;
              type string;
            }
            leaf tcp {
              tailf:cli-drop-node-name;
              type string;
            }
            leaf tcp-proxy {
              tailf:cli-drop-node-name;
              type string;
            }
            leaf virtual-port {
              tailf:cli-drop-node-name;
              type string;
            }
            leaf client-ssl {
              tailf:cli-drop-node-name;
              type string;
            }
            leaf server-ssl {
              tailf:cli-drop-node-name;
              type string;
            }
            leaf http {
              tailf:cli-drop-node-name;
              type string;
            }
            leaf external-service {
              tailf:cli-drop-node-name;
              type string;
            }
            leaf dynamic-service {
              tailf:cli-drop-node-name;
              type string;
            }
          }
        }
        container template {
          leaf logging {
            type string;
          }
          leaf policy {
            type string;
          }
          leaf virtual-server {
            type string;
          }
        }
      }
      container resource-usage {
        uses ncs_compliance_template_resource-usage-grouping;
      }
      leaf transparent-tcp-template {
        type string;
      }
    }
  }

  grouping ncs_compliance_template_gslb-group-grouping {
    list group {
      // NCS patched for predictable order
      ordered-by user;
      key "name";
      leaf name {
        type string;
      }
      leaf config-merge {
        type empty;
      }
      leaf enable {
        type empty;
      }
      list primary {
        // NCS patched for predictable order
        ordered-by user;
        tailf:cli-suppress-mode;
        key "ip-address";
        leaf ip-address {
          type string;
        }
      }
      leaf priority {
        type string;
      }
    }
  }

  grouping ncs_compliance_template_gslb-service-ip-grouping {
    list service-ip {
      // NCS patched for predictable order
      ordered-by user;
      key "name";
      leaf name {
        type string;
      }
      leaf disable {
        type empty;
      }
      leaf ip {
        tailf:cli-drop-node-name;
        type string;
      }
      leaf health-check {
        type string;
      }
      leaf health-check-protocol-disable {
        type empty;
      }
      leaf health-check-disable {
        type empty;
      }

      grouping service-port-grouping {
        leaf number {
          type string;
        }
        leaf udp-tcp {
          tailf:cli-drop-node-name;
          type string;
        }
        leaf service-name {
          type string;
        }
        leaf health-check {
          type string;
        }
        leaf health-check-protocol-disable {
          type empty;
        }
        leaf state {
          tailf:cli-drop-node-name;
          type string;
        }
      }
      list port {
        // NCS patched for predictable order
        ordered-by user;
        key "number service-name";
        uses service-port-grouping;
      }
      list service {
        // NCS patched for predictable order
        ordered-by user;
        key "number service-name";
        uses service-port-grouping;
      }
      container port-name {
        tailf:cli-drop-node-name;
        list port {
          // NCS patched for predictable order
          ordered-by user;
          key "number name";
          leaf number {
            type string;
          }
          leaf udp-tcp {
            tailf:cli-drop-node-name;
            type string;
          }
          leaf name {
            type string;
          }
          leaf health-check {
            type string;
          }
          leaf health-check-protocol-disable {
            type empty;
          }
          leaf state {
            tailf:cli-drop-node-name;
            type string;
          }
        }
      }
    }
  }

  grouping ncs_compliance_template_gslb-site-grouping {
    list site {
      // NCS patched for predictable order
      ordered-by user;
      key "name";
      leaf name {
        type string;
      }
      list slb-dev {
        // NCS patched for predictable order
        ordered-by user;
        key "name";
        leaf name {
          type string;
        }
        leaf ip-address {
          tailf:cli-drop-node-name;
          type string;
        }
        list vip-server {
          // NCS patched for predictable order
          ordered-by user;
          tailf:cli-suppress-mode;
          key "name";
          leaf name {
            type string;
          }
        }
      }
    }
  }

  grouping ncs_compliance_template_gslb-policy-grouping {
    list policy {
      // NCS patched for predictable order
      ordered-by user;
      key "name";
      leaf name {
        type string;
      }
      container admin-ip {
        leaf top-only {
          type empty;
        }
      }
      leaf admin-ip-enable {
        type empty;
      }
      leaf geographic {
        type string;
      }
      container metric-order {
        leaf-list options {
          // NCS patched for predictable order
          ordered-by user;
          tailf:cli-drop-node-name;
          type string;
        }
      }
      container dns {
        container active-only {
          presence "true";
          leaf fail-safe {
            type empty;
          }
        }
        leaf backup-server {
          type empty;
        }
        container selected-only {
          presence "true";
          leaf number {
            tailf:cli-drop-node-name;
            type string;
          }
        }
        leaf ttl {
          type string;
        }
        container server {
          choice dns-server-choice {
            leaf any {
              type empty;
            }
            leaf-list records {
              // NCS patched for predictable order
              ordered-by user;
              tailf:cli-drop-node-name;
              type string;
            }
          }
        }
        container sticky {
          leaf ip-mask {
            tailf:cli-drop-node-name;
            type string;
          }
          leaf ipv6-mask {
            type string;
          }
          leaf aging-time {
            type string;
          }
        }
      }
      container active-rdt {
        leaf enable {
          type empty;
        }
        leaf single-shot {
          type empty;
        }
      }
    }
  }

  grouping ncs_compliance_template_gslb-zone-grouping {
    list zone {
      // NCS patched for predictable order
      ordered-by user;
      key "name";
      leaf name {
        type string;
      }
      container service {
        list service-port {
          // NCS patched for predictable order
          ordered-by user;
          tailf:cli-drop-node-name;
          key "port";
          leaf port {
            type string;
          }
          uses ncs_compliance_template_gslb-zone-service-grouping;
        }
        list service-port-name {
          // NCS patched for predictable order
          ordered-by user;
          tailf:cli-drop-node-name;
          key "port name";
          leaf port {
            type string;
          }
          leaf name {
            type string;
          }
          uses ncs_compliance_template_gslb-zone-service-grouping;
        }
      }
    }
  }

  grouping ncs_compliance_template_gslb-grouping {
    container gslb {
      uses ncs_compliance_template_gslb-service-ip-grouping;
      uses ncs_compliance_template_gslb-group-grouping;
      uses ncs_compliance_template_gslb-site-grouping;
      uses ncs_compliance_template_gslb-policy-grouping;
      uses ncs_compliance_template_gslb-zone-grouping;
      container protocol {
        container enable {
          leaf controller {
            type empty;
          }
          leaf device {
            type empty;
          }
        }
      }
      container active-rdt {
        leaf icmp {
          type empty;
        }
      }
    }
  }

  grouping ncs_compliance_template_bw-list-grouping {
    list bw-list {
      // NCS patched for predictable order
      ordered-by user;
      tailf:cli-suppress-mode;
      key "name";
      leaf name {
        type string;
      }
      leaf import-info {
        type string;
      }
    }
    list import-info {
      // NCS patched for predictable order
      ordered-by user;
      tailf:cli-suppress-mode;
      key "name";
      leaf name {
        type string;
      }
      leaf url {
        type string;
      }
      leaf username {
        type string;
      }
      leaf password {
        type string;
      }
    }
  }

  grouping ncs_compliance_template_aflex-grouping {
    list aflex {
      // NCS patched for predictable order
      ordered-by user;
      key "name";
      leaf name {
        type string;
      }
      leaf script {
        type string;
      }
    }
  }

  grouping ncs_compliance_template_action-grouping {
    list action {
      // NCS patched for predictable order
      ordered-by user;
      tailf:cli-suppress-mode;
      key "type";
      leaf type {
        type string;
      }
      leaf pool {
        type string;
      }
      leaf domain {
        type string;
      }
    }
    leaf no-action {
      type empty;
    }
  }

  grouping ncs_compliance_template_port-grouping {
    list port {
      // NCS patched for predictable order
      ordered-by user;
      tailf:cli-suppress-mode;
      key "id";
      leaf id {
        type string;
      }
      // NCS expand uses statement
      list action {
        // NCS patched for predictable order
        ordered-by user;
        tailf:cli-suppress-mode;
        key "type";
        leaf type {
          type string;
        }
        leaf pool {
          type string;
        }
        leaf domain {
          type string;
        }
      }
      leaf no-action {
        type empty;
      }
    }
  }

  grouping ncs_compliance_template_system-jumbo-global-grouping {
    container system-jumbo-global {
      leaf enable-jumbo {
        type empty;
      }
    }
  }

  grouping ncs_compliance_template_hd-monitor-grouping {
    container hd-monitor {
      leaf enable {
        type empty;
      }
    }
  }

  grouping ncs_compliance_template_timezone-grouping {
    container timezone {
      leaf timezone {
        tailf:cli-drop-node-name;
        type string;
      }
      leaf nodst {
        type empty;
      }
    }
  }

  grouping ncs_compliance_template_clock-grouping {
    container clock {
      uses ncs_compliance_template_timezone-grouping;
      leaf nodst {
        type empty;
      }
    }
  }

  grouping ncs_compliance_template_timezone-nodst-grouping {
    container timezone-nodst {
      tailf:cli-drop-node-name;
      uses ncs_compliance_template_timezone-grouping;
      leaf nodst {
        type empty;
      }
    }
  }

  grouping ncs_compliance_template_ntp-grouping {
    container ntp {
      list server {
        // NCS patched for predictable order
        ordered-by user;
        key "name";
        leaf name {
          type string;
        }
        leaf interval {
          tailf:cli-drop-node-name;
          type string;
        }
        leaf prefer {
          type empty;
        }
      }
    }
  }

  grouping ncs_compliance_template_netflow-grouping {
    container netflow {
      container common {
        leaf max-packet-queue-time {
          type string;
        }
      }
      list monitor {
        // NCS patched for predictable order
        ordered-by user;
        key "name";
        leaf name {
          type string;
        }
        container destination {
          leaf ip {
            tailf:cli-drop-node-name;
            type string;
          }
          leaf port {
            tailf:cli-drop-node-name;
            type string;
          }
        }
        leaf flow-timeout {
          type string;
        }
        leaf protocol {
          type string;
        }
        list record {
          // NCS patched for predictable order
          ordered-by user;
          tailf:cli-suppress-mode;
          key "name";
          leaf name {
            type string;
          }
          leaf events {
            tailf:cli-drop-node-name;
            type string;
          }
        }
        container resend-template {
          leaf records {
            type string;
          }
          leaf timeout {
            type string;
          }
        }

        grouping sample-grouping {
          container sample {
            list ve {
              // NCS patched for predictable order
              ordered-by user;
              tailf:cli-suppress-mode;
              key "id";
              leaf id {
                type string;
              }
            }
          }
        }
        uses sample-grouping;

        grouping source-address-grouping {
          container source-address {
            leaf ip {
              type string;
            }
            leaf ipv6 {
              type string;
            }
          }
        }
        uses source-address-grouping;
        leaf source-ip-use-mgmt {
          type empty;
        }
        list device-context {
          // NCS patched for predictable order
          ordered-by user;
          key "id";
          leaf id {
            type string;
          }
          uses sample-grouping;
          uses source-address-grouping;
        }
      }
    }
  }

  grouping ncs_compliance_template_trunk-grouping {
    list trunk {
      // NCS patched for predictable order
      ordered-by user;
      key "id";
      leaf id {
        type string;
      }
      leaf-list ethernet {
        // NCS patched for predictable order
        ordered-by user;
        tailf:cli-range-list-syntax;
        type string;
      }
      container disable {
        leaf-list ethernet {
          // NCS patched for predictable order
          ordered-by user;
          tailf:cli-range-list-syntax;
          type string;
        }
      }
      leaf ports-threshold {
        type string;
      }
      leaf port-threshold-timer {
        type string;
      }
      leaf name {
        type string;
      }
    }
  }

  grouping ncs_compliance_template_class-list-grouping {
    list class-list {
      // NCS patched for predictable order
      ordered-by user;
      key "name";
      leaf name {
        type string;
      }
      leaf cl-type {
        tailf:cli-drop-node-name;
        type string;
      }
      choice v4v6str-choice {
        list str {
          // NCS patched for predictable order
          ordered-by user;
          tailf:cli-suppress-mode;
          key "str";
          leaf str {
            type string;
          }
          uses ncs_compliance_template_lid-grouping;
          leaf string {
            tailf:cli-drop-node-name;
            type string;
          }
        }
        list v4 {
          // NCS patched for predictable order
          ordered-by user;
          tailf:cli-drop-node-name;
          tailf:cli-suppress-mode;
          key "ip";
          leaf ip {
            type string;
          }
          uses ncs_compliance_template_lid-grouping;
        }
        list v6 {
          // NCS patched for predictable order
          ordered-by user;
          tailf:cli-drop-node-name;
          tailf:cli-suppress-mode;
          key "ip";
          leaf ip {
            type string;
          }
          uses ncs_compliance_template_lid-grouping;
        }
      }
    }
  }

  grouping ncs_compliance_template_class-list-group-grouping {
    list class-list-group {
      // NCS patched for predictable order
      ordered-by user;
      key "name";
      leaf name {
        type string;
      }
      list sequence-number {
        // NCS patched for predictable order
        ordered-by user;
        tailf:cli-suppress-mode;
        key "id";
        leaf id {
          type string;
        }
        leaf host-url {
          tailf:cli-drop-node-name;
          type string;
        }
        choice string-choice {
          leaf contains {
            type string;
          }
          leaf ends-with {
            type string;
          }
          leaf equals {
            type string;
          }
          leaf starts-with {
            type string;
          }
        }
        leaf lid {
          type string;
        }
      }
    }
  }

  grouping ncs_compliance_template_tacacs-server-grouping {
    container tacacs-server {
      list host {
        // NCS patched for predictable order
        ordered-by user;
        tailf:cli-suppress-mode;
        key "name";
        leaf name {
          type string;
        }
        container secret {
          leaf encrypted {
            type empty;
          }
          leaf secret {
            tailf:cli-drop-node-name;
            type string;
          }
        }
        leaf port {
          type string;
        }
        leaf timeout {
          type string;
        }
      }
    }
  }

  grouping ncs_compliance_template_radius-server-grouping {
    container radius-server {
      list host {
        // NCS patched for predictable order
        ordered-by user;
        tailf:cli-suppress-mode;
        key "name";
        leaf name {
          type string;
        }
        container secret {
          leaf cleartext {
            tailf:cli-drop-node-name;
            type string;
          }
          leaf secret-encrypted {
            type string;
          }
          leaf auth-port {
            type string;
          }
          leaf acct-port {
            type string;
          }
          leaf timeout {
            type string;
          }
        }
      }
    }
  }

  grouping ncs_compliance_template_authentication-grouping {
    container authentication {
      container enable {
        choice authetication-enable-choice {
          container local {
            leaf tacplus {
              type empty;
            }
          }
          container tacplus {
            presence "true";
            leaf local {
              type empty;
            }
          }
        }
      }
      leaf-list type {
        // NCS patched for predictable order
        ordered-by user;
        type string;
      }
      leaf mode {
        type string;
      }
      container console {
        leaf-list type {
          // NCS patched for predictable order
          ordered-by user;
          type string;
        }
      }
      leaf disable-local {
        type empty;
      }
      container login {
        leaf privilege-mode {
          type empty;
        }
      }
    }
  }

  grouping ncs_compliance_template_vlan-grouping {
    list vlan {
      // NCS patched for predictable order
      ordered-by user;
      key "id";
      leaf id {
        type ncs_compliance_template_vlan-index;
      }
      container untagged {
        leaf-list ethernet {
          // NCS patched for predictable order
          ordered-by user;
          tailf:cli-range-list-syntax;
          type string;
        }
        leaf trunk {
          type string;
        }
      }
      container tagged {
        leaf-list ethernet {
          // NCS patched for predictable order
          ordered-by user;
          tailf:cli-range-list-syntax;
          type string;
        }
        leaf trunk {
          type string;
        }
      }
      container router-interface {
        leaf ve {
          type ncs_compliance_template_vlan-index;
        }
      }
      leaf name {
        type string;
      }
    }
  }

  grouping ncs_compliance_template_ipv6-route-grouping {
    container route {
      list route-no-if {
        // NCS patched for predictable order
        ordered-by user;
        tailf:cli-drop-node-name;
        tailf:cli-suppress-mode;
        key "ip forwarding-router";
        leaf ip {
          type string;
        }
        leaf forwarding-router {
          tailf:cli-drop-node-name;
          type string;
        }
        leaf distance {
          tailf:cli-drop-node-name;
          type string;
        }
      }
      list route-if {
        // NCS patched for predictable order
        ordered-by user;
        tailf:cli-drop-node-name;
        tailf:cli-suppress-mode;
        key "ip forwarding-router interface-type interface-nr";
        leaf ip {
          type string;
        }
        leaf forwarding-router {
          tailf:cli-drop-node-name;
          type string;
        }
        leaf interface-type {
          type string;
        }
        leaf interface-nr {
          type string;
        }
        leaf distance {
          tailf:cli-drop-node-name;
          type string;
        }
      }
    }
  }

  grouping ncs_compliance_template_ipv6-grouping {
    container ipv6 {
      uses ncs_compliance_template_ipv6-route-grouping;
      container nat {
        list pool {
          // NCS patched for predictable order
          ordered-by user;
          tailf:cli-suppress-mode;
          key "name";
          leaf name {
            type string;
          }
          leaf ipstart {
            // NCS drop mandatory statement
            tailf:cli-drop-node-name;
            type string;
          }
          leaf ipend {
            // NCS drop mandatory statement
            tailf:cli-drop-node-name;
            type string;
          }
          leaf netmask {
            // NCS drop mandatory statement
            type string;
          }
        }
      }
      list access-list {
        // NCS patched for predictable order
        ordered-by user;
        key "id";
        leaf id {
          type string;
        }
        list rules {
          // NCS patched for predictable order
          ordered-by user;
          tailf:cli-suppress-mode;
          tailf:cli-drop-node-name;
          key "acc-type txt";
          leaf acc-type {
            type string;
          }
          leaf txt {
            type string;
          }
        }
        list remark {
          // NCS patched for predictable order
          ordered-by user;
          tailf:cli-suppress-mode;
          key "name";
          leaf name {
            type string;
          }
        }
      }
      list prefix-list {
        // NCS patched for predictable order
        ordered-by user;
        tailf:cli-suppress-mode;
        key "name seq";
        leaf name {
          type string;
        }
        leaf seq {
          type string;
        }
        choice permit-deny {
          leaf permit {
            type string;
          }
          leaf deny {
            type string;
          }
        }
      }
    }
  }

  grouping ncs_compliance_template_nat64-grouping {
    container nat64 {
      uses ncs_compliance_template_algs;
      leaf user-quota-prefix-length {
        type string;
      }
      container inside {
        container source {
          leaf class-list {
            type string;
          }
        }
      }
      leaf prefix {
        type string;
      }
    }
  }

  grouping ncs_compliance_template_lsn-lid-grouping {
    list lsn-lid {
      // NCS patched for predictable order
      ordered-by user;
      key "lsn-lid-id";
      leaf lsn-lid-id {
        type string;
      }
      leaf name {
        type string;
      }
      leaf source-nat-pool {
        type string;
      }
      container user-quota {
        leaf session {
          type string;
        }
      }
      leaf respond-to-user-mac {
        type empty;
      }
    }
  }

  grouping ncs_compliance_template_ha-grouping {
    container ha {
      leaf arp-retry {
        type string;
      }
      container check {
        list gateway {
          // NCS patched for predictable order
          ordered-by user;
          key "ip";
          tailf:cli-suppress-mode;
          leaf ip {
            type string;
          }
        }
        list route {
          // NCS patched for predictable order
          ordered-by user;
          key "ip mask gateway distance protocol priority-cost";
          unique "ip mask gateway distance protocol";
          tailf:cli-suppress-mode;
          leaf ip {
            type string;
          }
          leaf mask {
            type ncs_compliance_template_ipv4-mask;
          }
          leaf gateway {
            type string;
          }
          leaf distance {
            type string;
          }
          leaf protocol {
            type string;
          }
          leaf priority-cost {
            type string;
          }
        }
        container vlan {
          leaf vlan-id {
            tailf:cli-drop-node-name;
            type ncs_compliance_template_vlan-index;
          }
          leaf timeout {
            // NCS drop must statement
            type string;
          }
        }
      }
      container conn-mirror {
        leaf ip {
          type string;
        }
      }
      container force-self-standby {
        list HA-group-id {
          // NCS patched for predictable order
          ordered-by user;
          key "id persistent";
          tailf:cli-suppress-mode;
          leaf id {
            type string;
          }
          leaf persistent {
            type string;
          }
        }
      }
      leaf forward-l4-packet-on-standby {
        type empty;
      }
      container id {
        leaf id {
          tailf:cli-drop-node-name;
          type string;
        }
        leaf set-id {
          type string;
        }
      }
      list group {
        // NCS patched for predictable order
        ordered-by user;
        tailf:cli-suppress-mode;
        key "id";
        leaf id {
          type string;
        }
        leaf priority {
          // NCS drop must statement
          type string;
        }
      }
      container inline-mode {
        presence "true";
        leaf preferred-port {
          type string;
        }
      }
      container interface {
        list ethernet {
          // NCS patched for predictable order
          ordered-by user;
          tailf:cli-suppress-mode;
          key "id";
          leaf id {
            type ncs_compliance_template_ethernet-index;
          }
          leaf type {
            tailf:cli-drop-node-name;
            type string;
          }
          choice xx {
            leaf no-heartbeat {
              type empty;
            }
            leaf vlan {
              type string;
            }
          }
        }
      }
      leaf preemption-enable {
        type empty;
      }
      leaf timeout-retry-count {
        type string;
      }
    }
  }

  grouping ncs_compliance_template_floating-ip-grouping {
    container floating-ip {
      list ipv4 {
        // NCS patched for predictable order
        ordered-by user;
        tailf:cli-suppress-mode;
        tailf:cli-drop-node-name;
        key "ip ha-group";
        leaf ip {
          type string;
        }
        leaf ha-group {
          type string;
        }
      }
      list ipv6 {
        // NCS patched for predictable order
        ordered-by user;
        tailf:cli-suppress-mode;
        tailf:cli-drop-node-name;
        key "ip ha-group";
        leaf ip {
          type string;
        }
        leaf ha-group {
          type string;
        }
        leaf anycast {
          type empty;
        }
        choice ipv6-interface {
          leaf ethernet {
            // NCS drop must statement
            type ncs_compliance_template_ethernet-index;
          }
          leaf trunk {
            type string;
          }
          leaf ve {
            // NCS drop must statement
            type ncs_compliance_template_vlan-index;
          }
        }
      }
    }
  }

  grouping ncs_compliance_template_glid-grouping {
    list glid {
      // NCS patched for predictable order
      ordered-by user;
      key "limit-id";
      leaf limit-id {
        type string;
      }
      container dns {
        leaf cache-leaf {
          tailf:cli-drop-node-name;
          type string;
        }
        container ttl {
          leaf ttl-value {
            tailf:cli-drop-node-name;
            type string;
          }
          leaf honor-server-response-ttl {
            type empty;
          }
        }
      }
      container over-limit-action {
        leaf over-limit-action-choice {
          tailf:cli-drop-node-name;
          type string;
        }
        leaf lockout {
          type string;
        }
        leaf lockout-val {
          tailf:cli-drop-node-name;
          type string;
        }
        leaf log {
          type empty;
        }
        leaf log-val {
          tailf:cli-drop-node-name;
          type string;
        }
      }
      leaf conn-limit {
        type string;
      }
      container conn-rate-limit {
        leaf limit {
          tailf:cli-drop-node-name;
          type string;
        }
        leaf per {
          // NCS drop must statement
          type string;
        }
      }
      leaf request-limit {
        type string;
      }
      container request-rate-limit {
        leaf limit {
          tailf:cli-drop-node-name;
          type string;
        }
        leaf per {
          // NCS drop must statement
          type string;
        }
      }
      leaf use-nat-pool {
        type string;
      }
    }
  }

  grouping ncs_compliance_template_gslb-zone-service-grouping {
    leaf policy {
      type string;
    }
    list dns-a-record {
      // NCS patched for predictable order
      ordered-by user;
      tailf:cli-suppress-mode;
      key "name";
      leaf name {
        type string;
      }
      leaf as-backup {
        type empty;
      }
      leaf port-service-name {
        tailf:cli-drop-node-name;
        type string;
      }
      leaf weight {
        type string;
      }
      container static {
        presence "true";
        leaf admin-ip {
          type string;
        }
      }
    }
  }

  grouping ncs_compliance_template_logging-grouping {
    container logging {
      container auditlog {
        leaf host {
          type string;
        }
        leaf facility {
          type string;
        }
      }
      container buffered {
        presence "true";
        leaf size {
          tailf:cli-drop-node-name;
          type string;
        }
        leaf severity {
          tailf:cli-drop-node-name;
          type string;
        }
      }
      leaf console {
        type string;
      }
      container email {
        container buffer {
          choice buffer-choice {
            leaf number {
              type string;
            }
            leaf time {
              type string;
            }
          }
        }
        leaf severity {
          tailf:cli-drop-node-name;
          type string;
        }
      }
      leaf-list email-address {
        // NCS patched for predictable order
        ordered-by user;
        type string;
      }
      leaf export {
        type empty;
      }
      leaf facility {
        type string;
      }
      leaf syslog {
        type string;
      }
      leaf trap {
        type string;
      }
      choice host-choice {
        container host-list {
          tailf:cli-drop-node-name;
          list host {
            // NCS patched for predictable order
            ordered-by user;
            tailf:cli-suppress-mode;
            key "hosts";
            leaf hosts {
              type string;
            }
            choice use-mgmt-port-choice {
              container port {
                leaf number {
                  tailf:cli-drop-node-name;
                  type string;
                }
                leaf tcp {
                  type empty;
                }
              }
              container use-mgmt-port {
                presence "true";
                leaf port {
                  type string;
                }
                leaf tcp {
                  type empty;
                }
              }
            }
          }
        }
        container host {
          leaf-list hosts {
            // NCS patched for predictable order
            ordered-by user;
            tailf:cli-drop-node-name;
            type string;
          }
          leaf port {
            type string;
          }
        }
        container host-alt {
          tailf:cli-drop-node-name;
          container host {
            leaf partition {
              type string;
            }
          }
        }
      }
      leaf monitor {
        type string;
      }
    }
  }

  grouping ncs_compliance_template_snmp-server-grouping {
    container snmp-server {
      container enable {
        leaf enabled {
          tailf:cli-drop-node-name;
          type empty;
        }
        leaf service {
          type empty;
        }
        container traps {
          leaf enabled {
            tailf:cli-drop-node-name;
            type empty;
          }
          leaf all {
            type empty;
          }
          container routing {
            container ospf {
              choice routing-choice {
                leaf-list ospf-traps {
                  // NCS patched for predictable order
                  ordered-by user;
                  tailf:cli-drop-node-name;
                  type string;
                }
                leaf all {
                  type empty;
                }
              }
            }
            container bgp {
              leaf bgpBackwardTransNotification {
                type empty;
              }
              leaf bgpEstablishedNotification {
                type empty;
              }
            }
          }
          container lsn {
            leaf all {
              type empty;
            }
          }
          container snmp {
            leaf enabled {
              tailf:cli-drop-node-name;
              type empty;
            }
            leaf all {
              type empty;
            }
            leaf linkdown {
              type empty;
            }
            leaf linkup {
              type empty;
            }
          }
          container ha {
            leaf enabled {
              tailf:cli-drop-node-name;
              type empty;
            }
            leaf active {
              type empty;
            }
            leaf active-active {
              type empty;
            }
            leaf standby {
              type empty;
            }
            leaf vrrp {
              type empty;
            }
          }
          container network {
            leaf enabled {
              tailf:cli-drop-node-name;
              type empty;
            }
            leaf trunk-port-threshold {
              type empty;
            }
          }
          container slb {
            leaf enabled {
              tailf:cli-drop-node-name;
              type empty;
            }
            leaf all {
              type empty;
            }
            leaf application-buffer-limit {
              type empty;
            }
            leaf server-conn-limit {
              type empty;
            }
            leaf server-conn-resume {
              type empty;
            }
            leaf server-down {
              type empty;
            }
            leaf server-up {
              type empty;
            }
            leaf service-conn-limit {
              type empty;
            }
            leaf service-conn-resume {
              type empty;
            }
            leaf service-down {
              type empty;
            }
            leaf service-up {
              type empty;
            }
            leaf vip-connlimit {
              type empty;
            }
            leaf vip-connratelimit {
              type empty;
            }
            leaf vip-port-connlimit {
              type empty;
            }
            leaf vip-port-connratelimit {
              type empty;
            }
            leaf vip-port-down {
              type empty;
            }
            leaf vip-port-up {
              type empty;
            }
          }
          container system {
            leaf enabled {
              tailf:cli-drop-node-name;
              type empty;
            }
            leaf all {
              type empty;
            }
            leaf control-cpu-high {
              type empty;
            }
            leaf data-cpu-high {
              type empty;
            }
            leaf fan {
              type empty;
            }
            leaf high-disk-use {
              type empty;
            }
            leaf high-memory-use {
              type empty;
            }
            leaf high-temp {
              type empty;
            }
            leaf packet-drop {
              type empty;
            }
            leaf power {
              type empty;
            }
            leaf pri-disk {
              type empty;
            }
            leaf restart {
              type empty;
            }
            leaf sec-disk {
              type empty;
            }
            leaf shutdown {
              type empty;
            }
            leaf start {
              type empty;
            }
          }
          container vrrp-a {
            leaf active {
              type empty;
            }
            leaf all {
              type empty;
            }
            leaf standby {
              type empty;
            }
          }
        }
      }
      leaf location {
        type string;
      }
      list user {
        // NCS patched for predictable order
        ordered-by user;
        tailf:cli-suppress-mode;
        key "name group type";
        leaf name {
          type string;
        }
        leaf group {
          type string;
        }
        leaf type {
          type string;
        }
        container auth {
          leaf mac {
            tailf:cli-drop-node-name;
            type string;
          }
          leaf cleartext {
            tailf:cli-drop-node-name;
            type string;
          }
        }
      }
      list view {
        // NCS patched for predictable order
        ordered-by user;
        key "name miboid";
        tailf:cli-suppress-mode;
        leaf name {
          type string;
        }
        leaf miboid {
          type string;
        }
        leaf included-excluded {
          tailf:cli-drop-node-name;
          type string;
        }
      }
      list group {
        // NCS patched for predictable order
        ordered-by user;
        tailf:cli-suppress-mode;
        key "name";
        leaf name {
          type string;
        }
        container v3 {
          container auth {
            leaf read {
              type string;
            }
          }
        }
      }
      container SNMPv1-v2c {
        list user {
          // NCS patched for predictable order
          ordered-by user;
          key "name";
          leaf name {
            type string;
          }
          container community {
            leaf read {
              type string;
            }
          }
          uses ncs_compliance_template_snmp-remote-grouping;
        }
      }
      container SNMPv3 {
        list user {
          // NCS patched for predictable order
          ordered-by user;
          tailf:cli-suppress-mode;
          key "name";
          leaf name {
            type string;
          }
          leaf group {
            type string;
          }
          leaf v3 {
            type empty;
          }
          choice smnp-server-v3-user-auth-choice {
            container auth {
              leaf hmac {
                tailf:cli-drop-node-name;
                type string;
              }
              leaf password {
                tailf:cli-drop-node-name;
                type string;
              }
              container priv {
                leaf algo {
                  tailf:cli-drop-node-name;
                  type string;
                }
                leaf passphrase {
                  tailf:cli-drop-node-name;
                  type string;
                }
              }
            }
            leaf noauth {
              type empty;
            }
          }
        }
      }
      container community-mode {
        tailf:cli-drop-node-name;
        list community {
          // NCS patched for predictable order
          ordered-by user;
          key "read";
          leaf read {
            type string;
          }
          uses ncs_compliance_template_snmp-remote-grouping;
        }
      }
      list community {
        // NCS patched for predictable order
        ordered-by user;
        key "read remote";
        tailf:cli-suppress-mode;
        leaf read {
          type string;
        }
        leaf remote {
          type string;
        }
        leaf oid {
          type string;
        }
        leaf mask {
          tailf:cli-drop-node-name;
          type string;
        }
      }
      leaf contact {
        type string;
      }
      list host {
        // NCS patched for predictable order
        ordered-by user;
        tailf:cli-suppress-mode;
        key "ip version";
        leaf ip {
          type string;
        }
        leaf version {
          type string;
        }
        leaf community-string {
          tailf:cli-drop-node-name;
          // NCS drop mandatory statement
          type string;
        }
        leaf udp-port {
          type string;
        }
      }
    }
  }

  grouping ncs_compliance_template_audit-grouping {
    container audit {
      container enable {
        leaf privilege {
          type empty;
        }
      }
      leaf size {
        type string;
      }
    }
  }

  grouping ncs_compliance_template_harmony-controller-grouping {
    container harmony-controller {
      leaf config-replace {
        type string;
      }
      container profile {
        presence "true";
        container host {
          leaf host-id {
            tailf:cli-drop-node-name;
            type string;
          }
          leaf use-mgmt-port {
            type empty;
          }
          leaf port {
            type string;
          }
        }
        leaf provider {
          type string;
        }
        leaf user-name {
          type string;
        }
        leaf cluster-name {
          type string;
        }
        leaf cluster-id {
          type string;
        }
        leaf password {
          type string;
        }
        leaf region {
          type string;
        }
        leaf availability-zone {
          type string;
        }
        leaf thunder-mgmt-ip {
          type string;
        }
        leaf reg-dereg {
          tailf:cli-drop-node-name;
          type string;
        }
        list device-context {
          // NCS patched for predictable order
          ordered-by user;
          key "id";
          leaf id {
            type string;
          }
          leaf thunder-mgmt-ip {
            type string;
          }
        }
      }
    }
  }

  grouping ncs_compliance_template_terminal-grouping {
    container terminal {
      leaf auto-size {
        type empty;
      }
      leaf editing {
        type empty;
      }
      container prompt {
        leaf hostname {
          type empty;
        }
        leaf ha-status {
          type empty;
        }
      }
      container history {
        leaf size {
          type string;
        }
      }
      leaf idle-timeout {
        type string;
      }
      leaf length {
        type string;
      }
      leaf no-ha-prompt {
        type empty;
      }
      leaf width {
        type string;
      }
    }
  }

  grouping ncs_compliance_template_web-service-grouping {
    container web-service {
      leaf auto-redir {
        type string;
      }
      container auto-redirt {
        leaf disable {
          type empty;
        }
      }
      container axapi-timeout-policy {
        leaf idle {
          type string;
        }
      }
      container timeout-policy {
        leaf idle {
          type string;
        }
      }
      leaf gui-session-limit {
        type string;
      }
      container gui-timeout-policy {
        leaf idle {
          type string;
        }
      }
      leaf login-message {
        type string;
      }
      leaf pre-login-message {
        type string;
      }
    }
  }

  grouping ncs_compliance_template_multi-config-grouping {
    container multi-config {
      leaf enable {
        type empty;
      }
    }
  }

  grouping ncs_compliance_template_banner-grouping {
    container banner {
      container login {
        choice text-multi {
          leaf text {
            tailf:cli-drop-node-name;
            type string;
          }
          leaf multi-line {
            type string;
          }
        }
      }
      container exec {
        choice text-multi {
          leaf text {
            tailf:cli-drop-node-name;
            type string;
          }
          leaf multi-line {
            type string;
          }
        }
      }
    }
  }

  grouping ncs_compliance_template_preferred-session-sync-port-grouping {
    container preferred-session-sync-port {
      list trunk {
        // NCS patched for predictable order
        ordered-by user;
        tailf:cli-suppress-mode;
        key "id";
        leaf id {
          type string;
        }
        leaf vlan {
          type string;
        }
      }
      list ethernet {
        // NCS patched for predictable order
        ordered-by user;
        tailf:cli-suppress-mode;
        key "id";
        leaf id {
          type ncs_compliance_template_ethernet-index;
        }
        leaf vlan {
          type string;
        }
      }
    }
  }

  grouping ncs_compliance_template_vrrp-a-grouping {
    container vrrp-a {

      grouping vrrp-a-common-grouping {
        leaf device-id {
          // NCS drop tailf-common:cli-diff-create-before statement
          // NCS drop tailf-common:cli-diff-create-before statement
          type string;
        }
        leaf disable-default-vrid {
          type empty;
        }
        leaf set-id {
          // NCS drop tailf-common:cli-diff-create-before statement
          // NCS drop tailf-common:cli-diff-create-before statement
          type string;
        }
        leaf hello-interval {
          type string;
        }
        leaf preemption-delay {
          type string;
        }
        leaf track-event-delay {
          type string;
        }
        leaf restart-time {
          type string;
        }
        leaf hostid-append-to-vrid {
          type string;
        }
        leaf enable {
          tailf:cli-drop-node-name;
          type string;
        }
      }
      uses vrrp-a-common-grouping;
      container common {
        presence "common-presence";
        uses vrrp-a-common-grouping;
      }
      list vrid {
        // NCS patched for predictable order
        ordered-by user;
        key "id";
        leaf id {
          type string;
        }

        grouping vrrp-a-vrid-grouping {
          list floating-ip {
            // NCS patched for predictable order
            ordered-by user;
            tailf:cli-suppress-mode;
            key "floating-ip-address";
            leaf floating-ip-address {
              tailf:cli-drop-node-name;
              type string;
            }
          }
          leaf priority {
            type string;
          }
          container preempt-mode {
            choice preempt-choice {
              leaf disable {
                type empty;
              }
              leaf threshold {
                type string;
              }
            }
          }
          container blade-parameters {
            leaf priority {
              type string;
            }
            container tracking-options {
              list gateway {
                // NCS patched for predictable order
                ordered-by user;
                tailf:cli-suppress-mode;
                key "address";
                leaf address {
                  type string;
                }
                uses ncs_compliance_template_priority-cost;
              }
              container interface {
                list ethernet {
                  // NCS patched for predictable order
                  ordered-by user;
                  tailf:cli-suppress-mode;
                  key "id";
                  leaf id {
                    type ncs_compliance_template_ethernet-index;
                  }
                  leaf priority-cost {
                    // NCS drop mandatory statement
                    type string;
                  }
                }
              }
              list route {
                // NCS patched for predictable order
                ordered-by user;
                tailf:cli-suppress-mode;
                key "ip mask";
                leaf ip {
                  type string;
                }
                leaf mask {
                  type ncs_compliance_template_ipv4-mask;
                }
                uses ncs_compliance_template_priority-cost;
                leaf distance {
                  type string;
                }
                leaf gateway {
                  type string;
                }
                leaf protocol {
                  type string;
                }
              }
              list trunk {
                // NCS patched for predictable order
                ordered-by user;
                tailf:cli-suppress-mode;
                key "id";
                leaf id {
                  type string;
                }
                uses ncs_compliance_template_priority-cost;
                leaf per-port-pri {
                  type string;
                }
              }
              list vlan {
                // NCS patched for predictable order
                ordered-by user;
                tailf:cli-suppress-mode;
                key "id";
                leaf id {
                  type ncs_compliance_template_vlan-index;
                }
                leaf timeout {
                  type string;
                }
                uses ncs_compliance_template_priority-cost;
              }
            }
          }
        }
        // NCS expand uses statement
        list floating-ip {
          // NCS patched for predictable order
          ordered-by user;
          tailf:cli-suppress-mode;
          key "floating-ip-address";
          leaf floating-ip-address {
            tailf:cli-drop-node-name;
            type string;
          }
        }
        leaf priority {
          type string;
        }
        container preempt-mode {
          choice preempt-choice {
            leaf disable {
              type empty;
            }
            leaf threshold {
              type string;
            }
          }
        }
        container blade-parameters {
          leaf priority {
            type string;
          }
          container tracking-options {
            list gateway {
              // NCS patched for predictable order
              ordered-by user;
              tailf:cli-suppress-mode;
              key "address";
              leaf address {
                type string;
              }
              // NCS expand uses statement
              leaf priority-cost {
                // NCS drop mandatory statement
                type string;
              }
            }
            container interface {
              list ethernet {
                // NCS patched for predictable order
                ordered-by user;
                tailf:cli-suppress-mode;
                key "id";
                leaf id {
                  type ncs_compliance_template_ethernet-index;
                }
                leaf priority-cost {
                  // NCS drop mandatory statement
                  type string;
                }
              }
            }
            list route {
              // NCS patched for predictable order
              ordered-by user;
              tailf:cli-suppress-mode;
              key "ip mask";
              leaf ip {
                type string;
              }
              leaf mask {
                type ncs_compliance_template_ipv4-mask;
              }
              // NCS expand uses statement
              leaf priority-cost {
                // NCS drop mandatory statement
                type string;
              }
              leaf distance {
                type string;
              }
              leaf gateway {
                type string;
              }
              leaf protocol {
                type string;
              }
            }
            list trunk {
              // NCS patched for predictable order
              ordered-by user;
              tailf:cli-suppress-mode;
              key "id";
              leaf id {
                type string;
              }
              // NCS expand uses statement
              leaf priority-cost {
                // NCS drop mandatory statement
                type string;
              }
              leaf per-port-pri {
                type string;
              }
            }
            list vlan {
              // NCS patched for predictable order
              ordered-by user;
              tailf:cli-suppress-mode;
              key "id";
              leaf id {
                type ncs_compliance_template_vlan-index;
              }
              leaf timeout {
                type string;
              }
              // NCS expand uses statement
              leaf priority-cost {
                // NCS drop mandatory statement
                type string;
              }
            }
          }
        }
        list device-context {
          // NCS patched for predictable order
          ordered-by user;
          key "id";
          leaf id {
            type string;
          }
          // NCS expand uses statement
          list floating-ip {
            // NCS patched for predictable order
            ordered-by user;
            tailf:cli-suppress-mode;
            key "floating-ip-address";
            leaf floating-ip-address {
              tailf:cli-drop-node-name;
              type string;
            }
          }
          leaf priority {
            type string;
          }
          container preempt-mode {
            choice preempt-choice {
              leaf disable {
                type empty;
              }
              leaf threshold {
                type string;
              }
            }
          }
          container blade-parameters {
            leaf priority {
              type string;
            }
            container tracking-options {
              list gateway {
                // NCS patched for predictable order
                ordered-by user;
                tailf:cli-suppress-mode;
                key "address";
                leaf address {
                  type string;
                }
                // NCS expand uses statement
                leaf priority-cost {
                  // NCS drop mandatory statement
                  type string;
                }
              }
              container interface {
                list ethernet {
                  // NCS patched for predictable order
                  ordered-by user;
                  tailf:cli-suppress-mode;
                  key "id";
                  leaf id {
                    type ncs_compliance_template_ethernet-index;
                  }
                  leaf priority-cost {
                    // NCS drop mandatory statement
                    type string;
                  }
                }
              }
              list route {
                // NCS patched for predictable order
                ordered-by user;
                tailf:cli-suppress-mode;
                key "ip mask";
                leaf ip {
                  type string;
                }
                leaf mask {
                  type ncs_compliance_template_ipv4-mask;
                }
                // NCS expand uses statement
                leaf priority-cost {
                  // NCS drop mandatory statement
                  type string;
                }
                leaf distance {
                  type string;
                }
                leaf gateway {
                  type string;
                }
                leaf protocol {
                  type string;
                }
              }
              list trunk {
                // NCS patched for predictable order
                ordered-by user;
                tailf:cli-suppress-mode;
                key "id";
                leaf id {
                  type string;
                }
                // NCS expand uses statement
                leaf priority-cost {
                  // NCS drop mandatory statement
                  type string;
                }
                leaf per-port-pri {
                  type string;
                }
              }
              list vlan {
                // NCS patched for predictable order
                ordered-by user;
                tailf:cli-suppress-mode;
                key "id";
                leaf id {
                  type ncs_compliance_template_vlan-index;
                }
                leaf timeout {
                  type string;
                }
                // NCS expand uses statement
                leaf priority-cost {
                  // NCS drop mandatory statement
                  type string;
                }
              }
            }
          }
        }
      }
      container interface {
        list ethernet {
          // NCS patched for predictable order
          ordered-by user;
          tailf:cli-suppress-mode;
          key "id";
          leaf id {
            type ncs_compliance_template_ethernet-index;
          }
          choice vrrp-a-ethernet-choice {
            leaf both {
              type empty;
            }
            leaf no-heartbeat {
              type empty;
            }
            container router-interface {
              choice vrrp-a-r-i-choice {
                leaf no-heartbeat {
                  type empty;
                }
                leaf vlan {
                  type string;
                }
              }
            }
            container server-interface {
              presence "true";
              choice vrrp-a-s-i-choice {
                leaf no-heartbeat {
                  type empty;
                }
                leaf vlan {
                  type string;
                }
              }
            }
            leaf vlan {
              type string;
            }
          }
        }
        list trunk {
          // NCS patched for predictable order
          ordered-by user;
          tailf:cli-suppress-mode;
          key "id";
          leaf id {
            type ncs_compliance_template_ethernet-index;
          }
          choice vrrp-a-trunk-choice {
            leaf both {
              type empty;
            }
            leaf no-heartbeat {
              type empty;
            }
            container router-interface {
              choice vrrp-a-r-i-choice {
                leaf no-heartbeat {
                  type empty;
                }
                leaf vlan {
                  type string;
                }
              }
            }
            container server-interface {
              presence "true";
              choice vrrp-a-s-i-choice {
                leaf no-heartbeat {
                  type empty;
                }
                leaf vlan {
                  type string;
                }
              }
            }
            leaf vlan {
              type string;
            }
          }
        }
      }
      // NCS expand uses statement
      container preferred-session-sync-port {
        list trunk {
          // NCS patched for predictable order
          ordered-by user;
          tailf:cli-suppress-mode;
          key "id";
          leaf id {
            type string;
          }
          leaf vlan {
            type string;
          }
        }
        list ethernet {
          // NCS patched for predictable order
          ordered-by user;
          tailf:cli-suppress-mode;
          key "id";
          leaf id {
            type ncs_compliance_template_ethernet-index;
          }
          leaf vlan {
            type string;
          }
        }
      }
    }
  }

  grouping ncs_compliance_template_router-grouping {
    container router {
      list bgp {
        // NCS patched for predictable order
        ordered-by user;
        key "as";
        leaf as {
          type string;
        }
        leaf maximum-paths {
          type string;
        }
        list network {
          // NCS patched for predictable order
          ordered-by user;
          tailf:cli-suppress-mode;
          key "address";
          leaf address {
            type string;
          }
        }

        grouping neighbor-grouping {
          list neighbor {
            // NCS patched for predictable order
            ordered-by user;
            tailf:cli-suppress-mode;
            key "ip";
            leaf ip {
              type string;
            }
            leaf activate {
              type string;
            }
            leaf description {
              type string;
            }
            list distribute-list {
              // NCS patched for predictable order
              ordered-by user;
              key "direction";
              tailf:cli-suppress-mode;
              leaf name {
                tailf:cli-drop-node-name;
                type string;
              }
              leaf direction {
                type string;
              }
            }
            container fall-over {
              leaf bfd {
                type empty;
              }
              leaf multihop {
                type empty;
              }
            }
            leaf maximum-prefix {
              type string;
            }
            leaf next-hop-self {
              type empty;
            }
            leaf password {
              type string;
            }
            container peer-group {
              presence "true";
              leaf name {
                tailf:cli-drop-node-name;
                type string;
              }
            }
            list prefix-list {
              // NCS patched for predictable order
              ordered-by user;
              tailf:cli-suppress-mode;
              key "direction";
              leaf direction {
                type string;
              }
              leaf name {
                tailf:cli-drop-node-name;
                type string;
              }
            }
            leaf remote-as {
              type string;
            }
            leaf remove-private-as {
              type empty;
            }
            list route-map {
              // NCS patched for predictable order
              ordered-by user;
              tailf:cli-suppress-mode;
              key "in-out";
              leaf in-out {
                type string;
              }
              leaf name {
                tailf:cli-drop-node-name;
                type string;
              }
            }
            container update-source {
              leaf address {
                tailf:cli-drop-node-name;
                type string;
              }
              leaf ve {
                type string;
              }
            }
            leaf soft-reconfiguration {
              type string;
            }
            leaf shutdown {
              type string;
            }
          }
        }
        uses neighbor-grouping;

        grouping redistribute-grouping {
          container redistribute {
            container connected {
              presence "true";
              leaf route-map {
                type string;
              }
            }
            container static {
              presence "true";
              leaf route-map {
                type string;
              }
            }
            container ip-nat {
              presence "true";
              leaf route-map {
                type string;
              }
            }
            container vip {
              container only-flagged {
                presence "true";
              }
            }
          }
        }
        uses redistribute-grouping;
        container address-family {
          container ipv6 {
            leaf maximum-paths {
              type string;
            }
            uses neighbor-grouping;
            uses redistribute-grouping;
          }
        }
        container bgp {
          leaf log-neighbor-changes {
            type empty;
          }
          container bestpath {
            leaf as-path {
              type string;
            }
          }
        }
      }
    }
  }

  grouping ncs_compliance_template_bfd-grouping {
    container bfd {
      leaf echo {
        type empty;
      }
      leaf enable {
        type empty;
      }
      container interval {
        leaf start {
          tailf:cli-drop-node-name;
          type string;
        }
        leaf min-rx {
          type string;
        }
        leaf multiplier {
          type string;
        }
      }
    }
  }

  grouping ncs_compliance_template_lldp-grouping {
    container lldp {
      leaf system-name {
        type string;
      }
      leaf system-description {
        type string;
      }
      leaf-list enable {
        // NCS patched for predictable order
        ordered-by user;
        type string;
      }
      container management-address {
        list ipv4 {
          // NCS patched for predictable order
          ordered-by user;
          tailf:cli-suppress-mode;
          key "address";
          leaf address {
            type string;
          }
        }
        list ipv6 {
          // NCS patched for predictable order
          ordered-by user;
          tailf:cli-suppress-mode;
          key "address";
          leaf address {
            type string;
          }
        }
      }
      container notification {
        leaf interval {
          type string;
        }
      }
    }
  }

  grouping ncs_compliance_template_route-map-grouping {
    list route-map {
      // NCS patched for predictable order
      ordered-by user;
      tailf:cli-suppress-mode;
      key "name";
      leaf name {
        type string;
      }

      grouping permit-deny-grouping {
        leaf id {
          type string;
        }

        grouping match-set-grouping {
          container ip {
            container address {
              leaf address {
                tailf:cli-drop-node-name;
                type string;
              }
              leaf prefix-list {
                type string;
              }
            }
            leaf next-hop {
              type string;
            }
          }
          container ipv6 {
            container address {
              leaf address {
                tailf:cli-drop-node-name;
                type string;
              }
              leaf prefix-list {
                type string;
              }
            }
            leaf next-hop {
              type string;
            }
          }
          leaf-list community {
            // NCS patched for predictable order
            ordered-by user;
            type string;
          }
        }
        container match {
          uses match-set-grouping;
        }
        container set {
          uses match-set-grouping;
        }
      }
      list permit {
        // NCS patched for predictable order
        ordered-by user;
        key "id";
        uses permit-deny-grouping;
      }
      list deny {
        // NCS patched for predictable order
        ordered-by user;
        key "id";
        uses permit-deny-grouping;
      }
    }
  }

  grouping ncs_compliance_template_device-context-grouping {
    list device-context {
      // NCS patched for predictable order
      ordered-by user;
      key "id";
      leaf id {
        type string;
      }
      uses ncs_compliance_template_aflex-grouping;
      uses ncs_compliance_template_hostname-grouping;
      // NCS expand uses statement
      container interface {

        grouping lldp-interface-grouping {
          container lldp {
            container enable {
              leaf rx {
                type empty;
              }
              leaf tx {
                type empty;
              }
            }
            leaf notification {
              type string;
            }
            leaf tx-dot1-tlvs {
              type string;
            }
          }
        }
        container management {
          container bcast-rate-limit {
            presence "present";
            leaf rate {
              type string;
            }
          }
          container ip {
            // NCS expand uses statement
            list address {
              // NCS patched for predictable order
              ordered-by user;
              tailf:cli-suppress-mode;
              key "address mask";
              leaf address {
                type string;
              }
              leaf mask {
                type string;
              }
            }
            leaf control-apps-use-mgmt-port {
              type empty;
            }
            leaf default-gateway {
              type string;
            }
          }
          container ipv6 {
            list address {
              // NCS patched for predictable order
              ordered-by user;
              key "ip";
              tailf:cli-suppress-mode;
              leaf ip {
                tailf:cli-drop-node-name;
                type ncs_compliance_template_ipv6-prefix;
              }
              leaf link-local {
                type empty;
              }
            }
            leaf default-gateway {
              type string;
            }
          }
          // NCS expand uses statement
          container lldp {
            container enable {
              leaf rx {
                type empty;
              }
              leaf tx {
                type empty;
              }
            }
            leaf notification {
              type string;
            }
            leaf tx-dot1-tlvs {
              type string;
            }
          }
          leaf flow-control {
            type empty;
          }
          container access-list {
            leaf id {
              tailf:cli-drop-node-name;
              type string;
            }
            leaf in {
              // NCS drop must statement
              type empty;
            }
          }
          leaf enabled-disabled {
            tailf:cli-drop-node-name;
            type string;
          }
          leaf duplexity {
            type string;
          }
          leaf mtu {
            type string;
          }
          leaf speed {
            type string;
          }
        }
        list ethernet {
          // NCS patched for predictable order
          ordered-by user;
          key "nr";
          leaf nr {
            type ncs_compliance_template_ethernet-index;
          }
          leaf name {
            type string;
          }
          container ip {
            // NCS expand uses statement
            list address {
              // NCS patched for predictable order
              ordered-by user;
              tailf:cli-suppress-mode;
              key "address mask";
              leaf address {
                type string;
              }
              leaf mask {
                type string;
              }
            }
            leaf cache-spoofing-port {
              type empty;
            }
            leaf helper-address {
              type string;
            }
            container nat {
              leaf inside {
                type empty;
              }
              leaf outside {
                type empty;
              }
            }
            container ospf;
            container router {
              container isis {
                presence "true";
                leaf cmds {
                  tailf:cli-drop-node-name;
                  type string;
                }
              }
            }
            leaf allow-promiscuous-vip {
              type empty;
            }
            container tcp {
              leaf syn-cookie {
                type empty;
              }
            }
          }
          container ipv6 {
            container access-list {
              leaf id {
                tailf:cli-drop-node-name;
                type string;
              }
              leaf in {
                // NCS drop must statement
                type empty;
              }
            }
            list address {
              // NCS patched for predictable order
              ordered-by user;
              key "ip";
              tailf:cli-suppress-mode;
              leaf ip {
                tailf:cli-drop-node-name;
                type ncs_compliance_template_ipv6-prefix;
              }
              leaf link-local {
                type empty;
              }
              leaf anycast {
                type empty;
              }
            }
            container nat {
              leaf inside {
                type empty;
              }
              leaf outside {
                type empty;
              }
            }
            container ndisc {
              container router-advertisement;
            }
            container ospf;
            container router {
              container isis {
                presence "true";
                leaf cmds {
                  tailf:cli-drop-node-name;
                  type string;
                }
              }
            }
          }
          leaf load-interval {
            type string;
          }
          container access-list {
            leaf id {
              tailf:cli-drop-node-name;
              type string;
            }
            leaf in {
              // NCS drop must statement
              type empty;
            }
          }
          leaf state {
            tailf:cli-drop-node-name;
            type string;
          }
          leaf state-alt {
            tailf:cli-drop-node-name;
            type string;
          }
          leaf duplexity {
            type string;
          }
          leaf cpu-process {
            type empty;
          }
          leaf flow-control {
            type empty;
          }
          container icmp-rate-limit {
            leaf rate {
              tailf:cli-drop-node-name;
              type string;
            }
            leaf lockup {
              // NCS drop must statement
              type string;
            }
            leaf lockup-period {
              // NCS drop must statement
              tailf:cli-drop-node-name;
              type string;
            }
          }
          container ospf;
          container isis;
          leaf l3-vlan-fwd-disable {
            type empty;
          }
          container lacp {
            leaf port-priority {
              type string;
            }
            leaf timeout {
              type string;
            }
            container trunk {
              leaf number {
                tailf:cli-drop-node-name;
                type string;
              }
              leaf admin-key {
                // NCS drop must statement
                type string;
              }
              leaf mode {
                // NCS drop must statement
                type string;
              }
              leaf unidirectional-detection {
                // NCS drop must statement
                type empty;
              }
            }
            container udld-timeout {
              leaf timeout-type {
                tailf:cli-drop-node-name;
                type string;
              }
              leaf milli {
                tailf:cli-drop-node-name;
                type string;
              }
              leaf secs {
                tailf:cli-drop-node-name;
                type string;
              }
            }
          }
          // NCS expand uses statement
          container lldp {
            container enable {
              leaf rx {
                type empty;
              }
              leaf tx {
                type empty;
              }
            }
            leaf notification {
              type string;
            }
            leaf tx-dot1-tlvs {
              type string;
            }
          }
          leaf mtu {
            type string;
          }
          leaf speed {
            type string;
          }
          list trunk-group-list {
            // NCS patched for predictable order
            ordered-by user;
            key "trunk-group-key";
            tailf:cli-drop-node-name;
            leaf trunk-group-key {
              type string;
            }
            leaf trunk-group-id {
              tailf:cli-drop-node-name;
              // NCS drop mandatory statement
              type string;
            }
            leaf trunk-group-type {
              tailf:cli-drop-node-name;
              type string;
            }
          }
        }
        list trunk {
          // NCS patched for predictable order
          ordered-by user;
          key "nr";
          leaf nr {
            type ncs_compliance_template_ethernet-index;
          }
          leaf name {
            type string;
          }
          leaf state {
            tailf:cli-drop-node-name;
            type string;
          }
          container icmp-rate-limit {
            leaf rate {
              tailf:cli-drop-node-name;
              type string;
            }
            leaf lockup {
              // NCS drop must statement
              type string;
            }
            leaf lockup-period {
              // NCS drop must statement
              tailf:cli-drop-node-name;
              type string;
            }
          }
          list access-list {
            // NCS patched for predictable order
            ordered-by user;
            tailf:cli-suppress-mode;
            key "id in-type";
            leaf id {
              type string;
            }
            leaf in-type {
              type string;
            }
          }
          container ip {
            list address {
              // NCS patched for predictable order
              ordered-by user;
              key "ip mask";
              tailf:cli-suppress-mode;
              leaf ip {
                type string;
              }
              leaf mask {
                type ncs_compliance_template_ipv4-mask;
              }
            }
            leaf allow-promiscuous-vip {
              type empty;
            }
            leaf cache-spoofing-port {
              type empty;
            }
            container nat {
              leaf inside {
                type empty;
              }
              leaf outside {
                type empty;
              }
            }
          }
        }
        list loopback {
          // NCS patched for predictable order
          ordered-by user;
          key "nr";
          leaf nr {
            type ncs_compliance_template_ethernet-index;
          }
          container ip {
            // NCS expand uses statement
            list address {
              // NCS patched for predictable order
              ordered-by user;
              tailf:cli-suppress-mode;
              key "address mask";
              leaf address {
                type string;
              }
              leaf mask {
                type string;
              }
            }
            container router {
              choice isis-choice {
                container isis-alt {
                  tailf:cli-drop-node-name;
                  leaf isis {
                    type string;
                  }
                }
                leaf isis {
                  type empty;
                }
              }
            }
          }
          container icmp-rate-limit {
            leaf rate {
              tailf:cli-drop-node-name;
              type string;
            }
            leaf lockup {
              // NCS drop must statement
              type string;
            }
            leaf lockup-period {
              tailf:cli-drop-node-name;
              // NCS drop must statement
              type string;
            }
          }
          leaf state {
            tailf:cli-drop-node-name;
            type string;
          }
        }
        list ve {
          // NCS patched for predictable order
          ordered-by user;
          key "id";
          leaf id {
            type ncs_compliance_template_vlan-index;
          }
          leaf name {
            type string;
          }
          container bfd {
            container echo {
              presence "true";
            }
          }
          container icmp-rate-limit {
            leaf rate {
              tailf:cli-drop-node-name;
              type string;
            }
            leaf lockup {
              // NCS drop must statement
              type string;
            }
            leaf lockup-period {
              tailf:cli-drop-node-name;
              // NCS drop must statement
              type string;
            }
          }
          container access-list {
            leaf id {
              tailf:cli-drop-node-name;
              type string;
            }
            leaf in {
              // NCS drop must statement
              type empty;
            }
          }
          leaf l3-vlan-fwd-disable {
            type empty;
          }
          container ip {
            leaf allow-promiscuous-vip {
              type empty;
            }
            leaf cache-spoofing-port {
              type empty;
            }
            leaf helper-address {
              type string;
            }
            container nat {
              leaf inside {
                type empty;
              }
              leaf outside {
                type empty;
              }
            }
            container ospf;
            container router {
              container isis {
                presence "true";
                leaf cmds {
                  tailf:cli-drop-node-name;
                  type string;
                }
              }
            }
            container tcp {
              leaf syn-cookie {
                type empty;
              }
            }
            // NCS expand uses statement
            list address {
              // NCS patched for predictable order
              ordered-by user;
              tailf:cli-suppress-mode;
              key "address mask";
              leaf address {
                type string;
              }
              leaf mask {
                type string;
              }
            }
          }
          container ipv6 {
            container access-list {
              leaf id {
                tailf:cli-drop-node-name;
                type string;
              }
              leaf in {
                // NCS drop must statement
                type empty;
              }
            }
            container nat {
              leaf inside {
                type empty;
              }
              leaf outside {
                type empty;
              }
            }
            container ndisc {
              container router-advertisement;
            }
            container ospf;
            container router {
              container isis {
                presence "true";
                leaf cmds {
                  tailf:cli-drop-node-name;
                  type string;
                }
              }
            }
            list address {
              // NCS patched for predictable order
              ordered-by user;
              key "ip";
              tailf:cli-suppress-mode;
              leaf ip {
                tailf:cli-drop-node-name;
                type ncs_compliance_template_ipv6-prefix;
              }
              leaf link-local {
                type empty;
              }
              leaf anycast {
                type empty;
              }
            }
          }
          leaf mtu {
            type string;
          }
          leaf state {
            tailf:cli-drop-node-name;
            type string;
          }
          container isis;
          container ospf;
        }
      }
      container ip {
        uses ncs_compliance_template_ip-prefix-list-grouping;
        uses ncs_compliance_template_ip-route-grouping;
      }
      container ipv6 {
        uses ncs_compliance_template_ipv6-route-grouping;
      }
      uses ncs_compliance_template_bfd-grouping;
      uses ncs_compliance_template_clock-grouping;
      uses ncs_compliance_template_lldp-grouping;
      // NCS expand uses statement
      container vcs {
        leaf state {
          tailf:cli-drop-node-name;
          type string;
        }
        list device {
          // NCS patched for predictable order
          ordered-by user;
          key "id";
          leaf id {
            type string;
          }
          leaf priority {
            type string;
          }
          container interfaces {
            leaf management {
              type empty;
            }
            list ethernet {
              // NCS patched for predictable order
              ordered-by user;
              tailf:cli-suppress-mode;
              key "id";
              leaf id {
                type string;
              }
            }
            list trunk {
              // NCS patched for predictable order
              ordered-by user;
              tailf:cli-suppress-mode;
              key "id";
              leaf id {
                type string;
              }
            }
            list ve {
              // NCS patched for predictable order
              ordered-by user;
              tailf:cli-suppress-mode;
              key "id";
              leaf id {
                type string;
              }
            }
          }
          leaf enable {
            type empty;
          }
        }
        list floating-ip {
          // NCS patched for predictable order
          ordered-by user;
          tailf:cli-suppress-mode;
          key "floating-ip-address";
          leaf floating-ip-address {
            tailf:cli-drop-node-name;
            type string;
          }
          leaf mask {
            tailf:cli-drop-node-name;
            type ncs_compliance_template_ipv4-mask;
          }
        }
        leaf ssl-enable {
          type empty;
        }
        leaf failure-retry-count {
          type string;
        }
      }
      uses ncs_compliance_template_tftp-grouping;
      uses ncs_compliance_template_enable-management-grouping;
      uses ncs_compliance_template_disable-management-grouping;
      uses ncs_compliance_template_lacp-grouping;
      uses ncs_compliance_template_route-map-grouping;
      uses ncs_compliance_template_ve-stats-grouping;
      uses ncs_compliance_template_bgp-grouping;
      uses ncs_compliance_template_router-grouping;
      uses ncs_compliance_template_timezone-grouping;
      uses ncs_compliance_template_sflow-grouping;
      container vrrp-a {
        // NCS expand uses statement
        container preferred-session-sync-port {
          list trunk {
            // NCS patched for predictable order
            ordered-by user;
            tailf:cli-suppress-mode;
            key "id";
            leaf id {
              type string;
            }
            leaf vlan {
              type string;
            }
          }
          list ethernet {
            // NCS patched for predictable order
            ordered-by user;
            tailf:cli-suppress-mode;
            key "id";
            leaf id {
              type ncs_compliance_template_ethernet-index;
            }
            leaf vlan {
              type string;
            }
          }
        }
      }
    }
  }

  grouping ncs_compliance_template_vcs-grouping {
    container vcs {
      leaf state {
        tailf:cli-drop-node-name;
        type string;
      }
      list device {
        // NCS patched for predictable order
        ordered-by user;
        key "id";
        leaf id {
          type string;
        }
        leaf priority {
          type string;
        }
        container interfaces {
          leaf management {
            type empty;
          }
          list ethernet {
            // NCS patched for predictable order
            ordered-by user;
            tailf:cli-suppress-mode;
            key "id";
            leaf id {
              type string;
            }
          }
          list trunk {
            // NCS patched for predictable order
            ordered-by user;
            tailf:cli-suppress-mode;
            key "id";
            leaf id {
              type string;
            }
          }
          list ve {
            // NCS patched for predictable order
            ordered-by user;
            tailf:cli-suppress-mode;
            key "id";
            leaf id {
              type string;
            }
          }
        }
        leaf enable {
          type empty;
        }
      }
      list floating-ip {
        // NCS patched for predictable order
        ordered-by user;
        tailf:cli-suppress-mode;
        key "floating-ip-address";
        leaf floating-ip-address {
          tailf:cli-drop-node-name;
          type string;
        }
        leaf mask {
          tailf:cli-drop-node-name;
          type ncs_compliance_template_ipv4-mask;
        }
      }
      leaf ssl-enable {
        type empty;
      }
      leaf failure-retry-count {
        type string;
      }
    }
  }

  grouping ncs_compliance_template_system-grouping {
    container system {
      container cpu-load-sharing {
        container cpu-usage {
          leaf low {
            type string;
          }
          leaf high {
            type string;
          }
        }
      }
      leaf module-ctrl-cpu {
        type string;
      }
      leaf glid {
        type string;
      }
      container all-vlan-limit {
        leaf bcast {
          type string;
        }
        leaf ipmcast {
          type string;
        }
        leaf mcast {
          type string;
        }
        leaf unknown-ucast {
          type string;
        }
      }
      container per-vlan-limit {
        leaf bcast {
          type string;
        }
        leaf ipmcast {
          type string;
        }
        leaf mcast {
          type string;
        }
        leaf unknown-ucast {
          type string;
        }
      }
      container resource-usage {
        uses ncs_compliance_template_resource-usage-grouping;
        list template {
          // NCS patched for predictable order
          ordered-by user;
          key "name";
          leaf name {
            type string;
          }
          container system-resources {
            leaf bw-limit {
              type string;
            }
            leaf ssl-throughput-limit {
              type string;
            }
            leaf l4cps-limit {
              type string;
            }
            leaf natcps-limit {
              type string;
            }
            leaf l7cps-limit {
              type string;
            }
            leaf sslcps-limit {
              type string;
            }
            leaf concurrent-session-limit {
              type string;
            }
          }
          container app-resources {
            leaf gslb-device-count {
              type string;
            }
            leaf gslb-geo-location-count {
              type string;
            }
            leaf gslb-ip-list-count {
              type string;
            }
            leaf gslb-policy-count {
              type string;
            }
            leaf gslb-service-count {
              type string;
            }
            leaf gslb-service-ip-count {
              type string;
            }
            leaf gslb-service-port-count {
              type string;
            }
            leaf gslb-site-count {
              type string;
            }
            leaf gslb-svc-group-count {
              type string;
            }
            leaf gslb-template-count {
              type string;
            }
            leaf gslb-zone-count {
              type string;
            }
          }
        }
      }
      container template {
        leaf policy {
          type string;
        }
      }
      container trunk {
        container load-balance {
          leaf layer-2 {
            type string;
          }
        }
      }
      leaf ve-mac-scheme {
        type string;
      }
      container apps-global {
        leaf log-session-on-established {
          type empty;
        }
        leaf msl-time {
          type string;
        }
      }
    }
  }

  grouping ncs_compliance_template_ve-stats-grouping {
    leaf ve-stats {
      type string;
    }
  }

  grouping ncs_compliance_template_partition-grouping {
    list partition {
      // NCS patched for predictable order
      ordered-by user;
      key "name";
      leaf name {
        type string;
      }
      leaf network-partition {
        type empty;
      }
      leaf id {
        type string;
      }
      leaf application-type {
        type string;
      }
      leaf template {
        type string;
      }
    }
  }

  grouping ncs_compliance_template_partition-group-grouping {
    list partition-group {
      // NCS patched for predictable order
      ordered-by user;
      key "name";
      leaf name {
        type string;
      }
      list member {
        // NCS patched for predictable order
        ordered-by user;
        tailf:cli-suppress-mode;
        key "partition-name";
        leaf partition-name {
          type string;
        }
      }
    }
  }

  grouping ncs_compliance_template_access-list-grouping {
    list access-list {
      // NCS patched for predictable order
      ordered-by user;
      tailf:cli-suppress-mode;
      key "id";
      leaf id {
        type string;
      }
      list rules {
        // NCS patched for predictable order
        ordered-by user;
        tailf:cli-suppress-mode;
        tailf:cli-drop-node-name;
        key "txt";
        leaf txt {
          type string;
        }
      }
    }
  }

  grouping ncs_compliance_template_tftp-grouping {
    container tftp {
      leaf blksize {
        type string;
      }
    }
  }

  grouping ncs_compliance_template_stats-data-disable-grouping {
    leaf stats-data-disable {
      type empty;
    }
  }

  grouping ncs_compliance_template_syn-cookie-grouping {
    container syn-cookie {
      leaf on-threshold {
        type string;
      }
      leaf off-threshold {
        type string;
      }
    }
  }

  grouping ncs_compliance_template_enable-management-grouping {
    container enable-management {
      container service {

        grouping enable-management-content-grouping {
          leaf-list ethernet {
            // NCS patched for predictable order
            ordered-by user;
            tailf:cli-range-list-syntax;
            type string;
          }
          list acl {
            // NCS patched for predictable order
            ordered-by user;
            key "id";
            leaf id {
              type string;
            }
          }
          list acl-v4 {
            // NCS patched for predictable order
            ordered-by user;
            key "id";
            leaf id {
              type string;
            }
          }
          leaf-list ve {
            // NCS patched for predictable order
            ordered-by user;
            tailf:cli-range-list-syntax;
            type string;
          }
        }
        container ssh {
          uses enable-management-content-grouping;
        }
        container ssh-alt {
          tailf:alt-name "ssh";
          leaf management {
            type empty;
          }
          uses enable-management-content-grouping;
        }
        container telnet {
          uses enable-management-content-grouping;
        }
        container telnet-alt {
          tailf:alt-name "telnet";
          leaf management {
            type empty;
          }
          uses enable-management-content-grouping;
        }
        container http {
          uses enable-management-content-grouping;
        }
        container http-alt {
          tailf:alt-name "http";
          leaf management {
            type empty;
          }
          uses enable-management-content-grouping;
        }
        container https {
          uses enable-management-content-grouping;
        }
        container https-alt {
          tailf:alt-name "https";
          leaf management {
            type empty;
          }
          uses enable-management-content-grouping;
        }
        container snmp {
          uses enable-management-content-grouping;
        }
        container snmp-alt {
          tailf:alt-name "snmp";
          leaf management {
            type empty;
          }
          uses enable-management-content-grouping;
        }
      }
    }
  }

  grouping ncs_compliance_template_disable-management-grouping {
    container disable-management {
      container service {
        container http {
          presence "present";
          leaf management {
            type empty;
          }
        }
      }
    }
  }

  grouping ncs_compliance_template_monitor-grouping {
    container monitor {
      leaf disk {
        type string;
      }
      leaf memory {
        type string;
      }
      leaf buffer-drop {
        type string;
      }
      leaf buffer-usage {
        type string;
      }
    }
  }

  grouping ncs_compliance_template_extended-stats-grouping {
    leaf extended-stats {
      type empty;
    }
  }

  grouping ncs_compliance_template_admin-grouping {
    container admin {
      container lockout {
        leaf enable {
          type empty;
        }
      }
    }
  }

  grouping ncs_compliance_template_zone-grouping {
    list zone {
      // NCS patched for predictable order
      ordered-by user;
      key "name";
      leaf name {
        type string;
      }
      container interface {
        leaf-list ethernet {
          // NCS patched for predictable order
          ordered-by user;
          tailf:cli-range-list-syntax;
          type ncs_compliance_template_ethernet-index;
        }
      }
    }
  }

  grouping ncs_compliance_template_object-grouping {
    container object {
      list network {
        // NCS patched for predictable order
        ordered-by user;
        key "name";
        leaf name {
          type string;
        }
        leaf ipv4-address {
          tailf:cli-drop-node-name;
          type string;
        }
        leaf ipv6-address {
          tailf:cli-drop-node-name;
          type string;
        }
      }
    }
  }

  grouping ncs_compliance_template_icmp-grouping {
    container icmp {
      list type {
        // NCS patched for predictable order
        ordered-by user;
        tailf:cli-suppress-mode;
        key "id";
        leaf id {
          type string;
        }
      }
    }
  }

  grouping ncs_compliance_template_object-group-grouping {
    container object-group {
      list service {
        // NCS patched for predictable order
        ordered-by user;
        key "service-name";
        leaf service-name {
          type string;
        }
        leaf description {
          type string;
        }
        list tcp {
          // NCS patched for predictable order
          ordered-by user;
          tailf:cli-suppress-mode;
          key "op port";
          leaf op {
            type string;
          }
          leaf port {
            type string;
          }
        }
        uses ncs_compliance_template_icmp-grouping;
      }
      list network {
        // NCS patched for predictable order
        ordered-by user;
        key "name";
        leaf name {
          type string;
        }
        leaf fw {
          type string;
        }
        leaf description {
          type string;
        }
        leaf any {
          type empty;
        }
        leaf host {
          type string;
        }
        leaf ipv6-address {
          tailf:cli-drop-node-name;
          type string;
        }
      }
    }
  }

  grouping ncs_compliance_template_rule-set-grouping {
    list rule-set {
      // NCS patched for predictable order
      ordered-by user;
      key "rule-name";
      leaf rule-name {
        type string;
      }
      list rule {
        // NCS patched for predictable order
        ordered-by user;
        key "name";
        leaf name {
          type string;
        }
        leaf action {
          type string;
        }

        grouping source-dest-grouping {
          list object {
            // NCS patched for predictable order
            ordered-by user;
            key "name";
            leaf name {
              type string;
            }
          }
          list object-group {
            // NCS patched for predictable order
            ordered-by user;
            key "name";
            leaf name {
              type string;
            }
          }
          leaf zone {
            type string;
          }
        }
        container source {
          uses source-dest-grouping;
        }
        container dest {
          uses source-dest-grouping;
        }
        container service {
          leaf any {
            type empty;
          }
          uses ncs_compliance_template_icmp-grouping;
          leaf object-group {
            type string;
          }
        }
      }
    }
  }

  grouping ncs_compliance_template_fw-grouping {
    container fw {
      leaf active-rule-set {
        type string;
      }
    }
  }

  grouping ncs_compliance_template_enable-core-grouping {
    leaf enable-core {
      type string;
    }
  }

  grouping ncs_template_slb-template-version-grouping {
    container version {
      leaf current {
        tailf:cli-drop-node-name;
        type string;
      }
      leaf lower {
        tailf:cli-drop-node-name;
        type string;
      }
    }
  }

  grouping ncs_template_ip-list-grouping {
    list ip-list {
      // NCS patched for predictable order
      ordered-by user;
      key "name";
      leaf name {
        type string;
      }
    }
  }

  grouping ncs_template_cgnv6-grouping {
    container cgnv6 {
      container logging {
        container nat-quota-exceeded {
          leaf level {
            type string;
          }
        }
        container sampling-enable {
          leaf all {
            type empty;
          }
        }
      }
      list server {
        // NCS patched for predictable order
        ordered-by user;
        key "name";
        unique "address";
        leaf name {
          type string;
        }
        leaf address {
          tailf:cli-drop-node-name;
          // NCS drop mandatory statement
          type string;
        }
        leaf health-check-disable {
          type empty;
        }
        list port {
          // NCS patched for predictable order
          ordered-by user;
          key "number tcpudp";
          leaf number {
            type string;
          }
          leaf tcpudp {
            type string;
          }
          leaf health-check-disable {
            type empty;
          }
        }
      }
      list service-group {
        // NCS patched for predictable order
        ordered-by user;
        key "name tcpudp";
        unique "name";
        leaf name {
          type string;
        }
        leaf tcpudp {
          type string;
        }
        container sampling-enable {
          leaf all {
            type empty;
          }
        }
        list member {
          // NCS patched for predictable order
          ordered-by user;
          key "host port";
          leaf host {
            type string;
          }
          leaf port {
            type string;
          }
          container sampling-enable {
            leaf all {
              type empty;
            }
          }
        }
        container shared {
          choice group-partition {
            leaf group {
              type string;
            }
            leaf partition {
              type string;
            }
          }
        }
      }
      container translation {
        leaf udp-timeout {
          type string;
        }
        leaf tcp-timeout {
          type string;
        }
        leaf icmp-timeout {
          type string;
        }
        container service-timeout {
          list tcp {
            // NCS patched for predictable order
            ordered-by user;
            tailf:cli-suppress-mode;
            key "port-id";
            leaf port-id {
              type string;
            }
            leaf to {
              type string;
            }
            leaf timeout {
              tailf:cli-drop-node-name;
              type string;
            }
          }
          list udp {
            // NCS patched for predictable order
            ordered-by user;
            tailf:cli-suppress-mode;
            key "port-id";
            leaf port-id {
              type string;
            }
            leaf timeout {
              tailf:cli-drop-node-name;
              type string;
            }
          }
        }
      }
      container lsn {
        list alg {
          // NCS patched for predictable order
          ordered-by user;
          tailf:cli-suppress-mode;
          key "alg-id";
          leaf alg-id {
            type string;
          }
          leaf enable {
            type empty;
          }
        }
        leaf hairpinning {
          type string;
        }
        leaf half-close-timeout {
          type string;
        }
        container logging {
          leaf default-template {
            type string;
          }
        }
        list endpoint-independent-mapping {
          // NCS patched for predictable order
          ordered-by user;
          key "proto";
          leaf proto {
            type string;
          }
          container port {
            leaf from {
              tailf:cli-drop-node-name;
              type string;
            }
            leaf to {
              type string;
            }
          }
        }
        list endpoint-independent-filtering {
          // NCS patched for predictable order
          ordered-by user;
          key "proto";
          leaf proto {
            type string;
          }
          container port {
            leaf from {
              tailf:cli-drop-node-name;
              type string;
            }
            leaf to {
              type string;
            }
          }
        }
        leaf ip-selection {
          type string;
        }
        container inside {
          container source {
            leaf class-list {
              type string;
            }
          }
        }
      }
      list lsn-rule-list {
        // NCS patched for predictable order
        ordered-by user;
        key "name";
        leaf name {
          type string;
        }
        container default {
          container tcp {
            uses ncs_template_port-grouping;
          }
          container udp {
            uses ncs_template_port-grouping;
          }
          container icmp {
            // NCS expand uses statement
            list action {
              // NCS patched for predictable order
              ordered-by user;
              tailf:cli-suppress-mode;
              key "type";
              leaf type {
                type string;
              }
              leaf pool {
                type string;
              }
              leaf domain {
                type string;
              }
            }
            leaf no-action {
              type empty;
            }
          }
          container others {
            // NCS expand uses statement
            list action {
              // NCS patched for predictable order
              ordered-by user;
              tailf:cli-suppress-mode;
              key "type";
              leaf type {
                type string;
              }
              leaf pool {
                type string;
              }
              leaf domain {
                type string;
              }
            }
            leaf no-action {
              type empty;
            }
          }
        }
        list ip {
          // NCS patched for predictable order
          ordered-by user;
          key "address";
          leaf address {
            type string;
          }
          container tcp {
            uses ncs_template_port-grouping;
          }
          container udp {
            uses ncs_template_port-grouping;
          }
          container icmp {
            // NCS expand uses statement
            list action {
              // NCS patched for predictable order
              ordered-by user;
              tailf:cli-suppress-mode;
              key "type";
              leaf type {
                type string;
              }
              leaf pool {
                type string;
              }
              leaf domain {
                type string;
              }
            }
            leaf no-action {
              type empty;
            }
          }
          container others {
            // NCS expand uses statement
            list action {
              // NCS patched for predictable order
              ordered-by user;
              tailf:cli-suppress-mode;
              key "type";
              leaf type {
                type string;
              }
              leaf pool {
                type string;
              }
              leaf domain {
                type string;
              }
            }
            leaf no-action {
              type empty;
            }
          }
        }
      }
      container fixed-nat {
        leaf create-port-mapping-file {
          type empty;
        }
      }
      container nat {
        list pool {
          // NCS patched for predictable order
          ordered-by user;
          tailf:cli-suppress-mode;
          key "name";
          leaf name {
            type string;
          }
          leaf address {
            tailf:cli-drop-node-name;
            type string;
          }
          leaf address-end {
            tailf:cli-drop-node-name;
            type string;
          }
          leaf netmask {
            type string;
          }
          leaf vrid {
            type string;
          }
          leaf port-batch-v2-size {
            type string;
          }
          leaf simultaneous-batch-allocation {
            type empty;
          }
          leaf tcp-time-wait-interval {
            type string;
          }
          container usable-nat-ports {
            leaf start {
              tailf:cli-drop-node-name;
              type string;
            }
            leaf end {
              tailf:cli-drop-node-name;
              type string;
            }
          }
        }
        list pool-group {
          // NCS patched for predictable order
          ordered-by user;
          key "name";
          leaf name {
            type string;
          }
          leaf vrid {
            type string;
          }
          list member {
            // NCS patched for predictable order
            ordered-by user;
            tailf:cli-suppress-mode;
            key "name";
            leaf name {
              type string;
            }
          }
        }
      }
      container resource-usage {
        leaf lsn-nat-addr-count {
          type string;
        }
      }
      list lsn-lid {
        // NCS patched for predictable order
        ordered-by user;
        key "lid";
        leaf lid {
          type string;
        }
        leaf name {
          type string;
        }
        container lsn-rule-list {
          leaf destination {
            type string;
          }
        }
        list user-quota {
          // NCS patched for predictable order
          ordered-by user;
          tailf:cli-suppress-mode;
          key "protocol";
          leaf protocol {
            type string;
          }
          leaf quota {
            tailf:cli-drop-node-name;
            type string;
          }
          leaf reserve {
            type string;
          }
        }
        leaf source-nat-pool {
          type string;
        }
      }
      container template {
        list logging {
          // NCS patched for predictable order
          ordered-by user;
          key "name";
          leaf name {
            type string;
          }
          container log {
            container fixed-nat {
              leaf port-mappings {
                type string;
              }
              container sessions {
                presence "true";
                leaf merged-style {
                  type empty;
                }
              }
            }
            leaf port-mappings {
              type string;
            }
            container sessions {
              presence "true";
              leaf merged-style {
                type empty;
              }
            }
          }
          leaf facility {
            type string;
          }
          leaf severity {
            type string;
          }
          container service-group {
            leaf name {
              tailf:cli-drop-node-name;
              type string;
            }
            leaf shared {
              type empty;
            }
          }
          container disable-log-by-destination {
            presence "true";
            leaf icmp {
              type empty;
            }
          }
          leaf include-destination {
            type empty;
          }
          leaf format {
            type string;
          }
          leaf batched-logging-disable {
            type empty;
          }
        }
      }
    }
  }

  grouping ncs_template_sflow-grouping {
    container sflow {
      container agent {
        leaf address {
          type string;
        }
      }
      container setting {
        leaf local-collection {
          type empty;
        }
        leaf source-ip-use-mgmt {
          type empty;
        }
      }
      list collector {
        // NCS patched for predictable order
        ordered-by user;
        tailf:cli-suppress-mode;
        key "ip port";
        leaf ip {
          type string;
        }
        leaf port {
          type string;
        }
      }
      list collector-alt {
        // NCS patched for predictable order
        ordered-by user;
        tailf:cli-suppress-mode;
        tailf:alt-name "collector";
        key "ip port";
        leaf ip {
          type string;
        }
        leaf port {
          type string;
        }
      }
      container polling {
        leaf cpu-usage {
          type empty;
        }
        leaf-list ve {
          // NCS patched for predictable order
          ordered-by user;
          tailf:cli-range-list-syntax;
          type string;
        }
      }
      container sampling {
        leaf-list ve {
          // NCS patched for predictable order
          ordered-by user;
          tailf:cli-range-list-syntax;
          type string;
        }
      }
      container source-address {
        leaf ip {
          type string;
        }
        leaf ipv6 {
          type string;
        }
      }
    }
  }

  grouping ncs_template_ip-address {
    list address {
      // NCS patched for predictable order
      ordered-by user;
      tailf:cli-suppress-mode;
      key "address mask";
      leaf address {
        type string;
      }
      leaf mask {
        type string;
      }
    }
  }

  grouping ncs_template_algs {
    container alg {
      uses ncs_template_pptp_alg;
      uses ncs_template_tftp_alg;
      uses ncs_template_rtsp_alg;
      uses ncs_template_esp_alg;
    }
  }

  grouping ncs_template_pptp_alg {
    leaf pptp {
      type string;
    }
  }

  grouping ncs_template_tftp_alg {
    leaf tftp {
      type string;
    }
  }

  grouping ncs_template_rtsp_alg {
    leaf rtsp {
      type string;
    }
  }

  grouping ncs_template_esp_alg {
    leaf esp {
      type string;
    }
  }

  grouping ncs_template_lid-grouping {
    choice lid-choice {
      leaf glid {
        type string;
      }
      leaf lid {
        type string;
      }
      leaf lsn-lid {
        type string;
      }
      leaf lsn-radius-profile {
        type string;
      }
    }
  }

  grouping ncs_template_mgmt-source-interface-grouping {
    container source-interface {
      leaf loopback {
        type string;
      }
    }
  }

  grouping ncs_template_priority-cost {
    leaf priority-cost {
      // NCS drop mandatory statement
      type string;
    }
  }

  grouping ncs_template_hostname-grouping {
    leaf hostname {
      type string;
    }
  }

  grouping ncs_template_password-grouping {
    leaf username {
      type string;
    }
    leaf password {
      type string;
    }
  }

  grouping ncs_template_interface-grouping {
    container interface {

      grouping lldp-interface-grouping {
        container lldp {
          container enable {
            leaf rx {
              type empty;
            }
            leaf tx {
              type empty;
            }
          }
          leaf notification {
            type string;
          }
          leaf tx-dot1-tlvs {
            type string;
          }
        }
      }
      container management {
        container bcast-rate-limit {
          presence "present";
          leaf rate {
            type string;
          }
        }
        container ip {
          uses ncs_template_ip-address;
          leaf control-apps-use-mgmt-port {
            type empty;
          }
          leaf default-gateway {
            type string;
          }
        }
        container ipv6 {
          list address {
            // NCS patched for predictable order
            ordered-by user;
            key "ip";
            tailf:cli-suppress-mode;
            leaf ip {
              tailf:cli-drop-node-name;
              type ncs_template_ipv6-prefix;
            }
            leaf link-local {
              type empty;
            }
          }
          leaf default-gateway {
            type string;
          }
        }
        uses lldp-interface-grouping;
        leaf flow-control {
          type empty;
        }
        container access-list {
          leaf id {
            tailf:cli-drop-node-name;
            type string;
          }
          leaf in {
            // NCS drop must statement
            type empty;
          }
        }
        leaf enabled-disabled {
          tailf:cli-drop-node-name;
          type string;
        }
        leaf duplexity {
          type string;
        }
        leaf mtu {
          type string;
        }
        leaf speed {
          type string;
        }
      }
      list ethernet {
        // NCS patched for predictable order
        ordered-by user;
        key "nr";
        leaf nr {
          type ncs_template_ethernet-index;
        }
        leaf name {
          type string;
        }
        container ip {
          uses ncs_template_ip-address;
          leaf cache-spoofing-port {
            type empty;
          }
          leaf helper-address {
            type string;
          }
          container nat {
            leaf inside {
              type empty;
            }
            leaf outside {
              type empty;
            }
          }
          container ospf;
          container router {
            container isis {
              presence "true";
              leaf cmds {
                tailf:cli-drop-node-name;
                type string;
              }
            }
          }
          leaf allow-promiscuous-vip {
            type empty;
          }
          container tcp {
            leaf syn-cookie {
              type empty;
            }
          }
        }
        container ipv6 {
          container access-list {
            leaf id {
              tailf:cli-drop-node-name;
              type string;
            }
            leaf in {
              // NCS drop must statement
              type empty;
            }
          }
          list address {
            // NCS patched for predictable order
            ordered-by user;
            key "ip";
            tailf:cli-suppress-mode;
            leaf ip {
              tailf:cli-drop-node-name;
              type ncs_template_ipv6-prefix;
            }
            leaf link-local {
              type empty;
            }
            leaf anycast {
              type empty;
            }
          }
          container nat {
            leaf inside {
              type empty;
            }
            leaf outside {
              type empty;
            }
          }
          container ndisc {
            container router-advertisement;
          }
          container ospf;
          container router {
            container isis {
              presence "true";
              leaf cmds {
                tailf:cli-drop-node-name;
                type string;
              }
            }
          }
        }
        leaf load-interval {
          type string;
        }
        container access-list {
          leaf id {
            tailf:cli-drop-node-name;
            type string;
          }
          leaf in {
            // NCS drop must statement
            type empty;
          }
        }
        leaf state {
          tailf:cli-drop-node-name;
          type string;
        }
        leaf state-alt {
          tailf:cli-drop-node-name;
          type string;
        }
        leaf duplexity {
          type string;
        }
        leaf cpu-process {
          type empty;
        }
        leaf flow-control {
          type empty;
        }
        container icmp-rate-limit {
          leaf rate {
            tailf:cli-drop-node-name;
            type string;
          }
          leaf lockup {
            // NCS drop must statement
            type string;
          }
          leaf lockup-period {
            // NCS drop must statement
            tailf:cli-drop-node-name;
            type string;
          }
        }
        container ospf;
        container isis;
        leaf l3-vlan-fwd-disable {
          type empty;
        }
        container lacp {
          leaf port-priority {
            type string;
          }
          leaf timeout {
            type string;
          }
          container trunk {
            leaf number {
              tailf:cli-drop-node-name;
              type string;
            }
            leaf admin-key {
              // NCS drop must statement
              type string;
            }
            leaf mode {
              // NCS drop must statement
              type string;
            }
            leaf unidirectional-detection {
              // NCS drop must statement
              type empty;
            }
          }
          container udld-timeout {
            leaf timeout-type {
              tailf:cli-drop-node-name;
              type string;
            }
            leaf milli {
              tailf:cli-drop-node-name;
              type string;
            }
            leaf secs {
              tailf:cli-drop-node-name;
              type string;
            }
          }
        }
        uses lldp-interface-grouping;
        leaf mtu {
          type string;
        }
        leaf speed {
          type string;
        }
        list trunk-group-list {
          // NCS patched for predictable order
          ordered-by user;
          key "trunk-group-key";
          tailf:cli-drop-node-name;
          leaf trunk-group-key {
            type string;
          }
          leaf trunk-group-id {
            tailf:cli-drop-node-name;
            // NCS drop mandatory statement
            type string;
          }
          leaf trunk-group-type {
            tailf:cli-drop-node-name;
            type string;
          }
        }
      }
      list trunk {
        // NCS patched for predictable order
        ordered-by user;
        key "nr";
        leaf nr {
          type ncs_template_ethernet-index;
        }
        leaf name {
          type string;
        }
        leaf state {
          tailf:cli-drop-node-name;
          type string;
        }
        container icmp-rate-limit {
          leaf rate {
            tailf:cli-drop-node-name;
            type string;
          }
          leaf lockup {
            // NCS drop must statement
            type string;
          }
          leaf lockup-period {
            // NCS drop must statement
            tailf:cli-drop-node-name;
            type string;
          }
        }
        list access-list {
          // NCS patched for predictable order
          ordered-by user;
          tailf:cli-suppress-mode;
          key "id in-type";
          leaf id {
            type string;
          }
          leaf in-type {
            type string;
          }
        }
        container ip {
          list address {
            // NCS patched for predictable order
            ordered-by user;
            key "ip mask";
            tailf:cli-suppress-mode;
            leaf ip {
              type string;
            }
            leaf mask {
              type ncs_template_ipv4-mask;
            }
          }
          leaf allow-promiscuous-vip {
            type empty;
          }
          leaf cache-spoofing-port {
            type empty;
          }
          container nat {
            leaf inside {
              type empty;
            }
            leaf outside {
              type empty;
            }
          }
        }
      }
      list loopback {
        // NCS patched for predictable order
        ordered-by user;
        key "nr";
        leaf nr {
          type ncs_template_ethernet-index;
        }
        container ip {
          uses ncs_template_ip-address;
          container router {
            choice isis-choice {
              container isis-alt {
                tailf:cli-drop-node-name;
                leaf isis {
                  type string;
                }
              }
              leaf isis {
                type empty;
              }
            }
          }
        }
        container icmp-rate-limit {
          leaf rate {
            tailf:cli-drop-node-name;
            type string;
          }
          leaf lockup {
            // NCS drop must statement
            type string;
          }
          leaf lockup-period {
            tailf:cli-drop-node-name;
            // NCS drop must statement
            type string;
          }
        }
        leaf state {
          tailf:cli-drop-node-name;
          type string;
        }
      }
      list ve {
        // NCS patched for predictable order
        ordered-by user;
        key "id";
        leaf id {
          type ncs_template_vlan-index;
        }
        leaf name {
          type string;
        }
        container bfd {
          container echo {
            presence "true";
          }
        }
        container icmp-rate-limit {
          leaf rate {
            tailf:cli-drop-node-name;
            type string;
          }
          leaf lockup {
            // NCS drop must statement
            type string;
          }
          leaf lockup-period {
            tailf:cli-drop-node-name;
            // NCS drop must statement
            type string;
          }
        }
        container access-list {
          leaf id {
            tailf:cli-drop-node-name;
            type string;
          }
          leaf in {
            // NCS drop must statement
            type empty;
          }
        }
        leaf l3-vlan-fwd-disable {
          type empty;
        }
        container ip {
          leaf allow-promiscuous-vip {
            type empty;
          }
          leaf cache-spoofing-port {
            type empty;
          }
          leaf helper-address {
            type string;
          }
          container nat {
            leaf inside {
              type empty;
            }
            leaf outside {
              type empty;
            }
          }
          container ospf;
          container router {
            container isis {
              presence "true";
              leaf cmds {
                tailf:cli-drop-node-name;
                type string;
              }
            }
          }
          container tcp {
            leaf syn-cookie {
              type empty;
            }
          }
          uses ncs_template_ip-address;
        }
        container ipv6 {
          container access-list {
            leaf id {
              tailf:cli-drop-node-name;
              type string;
            }
            leaf in {
              // NCS drop must statement
              type empty;
            }
          }
          container nat {
            leaf inside {
              type empty;
            }
            leaf outside {
              type empty;
            }
          }
          container ndisc {
            container router-advertisement;
          }
          container ospf;
          container router {
            container isis {
              presence "true";
              leaf cmds {
                tailf:cli-drop-node-name;
                type string;
              }
            }
          }
          list address {
            // NCS patched for predictable order
            ordered-by user;
            key "ip";
            tailf:cli-suppress-mode;
            leaf ip {
              tailf:cli-drop-node-name;
              type ncs_template_ipv6-prefix;
            }
            leaf link-local {
              type empty;
            }
            leaf anycast {
              type empty;
            }
          }
        }
        leaf mtu {
          type string;
        }
        leaf state {
          tailf:cli-drop-node-name;
          type string;
        }
        container isis;
        container ospf;
      }
    }
  }

  grouping ncs_template_ip-route-grouping {
    list route {
      // NCS patched for predictable order
      ordered-by user;
      tailf:cli-suppress-mode;
      key "ip mask forwarding-router";
      leaf ip {
        type string;
      }
      leaf mask {
        type string;
      }
      leaf forwarding-router {
        type string;
      }
      leaf distance {
        tailf:cli-drop-node-name;
        type string;
      }
      leaf cpu-process {
        tailf:cli-drop-node-name;
        type string;
      }
    }
  }

  grouping ncs_template_ip-prefix-list-grouping {
    list prefix-list {
      // NCS patched for predictable order
      ordered-by user;
      tailf:cli-suppress-mode;
      key "name seq";
      leaf name {
        type string;
      }
      leaf seq {
        type string;
      }
      choice permit-deny {
        leaf permit {
          type string;
        }
        leaf deny {
          type string;
        }
      }
      leaf ge {
        type string;
      }
      leaf le {
        type string;
      }
    }
  }

  grouping ncs_template_ip-grouping {
    container ip {
      list access-list {
        // NCS patched for predictable order
        ordered-by user;
        key "name";
        leaf name {
          type string;
        }
        list access-list-rule {
          // NCS patched for predictable order
          ordered-by user;
          tailf:cli-suppress-mode;
          tailf:cli-drop-node-name;
          key "rule";
          leaf rule {
            type string;
          }
        }
      }
      list address {
        // NCS patched for predictable order
        ordered-by user;
        key "ip";
        tailf:cli-suppress-mode;
        leaf ip {
          tailf:cli-drop-node-name;
          type string;
        }
        leaf mask {
          tailf:cli-drop-node-name;
          type ncs_template_ipv4-mask;
        }
      }
      container anomaly-drop {
        leaf bad-content {
          type string;
        }
        leaf drop-all {
          type empty;
        }
        leaf frag {
          type empty;
        }
        leaf ip-option {
          type string;
        }
        leaf land-attack {
          type empty;
        }
        leaf out-of-sequence {
          type string;
        }
        leaf ping-of-death {
          type empty;
        }
        leaf tcp-no-flag {
          type empty;
        }
        leaf tcp-syn-fin {
          type empty;
        }
        leaf tcp-syn-frag {
          type empty;
        }
        leaf zero-window {
          type string;
        }
        container security-attack {
          leaf layer-3 {
            type empty;
          }
          leaf layer-4 {
            type empty;
          }
        }
        list packet-deformity {
          // NCS patched for predictable order
          ordered-by user;
          tailf:cli-suppress-mode;
          key "layer";
          leaf layer {
            type string;
          }
        }
      }
      container as-path {
        list access-list {
          // NCS patched for predictable order
          ordered-by user;
          tailf:cli-suppress-mode;
          key "name action path";
          leaf name {
            type string;
          }
          leaf action {
            type string;
          }
          leaf path {
            type string;
          }
        }
      }
      container community-list {
        list standard-number {
          // NCS patched for predictable order
          ordered-by user;
          tailf:cli-drop-node-name;
          tailf:cli-suppress-mode;
          key "nr";
          leaf nr {
            type string;
          }
          list rules {
            // NCS patched for predictable order
            ordered-by user;
            tailf:cli-drop-node-name;
            tailf:cli-suppress-mode;
            key "action expr";
            leaf action {
              type string;
            }
            leaf expr {
              type string;
            }
          }
        }
        list expanded-number {
          // NCS patched for predictable order
          ordered-by user;
          tailf:cli-drop-node-name;
          tailf:cli-suppress-mode;
          key "nr";
          leaf nr {
            type string;
          }
          list rules {
            // NCS patched for predictable order
            ordered-by user;
            tailf:cli-drop-node-name;
            tailf:cli-suppress-mode;
            key "action expr";
            leaf action {
              type string;
            }
            leaf expr {
              type string;
            }
          }
        }
        list word {
          // NCS patched for predictable order
          ordered-by user;
          tailf:cli-drop-node-name;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
        list expanded {
          // NCS patched for predictable order
          ordered-by user;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
        list standard {
          // NCS patched for predictable order
          ordered-by user;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
      }
      leaf default-gateway {
        type string;
      }
      container dns {
        leaf primary {
          type string;
        }
        leaf secondary {
          type string;
        }
        leaf suffix {
          type string;
        }
      }
      container extcommunity-list {
        list standard-number {
          // NCS patched for predictable order
          ordered-by user;
          tailf:cli-drop-node-name;
          tailf:cli-suppress-mode;
          key "nr";
          leaf nr {
            type string;
          }
          list rules {
            // NCS patched for predictable order
            ordered-by user;
            tailf:cli-drop-node-name;
            tailf:cli-suppress-mode;
            key "action expr";
            leaf action {
              type string;
            }
            leaf expr {
              type string;
            }
          }
        }
        list expanded-number {
          // NCS patched for predictable order
          ordered-by user;
          tailf:cli-drop-node-name;
          tailf:cli-suppress-mode;
          key "nr";
          leaf nr {
            type string;
          }
          list rules {
            // NCS patched for predictable order
            ordered-by user;
            tailf:cli-drop-node-name;
            tailf:cli-suppress-mode;
            key "action expr";
            leaf action {
              type string;
            }
            leaf expr {
              type string;
            }
          }
        }
        list expanded {
          // NCS patched for predictable order
          ordered-by user;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
        list standard {
          // NCS patched for predictable order
          ordered-by user;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
      }
      container frag {
        leaf buff {
          type string;
        }
        container cpu-threshold {
          leaf high {
            type string;
          }
          leaf low {
            type string;
          }
        }
        leaf max-reassembly-sessions {
          type string;
        }
        leaf timeout {
          type string;
        }
      }
      container icmp {
        container disable {
          leaf redirect {
            type empty;
          }
          leaf unreachable {
            type empty;
          }
        }
      }
      container mgmt-traffic {
        container snmp {
          uses ncs_template_mgmt-source-interface-grouping;
        }
        container ntp {
          uses ncs_template_mgmt-source-interface-grouping;
        }
        container syslog {
          uses ncs_template_mgmt-source-interface-grouping;
        }
        container ssh {
          uses ncs_template_mgmt-source-interface-grouping;
        }
        container telnet {
          uses ncs_template_mgmt-source-interface-grouping;
        }
        container ftp {
          uses ncs_template_mgmt-source-interface-grouping;
        }
        container tftp {
          uses ncs_template_mgmt-source-interface-grouping;
        }
        container rcp {
          uses ncs_template_mgmt-source-interface-grouping;
        }
        container web {
          uses ncs_template_mgmt-source-interface-grouping;
        }
        container all {
          uses ncs_template_mgmt-source-interface-grouping;
        }
      }
      container nat {
        uses ncs_template_algs;
        leaf allow-static-host {
          type empty;
        }
        container inside {
          container source {
            list list {
              // NCS patched for predictable order
              ordered-by user;
              tailf:cli-suppress-mode;
              key "id";
              leaf id {
                type string;
              }
              leaf pool {
                // NCS drop mandatory statement
                type string;
              }
            }
            leaf class-list {
              type string;
            }
            list static {
              // NCS patched for predictable order
              ordered-by user;
              tailf:cli-suppress-mode;
              key "source nat";
              leaf source {
                type string;
              }
              leaf nat {
                type string;
              }
              leaf vrid {
                type string;
              }
            }
          }
        }
        list pool {
          // NCS patched for predictable order
          ordered-by user;
          tailf:cli-suppress-mode;
          key "name";
          leaf name {
            type string;
          }
          leaf ipstart {
            // NCS drop mandatory statement
            tailf:cli-drop-node-name;
            type string;
          }
          leaf ipend {
            // NCS drop mandatory statement
            tailf:cli-drop-node-name;
            type string;
          }
          leaf netmask {
            // NCS drop mandatory statement
            type string;
          }
          leaf gateway {
            type string;
          }
          leaf ha-group-id {
            type string;
          }
          leaf ha-use-all-ports {
            type empty;
          }
          leaf vrid {
            type string;
          }
          leaf ip-rr {
            type empty;
          }
          leaf lsn {
            type empty;
          }
          leaf max-users-per-ip {
            type string;
          }
        }
        list pool-group {
          // NCS patched for predictable order
          ordered-by user;
          key "name";
          leaf name {
            type string;
          }
          leaf ha-group-id {
            type string;
          }
          list member {
            // NCS patched for predictable order
            ordered-by user;
            key "member-id";
            tailf:cli-suppress-mode;
            leaf member-id {
              type string;
            }
          }
        }
        container range-list;
        leaf reset-idle-tcp-conn {
          type empty;
        }
        container template {
          list logging {
            // NCS patched for predictable order
            ordered-by user;
            key "name";
            leaf name {
              type string;
            }
          }
        }
        container translation {
          leaf icmp-timeout {
            type string;
          }
          leaf tcp-timeout {
            type string;
          }
          leaf udp-timeout {
            type string;
          }
          leaf syn-timeout {
            type string;
          }
          list service-timeout {
            // NCS patched for predictable order
            ordered-by user;
            tailf:cli-suppress-mode;
            key "protocol from";
            leaf protocol {
              type string;
            }
            leaf from {
              type string;
            }
            leaf to {
              type string;
            }
            leaf timeout {
              tailf:cli-drop-node-name;
              type string;
            }
          }
        }
        container lsn {
          container endpoint-independent-mapping {
            container tcp {
              container enable {
                leaf ephemeral {
                  type empty;
                }
                leaf well-known {
                  type empty;
                }
              }
            }
            container udp {
              container enable {
                leaf ephemeral {
                  type empty;
                }
                leaf well-known {
                  type empty;
                }
              }
            }
          }
          container endpoint-independent-filtering {
            container tcp {
              container enable {
                leaf ephemeral {
                  type empty;
                  // NCS drop must statement
                }
                leaf well-known {
                  type empty;
                  // NCS drop must statement
                }
              }
            }
            container udp {
              container enable {
                leaf ephemeral {
                  type empty;
                  // NCS drop must statement
                }
                leaf well-known {
                  type empty;
                  // NCS drop must statement
                }
              }
            }
          }
          leaf ip-selection {
            type string;
          }
          leaf attempt-port-preservation {
            type string;
          }
          uses ncs_template_algs;
        }
      }
      uses ncs_template_ip-prefix-list-grouping;
      uses ncs_template_ip-route-grouping;
      container tcp {
        container syn-cookie {
          leaf threshold {
            type string;
          }
        }
      }
    }
  }

  grouping ncs_template_resource-usage-grouping {
    leaf class-list-ipv6-addr-count {
      type string;
    }
    leaf client-ssl-template-count {
      type string;
    }
    leaf conn-reuse-template-count {
      type string;
    }
    leaf fast-tcp-template-count {
      type string;
    }
    leaf fast-udp-template-count {
      type string;
    }
    leaf http-template-count {
      type string;
    }
    leaf l4-session-count {
      type string;
    }
    leaf nat-pool-addr-count {
      type string;
    }
    leaf persist-cookie-template-count {
      type string;
    }
    leaf persist-srcip-template-count {
      type string;
    }
    leaf proxy-template-count {
      type string;
    }
    leaf real-port-count {
      type string;
    }
    leaf real-server-count {
      type string;
    }
    leaf server-ssl-template-count {
      type string;
    }
    leaf service-group-count {
      type string;
    }
    leaf stream-template-count {
      type string;
    }
    leaf virtual-port-count {
      type string;
    }
    leaf virtual-server-count {
      type string;
    }
  }

  grouping ncs_template_snmp-remote-grouping {
    list remote {
      // NCS patched for predictable order
      ordered-by user;
      tailf:cli-suppress-mode;
      key "host";
      leaf host {
        type string;
      }
      leaf mask {
        tailf:cli-drop-node-name;
        type string;
      }
    }
  }

  grouping ncs_template_health-grouping {
    container health {
      list monitor {
        // NCS patched for predictable order
        ordered-by user;
        key "name";
        leaf name {
          type string;
        }
        container interval {
          leaf interval {
            tailf:cli-drop-node-name;
            type string;
          }
          leaf timeout {
            type string;
          }
        }
        leaf interval-alt {
          tailf:alt-name "interval";
          type string;
        }
        leaf timeout-alt {
          tailf:alt-name "timeout";
          type string;
        }
        leaf retry {
          type string;
        }
        leaf retry-alt {
          tailf:alt-name "retry";
          type string;
        }
        leaf up-retry {
          type string;
        }
        leaf up-retry-alt {
          tailf:alt-name "up-retry";
          type string;
        }
        leaf strictly-retry-on-server-error-response {
          type empty;
        }
        leaf disable-after-down {
          type empty;
        }
        leaf override-port {
          type string;
        }
        leaf override-ipv4 {
          type string;
        }
        leaf override-ipv6 {
          type string;
        }
        container method {
          choice method-choice {
            container icmp {
              leaf transparent {
                type string;
              }
            }
            container http {
              presence "true";
              leaf port {
                type string;
              }
              // NCS expand uses statement
              leaf username {
                type string;
              }
              leaf password {
                type string;
              }
              leaf url {
                type empty;
              }
              leaf method {
                tailf:cli-drop-node-name;
                type string;
              }
              leaf path {
                tailf:cli-drop-node-name;
                type string;
              }
              leaf postdata {
                type string;
              }
              leaf postfile {
                type string;
              }
              container expect {
                choice expect-choice {
                  leaf response-code {
                    type string;
                  }
                  leaf text {
                    tailf:cli-drop-node-name;
                    type string;
                  }
                }
              }
              leaf maintenance-code {
                type string;
              }
              leaf host {
                type string;
              }
            }
            container https {
              presence "true";
              leaf port {
                type string;
              }
              leaf disable-sslv2hello {
                type empty;
              }
              uses ncs_template_password-grouping;
              leaf url {
                type empty;
              }
              leaf method {
                tailf:cli-drop-node-name;
                type string;
              }
              leaf path {
                tailf:cli-drop-node-name;
                type string;
              }
              container expect {
                choice expect-choice {
                  leaf response-code {
                    type string;
                  }
                  leaf text {
                    tailf:cli-drop-node-name;
                    type string;
                  }
                }
              }
              leaf maintenance-code {
                type string;
              }
              leaf host {
                type string;
              }
              container cert {
                leaf cert {
                  tailf:cli-drop-node-name;
                  type string;
                }
                leaf key {
                  type string;
                }
              }
            }
            container tcp {
              leaf port {
                type string;
              }
              leaf method {
                tailf:cli-drop-node-name;
                type string;
              }
              leaf sendcontent {
                tailf:cli-drop-node-name;
                type string;
              }
              leaf response {
                type empty;
              }
              leaf contains {
                type string;
              }
            }
            container udp {
              leaf port {
                type string;
              }
            }
            container ftp {
              presence "present";
              leaf port {
                type string;
              }
              uses ncs_template_password-grouping;
            }
            container snmp {
              presence "present";
              leaf community {
                type string;
              }
              leaf oid {
                type string;
              }
              leaf operation {
                type string;
              }
              leaf port {
                type string;
              }
            }
            container smtp {
              leaf domain {
                type string;
              }
              leaf port {
                type string;
              }
            }
            container dns {
              choice dns-health-choice {
                leaf domain {
                  type string;
                }
                leaf ipaddress {
                  type string;
                }
              }
              leaf port {
                type string;
              }
              leaf expect {
                type empty;
              }
              leaf response-code {
                type string;
              }
              leaf recurse {
                type string;
              }
              leaf tcp {
                type empty;
              }
              leaf type {
                type string;
              }
            }
            container pop3 {
              uses ncs_template_password-grouping;
              leaf port {
                type string;
              }
            }
            container imap {
              leaf port {
                type string;
              }
              uses ncs_template_password-grouping;
              leaf-list auth {
                // NCS patched for predictable order
                ordered-by user;
                type string;
              }
            }
            container sip {
              leaf port {
                type string;
              }
              leaf register {
                type empty;
              }
              leaf tcp {
                type empty;
              }
              leaf expect-response-code {
                type string;
              }
            }
            container radius {
              uses ncs_template_password-grouping;
              leaf secret {
                // NCS drop mandatory statement
                type string;
              }
              leaf port {
                type string;
              }
            }
            container tacplus {
              uses ncs_template_password-grouping;
              leaf secret {
                type string;
              }
              leaf port {
                type string;
              }
            }
            container ldap {
              leaf port {
                type string;
              }
              leaf overssl {
                type empty;
              }
              leaf binddn {
                type string;
              }
              leaf password {
                // NCS drop mandatory statement
                type string;
              }
            }
            container rtsp {
              leaf port {
                type string;
              }
              leaf rtspurl {
                type string;
              }
            }
            container database {
              leaf dbtype {
                tailf:cli-drop-node-name;
                type string;
              }
              leaf db-name {
                type string;
              }
              uses ncs_template_password-grouping;
              leaf send {
                type string;
              }
              leaf receive {
                type string;
              }
              leaf row {
                type string;
              }
              leaf column {
                type string;
              }
            }
            container external {
              leaf program {
                type string;
              }
            }
            container ntp;
            container compound {
              leaf name {
                tailf:cli-drop-node-name;
                type string;
              }
            }
          }
        }
      }
    }
  }

  grouping ncs_template_accounting-grouping {
    container accounting {
      container commands {
        leaf level {
          tailf:cli-drop-node-name;
          type string;
        }
        leaf stop-only {
          type empty;
        }
        leaf tacplus {
          type empty;
        }
      }
      leaf debug {
        type string;
      }
      container exec {
        choice st-st {
          leaf start-stop {
            type empty;
          }
          leaf stop-only {
            type empty;
          }
        }
        choice service {
          leaf tacplus {
            type empty;
          }
          leaf radius {
            type empty;
          }
        }
      }
    }
  }

  grouping ncs_template_acos-events-grouping {
    container acos-events {
      container logdb {
        leaf enable-all {
          type empty;
        }
        leaf enable-cgn {
          type empty;
        }
        leaf enable-http-forward-proxy {
          type empty;
        }
        leaf enable-smtp {
          type empty;
        }
      }
    }
  }

  grouping ncs_template_authorization-grouping {
    container authorization {
      container commands {
        leaf level {
          tailf:cli-drop-node-name;
          type string;
        }
        leaf-list method {
          // NCS patched for predictable order
          ordered-by user;
          type string;
        }
      }
    }
  }

  grouping ncs_template_bgp-grouping {
    container bgp {
      leaf extended-asn-cap {
        type empty;
      }
    }
  }

  grouping ncs_template_lacp-grouping {
    container lacp {
      leaf system-priority {
        type string;
      }
    }
  }

  grouping ncs_template_slb-grouping {
    container slb {
      container graceful-shutdown {
        leaf timeout {
          tailf:cli-drop-node-name;
          type string;
        }
        leaf when {
          // NCS drop must statement
          tailf:cli-drop-node-name;
          type string;
        }
      }
      leaf disable-server-auto-reselect {
        type empty;
      }
      container buff-thresh {
        leaf hw-buff {
          type string;
        }
        leaf relieve-thresh {
          type string;
        }
        leaf sys-buff-low {
          type string;
        }
        leaf sys-buff-high {
          type string;
        }
      }
      container template {
        list server {
          // NCS patched for predictable order
          ordered-by user;
          key "name";
          leaf name {
            type string;
          }
          leaf health-check {
            type string;
          }
          container conn-limit {
            leaf limit {
              tailf:cli-drop-node-name;
              type string;
            }
            leaf resume {
              // NCS drop must statement
              type string;
            }
            leaf no-logging {
              type empty;
            }
          }
          container conn-rate-limit {
            leaf limit {
              tailf:cli-drop-node-name;
              type string;
            }
            leaf per {
              // NCS drop must statement
              type string;
            }
            leaf no-logging {
              type empty;
            }
          }
          leaf dns-query-interval {
            type string;
          }
          leaf dynamic-server-prefix {
            type string;
          }
          leaf max-dynamic-server {
            type string;
          }
          leaf min-ttl-ratio {
            type string;
          }
          container slow-start {
            presence "present";
            leaf from {
              type string;
            }
            choice slow-start-choice {
              leaf add {
                type string;
              }
              leaf times {
                type string;
              }
            }
            leaf every {
              type string;
            }
            leaf till {
              type string;
            }
          }
        }
        list port {
          // NCS patched for predictable order
          ordered-by user;
          key "name";
          leaf name {
            type string;
          }
          container health-check {
            presence "true";
            choice mon-choice {
              leaf monitor {
                tailf:cli-drop-node-name;
                type string;
              }
              leaf ping {
                type empty;
              }
            }
          }
          container conn-limit {
            leaf limit {
              tailf:cli-drop-node-name;
              type string;
            }
            leaf resume {
              // NCS drop must statement
              type string;
            }
            leaf no-logging {
              type empty;
            }
          }
          container conn-rate-limit {
            leaf limit {
              tailf:cli-drop-node-name;
              type string;
            }
            leaf per {
              // NCS drop must statement
              type string;
            }
            leaf no-logging {
              type empty;
            }
          }
          leaf dest-nat {
            type empty;
          }
          leaf down-grace-period {
            type string;
          }
          leaf dscp {
            type string;
          }
          container dynamic-member-priority {
            leaf priority {
              tailf:cli-drop-node-name;
              type string;
            }
            leaf decrement {
              // NCS drop must statement
              type string;
            }
          }
          container inband-health-check {
            presence "true";
            leaf retry {
              type string;
            }
            leaf reassign {
              type string;
            }
          }
          leaf no-ssl {
            type empty;
          }
          container slow-start {
            presence "present";
            leaf from {
              type string;
            }
            choice slow-start-choice {
              leaf add {
                type string;
              }
              leaf times {
                type string;
              }
            }
            leaf every {
              type string;
            }
            leaf till {
              type string;
            }
          }
          leaf source-nat {
            type string;
          }
          leaf weight {
            type string;
          }
        }
        container cache;
        list client-ssl {
          // NCS patched for predictable order
          ordered-by user;
          key "name";
          leaf name {
            type string;
          }
          container cert {
            leaf cert {
              tailf:cli-drop-node-name;
              type string;
            }
            leaf partition {
              type string;
            }
          }
          container chain-cert {
            leaf chain-cert {
              tailf:cli-drop-node-name;
              type string;
            }
            leaf partition {
              type string;
            }
          }
          list ca-cert {
            // NCS patched for predictable order
            ordered-by user;
            tailf:cli-suppress-mode;
            key "name";
            leaf name {
              type string;
            }
            leaf partition {
              type string;
            }
          }
          container key {
            leaf key-name {
              tailf:cli-drop-node-name;
              type string;
            }
            leaf partition {
              type string;
            }
            leaf pass-phrase {
              type empty;
            }
            leaf pass-phrase-value {
              tailf:cli-drop-node-name;
              type string;
            }
          }
          list cipher {
            // NCS patched for predictable order
            ordered-by user;
            tailf:cli-suppress-mode;
            key "name";
            leaf name {
              type ncs_template_cipher;
            }
          }
          container template {
            container cipher {
              leaf name {
                tailf:cli-drop-node-name;
                type string;
              }
            }
          }
          leaf close-notify {
            type empty;
          }
          leaf renegotiation-disable {
            type empty;
          }
          leaf session-cache-size {
            type string;
          }
          leaf session-cache-timeout {
            type string;
          }
          leaf session-ticket-lifetime {
            type string;
          }
          uses ncs_template_slb-template-version-grouping;
          leaf auth-username-attribute {
            type string;
          }
          container certificate {
            leaf name {
              tailf:cli-drop-node-name;
              type string;
            }
            leaf key {
              type string;
            }
            leaf pass-phrase {
              type string;
            }
            leaf chain-cert {
              type string;
            }
          }
          leaf disable-sslv3 {
            type empty;
          }
        }
        list connection-reuse {
          // NCS patched for predictable order
          ordered-by user;
          key "name";
          leaf name {
            type string;
          }
          leaf timeout {
            type string;
          }
          leaf limit-per-server {
            type string;
          }
          container keep-alive-conn {
            presence "present";
            leaf preopen {
              type empty;
            }
            leaf connections {
              tailf:cli-drop-node-name;
              type string;
            }
          }
        }
        container diameter;
        list dns {
          // NCS patched for predictable order
          ordered-by user;
          key "name";
          leaf name {
            type string;
          }
          leaf max-query-length {
            type string;
          }
          leaf max-cache-size {
            type string;
          }
          leaf max-cache-entry-size {
            type string;
          }
          container dns-log-enable {
            leaf period {
              type string;
            }
          }
          leaf query-id-switch {
            type empty;
          }
        }
        list dynamic-service {
          // NCS patched for predictable order
          ordered-by user;
          key "name";
          leaf name {
            type string;
          }
          container dns {
            list server {
              // NCS patched for predictable order
              ordered-by user;
              tailf:cli-suppress-mode;
              key "ip";
              leaf ip {
                type string;
              }
            }
          }
        }
        list http {
          // NCS patched for predictable order
          ordered-by user;
          key "name";
          leaf name {
            type string;
          }
          container insert-client-ip {
            presence "true";
            leaf header-name {
              tailf:cli-drop-node-name;
              type string;
            }
            leaf replace {
              type empty;
            }
          }
          container non-http-bypass {
            leaf service-group {
              type string;
            }
          }
          container url-hash-persist {
            leaf offset {
              type string;
            }
            choice hash-choice {
              leaf first {
                type string;
              }
              leaf last {
                type string;
              }
            }
            leaf use-server-status {
              type empty;
            }
          }
          list host-switching {
            // NCS patched for predictable order
            ordered-by user;
            tailf:cli-suppress-mode;
            key "match-type identifier";
            leaf match-type {
              type string;
            }
            leaf identifier {
              type string;
            }
            leaf service-group {
              // NCS drop mandatory statement
              type string;
            }
          }
          list url-switching {
            // NCS patched for predictable order
            ordered-by user;
            tailf:cli-suppress-mode;
            key "match-type identifier";
            leaf match-type {
              type string;
            }
            leaf identifier {
              type string;
            }
            leaf service-group {
              // NCS drop mandatory statement
              type string;
            }
          }
          leaf request-line-case-insensitive {
            type empty;
          }
          container redirect-rewrite {
            leaf secure {
              type empty;
            }
          }
          list request-header-insert {
            // NCS patched for predictable order
            ordered-by user;
            tailf:cli-suppress-mode;
            key "header";
            leaf header {
              type string;
            }
            leaf insert-mode {
              tailf:cli-drop-node-name;
              type string;
            }
          }
          list response-header-insert {
            // NCS patched for predictable order
            ordered-by user;
            tailf:cli-suppress-mode;
            key "header";
            leaf header {
              type string;
            }
            leaf insert-mode {
              tailf:cli-drop-node-name;
              type string;
            }
          }
          leaf keep-client-alive {
            type empty;
          }
        }
        container persist {
          list source-ip {
            // NCS patched for predictable order
            ordered-by user;
            key "name";
            leaf name {
              type string;
            }
            leaf dont-honor-conn-rules {
              type empty;
            }
            leaf enforce-higher-priority {
              type empty;
            }
            leaf incl-sport {
              type empty;
            }
            container match-type {
              choice match-choice {
                leaf server {
                  type empty;
                }
                leaf service-group {
                  type empty;
                }
              }
              leaf scan-all-members {
                type empty;
              }
            }
            leaf netmask {
              type string;
            }
            leaf netmask6 {
              type string;
            }
            leaf timeout {
              type string;
            }
          }
          list cookie {
            // NCS patched for predictable order
            ordered-by user;
            key "id";
            leaf id {
              type string;
            }
            leaf name {
              type string;
            }
            leaf expire {
              type string;
            }
            container match-type {
              leaf server {
                type empty;
              }
              leaf service-group {
                type empty;
              }
              leaf scan-all-members {
                type empty;
              }
            }
            leaf insert-always {
              type empty;
            }
            leaf pass-thru {
              type empty;
            }
          }
          list destination-ip {
            // NCS patched for predictable order
            ordered-by user;
            key "name";
            leaf name {
              type string;
            }
          }
          list ssl-sid {
            // NCS patched for predictable order
            ordered-by user;
            key "name";
            leaf name {
              type string;
            }
            leaf timeout {
              type string;
            }
          }
        }
        list policy {
          // NCS patched for predictable order
          ordered-by user;
          key "name";
          leaf name {
            type string;
          }
          leaf proxy-keep-alive {
            type empty;
          }

          grouping stp-class-list-grouping {
            list lid {
              // NCS patched for predictable order
              ordered-by user;
              key "limit-id";
              leaf limit-id {
                type string;
              }
              leaf class-list-group {
                type string;
              }
              container action {
                choice action-choice {
                  leaf drop {
                    type empty;
                  }
                  leaf forward-to-internet {
                    type string;
                  }
                  leaf forward-to-service-group {
                    type string;
                  }
                }
                leaf log {
                  type empty;
                }
              }
              leaf conn-limit {
                type string;
              }
              container conn-rate-limit {
                leaf limit {
                  tailf:cli-drop-node-name;
                  type string;
                }
                leaf per {
                  // NCS drop must statement
                  type string;
                }
              }
              leaf request-limit {
                type string;
              }
              container request-rate-limit {
                leaf limit {
                  tailf:cli-drop-node-name;
                  type string;
                }
                leaf per {
                  // NCS drop must statement
                  type string;
                }
              }
              container over-limit-action {
                leaf over-limit-action-choice {
                  tailf:cli-drop-node-name;
                  type string;
                }
                leaf lockout {
                  type string;
                }
                leaf lockout-val {
                  tailf:cli-drop-node-name;
                  type string;
                }
                leaf log {
                  type empty;
                }
                leaf log-val {
                  tailf:cli-drop-node-name;
                  type string;
                }
              }
            }
            container client-ip {
              choice client-ip-choice {
                leaf l3-dest {
                  type empty;
                }
                leaf l7-header {
                  type empty;
                }
              }
              leaf l7-header-string {
                tailf:cli-drop-node-name;
                type string;
              }
            }
          }
          container class-list {
            leaf name {
              type string;
            }
            uses stp-class-list-grouping;
          }
          container class-list-alt {
            tailf:alt-name "class-list";
            leaf name {
              tailf:cli-drop-node-name;
              type string;
            }
            uses stp-class-list-grouping;
          }
          leaf class-list-group {
            type string;
          }
          container bw-list {
            leaf name {
              type string;
            }
            list id {
              // NCS patched for predictable order
              ordered-by user;
              tailf:cli-suppress-mode;
              key "id";
              leaf id {
                type string;
              }
              leaf service-group {
                type string;
              }
            }
          }
        }
        list server-ssl {
          // NCS patched for predictable order
          ordered-by user;
          key "name";
          leaf name {
            type string;
          }
          leaf cert {
            type string;
          }
          leaf ca-cert {
            type string;
          }
          list cipher {
            // NCS patched for predictable order
            ordered-by user;
            tailf:cli-suppress-mode;
            key "name";
            leaf name {
              type ncs_template_cipher;
            }
          }
          container server-certificate-error {
            leaf trap {
              type empty;
            }
            leaf email {
              type empty;
            }
            leaf logging {
              type empty;
            }
            leaf ignore {
              type empty;
            }
          }
          leaf close-notify {
            type empty;
          }
          container key {
            leaf key-name {
              tailf:cli-drop-node-name;
              type string;
            }
            leaf partition {
              type string;
            }
            leaf pass-phrase {
              type empty;
            }
            leaf pass-phrase-value {
              tailf:cli-drop-node-name;
              type string;
            }
          }
          container template {
            container cipher {
              leaf name {
                tailf:cli-drop-node-name;
                type string;
              }
            }
          }
          uses ncs_template_slb-template-version-grouping;
        }
        list sip {
          // NCS patched for predictable order
          ordered-by user;
          key "name";
          leaf name {
            type string;
          }
          leaf timeout {
            type string;
          }
          leaf call-id-persist-disable {
            type empty;
          }
          leaf insert-client-ip {
            type empty;
          }
        }
        container smtp;
        container streaming-media;
        list tcp {
          // NCS patched for predictable order
          ordered-by user;
          key "name";
          leaf name {
            type string;
          }
          leaf idle-timeout {
            type string;
          }
          container force-delete-timeout {
            leaf timeout {
              tailf:cli-drop-node-name;
              type string;
            }
            leaf alive-if-active {
              // NCS drop must statement
              type empty;
            }
          }
          leaf half-close-idle-timeout {
            type string;
          }
          leaf initial-window-size {
            type string;
          }
          leaf lan-fast-ack {
            type empty;
          }
          leaf reset-fwd {
            type empty;
          }
          leaf reset-rev {
            type empty;
          }
        }
        list tcp-proxy {
          // NCS patched for predictable order
          ordered-by user;
          key "name";
          leaf name {
            type string;
          }
          leaf idle-timeout {
            type string;
          }
          leaf syn-retries {
            type string;
          }
          leaf retransmit-retries {
            type string;
          }
          leaf half-close-idle-timeout {
            type string;
          }
          leaf backend-wscale {
            type string;
          }
          leaf reset-fwd {
            type empty;
          }
          leaf reset-rev {
            type empty;
          }
          leaf receive-buffer {
            type string;
          }
          leaf transmit-buffer {
            type string;
          }
          leaf nagle {
            type empty;
          }
          leaf timewait {
            type string;
          }
          leaf reno {
            type empty;
          }
        }
        list udp {
          // NCS patched for predictable order
          ordered-by user;
          key "name";
          leaf name {
            type string;
          }
          leaf idle-timeout {
            type string;
          }
          container aging {
            choice aging-choice {
              leaf immediate {
                type empty;
              }
              container short {
                presence "present";
                leaf short-value {
                  tailf:cli-drop-node-name;
                  type string;
                }
              }
            }
          }
          leaf re-select-if-server-down {
            type empty;
          }
        }
        list virtual-port {
          // NCS patched for predictable order
          ordered-by user;
          key "name";
          leaf name {
            type string;
          }
          leaf reset-unknown-conn {
            type empty;
          }
          leaf ignore-tcp-msl {
            type empty;
          }
          leaf allow-syn-otherflags {
            type empty;
          }
          leaf snat-port-preserve {
            type empty;
          }
        }
        list external-service {
          // NCS patched for predictable order
          ordered-by user;
          key "name";
          leaf name {
            type string;
          }
          container timeout {
            leaf time {
              tailf:cli-drop-node-name;
              type string;
            }
            leaf action {
              type string;
            }
          }
          leaf service-group {
            type string;
          }
          container template {
            leaf tcp-proxy {
              type string;
            }
          }
        }
        list virtual-server {
          // NCS patched for predictable order
          ordered-by user;
          key "name";
          leaf name {
            type string;
          }
          container conn-limit {
            leaf limit {
              tailf:cli-drop-node-name;
              type string;
            }
            leaf reset {
              // NCS drop must statement
              type empty;
            }
            leaf no-logging {
              type empty;
            }
          }
          container conn-rate-limit {
            leaf limit {
              tailf:cli-drop-node-name;
              type string;
            }
            leaf per {
              // NCS drop must statement
              type string;
            }
            leaf reset {
              // NCS drop must statement
              type empty;
            }
            leaf no-logging {
              type empty;
            }
          }
          container icmp-rate-limit {
            leaf rate {
              tailf:cli-drop-node-name;
              type string;
            }
            leaf lockup {
              // NCS drop must statement
              type string;
            }
            leaf lockup-period {
              tailf:cli-drop-node-name;
              // NCS drop must statement
              type string;
            }
          }
          leaf subnet-gratuitous-arp {
            type empty;
          }
        }
        list cipher {
          // NCS patched for predictable order
          ordered-by user;
          key "name";
          leaf name {
            type string;
          }

          grouping cipher-prio-grouping {
            leaf priority {
              type string;
            }
          }
          container SSL3_RSA_DES_192_CBC3_SHA {
            presence "present";
            uses cipher-prio-grouping;
          }
          container SSL3_RSA_DES_40_CBC_SHA {
            presence "present";
            uses cipher-prio-grouping;
          }
          container SSL3_RSA_DES_64_CBC_SHA {
            presence "present";
            uses cipher-prio-grouping;
          }
          container SSL3_RSA_RC4_128_MD5 {
            presence "present";
            uses cipher-prio-grouping;
          }
          container SSL3_RSA_RC4_128_SHA {
            presence "present";
            uses cipher-prio-grouping;
          }
          container SSL3_RSA_RC4_40_MD5 {
            presence "present";
            uses cipher-prio-grouping;
          }
          container TLS1_RSA_AES_128_SHA {
            presence "present";
            uses cipher-prio-grouping;
          }
          container TLS1_RSA_AES_256_SHA {
            presence "present";
            uses cipher-prio-grouping;
          }
          container TLS1_RSA_EXPORT1024_RC4_56_MD5 {
            presence "present";
            uses cipher-prio-grouping;
          }
          container TLS1_RSA_EXPORT1024_RC4_56_SHA {
            presence "present";
            uses cipher-prio-grouping;
          }
          container TLS1_RSA_AES_128_SHA256 {
            presence "present";
            uses cipher-prio-grouping;
          }
          container TLS1_RSA_AES_256_SHA256 {
            presence "present";
            uses cipher-prio-grouping;
          }
          container TLS1_DHE_RSA_AES_128_GCM_SHA256 {
            presence "present";
            uses cipher-prio-grouping;
          }
          container TLS1_DHE_RSA_AES_128_SHA {
            presence "present";
            uses cipher-prio-grouping;
          }
          container TLS1_DHE_RSA_AES_128_SHA256 {
            presence "present";
            uses cipher-prio-grouping;
          }
          container TLS1_DHE_RSA_AES_256_GCM_SHA384 {
            presence "present";
            uses cipher-prio-grouping;
          }
          container TLS1_DHE_RSA_AES_256_SHA {
            presence "present";
            uses cipher-prio-grouping;
          }
          container TLS1_DHE_RSA_AES_256_SHA256 {
            presence "present";
            uses cipher-prio-grouping;
          }
          container TLS1_ECDHE_ECDSA_AES_128_GCM_SHA256 {
            presence "present";
            uses cipher-prio-grouping;
          }
          container TLS1_ECDHE_ECDSA_AES_128_SHA {
            presence "present";
            uses cipher-prio-grouping;
          }
          container TLS1_ECDHE_ECDSA_AES_128_SHA256 {
            presence "present";
            uses cipher-prio-grouping;
          }
          container TLS1_ECDHE_ECDSA_AES_256_GCM_SHA384 {
            presence "present";
            uses cipher-prio-grouping;
          }
          container TLS1_ECDHE_ECDSA_AES_256_SHA {
            presence "present";
            uses cipher-prio-grouping;
          }
          container TLS1_ECDHE_RSA_AES_128_GCM_SHA256 {
            presence "present";
            uses cipher-prio-grouping;
          }
          container TLS1_ECDHE_RSA_AES_128_SHA {
            presence "present";
            uses cipher-prio-grouping;
          }
          container TLS1_ECDHE_RSA_AES_128_SHA256 {
            presence "present";
            uses cipher-prio-grouping;
          }
          container TLS1_ECDHE_RSA_AES_256_GCM_SHA384 {
            presence "present";
            uses cipher-prio-grouping;
          }
          container TLS1_ECDHE_RSA_AES_256_SHA {
            presence "present";
            uses cipher-prio-grouping;
          }
          container TLS1_RSA_AES_128_GCM_SHA256 {
            presence "present";
            uses cipher-prio-grouping;
          }
          container TLS1_RSA_AES_256_GCM_SHA384 {
            presence "present";
            uses cipher-prio-grouping;
          }
        }
      }
      list server {
        // NCS patched for predictable order
        ordered-by user;
        key "name";
        unique "address";
        leaf name {
          type string;
        }
        leaf address {
          tailf:cli-drop-node-name;
          // NCS drop mandatory statement
          type string;
        }
        leaf disable {
          type empty;
        }
        choice hc-choice {
          leaf health-check {
            type string;
          }
          container health-check-conf {
            tailf:cli-drop-node-name;
            container health-check {
              choice monitor-choice {
                leaf ping {
                  type empty;
                }
                leaf host {
                  tailf:cli-drop-node-name;
                  type string;
                }
              }
            }
          }
          leaf health-check-disable {
            type empty;
          }
        }
        container conn-limit {
          leaf limit {
            tailf:cli-drop-node-name;
            type string;
          }
          leaf resume {
            // NCS drop must statement
            type string;
          }
          leaf no-logging {
            type empty;
          }
        }
        leaf conn-resume {
          type string;
        }
        leaf extended-stats {
          type empty;
        }
        leaf external-ip {
          type string;
        }
        container ha-priority-cost {
          leaf cost {
            tailf:cli-drop-node-name;
            type string;
          }
          leaf ha-group {
            type string;
          }
        }
        leaf ipv6 {
          type string;
        }
        leaf slow-start {
          type empty;
        }
        leaf spoofing-cache {
          type empty;
        }
        leaf stats-data-disable {
          type empty;
        }
        leaf weight {
          type string;
        }
        list port {
          // NCS patched for predictable order
          ordered-by user;
          key "number tcpudp";
          leaf number {
            type string;
          }
          leaf tcpudp {
            type string;
          }
          container conn-limit {
            leaf limit {
              tailf:cli-drop-node-name;
              type string;
            }
            leaf resume {
              // NCS drop must statement
              type string;
            }
            leaf no-logging {
              type empty;
            }
          }
          leaf conn-resume {
            type string;
          }
          leaf extended-stats {
            type empty;
          }
          container ha-priority-cost {
            leaf cost {
              tailf:cli-drop-node-name;
              type string;
            }
            leaf ha-group {
              // NCS drop must statement
              type string;
            }
          }
          leaf health-check-disable {
            type empty;
          }
          container template {
            leaf port {
              type string;
            }
          }
          choice hc-choice {
            leaf health-check {
              type string;
            }
            container health-check-conf {
              tailf:cli-drop-node-name;
              container health-check {
                choice monitor-choice {
                  leaf ping {
                    type empty;
                  }
                  leaf host {
                    tailf:cli-drop-node-name;
                    type string;
                  }
                  container follow-port {
                    leaf port {
                      tailf:cli-drop-node-name;
                      type string;
                    }
                    leaf tcpudp {
                      tailf:cli-drop-node-name;
                      type string;
                    }
                  }
                }
              }
            }
          }
          leaf no-ssl {
            type empty;
          }
          leaf stats-data-disable {
            type empty;
          }
          leaf state {
            tailf:cli-drop-node-name;
            type string;
          }
        }
        container template {
          leaf server {
            type string;
          }
        }
        leaf state {
          tailf:cli-drop-node-name;
          type string;
        }
      }
      list service-group {
        // NCS patched for predictable order
        ordered-by user;
        key "name tcpudp";
        unique "name";
        leaf name {
          type string;
        }
        leaf tcpudp {
          type string;
        }
        leaf backup-server-event-log {
          type empty;
        }
        leaf extended-stats {
          type empty;
        }
        container health-check {
          choice monitor-choice {
            leaf ping {
              type empty;
            }
            leaf host {
              tailf:cli-drop-node-name;
              type string;
            }
          }
          leaf partition {
            type string;
          }
        }
        list member1 {
          // NCS patched for predictable order
          ordered-by user;
          tailf:cli-suppress-mode;
          tailf:alt-name "member";
          key "host port";
          leaf host {
            type string;
          }
          leaf port {
            type string;
          }
          leaf partition {
            type string;
          }
          leaf state {
            tailf:cli-drop-node-name;
            type string;
          }
          leaf priority {
            type string;
          }
        }
        list member2 {
          // NCS patched for predictable order
          ordered-by user;
          tailf:alt-name "member";
          key "host port";
          leaf host {
            type string;
          }
          leaf port {
            type string;
          }
          leaf partition {
            type string;
          }
          leaf state {
            tailf:cli-drop-node-name;
            type string;
          }
          leaf priority {
            type string;
          }
          leaf template {
            type string;
          }
        }
        container method {
          choice method-choice {
            leaf fastest-response {
              type empty;
            }
            container least-connection {
              presence "true";
              leaf pseudo-round-robin {
                type empty;
              }
            }
            leaf least-request {
              type empty;
            }
            leaf round-robin {
              type empty;
            }
            leaf round-robin-strict {
              type empty;
            }
            container service-least-connection {
              presence "true";
              leaf pseudo-round-robin {
                type empty;
              }
            }
            container service-weighted-least-connection {
              presence "true";
              leaf pseudo-round-robin {
                type empty;
              }
            }
            leaf stateless-dst-ip-hash {
              type empty;
            }
            leaf stateless-per-pkt-round-robin {
              type empty;
            }
            leaf stateless-src-dst-ip-hash {
              type empty;
            }
            leaf stateless-src-ip-hash {
              type empty;
            }
            leaf stateless-src-ip-only-hash {
              type empty;
            }
            container weighted-least-connection {
              presence "true";
              leaf pseudo-round-robin {
                type empty;
              }
            }
            leaf weighted-rr {
              type empty;
            }
          }
        }
        container min-active-member {
          leaf min {
            tailf:cli-drop-node-name;
            type string;
          }
          leaf method {
            // NCS drop must statement
            tailf:cli-drop-node-name;
            type string;
          }
        }
        list priority {
          // NCS patched for predictable order
          ordered-by user;
          tailf:cli-suppress-mode;
          key "prio";
          leaf prio {
            type string;
          }
          leaf action {
            tailf:cli-drop-node-name;
            type string;
          }
        }
        container priority-affinity {
          presence "true";
        }
        leaf reset-on-server-selection-fail {
          type empty;
        }
        leaf stats-data-disable {
          type empty;
        }
      }
      list virtual-server {
        // NCS patched for predictable order
        ordered-by user;
        key "name";
        leaf name {
          type string;
        }
        leaf address {
          tailf:cli-drop-node-name;
          // NCS drop mandatory statement
          type string;
        }
        leaf netmask {
          tailf:cli-drop-node-name;
          type string;
        }
        leaf acl {
          type string;
        }
        leaf arp-disable {
          type empty;
        }
        leaf disable {
          type empty;
        }
        leaf extended-stats {
          type empty;
        }
        leaf ha-dynamic {
          type string;
        }
        choice disable-choice {
          leaf disable-when-any-port-down {
            type empty;
          }
          leaf disable-when-all-ports-down {
            type empty;
          }
        }
        leaf ha-group {
          type string;
        }
        leaf redistribution-flagged {
          type empty;
        }
        leaf stats-data-disable {
          type empty;
        }
        leaf vrid {
          type string;
        }
        list port {
          // NCS patched for predictable order
          ordered-by user;
          key "id type";
          leaf id {
            type string;
          }
          leaf type {
            // NCS drop must statement
            type string;
          }
          container access-list {
            choice access-list-id {
              leaf acl-id {
                tailf:cli-drop-node-name;
                type string;
              }
              leaf name {
                type string;
              }
            }
            choice nat-choice {
              leaf source-nat-pool-alt1 {
                tailf:alt-name "source-nat-pool";
                type string;
              }
              leaf source-nat-pool-alt2 {
                tailf:alt-name "source-nat-pool";
                type string;
              }
              leaf source-nat-pool-alt3 {
                tailf:alt-name "source-nat-pool";
                type string;
              }
            }
            leaf sequence-number {
              type string;
            }
          }
          list aflex {
            // NCS patched for predictable order
            ordered-by user;
            tailf:cli-suppress-mode;
            key "id";
            leaf id {
              type string;
            }
          }
          container conn-limit {
            leaf limit {
              tailf:cli-drop-node-name;
              type string;
            }
            leaf reset {
              // NCS drop must statement
              type empty;
            }
            leaf no-logging {
              type empty;
            }
          }
          leaf def-selection-if-pref-failed-disable {
            type empty;
          }
          leaf disable {
            type empty;
          }
          leaf extended-stats {
            type empty;
          }
          leaf ha-conn-mirror {
            type empty;
            // NCS drop must statement
          }
          leaf message-switching {
            type empty;
          }
          leaf name {
            type string;
          }
          container no-dest-nat {
            presence "true";
            leaf port-translation {
              type empty;
            }
          }
          leaf pbslb {
            type empty;
          }
          leaf reset-on-server-selection-fail {
            type empty;
          }
          leaf redirect-to-https {
            type empty;
          }
          leaf support-http2 {
            type empty;
          }
          leaf service-group {
            type string;
          }
          leaf snat-on-vip {
            type empty;
          }
          container source-nat {
            choice source-nat-choice {
              container auto {
                presence "true";
                leaf precedence {
                  type empty;
                }
              }
              leaf class-list {
                type string;
              }
              list pool {
                // NCS patched for predictable order
                ordered-by user;
                tailf:cli-suppress-mode;
                // NCS drop tailf-common:cli-diff-create-before statement
                key "name";
                leaf name {
                  type string;
                }
              }
            }
          }
          leaf stats-data-disable {
            type empty;
          }
          leaf syn-cookie {
            type empty;
          }
          container use-default-if-no-server {
            presence "true";
            leaf sack {
              type empty;
            }
          }
          leaf use-rcv-hop-for-resp {
            type empty;
          }
          list template {
            // NCS patched for predictable order
            ordered-by user;
            tailf:cli-suppress-mode;
            key "template-type";
            leaf template-type {
              type string;
            }
            leaf udp {
              tailf:cli-drop-node-name;
              type string;
            }
            leaf sip {
              tailf:cli-drop-node-name;
              type string;
            }
            leaf diameter {
              tailf:cli-drop-node-name;
              type string;
            }
            container persist {
              tailf:cli-drop-node-name;
              leaf source-ip {
                type string;
              }
              leaf destination-ip {
                type string;
              }
              leaf ssl-sid {
                type string;
              }
              leaf cookie {
                type string;
              }
            }
            leaf policy {
              tailf:cli-drop-node-name;
              type string;
            }
            leaf tcp {
              tailf:cli-drop-node-name;
              type string;
            }
            leaf tcp-proxy {
              tailf:cli-drop-node-name;
              type string;
            }
            leaf virtual-port {
              tailf:cli-drop-node-name;
              type string;
            }
            leaf client-ssl {
              tailf:cli-drop-node-name;
              type string;
            }
            leaf server-ssl {
              tailf:cli-drop-node-name;
              type string;
            }
            leaf http {
              tailf:cli-drop-node-name;
              type string;
            }
            leaf external-service {
              tailf:cli-drop-node-name;
              type string;
            }
            leaf dynamic-service {
              tailf:cli-drop-node-name;
              type string;
            }
          }
        }
        container template {
          leaf logging {
            type string;
          }
          leaf policy {
            type string;
          }
          leaf virtual-server {
            type string;
          }
        }
      }
      container resource-usage {
        uses ncs_template_resource-usage-grouping;
      }
      leaf transparent-tcp-template {
        type string;
      }
    }
  }

  grouping ncs_template_gslb-group-grouping {
    list group {
      // NCS patched for predictable order
      ordered-by user;
      key "name";
      leaf name {
        type string;
      }
      leaf config-merge {
        type empty;
      }
      leaf enable {
        type empty;
      }
      list primary {
        // NCS patched for predictable order
        ordered-by user;
        tailf:cli-suppress-mode;
        key "ip-address";
        leaf ip-address {
          type string;
        }
      }
      leaf priority {
        type string;
      }
    }
  }

  grouping ncs_template_gslb-service-ip-grouping {
    list service-ip {
      // NCS patched for predictable order
      ordered-by user;
      key "name";
      leaf name {
        type string;
      }
      leaf disable {
        type empty;
      }
      leaf ip {
        tailf:cli-drop-node-name;
        type string;
      }
      leaf health-check {
        type string;
      }
      leaf health-check-protocol-disable {
        type empty;
      }
      leaf health-check-disable {
        type empty;
      }

      grouping service-port-grouping {
        leaf number {
          type string;
        }
        leaf udp-tcp {
          tailf:cli-drop-node-name;
          type string;
        }
        leaf service-name {
          type string;
        }
        leaf health-check {
          type string;
        }
        leaf health-check-protocol-disable {
          type empty;
        }
        leaf state {
          tailf:cli-drop-node-name;
          type string;
        }
      }
      list port {
        // NCS patched for predictable order
        ordered-by user;
        key "number service-name";
        uses service-port-grouping;
      }
      list service {
        // NCS patched for predictable order
        ordered-by user;
        key "number service-name";
        uses service-port-grouping;
      }
      container port-name {
        tailf:cli-drop-node-name;
        list port {
          // NCS patched for predictable order
          ordered-by user;
          key "number name";
          leaf number {
            type string;
          }
          leaf udp-tcp {
            tailf:cli-drop-node-name;
            type string;
          }
          leaf name {
            type string;
          }
          leaf health-check {
            type string;
          }
          leaf health-check-protocol-disable {
            type empty;
          }
          leaf state {
            tailf:cli-drop-node-name;
            type string;
          }
        }
      }
    }
  }

  grouping ncs_template_gslb-site-grouping {
    list site {
      // NCS patched for predictable order
      ordered-by user;
      key "name";
      leaf name {
        type string;
      }
      list slb-dev {
        // NCS patched for predictable order
        ordered-by user;
        key "name";
        leaf name {
          type string;
        }
        leaf ip-address {
          tailf:cli-drop-node-name;
          type string;
        }
        list vip-server {
          // NCS patched for predictable order
          ordered-by user;
          tailf:cli-suppress-mode;
          key "name";
          leaf name {
            type string;
          }
        }
      }
    }
  }

  grouping ncs_template_gslb-policy-grouping {
    list policy {
      // NCS patched for predictable order
      ordered-by user;
      key "name";
      leaf name {
        type string;
      }
      container admin-ip {
        leaf top-only {
          type empty;
        }
      }
      leaf admin-ip-enable {
        type empty;
      }
      leaf geographic {
        type string;
      }
      container metric-order {
        leaf-list options {
          // NCS patched for predictable order
          ordered-by user;
          tailf:cli-drop-node-name;
          type string;
        }
      }
      container dns {
        container active-only {
          presence "true";
          leaf fail-safe {
            type empty;
          }
        }
        leaf backup-server {
          type empty;
        }
        container selected-only {
          presence "true";
          leaf number {
            tailf:cli-drop-node-name;
            type string;
          }
        }
        leaf ttl {
          type string;
        }
        container server {
          choice dns-server-choice {
            leaf any {
              type empty;
            }
            leaf-list records {
              // NCS patched for predictable order
              ordered-by user;
              tailf:cli-drop-node-name;
              type string;
            }
          }
        }
        container sticky {
          leaf ip-mask {
            tailf:cli-drop-node-name;
            type string;
          }
          leaf ipv6-mask {
            type string;
          }
          leaf aging-time {
            type string;
          }
        }
      }
      container active-rdt {
        leaf enable {
          type empty;
        }
        leaf single-shot {
          type empty;
        }
      }
    }
  }

  grouping ncs_template_gslb-zone-grouping {
    list zone {
      // NCS patched for predictable order
      ordered-by user;
      key "name";
      leaf name {
        type string;
      }
      container service {
        list service-port {
          // NCS patched for predictable order
          ordered-by user;
          tailf:cli-drop-node-name;
          key "port";
          leaf port {
            type string;
          }
          uses ncs_template_gslb-zone-service-grouping;
        }
        list service-port-name {
          // NCS patched for predictable order
          ordered-by user;
          tailf:cli-drop-node-name;
          key "port name";
          leaf port {
            type string;
          }
          leaf name {
            type string;
          }
          uses ncs_template_gslb-zone-service-grouping;
        }
      }
    }
  }

  grouping ncs_template_gslb-grouping {
    container gslb {
      uses ncs_template_gslb-service-ip-grouping;
      uses ncs_template_gslb-group-grouping;
      uses ncs_template_gslb-site-grouping;
      uses ncs_template_gslb-policy-grouping;
      uses ncs_template_gslb-zone-grouping;
      container protocol {
        container enable {
          leaf controller {
            type empty;
          }
          leaf device {
            type empty;
          }
        }
      }
      container active-rdt {
        leaf icmp {
          type empty;
        }
      }
    }
  }

  grouping ncs_template_bw-list-grouping {
    list bw-list {
      // NCS patched for predictable order
      ordered-by user;
      tailf:cli-suppress-mode;
      key "name";
      leaf name {
        type string;
      }
      leaf import-info {
        type string;
      }
    }
    list import-info {
      // NCS patched for predictable order
      ordered-by user;
      tailf:cli-suppress-mode;
      key "name";
      leaf name {
        type string;
      }
      leaf url {
        type string;
      }
      leaf username {
        type string;
      }
      leaf password {
        type string;
      }
    }
  }

  grouping ncs_template_aflex-grouping {
    list aflex {
      // NCS patched for predictable order
      ordered-by user;
      key "name";
      leaf name {
        type string;
      }
      leaf script {
        type string;
      }
    }
  }

  grouping ncs_template_action-grouping {
    list action {
      // NCS patched for predictable order
      ordered-by user;
      tailf:cli-suppress-mode;
      key "type";
      leaf type {
        type string;
      }
      leaf pool {
        type string;
      }
      leaf domain {
        type string;
      }
    }
    leaf no-action {
      type empty;
    }
  }

  grouping ncs_template_port-grouping {
    list port {
      // NCS patched for predictable order
      ordered-by user;
      tailf:cli-suppress-mode;
      key "id";
      leaf id {
        type string;
      }
      // NCS expand uses statement
      list action {
        // NCS patched for predictable order
        ordered-by user;
        tailf:cli-suppress-mode;
        key "type";
        leaf type {
          type string;
        }
        leaf pool {
          type string;
        }
        leaf domain {
          type string;
        }
      }
      leaf no-action {
        type empty;
      }
    }
  }

  grouping ncs_template_system-jumbo-global-grouping {
    container system-jumbo-global {
      leaf enable-jumbo {
        type empty;
      }
    }
  }

  grouping ncs_template_hd-monitor-grouping {
    container hd-monitor {
      leaf enable {
        type empty;
      }
    }
  }

  grouping ncs_template_timezone-grouping {
    container timezone {
      leaf timezone {
        tailf:cli-drop-node-name;
        type string;
      }
      leaf nodst {
        type empty;
      }
    }
  }

  grouping ncs_template_clock-grouping {
    container clock {
      uses ncs_template_timezone-grouping;
      leaf nodst {
        type empty;
      }
    }
  }

  grouping ncs_template_timezone-nodst-grouping {
    container timezone-nodst {
      tailf:cli-drop-node-name;
      uses ncs_template_timezone-grouping;
      leaf nodst {
        type empty;
      }
    }
  }

  grouping ncs_template_ntp-grouping {
    container ntp {
      list server {
        // NCS patched for predictable order
        ordered-by user;
        key "name";
        leaf name {
          type string;
        }
        leaf interval {
          tailf:cli-drop-node-name;
          type string;
        }
        leaf prefer {
          type empty;
        }
      }
    }
  }

  grouping ncs_template_netflow-grouping {
    container netflow {
      container common {
        leaf max-packet-queue-time {
          type string;
        }
      }
      list monitor {
        // NCS patched for predictable order
        ordered-by user;
        key "name";
        leaf name {
          type string;
        }
        container destination {
          leaf ip {
            tailf:cli-drop-node-name;
            type string;
          }
          leaf port {
            tailf:cli-drop-node-name;
            type string;
          }
        }
        leaf flow-timeout {
          type string;
        }
        leaf protocol {
          type string;
        }
        list record {
          // NCS patched for predictable order
          ordered-by user;
          tailf:cli-suppress-mode;
          key "name";
          leaf name {
            type string;
          }
          leaf events {
            tailf:cli-drop-node-name;
            type string;
          }
        }
        container resend-template {
          leaf records {
            type string;
          }
          leaf timeout {
            type string;
          }
        }

        grouping sample-grouping {
          container sample {
            list ve {
              // NCS patched for predictable order
              ordered-by user;
              tailf:cli-suppress-mode;
              key "id";
              leaf id {
                type string;
              }
            }
          }
        }
        uses sample-grouping;

        grouping source-address-grouping {
          container source-address {
            leaf ip {
              type string;
            }
            leaf ipv6 {
              type string;
            }
          }
        }
        uses source-address-grouping;
        leaf source-ip-use-mgmt {
          type empty;
        }
        list device-context {
          // NCS patched for predictable order
          ordered-by user;
          key "id";
          leaf id {
            type string;
          }
          uses sample-grouping;
          uses source-address-grouping;
        }
      }
    }
  }

  grouping ncs_template_trunk-grouping {
    list trunk {
      // NCS patched for predictable order
      ordered-by user;
      key "id";
      leaf id {
        type string;
      }
      leaf-list ethernet {
        // NCS patched for predictable order
        ordered-by user;
        tailf:cli-range-list-syntax;
        type string;
      }
      container disable {
        leaf-list ethernet {
          // NCS patched for predictable order
          ordered-by user;
          tailf:cli-range-list-syntax;
          type string;
        }
      }
      leaf ports-threshold {
        type string;
      }
      leaf port-threshold-timer {
        type string;
      }
      leaf name {
        type string;
      }
    }
  }

  grouping ncs_template_class-list-grouping {
    list class-list {
      // NCS patched for predictable order
      ordered-by user;
      key "name";
      leaf name {
        type string;
      }
      leaf cl-type {
        tailf:cli-drop-node-name;
        type string;
      }
      choice v4v6str-choice {
        list str {
          // NCS patched for predictable order
          ordered-by user;
          tailf:cli-suppress-mode;
          key "str";
          leaf str {
            type string;
          }
          uses ncs_template_lid-grouping;
          leaf string {
            tailf:cli-drop-node-name;
            type string;
          }
        }
        list v4 {
          // NCS patched for predictable order
          ordered-by user;
          tailf:cli-drop-node-name;
          tailf:cli-suppress-mode;
          key "ip";
          leaf ip {
            type string;
          }
          uses ncs_template_lid-grouping;
        }
        list v6 {
          // NCS patched for predictable order
          ordered-by user;
          tailf:cli-drop-node-name;
          tailf:cli-suppress-mode;
          key "ip";
          leaf ip {
            type string;
          }
          uses ncs_template_lid-grouping;
        }
      }
    }
  }

  grouping ncs_template_class-list-group-grouping {
    list class-list-group {
      // NCS patched for predictable order
      ordered-by user;
      key "name";
      leaf name {
        type string;
      }
      list sequence-number {
        // NCS patched for predictable order
        ordered-by user;
        tailf:cli-suppress-mode;
        key "id";
        leaf id {
          type string;
        }
        leaf host-url {
          tailf:cli-drop-node-name;
          type string;
        }
        choice string-choice {
          leaf contains {
            type string;
          }
          leaf ends-with {
            type string;
          }
          leaf equals {
            type string;
          }
          leaf starts-with {
            type string;
          }
        }
        leaf lid {
          type string;
        }
      }
    }
  }

  grouping ncs_template_tacacs-server-grouping {
    container tacacs-server {
      list host {
        // NCS patched for predictable order
        ordered-by user;
        tailf:cli-suppress-mode;
        key "name";
        leaf name {
          type string;
        }
        container secret {
          leaf encrypted {
            type empty;
          }
          leaf secret {
            tailf:cli-drop-node-name;
            type string;
          }
        }
        leaf port {
          type string;
        }
        leaf timeout {
          type string;
        }
      }
    }
  }

  grouping ncs_template_radius-server-grouping {
    container radius-server {
      list host {
        // NCS patched for predictable order
        ordered-by user;
        tailf:cli-suppress-mode;
        key "name";
        leaf name {
          type string;
        }
        container secret {
          leaf cleartext {
            tailf:cli-drop-node-name;
            type string;
          }
          leaf secret-encrypted {
            type string;
          }
          leaf auth-port {
            type string;
          }
          leaf acct-port {
            type string;
          }
          leaf timeout {
            type string;
          }
        }
      }
    }
  }

  grouping ncs_template_authentication-grouping {
    container authentication {
      container enable {
        choice authetication-enable-choice {
          container local {
            leaf tacplus {
              type empty;
            }
          }
          container tacplus {
            presence "true";
            leaf local {
              type empty;
            }
          }
        }
      }
      leaf-list type {
        // NCS patched for predictable order
        ordered-by user;
        type string;
      }
      leaf mode {
        type string;
      }
      container console {
        leaf-list type {
          // NCS patched for predictable order
          ordered-by user;
          type string;
        }
      }
      leaf disable-local {
        type empty;
      }
      container login {
        leaf privilege-mode {
          type empty;
        }
      }
    }
  }

  grouping ncs_template_vlan-grouping {
    list vlan {
      // NCS patched for predictable order
      ordered-by user;
      key "id";
      leaf id {
        type ncs_template_vlan-index;
      }
      container untagged {
        leaf-list ethernet {
          // NCS patched for predictable order
          ordered-by user;
          tailf:cli-range-list-syntax;
          type string;
        }
        leaf trunk {
          type string;
        }
      }
      container tagged {
        leaf-list ethernet {
          // NCS patched for predictable order
          ordered-by user;
          tailf:cli-range-list-syntax;
          type string;
        }
        leaf trunk {
          type string;
        }
      }
      container router-interface {
        leaf ve {
          type ncs_template_vlan-index;
        }
      }
      leaf name {
        type string;
      }
    }
  }

  grouping ncs_template_ipv6-route-grouping {
    container route {
      list route-no-if {
        // NCS patched for predictable order
        ordered-by user;
        tailf:cli-drop-node-name;
        tailf:cli-suppress-mode;
        key "ip forwarding-router";
        leaf ip {
          type string;
        }
        leaf forwarding-router {
          tailf:cli-drop-node-name;
          type string;
        }
        leaf distance {
          tailf:cli-drop-node-name;
          type string;
        }
      }
      list route-if {
        // NCS patched for predictable order
        ordered-by user;
        tailf:cli-drop-node-name;
        tailf:cli-suppress-mode;
        key "ip forwarding-router interface-type interface-nr";
        leaf ip {
          type string;
        }
        leaf forwarding-router {
          tailf:cli-drop-node-name;
          type string;
        }
        leaf interface-type {
          type string;
        }
        leaf interface-nr {
          type string;
        }
        leaf distance {
          tailf:cli-drop-node-name;
          type string;
        }
      }
    }
  }

  grouping ncs_template_ipv6-grouping {
    container ipv6 {
      uses ncs_template_ipv6-route-grouping;
      container nat {
        list pool {
          // NCS patched for predictable order
          ordered-by user;
          tailf:cli-suppress-mode;
          key "name";
          leaf name {
            type string;
          }
          leaf ipstart {
            // NCS drop mandatory statement
            tailf:cli-drop-node-name;
            type string;
          }
          leaf ipend {
            // NCS drop mandatory statement
            tailf:cli-drop-node-name;
            type string;
          }
          leaf netmask {
            // NCS drop mandatory statement
            type string;
          }
        }
      }
      list access-list {
        // NCS patched for predictable order
        ordered-by user;
        key "id";
        leaf id {
          type string;
        }
        list rules {
          // NCS patched for predictable order
          ordered-by user;
          tailf:cli-suppress-mode;
          tailf:cli-drop-node-name;
          key "acc-type txt";
          leaf acc-type {
            type string;
          }
          leaf txt {
            type string;
          }
        }
        list remark {
          // NCS patched for predictable order
          ordered-by user;
          tailf:cli-suppress-mode;
          key "name";
          leaf name {
            type string;
          }
        }
      }
      list prefix-list {
        // NCS patched for predictable order
        ordered-by user;
        tailf:cli-suppress-mode;
        key "name seq";
        leaf name {
          type string;
        }
        leaf seq {
          type string;
        }
        choice permit-deny {
          leaf permit {
            type string;
          }
          leaf deny {
            type string;
          }
        }
      }
    }
  }

  grouping ncs_template_nat64-grouping {
    container nat64 {
      uses ncs_template_algs;
      leaf user-quota-prefix-length {
        type string;
      }
      container inside {
        container source {
          leaf class-list {
            type string;
          }
        }
      }
      leaf prefix {
        type string;
      }
    }
  }

  grouping ncs_template_lsn-lid-grouping {
    list lsn-lid {
      // NCS patched for predictable order
      ordered-by user;
      key "lsn-lid-id";
      leaf lsn-lid-id {
        type string;
      }
      leaf name {
        type string;
      }
      leaf source-nat-pool {
        type string;
      }
      container user-quota {
        leaf session {
          type string;
        }
      }
      leaf respond-to-user-mac {
        type empty;
      }
    }
  }

  grouping ncs_template_ha-grouping {
    container ha {
      leaf arp-retry {
        type string;
      }
      container check {
        list gateway {
          // NCS patched for predictable order
          ordered-by user;
          key "ip";
          tailf:cli-suppress-mode;
          leaf ip {
            type string;
          }
        }
        list route {
          // NCS patched for predictable order
          ordered-by user;
          key "ip mask gateway distance protocol priority-cost";
          unique "ip mask gateway distance protocol";
          tailf:cli-suppress-mode;
          leaf ip {
            type string;
          }
          leaf mask {
            type ncs_template_ipv4-mask;
          }
          leaf gateway {
            type string;
          }
          leaf distance {
            type string;
          }
          leaf protocol {
            type string;
          }
          leaf priority-cost {
            type string;
          }
        }
        container vlan {
          leaf vlan-id {
            tailf:cli-drop-node-name;
            type ncs_template_vlan-index;
          }
          leaf timeout {
            // NCS drop must statement
            type string;
          }
        }
      }
      container conn-mirror {
        leaf ip {
          type string;
        }
      }
      container force-self-standby {
        list HA-group-id {
          // NCS patched for predictable order
          ordered-by user;
          key "id persistent";
          tailf:cli-suppress-mode;
          leaf id {
            type string;
          }
          leaf persistent {
            type string;
          }
        }
      }
      leaf forward-l4-packet-on-standby {
        type empty;
      }
      container id {
        leaf id {
          tailf:cli-drop-node-name;
          type string;
        }
        leaf set-id {
          type string;
        }
      }
      list group {
        // NCS patched for predictable order
        ordered-by user;
        tailf:cli-suppress-mode;
        key "id";
        leaf id {
          type string;
        }
        leaf priority {
          // NCS drop must statement
          type string;
        }
      }
      container inline-mode {
        presence "true";
        leaf preferred-port {
          type string;
        }
      }
      container interface {
        list ethernet {
          // NCS patched for predictable order
          ordered-by user;
          tailf:cli-suppress-mode;
          key "id";
          leaf id {
            type ncs_template_ethernet-index;
          }
          leaf type {
            tailf:cli-drop-node-name;
            type string;
          }
          choice xx {
            leaf no-heartbeat {
              type empty;
            }
            leaf vlan {
              type string;
            }
          }
        }
      }
      leaf preemption-enable {
        type empty;
      }
      leaf timeout-retry-count {
        type string;
      }
    }
  }

  grouping ncs_template_floating-ip-grouping {
    container floating-ip {
      list ipv4 {
        // NCS patched for predictable order
        ordered-by user;
        tailf:cli-suppress-mode;
        tailf:cli-drop-node-name;
        key "ip ha-group";
        leaf ip {
          type string;
        }
        leaf ha-group {
          type string;
        }
      }
      list ipv6 {
        // NCS patched for predictable order
        ordered-by user;
        tailf:cli-suppress-mode;
        tailf:cli-drop-node-name;
        key "ip ha-group";
        leaf ip {
          type string;
        }
        leaf ha-group {
          type string;
        }
        leaf anycast {
          type empty;
        }
        choice ipv6-interface {
          leaf ethernet {
            // NCS drop must statement
            type ncs_template_ethernet-index;
          }
          leaf trunk {
            type string;
          }
          leaf ve {
            // NCS drop must statement
            type ncs_template_vlan-index;
          }
        }
      }
    }
  }

  grouping ncs_template_glid-grouping {
    list glid {
      // NCS patched for predictable order
      ordered-by user;
      key "limit-id";
      leaf limit-id {
        type string;
      }
      container dns {
        leaf cache-leaf {
          tailf:cli-drop-node-name;
          type string;
        }
        container ttl {
          leaf ttl-value {
            tailf:cli-drop-node-name;
            type string;
          }
          leaf honor-server-response-ttl {
            type empty;
          }
        }
      }
      container over-limit-action {
        leaf over-limit-action-choice {
          tailf:cli-drop-node-name;
          type string;
        }
        leaf lockout {
          type string;
        }
        leaf lockout-val {
          tailf:cli-drop-node-name;
          type string;
        }
        leaf log {
          type empty;
        }
        leaf log-val {
          tailf:cli-drop-node-name;
          type string;
        }
      }
      leaf conn-limit {
        type string;
      }
      container conn-rate-limit {
        leaf limit {
          tailf:cli-drop-node-name;
          type string;
        }
        leaf per {
          // NCS drop must statement
          type string;
        }
      }
      leaf request-limit {
        type string;
      }
      container request-rate-limit {
        leaf limit {
          tailf:cli-drop-node-name;
          type string;
        }
        leaf per {
          // NCS drop must statement
          type string;
        }
      }
      leaf use-nat-pool {
        type string;
      }
    }
  }

  grouping ncs_template_gslb-zone-service-grouping {
    leaf policy {
      type string;
    }
    list dns-a-record {
      // NCS patched for predictable order
      ordered-by user;
      tailf:cli-suppress-mode;
      key "name";
      leaf name {
        type string;
      }
      leaf as-backup {
        type empty;
      }
      leaf port-service-name {
        tailf:cli-drop-node-name;
        type string;
      }
      leaf weight {
        type string;
      }
      container static {
        presence "true";
        leaf admin-ip {
          type string;
        }
      }
    }
  }

  grouping ncs_template_logging-grouping {
    container logging {
      container auditlog {
        leaf host {
          type string;
        }
        leaf facility {
          type string;
        }
      }
      container buffered {
        presence "true";
        leaf size {
          tailf:cli-drop-node-name;
          type string;
        }
        leaf severity {
          tailf:cli-drop-node-name;
          type string;
        }
      }
      leaf console {
        type string;
      }
      container email {
        container buffer {
          choice buffer-choice {
            leaf number {
              type string;
            }
            leaf time {
              type string;
            }
          }
        }
        leaf severity {
          tailf:cli-drop-node-name;
          type string;
        }
      }
      leaf-list email-address {
        // NCS patched for predictable order
        ordered-by user;
        type string;
      }
      leaf export {
        type empty;
      }
      leaf facility {
        type string;
      }
      leaf syslog {
        type string;
      }
      leaf trap {
        type string;
      }
      choice host-choice {
        container host-list {
          tailf:cli-drop-node-name;
          list host {
            // NCS patched for predictable order
            ordered-by user;
            tailf:cli-suppress-mode;
            key "hosts";
            leaf hosts {
              type string;
            }
            choice use-mgmt-port-choice {
              container port {
                leaf number {
                  tailf:cli-drop-node-name;
                  type string;
                }
                leaf tcp {
                  type empty;
                }
              }
              container use-mgmt-port {
                presence "true";
                leaf port {
                  type string;
                }
                leaf tcp {
                  type empty;
                }
              }
            }
          }
        }
        container host {
          leaf-list hosts {
            // NCS patched for predictable order
            ordered-by user;
            tailf:cli-drop-node-name;
            type string;
          }
          leaf port {
            type string;
          }
        }
        container host-alt {
          tailf:cli-drop-node-name;
          container host {
            leaf partition {
              type string;
            }
          }
        }
      }
      leaf monitor {
        type string;
      }
    }
  }

  grouping ncs_template_snmp-server-grouping {
    container snmp-server {
      container enable {
        leaf enabled {
          tailf:cli-drop-node-name;
          type empty;
        }
        leaf service {
          type empty;
        }
        container traps {
          leaf enabled {
            tailf:cli-drop-node-name;
            type empty;
          }
          leaf all {
            type empty;
          }
          container routing {
            container ospf {
              choice routing-choice {
                leaf-list ospf-traps {
                  // NCS patched for predictable order
                  ordered-by user;
                  tailf:cli-drop-node-name;
                  type string;
                }
                leaf all {
                  type empty;
                }
              }
            }
            container bgp {
              leaf bgpBackwardTransNotification {
                type empty;
              }
              leaf bgpEstablishedNotification {
                type empty;
              }
            }
          }
          container lsn {
            leaf all {
              type empty;
            }
          }
          container snmp {
            leaf enabled {
              tailf:cli-drop-node-name;
              type empty;
            }
            leaf all {
              type empty;
            }
            leaf linkdown {
              type empty;
            }
            leaf linkup {
              type empty;
            }
          }
          container ha {
            leaf enabled {
              tailf:cli-drop-node-name;
              type empty;
            }
            leaf active {
              type empty;
            }
            leaf active-active {
              type empty;
            }
            leaf standby {
              type empty;
            }
            leaf vrrp {
              type empty;
            }
          }
          container network {
            leaf enabled {
              tailf:cli-drop-node-name;
              type empty;
            }
            leaf trunk-port-threshold {
              type empty;
            }
          }
          container slb {
            leaf enabled {
              tailf:cli-drop-node-name;
              type empty;
            }
            leaf all {
              type empty;
            }
            leaf application-buffer-limit {
              type empty;
            }
            leaf server-conn-limit {
              type empty;
            }
            leaf server-conn-resume {
              type empty;
            }
            leaf server-down {
              type empty;
            }
            leaf server-up {
              type empty;
            }
            leaf service-conn-limit {
              type empty;
            }
            leaf service-conn-resume {
              type empty;
            }
            leaf service-down {
              type empty;
            }
            leaf service-up {
              type empty;
            }
            leaf vip-connlimit {
              type empty;
            }
            leaf vip-connratelimit {
              type empty;
            }
            leaf vip-port-connlimit {
              type empty;
            }
            leaf vip-port-connratelimit {
              type empty;
            }
            leaf vip-port-down {
              type empty;
            }
            leaf vip-port-up {
              type empty;
            }
          }
          container system {
            leaf enabled {
              tailf:cli-drop-node-name;
              type empty;
            }
            leaf all {
              type empty;
            }
            leaf control-cpu-high {
              type empty;
            }
            leaf data-cpu-high {
              type empty;
            }
            leaf fan {
              type empty;
            }
            leaf high-disk-use {
              type empty;
            }
            leaf high-memory-use {
              type empty;
            }
            leaf high-temp {
              type empty;
            }
            leaf packet-drop {
              type empty;
            }
            leaf power {
              type empty;
            }
            leaf pri-disk {
              type empty;
            }
            leaf restart {
              type empty;
            }
            leaf sec-disk {
              type empty;
            }
            leaf shutdown {
              type empty;
            }
            leaf start {
              type empty;
            }
          }
          container vrrp-a {
            leaf active {
              type empty;
            }
            leaf all {
              type empty;
            }
            leaf standby {
              type empty;
            }
          }
        }
      }
      leaf location {
        type string;
      }
      list user {
        // NCS patched for predictable order
        ordered-by user;
        tailf:cli-suppress-mode;
        key "name group type";
        leaf name {
          type string;
        }
        leaf group {
          type string;
        }
        leaf type {
          type string;
        }
        container auth {
          leaf mac {
            tailf:cli-drop-node-name;
            type string;
          }
          leaf cleartext {
            tailf:cli-drop-node-name;
            type string;
          }
        }
      }
      list view {
        // NCS patched for predictable order
        ordered-by user;
        key "name miboid";
        tailf:cli-suppress-mode;
        leaf name {
          type string;
        }
        leaf miboid {
          type string;
        }
        leaf included-excluded {
          tailf:cli-drop-node-name;
          type string;
        }
      }
      list group {
        // NCS patched for predictable order
        ordered-by user;
        tailf:cli-suppress-mode;
        key "name";
        leaf name {
          type string;
        }
        container v3 {
          container auth {
            leaf read {
              type string;
            }
          }
        }
      }
      container SNMPv1-v2c {
        list user {
          // NCS patched for predictable order
          ordered-by user;
          key "name";
          leaf name {
            type string;
          }
          container community {
            leaf read {
              type string;
            }
          }
          uses ncs_template_snmp-remote-grouping;
        }
      }
      container SNMPv3 {
        list user {
          // NCS patched for predictable order
          ordered-by user;
          tailf:cli-suppress-mode;
          key "name";
          leaf name {
            type string;
          }
          leaf group {
            type string;
          }
          leaf v3 {
            type empty;
          }
          choice smnp-server-v3-user-auth-choice {
            container auth {
              leaf hmac {
                tailf:cli-drop-node-name;
                type string;
              }
              leaf password {
                tailf:cli-drop-node-name;
                type string;
              }
              container priv {
                leaf algo {
                  tailf:cli-drop-node-name;
                  type string;
                }
                leaf passphrase {
                  tailf:cli-drop-node-name;
                  type string;
                }
              }
            }
            leaf noauth {
              type empty;
            }
          }
        }
      }
      container community-mode {
        tailf:cli-drop-node-name;
        list community {
          // NCS patched for predictable order
          ordered-by user;
          key "read";
          leaf read {
            type string;
          }
          uses ncs_template_snmp-remote-grouping;
        }
      }
      list community {
        // NCS patched for predictable order
        ordered-by user;
        key "read remote";
        tailf:cli-suppress-mode;
        leaf read {
          type string;
        }
        leaf remote {
          type string;
        }
        leaf oid {
          type string;
        }
        leaf mask {
          tailf:cli-drop-node-name;
          type string;
        }
      }
      leaf contact {
        type string;
      }
      list host {
        // NCS patched for predictable order
        ordered-by user;
        tailf:cli-suppress-mode;
        key "ip version";
        leaf ip {
          type string;
        }
        leaf version {
          type string;
        }
        leaf community-string {
          tailf:cli-drop-node-name;
          // NCS drop mandatory statement
          type string;
        }
        leaf udp-port {
          type string;
        }
      }
    }
  }

  grouping ncs_template_audit-grouping {
    container audit {
      container enable {
        leaf privilege {
          type empty;
        }
      }
      leaf size {
        type string;
      }
    }
  }

  grouping ncs_template_harmony-controller-grouping {
    container harmony-controller {
      leaf config-replace {
        type string;
      }
      container profile {
        presence "true";
        container host {
          leaf host-id {
            tailf:cli-drop-node-name;
            type string;
          }
          leaf use-mgmt-port {
            type empty;
          }
          leaf port {
            type string;
          }
        }
        leaf provider {
          type string;
        }
        leaf user-name {
          type string;
        }
        leaf cluster-name {
          type string;
        }
        leaf cluster-id {
          type string;
        }
        leaf password {
          type string;
        }
        leaf region {
          type string;
        }
        leaf availability-zone {
          type string;
        }
        leaf thunder-mgmt-ip {
          type string;
        }
        leaf reg-dereg {
          tailf:cli-drop-node-name;
          type string;
        }
        list device-context {
          // NCS patched for predictable order
          ordered-by user;
          key "id";
          leaf id {
            type string;
          }
          leaf thunder-mgmt-ip {
            type string;
          }
        }
      }
    }
  }

  grouping ncs_template_terminal-grouping {
    container terminal {
      leaf auto-size {
        type empty;
      }
      leaf editing {
        type empty;
      }
      container prompt {
        leaf hostname {
          type empty;
        }
        leaf ha-status {
          type empty;
        }
      }
      container history {
        leaf size {
          type string;
        }
      }
      leaf idle-timeout {
        type string;
      }
      leaf length {
        type string;
      }
      leaf no-ha-prompt {
        type empty;
      }
      leaf width {
        type string;
      }
    }
  }

  grouping ncs_template_web-service-grouping {
    container web-service {
      leaf auto-redir {
        type string;
      }
      container auto-redirt {
        leaf disable {
          type empty;
        }
      }
      container axapi-timeout-policy {
        leaf idle {
          type string;
        }
      }
      container timeout-policy {
        leaf idle {
          type string;
        }
      }
      leaf gui-session-limit {
        type string;
      }
      container gui-timeout-policy {
        leaf idle {
          type string;
        }
      }
      leaf login-message {
        type string;
      }
      leaf pre-login-message {
        type string;
      }
    }
  }

  grouping ncs_template_multi-config-grouping {
    container multi-config {
      leaf enable {
        type empty;
      }
    }
  }

  grouping ncs_template_banner-grouping {
    container banner {
      container login {
        choice text-multi {
          leaf text {
            tailf:cli-drop-node-name;
            type string;
          }
          leaf multi-line {
            type string;
          }
        }
      }
      container exec {
        choice text-multi {
          leaf text {
            tailf:cli-drop-node-name;
            type string;
          }
          leaf multi-line {
            type string;
          }
        }
      }
    }
  }

  grouping ncs_template_preferred-session-sync-port-grouping {
    container preferred-session-sync-port {
      list trunk {
        // NCS patched for predictable order
        ordered-by user;
        tailf:cli-suppress-mode;
        key "id";
        leaf id {
          type string;
        }
        leaf vlan {
          type string;
        }
      }
      list ethernet {
        // NCS patched for predictable order
        ordered-by user;
        tailf:cli-suppress-mode;
        key "id";
        leaf id {
          type ncs_template_ethernet-index;
        }
        leaf vlan {
          type string;
        }
      }
    }
  }

  grouping ncs_template_vrrp-a-grouping {
    container vrrp-a {

      grouping vrrp-a-common-grouping {
        leaf device-id {
          // NCS drop tailf-common:cli-diff-create-before statement
          // NCS drop tailf-common:cli-diff-create-before statement
          type string;
        }
        leaf disable-default-vrid {
          type empty;
        }
        leaf set-id {
          // NCS drop tailf-common:cli-diff-create-before statement
          // NCS drop tailf-common:cli-diff-create-before statement
          type string;
        }
        leaf hello-interval {
          type string;
        }
        leaf preemption-delay {
          type string;
        }
        leaf track-event-delay {
          type string;
        }
        leaf restart-time {
          type string;
        }
        leaf hostid-append-to-vrid {
          type string;
        }
        leaf enable {
          tailf:cli-drop-node-name;
          type string;
        }
      }
      uses vrrp-a-common-grouping;
      container common {
        presence "common-presence";
        uses vrrp-a-common-grouping;
      }
      list vrid {
        // NCS patched for predictable order
        ordered-by user;
        key "id";
        leaf id {
          type string;
        }

        grouping vrrp-a-vrid-grouping {
          list floating-ip {
            // NCS patched for predictable order
            ordered-by user;
            tailf:cli-suppress-mode;
            key "floating-ip-address";
            leaf floating-ip-address {
              tailf:cli-drop-node-name;
              type string;
            }
          }
          leaf priority {
            type string;
          }
          container preempt-mode {
            choice preempt-choice {
              leaf disable {
                type empty;
              }
              leaf threshold {
                type string;
              }
            }
          }
          container blade-parameters {
            leaf priority {
              type string;
            }
            container tracking-options {
              list gateway {
                // NCS patched for predictable order
                ordered-by user;
                tailf:cli-suppress-mode;
                key "address";
                leaf address {
                  type string;
                }
                uses ncs_template_priority-cost;
              }
              container interface {
                list ethernet {
                  // NCS patched for predictable order
                  ordered-by user;
                  tailf:cli-suppress-mode;
                  key "id";
                  leaf id {
                    type ncs_template_ethernet-index;
                  }
                  leaf priority-cost {
                    // NCS drop mandatory statement
                    type string;
                  }
                }
              }
              list route {
                // NCS patched for predictable order
                ordered-by user;
                tailf:cli-suppress-mode;
                key "ip mask";
                leaf ip {
                  type string;
                }
                leaf mask {
                  type ncs_template_ipv4-mask;
                }
                uses ncs_template_priority-cost;
                leaf distance {
                  type string;
                }
                leaf gateway {
                  type string;
                }
                leaf protocol {
                  type string;
                }
              }
              list trunk {
                // NCS patched for predictable order
                ordered-by user;
                tailf:cli-suppress-mode;
                key "id";
                leaf id {
                  type string;
                }
                uses ncs_template_priority-cost;
                leaf per-port-pri {
                  type string;
                }
              }
              list vlan {
                // NCS patched for predictable order
                ordered-by user;
                tailf:cli-suppress-mode;
                key "id";
                leaf id {
                  type ncs_template_vlan-index;
                }
                leaf timeout {
                  type string;
                }
                uses ncs_template_priority-cost;
              }
            }
          }
        }
        // NCS expand uses statement
        list floating-ip {
          // NCS patched for predictable order
          ordered-by user;
          tailf:cli-suppress-mode;
          key "floating-ip-address";
          leaf floating-ip-address {
            tailf:cli-drop-node-name;
            type string;
          }
        }
        leaf priority {
          type string;
        }
        container preempt-mode {
          choice preempt-choice {
            leaf disable {
              type empty;
            }
            leaf threshold {
              type string;
            }
          }
        }
        container blade-parameters {
          leaf priority {
            type string;
          }
          container tracking-options {
            list gateway {
              // NCS patched for predictable order
              ordered-by user;
              tailf:cli-suppress-mode;
              key "address";
              leaf address {
                type string;
              }
              // NCS expand uses statement
              leaf priority-cost {
                // NCS drop mandatory statement
                type string;
              }
            }
            container interface {
              list ethernet {
                // NCS patched for predictable order
                ordered-by user;
                tailf:cli-suppress-mode;
                key "id";
                leaf id {
                  type ncs_template_ethernet-index;
                }
                leaf priority-cost {
                  // NCS drop mandatory statement
                  type string;
                }
              }
            }
            list route {
              // NCS patched for predictable order
              ordered-by user;
              tailf:cli-suppress-mode;
              key "ip mask";
              leaf ip {
                type string;
              }
              leaf mask {
                type ncs_template_ipv4-mask;
              }
              // NCS expand uses statement
              leaf priority-cost {
                // NCS drop mandatory statement
                type string;
              }
              leaf distance {
                type string;
              }
              leaf gateway {
                type string;
              }
              leaf protocol {
                type string;
              }
            }
            list trunk {
              // NCS patched for predictable order
              ordered-by user;
              tailf:cli-suppress-mode;
              key "id";
              leaf id {
                type string;
              }
              // NCS expand uses statement
              leaf priority-cost {
                // NCS drop mandatory statement
                type string;
              }
              leaf per-port-pri {
                type string;
              }
            }
            list vlan {
              // NCS patched for predictable order
              ordered-by user;
              tailf:cli-suppress-mode;
              key "id";
              leaf id {
                type ncs_template_vlan-index;
              }
              leaf timeout {
                type string;
              }
              // NCS expand uses statement
              leaf priority-cost {
                // NCS drop mandatory statement
                type string;
              }
            }
          }
        }
        list device-context {
          // NCS patched for predictable order
          ordered-by user;
          key "id";
          leaf id {
            type string;
          }
          // NCS expand uses statement
          list floating-ip {
            // NCS patched for predictable order
            ordered-by user;
            tailf:cli-suppress-mode;
            key "floating-ip-address";
            leaf floating-ip-address {
              tailf:cli-drop-node-name;
              type string;
            }
          }
          leaf priority {
            type string;
          }
          container preempt-mode {
            choice preempt-choice {
              leaf disable {
                type empty;
              }
              leaf threshold {
                type string;
              }
            }
          }
          container blade-parameters {
            leaf priority {
              type string;
            }
            container tracking-options {
              list gateway {
                // NCS patched for predictable order
                ordered-by user;
                tailf:cli-suppress-mode;
                key "address";
                leaf address {
                  type string;
                }
                // NCS expand uses statement
                leaf priority-cost {
                  // NCS drop mandatory statement
                  type string;
                }
              }
              container interface {
                list ethernet {
                  // NCS patched for predictable order
                  ordered-by user;
                  tailf:cli-suppress-mode;
                  key "id";
                  leaf id {
                    type ncs_template_ethernet-index;
                  }
                  leaf priority-cost {
                    // NCS drop mandatory statement
                    type string;
                  }
                }
              }
              list route {
                // NCS patched for predictable order
                ordered-by user;
                tailf:cli-suppress-mode;
                key "ip mask";
                leaf ip {
                  type string;
                }
                leaf mask {
                  type ncs_template_ipv4-mask;
                }
                // NCS expand uses statement
                leaf priority-cost {
                  // NCS drop mandatory statement
                  type string;
                }
                leaf distance {
                  type string;
                }
                leaf gateway {
                  type string;
                }
                leaf protocol {
                  type string;
                }
              }
              list trunk {
                // NCS patched for predictable order
                ordered-by user;
                tailf:cli-suppress-mode;
                key "id";
                leaf id {
                  type string;
                }
                // NCS expand uses statement
                leaf priority-cost {
                  // NCS drop mandatory statement
                  type string;
                }
                leaf per-port-pri {
                  type string;
                }
              }
              list vlan {
                // NCS patched for predictable order
                ordered-by user;
                tailf:cli-suppress-mode;
                key "id";
                leaf id {
                  type ncs_template_vlan-index;
                }
                leaf timeout {
                  type string;
                }
                // NCS expand uses statement
                leaf priority-cost {
                  // NCS drop mandatory statement
                  type string;
                }
              }
            }
          }
        }
      }
      container interface {
        list ethernet {
          // NCS patched for predictable order
          ordered-by user;
          tailf:cli-suppress-mode;
          key "id";
          leaf id {
            type ncs_template_ethernet-index;
          }
          choice vrrp-a-ethernet-choice {
            leaf both {
              type empty;
            }
            leaf no-heartbeat {
              type empty;
            }
            container router-interface {
              choice vrrp-a-r-i-choice {
                leaf no-heartbeat {
                  type empty;
                }
                leaf vlan {
                  type string;
                }
              }
            }
            container server-interface {
              presence "true";
              choice vrrp-a-s-i-choice {
                leaf no-heartbeat {
                  type empty;
                }
                leaf vlan {
                  type string;
                }
              }
            }
            leaf vlan {
              type string;
            }
          }
        }
        list trunk {
          // NCS patched for predictable order
          ordered-by user;
          tailf:cli-suppress-mode;
          key "id";
          leaf id {
            type ncs_template_ethernet-index;
          }
          choice vrrp-a-trunk-choice {
            leaf both {
              type empty;
            }
            leaf no-heartbeat {
              type empty;
            }
            container router-interface {
              choice vrrp-a-r-i-choice {
                leaf no-heartbeat {
                  type empty;
                }
                leaf vlan {
                  type string;
                }
              }
            }
            container server-interface {
              presence "true";
              choice vrrp-a-s-i-choice {
                leaf no-heartbeat {
                  type empty;
                }
                leaf vlan {
                  type string;
                }
              }
            }
            leaf vlan {
              type string;
            }
          }
        }
      }
      // NCS expand uses statement
      container preferred-session-sync-port {
        list trunk {
          // NCS patched for predictable order
          ordered-by user;
          tailf:cli-suppress-mode;
          key "id";
          leaf id {
            type string;
          }
          leaf vlan {
            type string;
          }
        }
        list ethernet {
          // NCS patched for predictable order
          ordered-by user;
          tailf:cli-suppress-mode;
          key "id";
          leaf id {
            type ncs_template_ethernet-index;
          }
          leaf vlan {
            type string;
          }
        }
      }
    }
  }

  grouping ncs_template_router-grouping {
    container router {
      list bgp {
        // NCS patched for predictable order
        ordered-by user;
        key "as";
        leaf as {
          type string;
        }
        leaf maximum-paths {
          type string;
        }
        list network {
          // NCS patched for predictable order
          ordered-by user;
          tailf:cli-suppress-mode;
          key "address";
          leaf address {
            type string;
          }
        }

        grouping neighbor-grouping {
          list neighbor {
            // NCS patched for predictable order
            ordered-by user;
            tailf:cli-suppress-mode;
            key "ip";
            leaf ip {
              type string;
            }
            leaf activate {
              type string;
            }
            leaf description {
              type string;
            }
            list distribute-list {
              // NCS patched for predictable order
              ordered-by user;
              key "direction";
              tailf:cli-suppress-mode;
              leaf name {
                tailf:cli-drop-node-name;
                type string;
              }
              leaf direction {
                type string;
              }
            }
            container fall-over {
              leaf bfd {
                type empty;
              }
              leaf multihop {
                type empty;
              }
            }
            leaf maximum-prefix {
              type string;
            }
            leaf next-hop-self {
              type empty;
            }
            leaf password {
              type string;
            }
            container peer-group {
              presence "true";
              leaf name {
                tailf:cli-drop-node-name;
                type string;
              }
            }
            list prefix-list {
              // NCS patched for predictable order
              ordered-by user;
              tailf:cli-suppress-mode;
              key "direction";
              leaf direction {
                type string;
              }
              leaf name {
                tailf:cli-drop-node-name;
                type string;
              }
            }
            leaf remote-as {
              type string;
            }
            leaf remove-private-as {
              type empty;
            }
            list route-map {
              // NCS patched for predictable order
              ordered-by user;
              tailf:cli-suppress-mode;
              key "in-out";
              leaf in-out {
                type string;
              }
              leaf name {
                tailf:cli-drop-node-name;
                type string;
              }
            }
            container update-source {
              leaf address {
                tailf:cli-drop-node-name;
                type string;
              }
              leaf ve {
                type string;
              }
            }
            leaf soft-reconfiguration {
              type string;
            }
            leaf shutdown {
              type string;
            }
          }
        }
        uses neighbor-grouping;

        grouping redistribute-grouping {
          container redistribute {
            container connected {
              presence "true";
              leaf route-map {
                type string;
              }
            }
            container static {
              presence "true";
              leaf route-map {
                type string;
              }
            }
            container ip-nat {
              presence "true";
              leaf route-map {
                type string;
              }
            }
            container vip {
              container only-flagged {
                presence "true";
              }
            }
          }
        }
        uses redistribute-grouping;
        container address-family {
          container ipv6 {
            leaf maximum-paths {
              type string;
            }
            uses neighbor-grouping;
            uses redistribute-grouping;
          }
        }
        container bgp {
          leaf log-neighbor-changes {
            type empty;
          }
          container bestpath {
            leaf as-path {
              type string;
            }
          }
        }
      }
    }
  }

  grouping ncs_template_bfd-grouping {
    container bfd {
      leaf echo {
        type empty;
      }
      leaf enable {
        type empty;
      }
      container interval {
        leaf start {
          tailf:cli-drop-node-name;
          type string;
        }
        leaf min-rx {
          type string;
        }
        leaf multiplier {
          type string;
        }
      }
    }
  }

  grouping ncs_template_lldp-grouping {
    container lldp {
      leaf system-name {
        type string;
      }
      leaf system-description {
        type string;
      }
      leaf-list enable {
        // NCS patched for predictable order
        ordered-by user;
        type string;
      }
      container management-address {
        list ipv4 {
          // NCS patched for predictable order
          ordered-by user;
          tailf:cli-suppress-mode;
          key "address";
          leaf address {
            type string;
          }
        }
        list ipv6 {
          // NCS patched for predictable order
          ordered-by user;
          tailf:cli-suppress-mode;
          key "address";
          leaf address {
            type string;
          }
        }
      }
      container notification {
        leaf interval {
          type string;
        }
      }
    }
  }

  grouping ncs_template_route-map-grouping {
    list route-map {
      // NCS patched for predictable order
      ordered-by user;
      tailf:cli-suppress-mode;
      key "name";
      leaf name {
        type string;
      }

      grouping permit-deny-grouping {
        leaf id {
          type string;
        }

        grouping match-set-grouping {
          container ip {
            container address {
              leaf address {
                tailf:cli-drop-node-name;
                type string;
              }
              leaf prefix-list {
                type string;
              }
            }
            leaf next-hop {
              type string;
            }
          }
          container ipv6 {
            container address {
              leaf address {
                tailf:cli-drop-node-name;
                type string;
              }
              leaf prefix-list {
                type string;
              }
            }
            leaf next-hop {
              type string;
            }
          }
          leaf-list community {
            // NCS patched for predictable order
            ordered-by user;
            type string;
          }
        }
        container match {
          uses match-set-grouping;
        }
        container set {
          uses match-set-grouping;
        }
      }
      list permit {
        // NCS patched for predictable order
        ordered-by user;
        key "id";
        uses permit-deny-grouping;
      }
      list deny {
        // NCS patched for predictable order
        ordered-by user;
        key "id";
        uses permit-deny-grouping;
      }
    }
  }

  grouping ncs_template_device-context-grouping {
    list device-context {
      // NCS patched for predictable order
      ordered-by user;
      key "id";
      leaf id {
        type string;
      }
      uses ncs_template_aflex-grouping;
      uses ncs_template_hostname-grouping;
      // NCS expand uses statement
      container interface {

        grouping lldp-interface-grouping {
          container lldp {
            container enable {
              leaf rx {
                type empty;
              }
              leaf tx {
                type empty;
              }
            }
            leaf notification {
              type string;
            }
            leaf tx-dot1-tlvs {
              type string;
            }
          }
        }
        container management {
          container bcast-rate-limit {
            presence "present";
            leaf rate {
              type string;
            }
          }
          container ip {
            // NCS expand uses statement
            list address {
              // NCS patched for predictable order
              ordered-by user;
              tailf:cli-suppress-mode;
              key "address mask";
              leaf address {
                type string;
              }
              leaf mask {
                type string;
              }
            }
            leaf control-apps-use-mgmt-port {
              type empty;
            }
            leaf default-gateway {
              type string;
            }
          }
          container ipv6 {
            list address {
              // NCS patched for predictable order
              ordered-by user;
              key "ip";
              tailf:cli-suppress-mode;
              leaf ip {
                tailf:cli-drop-node-name;
                type ncs_template_ipv6-prefix;
              }
              leaf link-local {
                type empty;
              }
            }
            leaf default-gateway {
              type string;
            }
          }
          // NCS expand uses statement
          container lldp {
            container enable {
              leaf rx {
                type empty;
              }
              leaf tx {
                type empty;
              }
            }
            leaf notification {
              type string;
            }
            leaf tx-dot1-tlvs {
              type string;
            }
          }
          leaf flow-control {
            type empty;
          }
          container access-list {
            leaf id {
              tailf:cli-drop-node-name;
              type string;
            }
            leaf in {
              // NCS drop must statement
              type empty;
            }
          }
          leaf enabled-disabled {
            tailf:cli-drop-node-name;
            type string;
          }
          leaf duplexity {
            type string;
          }
          leaf mtu {
            type string;
          }
          leaf speed {
            type string;
          }
        }
        list ethernet {
          // NCS patched for predictable order
          ordered-by user;
          key "nr";
          leaf nr {
            type ncs_template_ethernet-index;
          }
          leaf name {
            type string;
          }
          container ip {
            // NCS expand uses statement
            list address {
              // NCS patched for predictable order
              ordered-by user;
              tailf:cli-suppress-mode;
              key "address mask";
              leaf address {
                type string;
              }
              leaf mask {
                type string;
              }
            }
            leaf cache-spoofing-port {
              type empty;
            }
            leaf helper-address {
              type string;
            }
            container nat {
              leaf inside {
                type empty;
              }
              leaf outside {
                type empty;
              }
            }
            container ospf;
            container router {
              container isis {
                presence "true";
                leaf cmds {
                  tailf:cli-drop-node-name;
                  type string;
                }
              }
            }
            leaf allow-promiscuous-vip {
              type empty;
            }
            container tcp {
              leaf syn-cookie {
                type empty;
              }
            }
          }
          container ipv6 {
            container access-list {
              leaf id {
                tailf:cli-drop-node-name;
                type string;
              }
              leaf in {
                // NCS drop must statement
                type empty;
              }
            }
            list address {
              // NCS patched for predictable order
              ordered-by user;
              key "ip";
              tailf:cli-suppress-mode;
              leaf ip {
                tailf:cli-drop-node-name;
                type ncs_template_ipv6-prefix;
              }
              leaf link-local {
                type empty;
              }
              leaf anycast {
                type empty;
              }
            }
            container nat {
              leaf inside {
                type empty;
              }
              leaf outside {
                type empty;
              }
            }
            container ndisc {
              container router-advertisement;
            }
            container ospf;
            container router {
              container isis {
                presence "true";
                leaf cmds {
                  tailf:cli-drop-node-name;
                  type string;
                }
              }
            }
          }
          leaf load-interval {
            type string;
          }
          container access-list {
            leaf id {
              tailf:cli-drop-node-name;
              type string;
            }
            leaf in {
              // NCS drop must statement
              type empty;
            }
          }
          leaf state {
            tailf:cli-drop-node-name;
            type string;
          }
          leaf state-alt {
            tailf:cli-drop-node-name;
            type string;
          }
          leaf duplexity {
            type string;
          }
          leaf cpu-process {
            type empty;
          }
          leaf flow-control {
            type empty;
          }
          container icmp-rate-limit {
            leaf rate {
              tailf:cli-drop-node-name;
              type string;
            }
            leaf lockup {
              // NCS drop must statement
              type string;
            }
            leaf lockup-period {
              // NCS drop must statement
              tailf:cli-drop-node-name;
              type string;
            }
          }
          container ospf;
          container isis;
          leaf l3-vlan-fwd-disable {
            type empty;
          }
          container lacp {
            leaf port-priority {
              type string;
            }
            leaf timeout {
              type string;
            }
            container trunk {
              leaf number {
                tailf:cli-drop-node-name;
                type string;
              }
              leaf admin-key {
                // NCS drop must statement
                type string;
              }
              leaf mode {
                // NCS drop must statement
                type string;
              }
              leaf unidirectional-detection {
                // NCS drop must statement
                type empty;
              }
            }
            container udld-timeout {
              leaf timeout-type {
                tailf:cli-drop-node-name;
                type string;
              }
              leaf milli {
                tailf:cli-drop-node-name;
                type string;
              }
              leaf secs {
                tailf:cli-drop-node-name;
                type string;
              }
            }
          }
          // NCS expand uses statement
          container lldp {
            container enable {
              leaf rx {
                type empty;
              }
              leaf tx {
                type empty;
              }
            }
            leaf notification {
              type string;
            }
            leaf tx-dot1-tlvs {
              type string;
            }
          }
          leaf mtu {
            type string;
          }
          leaf speed {
            type string;
          }
          list trunk-group-list {
            // NCS patched for predictable order
            ordered-by user;
            key "trunk-group-key";
            tailf:cli-drop-node-name;
            leaf trunk-group-key {
              type string;
            }
            leaf trunk-group-id {
              tailf:cli-drop-node-name;
              // NCS drop mandatory statement
              type string;
            }
            leaf trunk-group-type {
              tailf:cli-drop-node-name;
              type string;
            }
          }
        }
        list trunk {
          // NCS patched for predictable order
          ordered-by user;
          key "nr";
          leaf nr {
            type ncs_template_ethernet-index;
          }
          leaf name {
            type string;
          }
          leaf state {
            tailf:cli-drop-node-name;
            type string;
          }
          container icmp-rate-limit {
            leaf rate {
              tailf:cli-drop-node-name;
              type string;
            }
            leaf lockup {
              // NCS drop must statement
              type string;
            }
            leaf lockup-period {
              // NCS drop must statement
              tailf:cli-drop-node-name;
              type string;
            }
          }
          list access-list {
            // NCS patched for predictable order
            ordered-by user;
            tailf:cli-suppress-mode;
            key "id in-type";
            leaf id {
              type string;
            }
            leaf in-type {
              type string;
            }
          }
          container ip {
            list address {
              // NCS patched for predictable order
              ordered-by user;
              key "ip mask";
              tailf:cli-suppress-mode;
              leaf ip {
                type string;
              }
              leaf mask {
                type ncs_template_ipv4-mask;
              }
            }
            leaf allow-promiscuous-vip {
              type empty;
            }
            leaf cache-spoofing-port {
              type empty;
            }
            container nat {
              leaf inside {
                type empty;
              }
              leaf outside {
                type empty;
              }
            }
          }
        }
        list loopback {
          // NCS patched for predictable order
          ordered-by user;
          key "nr";
          leaf nr {
            type ncs_template_ethernet-index;
          }
          container ip {
            // NCS expand uses statement
            list address {
              // NCS patched for predictable order
              ordered-by user;
              tailf:cli-suppress-mode;
              key "address mask";
              leaf address {
                type string;
              }
              leaf mask {
                type string;
              }
            }
            container router {
              choice isis-choice {
                container isis-alt {
                  tailf:cli-drop-node-name;
                  leaf isis {
                    type string;
                  }
                }
                leaf isis {
                  type empty;
                }
              }
            }
          }
          container icmp-rate-limit {
            leaf rate {
              tailf:cli-drop-node-name;
              type string;
            }
            leaf lockup {
              // NCS drop must statement
              type string;
            }
            leaf lockup-period {
              tailf:cli-drop-node-name;
              // NCS drop must statement
              type string;
            }
          }
          leaf state {
            tailf:cli-drop-node-name;
            type string;
          }
        }
        list ve {
          // NCS patched for predictable order
          ordered-by user;
          key "id";
          leaf id {
            type ncs_template_vlan-index;
          }
          leaf name {
            type string;
          }
          container bfd {
            container echo {
              presence "true";
            }
          }
          container icmp-rate-limit {
            leaf rate {
              tailf:cli-drop-node-name;
              type string;
            }
            leaf lockup {
              // NCS drop must statement
              type string;
            }
            leaf lockup-period {
              tailf:cli-drop-node-name;
              // NCS drop must statement
              type string;
            }
          }
          container access-list {
            leaf id {
              tailf:cli-drop-node-name;
              type string;
            }
            leaf in {
              // NCS drop must statement
              type empty;
            }
          }
          leaf l3-vlan-fwd-disable {
            type empty;
          }
          container ip {
            leaf allow-promiscuous-vip {
              type empty;
            }
            leaf cache-spoofing-port {
              type empty;
            }
            leaf helper-address {
              type string;
            }
            container nat {
              leaf inside {
                type empty;
              }
              leaf outside {
                type empty;
              }
            }
            container ospf;
            container router {
              container isis {
                presence "true";
                leaf cmds {
                  tailf:cli-drop-node-name;
                  type string;
                }
              }
            }
            container tcp {
              leaf syn-cookie {
                type empty;
              }
            }
            // NCS expand uses statement
            list address {
              // NCS patched for predictable order
              ordered-by user;
              tailf:cli-suppress-mode;
              key "address mask";
              leaf address {
                type string;
              }
              leaf mask {
                type string;
              }
            }
          }
          container ipv6 {
            container access-list {
              leaf id {
                tailf:cli-drop-node-name;
                type string;
              }
              leaf in {
                // NCS drop must statement
                type empty;
              }
            }
            container nat {
              leaf inside {
                type empty;
              }
              leaf outside {
                type empty;
              }
            }
            container ndisc {
              container router-advertisement;
            }
            container ospf;
            container router {
              container isis {
                presence "true";
                leaf cmds {
                  tailf:cli-drop-node-name;
                  type string;
                }
              }
            }
            list address {
              // NCS patched for predictable order
              ordered-by user;
              key "ip";
              tailf:cli-suppress-mode;
              leaf ip {
                tailf:cli-drop-node-name;
                type ncs_template_ipv6-prefix;
              }
              leaf link-local {
                type empty;
              }
              leaf anycast {
                type empty;
              }
            }
          }
          leaf mtu {
            type string;
          }
          leaf state {
            tailf:cli-drop-node-name;
            type string;
          }
          container isis;
          container ospf;
        }
      }
      container ip {
        uses ncs_template_ip-prefix-list-grouping;
        uses ncs_template_ip-route-grouping;
      }
      container ipv6 {
        uses ncs_template_ipv6-route-grouping;
      }
      uses ncs_template_bfd-grouping;
      uses ncs_template_clock-grouping;
      uses ncs_template_lldp-grouping;
      // NCS expand uses statement
      container vcs {
        leaf state {
          tailf:cli-drop-node-name;
          type string;
        }
        list device {
          // NCS patched for predictable order
          ordered-by user;
          key "id";
          leaf id {
            type string;
          }
          leaf priority {
            type string;
          }
          container interfaces {
            leaf management {
              type empty;
            }
            list ethernet {
              // NCS patched for predictable order
              ordered-by user;
              tailf:cli-suppress-mode;
              key "id";
              leaf id {
                type string;
              }
            }
            list trunk {
              // NCS patched for predictable order
              ordered-by user;
              tailf:cli-suppress-mode;
              key "id";
              leaf id {
                type string;
              }
            }
            list ve {
              // NCS patched for predictable order
              ordered-by user;
              tailf:cli-suppress-mode;
              key "id";
              leaf id {
                type string;
              }
            }
          }
          leaf enable {
            type empty;
          }
        }
        list floating-ip {
          // NCS patched for predictable order
          ordered-by user;
          tailf:cli-suppress-mode;
          key "floating-ip-address";
          leaf floating-ip-address {
            tailf:cli-drop-node-name;
            type string;
          }
          leaf mask {
            tailf:cli-drop-node-name;
            type ncs_template_ipv4-mask;
          }
        }
        leaf ssl-enable {
          type empty;
        }
        leaf failure-retry-count {
          type string;
        }
      }
      uses ncs_template_tftp-grouping;
      uses ncs_template_enable-management-grouping;
      uses ncs_template_disable-management-grouping;
      uses ncs_template_lacp-grouping;
      uses ncs_template_route-map-grouping;
      uses ncs_template_ve-stats-grouping;
      uses ncs_template_bgp-grouping;
      uses ncs_template_router-grouping;
      uses ncs_template_timezone-grouping;
      uses ncs_template_sflow-grouping;
      container vrrp-a {
        // NCS expand uses statement
        container preferred-session-sync-port {
          list trunk {
            // NCS patched for predictable order
            ordered-by user;
            tailf:cli-suppress-mode;
            key "id";
            leaf id {
              type string;
            }
            leaf vlan {
              type string;
            }
          }
          list ethernet {
            // NCS patched for predictable order
            ordered-by user;
            tailf:cli-suppress-mode;
            key "id";
            leaf id {
              type ncs_template_ethernet-index;
            }
            leaf vlan {
              type string;
            }
          }
        }
      }
    }
  }

  grouping ncs_template_vcs-grouping {
    container vcs {
      leaf state {
        tailf:cli-drop-node-name;
        type string;
      }
      list device {
        // NCS patched for predictable order
        ordered-by user;
        key "id";
        leaf id {
          type string;
        }
        leaf priority {
          type string;
        }
        container interfaces {
          leaf management {
            type empty;
          }
          list ethernet {
            // NCS patched for predictable order
            ordered-by user;
            tailf:cli-suppress-mode;
            key "id";
            leaf id {
              type string;
            }
          }
          list trunk {
            // NCS patched for predictable order
            ordered-by user;
            tailf:cli-suppress-mode;
            key "id";
            leaf id {
              type string;
            }
          }
          list ve {
            // NCS patched for predictable order
            ordered-by user;
            tailf:cli-suppress-mode;
            key "id";
            leaf id {
              type string;
            }
          }
        }
        leaf enable {
          type empty;
        }
      }
      list floating-ip {
        // NCS patched for predictable order
        ordered-by user;
        tailf:cli-suppress-mode;
        key "floating-ip-address";
        leaf floating-ip-address {
          tailf:cli-drop-node-name;
          type string;
        }
        leaf mask {
          tailf:cli-drop-node-name;
          type ncs_template_ipv4-mask;
        }
      }
      leaf ssl-enable {
        type empty;
      }
      leaf failure-retry-count {
        type string;
      }
    }
  }

  grouping ncs_template_system-grouping {
    container system {
      container cpu-load-sharing {
        container cpu-usage {
          leaf low {
            type string;
          }
          leaf high {
            type string;
          }
        }
      }
      leaf module-ctrl-cpu {
        type string;
      }
      leaf glid {
        type string;
      }
      container all-vlan-limit {
        leaf bcast {
          type string;
        }
        leaf ipmcast {
          type string;
        }
        leaf mcast {
          type string;
        }
        leaf unknown-ucast {
          type string;
        }
      }
      container per-vlan-limit {
        leaf bcast {
          type string;
        }
        leaf ipmcast {
          type string;
        }
        leaf mcast {
          type string;
        }
        leaf unknown-ucast {
          type string;
        }
      }
      container resource-usage {
        uses ncs_template_resource-usage-grouping;
        list template {
          // NCS patched for predictable order
          ordered-by user;
          key "name";
          leaf name {
            type string;
          }
          container system-resources {
            leaf bw-limit {
              type string;
            }
            leaf ssl-throughput-limit {
              type string;
            }
            leaf l4cps-limit {
              type string;
            }
            leaf natcps-limit {
              type string;
            }
            leaf l7cps-limit {
              type string;
            }
            leaf sslcps-limit {
              type string;
            }
            leaf concurrent-session-limit {
              type string;
            }
          }
          container app-resources {
            leaf gslb-device-count {
              type string;
            }
            leaf gslb-geo-location-count {
              type string;
            }
            leaf gslb-ip-list-count {
              type string;
            }
            leaf gslb-policy-count {
              type string;
            }
            leaf gslb-service-count {
              type string;
            }
            leaf gslb-service-ip-count {
              type string;
            }
            leaf gslb-service-port-count {
              type string;
            }
            leaf gslb-site-count {
              type string;
            }
            leaf gslb-svc-group-count {
              type string;
            }
            leaf gslb-template-count {
              type string;
            }
            leaf gslb-zone-count {
              type string;
            }
          }
        }
      }
      container template {
        leaf policy {
          type string;
        }
      }
      container trunk {
        container load-balance {
          leaf layer-2 {
            type string;
          }
        }
      }
      leaf ve-mac-scheme {
        type string;
      }
      container apps-global {
        leaf log-session-on-established {
          type empty;
        }
        leaf msl-time {
          type string;
        }
      }
    }
  }

  grouping ncs_template_ve-stats-grouping {
    leaf ve-stats {
      type string;
    }
  }

  grouping ncs_template_partition-grouping {
    list partition {
      // NCS patched for predictable order
      ordered-by user;
      key "name";
      leaf name {
        type string;
      }
      leaf network-partition {
        type empty;
      }
      leaf id {
        type string;
      }
      leaf application-type {
        type string;
      }
      leaf template {
        type string;
      }
    }
  }

  grouping ncs_template_partition-group-grouping {
    list partition-group {
      // NCS patched for predictable order
      ordered-by user;
      key "name";
      leaf name {
        type string;
      }
      list member {
        // NCS patched for predictable order
        ordered-by user;
        tailf:cli-suppress-mode;
        key "partition-name";
        leaf partition-name {
          type string;
        }
      }
    }
  }

  grouping ncs_template_access-list-grouping {
    list access-list {
      // NCS patched for predictable order
      ordered-by user;
      tailf:cli-suppress-mode;
      key "id";
      leaf id {
        type string;
      }
      list rules {
        // NCS patched for predictable order
        ordered-by user;
        tailf:cli-suppress-mode;
        tailf:cli-drop-node-name;
        key "txt";
        leaf txt {
          type string;
        }
      }
    }
  }

  grouping ncs_template_tftp-grouping {
    container tftp {
      leaf blksize {
        type string;
      }
    }
  }

  grouping ncs_template_stats-data-disable-grouping {
    leaf stats-data-disable {
      type empty;
    }
  }

  grouping ncs_template_syn-cookie-grouping {
    container syn-cookie {
      leaf on-threshold {
        type string;
      }
      leaf off-threshold {
        type string;
      }
    }
  }

  grouping ncs_template_enable-management-grouping {
    container enable-management {
      container service {

        grouping enable-management-content-grouping {
          leaf-list ethernet {
            // NCS patched for predictable order
            ordered-by user;
            tailf:cli-range-list-syntax;
            type string;
          }
          list acl {
            // NCS patched for predictable order
            ordered-by user;
            key "id";
            leaf id {
              type string;
            }
          }
          list acl-v4 {
            // NCS patched for predictable order
            ordered-by user;
            key "id";
            leaf id {
              type string;
            }
          }
          leaf-list ve {
            // NCS patched for predictable order
            ordered-by user;
            tailf:cli-range-list-syntax;
            type string;
          }
        }
        container ssh {
          uses enable-management-content-grouping;
        }
        container ssh-alt {
          tailf:alt-name "ssh";
          leaf management {
            type empty;
          }
          uses enable-management-content-grouping;
        }
        container telnet {
          uses enable-management-content-grouping;
        }
        container telnet-alt {
          tailf:alt-name "telnet";
          leaf management {
            type empty;
          }
          uses enable-management-content-grouping;
        }
        container http {
          uses enable-management-content-grouping;
        }
        container http-alt {
          tailf:alt-name "http";
          leaf management {
            type empty;
          }
          uses enable-management-content-grouping;
        }
        container https {
          uses enable-management-content-grouping;
        }
        container https-alt {
          tailf:alt-name "https";
          leaf management {
            type empty;
          }
          uses enable-management-content-grouping;
        }
        container snmp {
          uses enable-management-content-grouping;
        }
        container snmp-alt {
          tailf:alt-name "snmp";
          leaf management {
            type empty;
          }
          uses enable-management-content-grouping;
        }
      }
    }
  }

  grouping ncs_template_disable-management-grouping {
    container disable-management {
      container service {
        container http {
          presence "present";
          leaf management {
            type empty;
          }
        }
      }
    }
  }

  grouping ncs_template_monitor-grouping {
    container monitor {
      leaf disk {
        type string;
      }
      leaf memory {
        type string;
      }
      leaf buffer-drop {
        type string;
      }
      leaf buffer-usage {
        type string;
      }
    }
  }

  grouping ncs_template_extended-stats-grouping {
    leaf extended-stats {
      type empty;
    }
  }

  grouping ncs_template_admin-grouping {
    container admin {
      container lockout {
        leaf enable {
          type empty;
        }
      }
    }
  }

  grouping ncs_template_zone-grouping {
    list zone {
      // NCS patched for predictable order
      ordered-by user;
      key "name";
      leaf name {
        type string;
      }
      container interface {
        leaf-list ethernet {
          // NCS patched for predictable order
          ordered-by user;
          tailf:cli-range-list-syntax;
          type ncs_template_ethernet-index;
        }
      }
    }
  }

  grouping ncs_template_object-grouping {
    container object {
      list network {
        // NCS patched for predictable order
        ordered-by user;
        key "name";
        leaf name {
          type string;
        }
        leaf ipv4-address {
          tailf:cli-drop-node-name;
          type string;
        }
        leaf ipv6-address {
          tailf:cli-drop-node-name;
          type string;
        }
      }
    }
  }

  grouping ncs_template_icmp-grouping {
    container icmp {
      list type {
        // NCS patched for predictable order
        ordered-by user;
        tailf:cli-suppress-mode;
        key "id";
        leaf id {
          type string;
        }
      }
    }
  }

  grouping ncs_template_object-group-grouping {
    container object-group {
      list service {
        // NCS patched for predictable order
        ordered-by user;
        key "service-name";
        leaf service-name {
          type string;
        }
        leaf description {
          type string;
        }
        list tcp {
          // NCS patched for predictable order
          ordered-by user;
          tailf:cli-suppress-mode;
          key "op port";
          leaf op {
            type string;
          }
          leaf port {
            type string;
          }
        }
        uses ncs_template_icmp-grouping;
      }
      list network {
        // NCS patched for predictable order
        ordered-by user;
        key "name";
        leaf name {
          type string;
        }
        leaf fw {
          type string;
        }
        leaf description {
          type string;
        }
        leaf any {
          type empty;
        }
        leaf host {
          type string;
        }
        leaf ipv6-address {
          tailf:cli-drop-node-name;
          type string;
        }
      }
    }
  }

  grouping ncs_template_rule-set-grouping {
    list rule-set {
      // NCS patched for predictable order
      ordered-by user;
      key "rule-name";
      leaf rule-name {
        type string;
      }
      list rule {
        // NCS patched for predictable order
        ordered-by user;
        key "name";
        leaf name {
          type string;
        }
        leaf action {
          type string;
        }

        grouping source-dest-grouping {
          list object {
            // NCS patched for predictable order
            ordered-by user;
            key "name";
            leaf name {
              type string;
            }
          }
          list object-group {
            // NCS patched for predictable order
            ordered-by user;
            key "name";
            leaf name {
              type string;
            }
          }
          leaf zone {
            type string;
          }
        }
        container source {
          uses source-dest-grouping;
        }
        container dest {
          uses source-dest-grouping;
        }
        container service {
          leaf any {
            type empty;
          }
          uses ncs_template_icmp-grouping;
          leaf object-group {
            type string;
          }
        }
      }
    }
  }

  grouping ncs_template_fw-grouping {
    container fw {
      leaf active-rule-set {
        type string;
      }
    }
  }

  grouping ncs_template_enable-core-grouping {
    leaf enable-core {
      type string;
    }
  }

  grouping ncs_rpc_notif_slb-template-version-grouping {
    container version {
      tailf:cli-compact-syntax;
      tailf:cli-sequence-commands {
        tailf:cli-reset-siblings;
      }
      leaf current {
        tailf:cli-drop-node-name;
        type uint8;
      }
      leaf lower {
        tailf:cli-drop-node-name;
        type uint8;
      }
    }
  }

  grouping ncs_rpc_notif_ip-list-grouping {
    list ip-list {
      key "name";
      leaf name {
        type string;
      }
    }
  }

  grouping ncs_rpc_notif_cgnv6-grouping {
    container cgnv6 {
      container logging {
        container nat-quota-exceeded {
          leaf level {
            type enumeration {
              enum "warning";
              enum "critical";
              enum "notice";
            }
          }
        }
        container sampling-enable {
          leaf all {
            type empty;
          }
        }
      }
      list server {
        key "name";
        unique "address";
        leaf name {
          type string;
        }
        leaf address {
          tailf:cli-drop-node-name;
          tailf:cli-hide-in-submode;
          mandatory true;
          type union {
            type inet:ipv4-address;
            type inet:ipv6-address;
            type string;
          }
        }
        leaf health-check-disable {
          type empty;
        }
        list port {
          key "number tcpudp";
          leaf number {
            type uint16;
          }
          leaf tcpudp {
            type enumeration {
              enum "tcp";
              enum "udp";
            }
          }
          leaf health-check-disable {
            type empty;
          }
        }
      }
      list service-group {
        key "name tcpudp";
        unique "name";
        leaf name {
          type string;
        }
        leaf tcpudp {
          type enumeration {
            enum "tcp";
            enum "udp";
          }
        }
        container sampling-enable {
          leaf all {
            type empty;
          }
        }
        list member {
          key "host port";
          leaf host {
            type string;
          }
          leaf port {
            type uint16;
          }
          container sampling-enable {
            leaf all {
              type empty;
            }
          }
        }
        container shared {
          choice group-partition {
            leaf group {
              type string;
            }
            leaf partition {
              type string;
            }
          }
        }
      }
      container translation {
        leaf udp-timeout {
          type uint32;
        }
        leaf tcp-timeout {
          type uint32;
        }
        leaf icmp-timeout {
          type union {
            type uint32;
            type enumeration {
              enum "fast";
            }
          }
        }
        container service-timeout {
          list tcp {
            tailf:cli-compact-syntax;
            tailf:cli-suppress-mode;
            key "port-id";
            leaf port-id {
              type uint32;
            }
            leaf to {
              type uint32;
            }
            leaf timeout {
              tailf:cli-drop-node-name;
              type uint32;
            }
          }
          list udp {
            tailf:cli-compact-syntax;
            tailf:cli-suppress-mode;
            key "port-id";
            leaf port-id {
              type uint32;
            }
            leaf timeout {
              tailf:cli-drop-node-name;
              type uint32;
            }
          }
        }
      }
      container lsn {
        list alg {
          tailf:cli-suppress-mode;
          key "alg-id";
          leaf alg-id {
            type enumeration {
              enum "esp";
              enum "ftp";
              enum "h323";
              enum "mgcp";
              enum "pptp";
              enum "rtp-stun-timeout";
              enum "rtsp";
              enum "sip";
              enum "tftp";
            }
          }
          leaf enable {
            type empty;
          }
        }
        leaf hairpinning {
          type enumeration {
            enum "filter-none";
            enum "filter-self-ip";
            enum "filter-self-ip-port";
          }
        }
        leaf half-close-timeout {
          type uint16;
        }
        container logging {
          leaf default-template {
            type string;
          }
        }
        list endpoint-independent-mapping {
          key "proto";
          leaf proto {
            type enumeration {
              enum "udp";
              enum "tcp";
            }
          }
          container port {
            tailf:cli-compact-syntax;
            leaf from {
              tailf:cli-drop-node-name;
              type uint32;
            }
            leaf to {
              type uint32;
            }
          }
        }
        list endpoint-independent-filtering {
          key "proto";
          leaf proto {
            type enumeration {
              enum "tcp";
              enum "udp";
            }
          }
          container port {
            tailf:cli-compact-syntax;
            leaf from {
              tailf:cli-drop-node-name;
              type uint32;
            }
            leaf to {
              type uint32;
            }
          }
        }
        leaf ip-selection {
          type enumeration {
            enum "random";
            enum "round-robin";
            enum "least-used-strict";
            enum "least-udp-used-strict";
            enum "least-tcp-used-strict";
            enum "least-reserved-strict";
            enum "least-udp-reserved-strict";
            enum "least-tcp-reserved-strict";
            enum "least-users-strict";
          }
        }
        container inside {
          container source {
            leaf class-list {
              type string;
            }
          }
        }
      }
      list lsn-rule-list {
        key "name";
        leaf name {
          type string;
        }
        container default {
          tailf:cli-add-mode;
          container tcp {
            tailf:cli-compact-syntax;
            uses ncs_rpc_notif_port-grouping;
          }
          container udp {
            tailf:cli-compact-syntax;
            uses ncs_rpc_notif_port-grouping;
          }
          container icmp {
            tailf:cli-compact-syntax;
            // NCS expand uses statement
            list action {
              tailf:cli-suppress-mode;
              key "type";
              leaf type {
                type enumeration {
                  enum "dnat";
                  enum "drop";
                  enum "one-to-one-snat";
                  enum "pass-through";
                  enum "snat";
                }
              }
              leaf pool {
                type string;
              }
              leaf domain {
                type string;
              }
            }
            leaf no-action {
              type empty;
            }
          }
          container others {
            tailf:cli-compact-syntax;
            // NCS expand uses statement
            list action {
              tailf:cli-suppress-mode;
              key "type";
              leaf type {
                type enumeration {
                  enum "dnat";
                  enum "drop";
                  enum "one-to-one-snat";
                  enum "pass-through";
                  enum "snat";
                }
              }
              leaf pool {
                type string;
              }
              leaf domain {
                type string;
              }
            }
            leaf no-action {
              type empty;
            }
          }
        }
        list ip {
          key "address";
          leaf address {
            type tailf:ipv4-address-and-prefix-length;
          }
          container tcp {
            tailf:cli-compact-syntax;
            uses ncs_rpc_notif_port-grouping;
          }
          container udp {
            tailf:cli-compact-syntax;
            uses ncs_rpc_notif_port-grouping;
          }
          container icmp {
            tailf:cli-compact-syntax;
            // NCS expand uses statement
            list action {
              tailf:cli-suppress-mode;
              key "type";
              leaf type {
                type enumeration {
                  enum "dnat";
                  enum "drop";
                  enum "one-to-one-snat";
                  enum "pass-through";
                  enum "snat";
                }
              }
              leaf pool {
                type string;
              }
              leaf domain {
                type string;
              }
            }
            leaf no-action {
              type empty;
            }
          }
          container others {
            tailf:cli-compact-syntax;
            // NCS expand uses statement
            list action {
              tailf:cli-suppress-mode;
              key "type";
              leaf type {
                type enumeration {
                  enum "dnat";
                  enum "drop";
                  enum "one-to-one-snat";
                  enum "pass-through";
                  enum "snat";
                }
              }
              leaf pool {
                type string;
              }
              leaf domain {
                type string;
              }
            }
            leaf no-action {
              type empty;
            }
          }
        }
      }
      container fixed-nat {
        leaf create-port-mapping-file {
          type empty;
        }
      }
      container nat {
        list pool {
          tailf:cli-sequence-commands;
          tailf:cli-compact-syntax;
          tailf:cli-suppress-mode;
          key "name";
          leaf name {
            type string;
          }
          leaf address {
            tailf:cli-drop-node-name;
            type inet:ipv4-address;
          }
          leaf address-end {
            tailf:cli-optional-in-sequence;
            tailf:cli-drop-node-name;
            type inet:ipv4-address;
          }
          leaf netmask {
            type union {
              type inet:ipv4-address;
              type string;
            }
          }
          leaf vrid {
            tailf:cli-optional-in-sequence;
            type union {
              type uint8;
              type enumeration {
                enum "default";
              }
            }
          }
          leaf port-batch-v2-size {
            type enumeration {
              enum "64";
              enum "128";
              enum "256";
              enum "512";
              enum "1024";
              enum "2048";
              enum "4096";
            }
          }
          leaf simultaneous-batch-allocation {
            type empty;
          }
          leaf tcp-time-wait-interval {
            tailf:cli-optional-in-sequence;
            type uint8;
          }
          container usable-nat-ports {
            tailf:cli-compact-syntax;
            tailf:cli-sequence-commands;
            tailf:cli-flatten-container;
            leaf start {
              tailf:cli-drop-node-name;
              type uint16;
            }
            leaf end {
              tailf:cli-drop-node-name;
              type uint16;
            }
          }
        }
        list pool-group {
          key "name";
          leaf name {
            type string;
          }
          leaf vrid {
            tailf:cli-hide-in-submode;
            type union {
              type uint8;
              type enumeration {
                enum "default";
              }
            }
          }
          list member {
            tailf:cli-suppress-mode;
            key "name";
            leaf name {
              type string;
            }
          }
        }
      }
      container resource-usage {
        leaf lsn-nat-addr-count {
          type uint32;
        }
      }
      list lsn-lid {
        key "lid";
        leaf lid {
          type uint32;
        }
        leaf name {
          type string;
        }
        container lsn-rule-list {
          leaf destination {
            type string;
          }
        }
        list user-quota {
          tailf:cli-compact-syntax;
          tailf:cli-suppress-mode;
          key "protocol";
          leaf protocol {
            type enumeration {
              enum "icmp";
              enum "udp";
              enum "tcp";
              enum "session";
              enum "session-tcp";
              enum "session-udp";
            }
          }
          leaf quota {
            tailf:cli-drop-node-name;
            type uint32;
          }
          leaf reserve {
            type uint32;
          }
        }
        leaf source-nat-pool {
          type string;
        }
      }
      container template {
        list logging {
          key "name";
          leaf name {
            type string;
          }
          container log {
            container fixed-nat {
              leaf port-mappings {
                type enumeration {
                  enum "both";
                  enum "creation";
                }
              }
              container sessions {
                presence "true";
                leaf merged-style {
                  type empty;
                }
              }
            }
            leaf port-mappings {
              type enumeration {
                enum "creation";
                enum "disable";
                enum "both";
              }
            }
            container sessions {
              presence "true";
              leaf merged-style {
                type empty;
              }
            }
          }
          leaf facility {
            type union {
              type enumeration {
                enum "kernel";
                enum "user";
                enum "mail";
                enum "daemon";
                enum "security-authorization";
                enum "syslog";
                enum "line-printer";
                enum "news";
                enum "uucp";
                enum "cron";
                enum "security-authorization-private";
                enum "ftp";
                enum "ntp";
                enum "audit";
                enum "alert";
                enum "clock";
                enum "local0";
                enum "local1";
                enum "local2";
                enum "local3";
                enum "local4";
                enum "local5";
                enum "local6";
                enum "local7";
              }
              type string;
            }
          }
          leaf severity {
            type union {
              type enumeration {
                enum "emergency";
                enum "alert";
                enum "critical";
                enum "error";
                enum "warning";
                enum "notice";
                enum "informational";
                enum "debug";
              }
              type uint8;
            }
          }
          container service-group {
            tailf:cli-compact-syntax;
            tailf:cli-sequence-commands {
              tailf:cli-reset-siblings;
            }
            leaf name {
              tailf:cli-drop-node-name;
              type string;
            }
            leaf shared {
              type empty;
            }
          }
          container disable-log-by-destination {
            tailf:cli-add-mode;
            presence "true";
            leaf icmp {
              type empty;
            }
          }
          leaf include-destination {
            type empty;
          }
          leaf format {
            type enumeration {
              enum "binary";
              enum "compact";
              enum "custom";
              enum "default";
              enum "rfc5424";
              enum "cef";
            }
          }
          leaf batched-logging-disable {
            type empty;
          }
        }
      }
    }
  }

  grouping ncs_rpc_notif_sflow-grouping {
    container sflow {
      container agent {
        leaf address {
          type union {
            type inet:ipv4-address;
            type inet:ipv6-address;
          }
        }
      }
      container setting {
        leaf local-collection {
          type empty;
        }
        leaf source-ip-use-mgmt {
          type empty;
        }
      }
      list collector {
        tailf:cli-suppress-mode;
        key "ip port";
        leaf ip {
          tailf:cli-expose-key-name;
          type inet:ipv4-address;
        }
        leaf port {
          type uint32;
        }
      }
      list collector-alt {
        tailf:cli-suppress-mode;
        tailf:alt-name "collector";
        key "ip port";
        leaf ip {
          type inet:ipv4-address;
        }
        leaf port {
          type uint32;
        }
      }
      container polling {
        leaf cpu-usage {
          type empty;
        }
        leaf-list ve {
          tailf:cli-range-list-syntax;
          type uint16;
        }
      }
      container sampling {
        leaf-list ve {
          tailf:cli-range-list-syntax;
          type uint16;
        }
      }
      container source-address {
        leaf ip {
          type inet:ipv4-address;
        }
        leaf ipv6 {
          type inet:ipv6-address;
        }
      }
    }
  }

  grouping ncs_rpc_notif_ip-address {
    list address {
      tailf:cli-suppress-mode;
      key "address mask";
      leaf address {
        type union {
          type inet:ipv4-address;
          type enumeration {
            enum "dhcp";
          }
        }
      }
      leaf mask {
        type union {
          type inet:ipv4-address;
          type string;
        }
      }
    }
  }

  grouping ncs_rpc_notif_algs {
    container alg {
      uses ncs_rpc_notif_pptp_alg;
      uses ncs_rpc_notif_tftp_alg;
      uses ncs_rpc_notif_rtsp_alg;
      uses ncs_rpc_notif_esp_alg;
    }
  }

  grouping ncs_rpc_notif_pptp_alg {
    leaf pptp {
      type enumeration {
        enum "disable";
        enum "enable";
      }
    }
  }

  grouping ncs_rpc_notif_tftp_alg {
    leaf tftp {
      type enumeration {
        enum "disable";
        enum "enable";
      }
    }
  }

  grouping ncs_rpc_notif_rtsp_alg {
    leaf rtsp {
      type enumeration {
        enum "disable";
        enum "enable";
      }
    }
  }

  grouping ncs_rpc_notif_esp_alg {
    leaf esp {
      type enumeration {
        enum "disable";
        enum "enable";
      }
    }
  }

  grouping ncs_rpc_notif_lid-grouping {
    choice lid-choice {
      leaf glid {
        type uint16;
      }
      leaf lid {
        type uint8;
      }
      leaf lsn-lid {
        type uint16;
      }
      leaf lsn-radius-profile {
        type uint8;
      }
    }
  }

  grouping ncs_rpc_notif_mgmt-source-interface-grouping {
    container source-interface {
      leaf loopback {
        type uint8;
      }
    }
  }

  grouping ncs_rpc_notif_priority-cost {
    leaf priority-cost {
      mandatory true;
      type uint8;
    }
  }

  grouping ncs_rpc_notif_hostname-grouping {
    leaf hostname {
      type string;
    }
  }

  grouping ncs_rpc_notif_password-grouping {
    leaf username {
      type string;
    }
    leaf password {
      tailf:cli-optional-in-sequence;
      type string;
    }
  }

  grouping ncs_rpc_notif_interface-grouping {
    container interface {

      grouping lldp-interface-grouping {
        container lldp {
          container enable {
            tailf:cli-compact-syntax;
            leaf rx {
              type empty;
            }
            leaf tx {
              type empty;
            }
          }
          leaf notification {
            type enumeration {
              enum "enable";
            }
          }
          leaf tx-dot1-tlvs {
            type enumeration {
              enum "link-aggregation";
              enum "vlan";
            }
          }
        }
      }
      container management {
        tailf:cli-add-mode;
        container bcast-rate-limit {
          presence "present";
          leaf rate {
            type uint16;
          }
        }
        container ip {
          uses ncs_rpc_notif_ip-address;
          leaf control-apps-use-mgmt-port {
            type empty;
          }
          leaf default-gateway {
            type inet:ipv4-address;
          }
        }
        container ipv6 {
          list address {
            key "ip";
            tailf:cli-suppress-mode;
            tailf:cli-sequence-commands {
              tailf:cli-reset-siblings;
            }
            tailf:cli-compact-syntax;
            leaf ip {
              tailf:cli-drop-node-name;
              type ncs_rpc_notif_ipv6-prefix;
            }
            leaf link-local {
              type empty;
            }
          }
          leaf default-gateway {
            type inet:ipv6-address;
          }
        }
        uses lldp-interface-grouping;
        leaf flow-control {
          type empty;
        }
        container access-list {
          tailf:cli-sequence-commands {
            tailf:cli-reset-siblings;
          }
          tailf:cli-compact-syntax;
          leaf id {
            tailf:cli-drop-node-name;
            type uint16;
          }
          leaf in {
            must '../id' {
              tailf:xpath-root 3;
            }
            type empty;
          }
        }
        leaf enabled-disabled {
          tailf:cli-drop-node-name;
          type enumeration {
            enum "enable";
            enum "disable";
          }
        }
        leaf duplexity {
          type enumeration {
            enum "full";
            enum "half";
            enum "auto";
          }
        }
        leaf mtu {
          type uint16;
        }
        leaf speed {
          type enumeration {
            enum "10";
            enum "100";
            enum "1000";
            enum "auto";
          }
        }
      }
      list ethernet {
        key "nr";
        leaf nr {
          type ncs_rpc_notif_ethernet-index;
        }
        leaf name {
          type string;
        }
        container ip {
          uses ncs_rpc_notif_ip-address;
          leaf cache-spoofing-port {
            type empty;
          }
          leaf helper-address {
            type inet:ipv4-address;
          }
          container nat {
            leaf inside {
              type empty;
            }
            leaf outside {
              type empty;
            }
          }
          container ospf;
          container router {
            container isis {
              presence "true";
              leaf cmds {
                tailf:cli-drop-node-name;
                type string;
              }
            }
          }
          leaf allow-promiscuous-vip {
            type empty;
          }
          container tcp {
            leaf syn-cookie {
              type empty;
            }
          }
        }
        container ipv6 {
          container access-list {
            tailf:cli-sequence-commands {
              tailf:cli-reset-siblings;
            }
            tailf:cli-compact-syntax;
            leaf id {
              tailf:cli-drop-node-name;
              type string;
            }
            leaf in {
              must '../id' {
                tailf:xpath-root 3;
              }
              type empty;
            }
          }
          list address {
            key "ip";
            tailf:cli-suppress-mode;
            tailf:cli-sequence-commands {
              tailf:cli-reset-all-siblings;
            }
            tailf:cli-compact-syntax;
            leaf ip {
              tailf:cli-drop-node-name;
              type ncs_rpc_notif_ipv6-prefix;
            }
            leaf link-local {
              type empty;
              tailf:cli-break-sequence-commands;
            }
            leaf anycast {
              type empty;
              tailf:cli-break-sequence-commands;
            }
          }
          container nat {
            leaf inside {
              type empty;
            }
            leaf outside {
              type empty;
            }
          }
          container ndisc {
            container router-advertisement;
          }
          container ospf;
          container router {
            container isis {
              presence "true";
              leaf cmds {
                tailf:cli-drop-node-name;
                type string;
              }
            }
          }
        }
        leaf load-interval {
          type uint16;
        }
        container access-list {
          tailf:cli-sequence-commands {
            tailf:cli-reset-siblings;
          }
          tailf:cli-compact-syntax;
          leaf id {
            tailf:cli-drop-node-name;
            type uint16;
          }
          leaf in {
            must '../id' {
              tailf:xpath-root 3;
            }
            type empty;
          }
        }
        leaf state {
          tailf:cli-drop-node-name;
          type enumeration {
            enum "enable";
            enum "disable";
          }
        }
        leaf state-alt {
          tailf:cli-drop-node-name;
          type enumeration {
            enum "enable";
            enum "disable";
          }
        }
        leaf duplexity {
          type enumeration {
            enum "full";
            enum "half";
            enum "auto";
          }
        }
        leaf cpu-process {
          type empty;
        }
        leaf flow-control {
          type empty;
        }
        container icmp-rate-limit {
          tailf:cli-sequence-commands {
            tailf:cli-reset-siblings;
          }
          tailf:cli-compact-syntax;
          leaf rate {
            tailf:cli-drop-node-name;
            type uint16;
          }
          leaf lockup {
            must '../rate' {
              tailf:xpath-root 3;
            }
            type uint16;
          }
          leaf lockup-period {
            must '../lockup' {
              tailf:xpath-root 3;
            }
            tailf:cli-drop-node-name;
            type uint16;
          }
        }
        container ospf;
        container isis;
        leaf l3-vlan-fwd-disable {
          type empty;
        }
        container lacp {
          leaf port-priority {
            type uint16;
          }
          leaf timeout {
            type enumeration {
              enum "long";
              enum "short";
            }
          }
          container trunk {
            tailf:cli-sequence-commands {
              tailf:cli-reset-all-siblings;
            }
            tailf:cli-compact-syntax;
            leaf number {
              tailf:cli-drop-node-name;
              type uint16;
            }
            leaf admin-key {
              tailf:cli-break-sequence-commands;
              must '../number' {
                tailf:xpath-root 3;
              }
              type uint16;
            }
            leaf mode {
              must '../number' {
                tailf:xpath-root 3;
              }
              type enumeration {
                enum "active";
                enum "passive";
              }
            }
            leaf unidirectional-detection {
              must '../number' {
                tailf:xpath-root 3;
              }
              type empty;
            }
          }
          container udld-timeout {
            tailf:cli-sequence-commands {
              tailf:cli-reset-all-siblings;
            }
            tailf:cli-compact-syntax;
            leaf timeout-type {
              tailf:cli-drop-node-name;
              type enumeration {
                enum "fast";
                enum "slow";
              }
            }
            leaf milli {
              tailf:cli-drop-node-name;
              type uint16;
            }
            leaf secs {
              tailf:cli-drop-node-name;
              type uint16;
            }
          }
        }
        uses lldp-interface-grouping;
        leaf mtu {
          type uint16;
        }
        leaf speed {
          type enumeration {
            enum "10";
            enum "100";
            enum "1000";
            enum "auto";
          }
        }
        list trunk-group-list {
          key "trunk-group-key";
          tailf:cli-drop-node-name;
          tailf:cli-compact-syntax;
          tailf:cli-sequence-commands {
            tailf:cli-reset-siblings;
          }
          leaf trunk-group-key {
            type enumeration {
              enum "trunk-group";
            }
          }
          leaf trunk-group-id {
            tailf:cli-drop-node-name;
            tailf:cli-hide-in-submode;
            mandatory true;
            type uint8;
          }
          leaf trunk-group-type {
            tailf:cli-drop-node-name;
            tailf:cli-hide-in-submode;
            type enumeration {
              enum "static";
              enum "lacp";
              enum "lacp-udld";
            }
          }
        }
      }
      list trunk {
        key "nr";
        leaf nr {
          type ncs_rpc_notif_ethernet-index;
        }
        leaf name {
          type string;
        }
        leaf state {
          tailf:cli-drop-node-name;
          type enumeration {
            enum "enable";
            enum "disable";
          }
        }
        container icmp-rate-limit {
          tailf:cli-sequence-commands {
            tailf:cli-reset-siblings;
          }
          tailf:cli-compact-syntax;
          leaf rate {
            tailf:cli-drop-node-name;
            type uint16;
          }
          leaf lockup {
            must '../rate' {
              tailf:xpath-root 3;
            }
            type uint16;
          }
          leaf lockup-period {
            must '../lockup' {
              tailf:xpath-root 3;
            }
            tailf:cli-drop-node-name;
            type uint16;
          }
        }
        list access-list {
          tailf:cli-suppress-mode;
          key "id in-type";
          leaf id {
            type uint16;
          }
          leaf in-type {
            type enumeration {
              enum "in";
            }
          }
        }
        container ip {
          list address {
            key "ip mask";
            tailf:cli-suppress-mode;
            leaf ip {
              type inet:ipv4-address;
            }
            leaf mask {
              type ncs_rpc_notif_ipv4-mask;
            }
          }
          leaf allow-promiscuous-vip {
            type empty;
          }
          leaf cache-spoofing-port {
            type empty;
          }
          container nat {
            leaf inside {
              type empty;
            }
            leaf outside {
              type empty;
            }
          }
        }
      }
      list loopback {
        key "nr";
        leaf nr {
          type ncs_rpc_notif_ethernet-index;
        }
        container ip {
          uses ncs_rpc_notif_ip-address;
          container router {
            choice isis-choice {
              container isis-alt {
                tailf:cli-drop-node-name;
                leaf isis {
                  type string;
                }
              }
              leaf isis {
                type empty;
              }
            }
          }
        }
        container icmp-rate-limit {
          tailf:cli-sequence-commands {
            tailf:cli-reset-siblings;
          }
          tailf:cli-compact-syntax;
          leaf rate {
            tailf:cli-drop-node-name;
            type uint16;
          }
          leaf lockup {
            must '../rate' {
              tailf:xpath-root 3;
            }
            type uint16;
          }
          leaf lockup-period {
            tailf:cli-drop-node-name;
            must '../lockup' {
              tailf:xpath-root 3;
            }
            type uint16;
          }
        }
        leaf state {
          tailf:cli-drop-node-name;
          type enumeration {
            enum "enable";
            enum "disable";
          }
        }
      }
      list ve {
        key "id";
        leaf id {
          type ncs_rpc_notif_vlan-index;
        }
        leaf name {
          type string;
        }
        container bfd {
          container echo {
            presence "true";
          }
        }
        container icmp-rate-limit {
          tailf:cli-sequence-commands {
            tailf:cli-reset-siblings;
          }
          tailf:cli-compact-syntax;
          leaf rate {
            tailf:cli-drop-node-name;
            type uint16;
          }
          leaf lockup {
            must '../rate' {
              tailf:xpath-root 3;
            }
            type uint16;
          }
          leaf lockup-period {
            tailf:cli-drop-node-name;
            must '../lockup' {
              tailf:xpath-root 3;
            }
            type uint16;
          }
        }
        container access-list {
          tailf:cli-sequence-commands {
            tailf:cli-reset-siblings;
          }
          tailf:cli-compact-syntax;
          leaf id {
            tailf:cli-drop-node-name;
            type uint16;
          }
          leaf in {
            must '../id' {
              tailf:xpath-root 3;
            }
            type empty;
          }
        }
        leaf l3-vlan-fwd-disable {
          type empty;
        }
        container ip {
          leaf allow-promiscuous-vip {
            type empty;
          }
          leaf cache-spoofing-port {
            type empty;
          }
          leaf helper-address {
            type inet:ipv4-address;
          }
          container nat {
            leaf inside {
              type empty;
            }
            leaf outside {
              type empty;
            }
          }
          container ospf;
          container router {
            container isis {
              presence "true";
              leaf cmds {
                tailf:cli-drop-node-name;
                type string;
              }
            }
          }
          container tcp {
            leaf syn-cookie {
              type empty;
            }
          }
          uses ncs_rpc_notif_ip-address;
        }
        container ipv6 {
          container access-list {
            tailf:cli-sequence-commands {
              tailf:cli-reset-siblings;
            }
            tailf:cli-compact-syntax;
            leaf id {
              tailf:cli-drop-node-name;
              type string;
            }
            leaf in {
              must '../id' {
                tailf:xpath-root 3;
              }
              type empty;
            }
          }
          container nat {
            leaf inside {
              type empty;
            }
            leaf outside {
              type empty;
            }
          }
          container ndisc {
            container router-advertisement;
          }
          container ospf;
          container router {
            container isis {
              presence "true";
              leaf cmds {
                tailf:cli-drop-node-name;
                type string;
              }
            }
          }
          list address {
            key "ip";
            tailf:cli-suppress-mode;
            tailf:cli-sequence-commands {
              tailf:cli-reset-all-siblings;
            }
            tailf:cli-compact-syntax;
            leaf ip {
              tailf:cli-drop-node-name;
              type ncs_rpc_notif_ipv6-prefix;
            }
            leaf link-local {
              type empty;
              tailf:cli-break-sequence-commands;
            }
            leaf anycast {
              type empty;
              tailf:cli-break-sequence-commands;
            }
          }
        }
        leaf mtu {
          type uint16;
        }
        leaf state {
          tailf:cli-drop-node-name;
          type enumeration {
            enum "enable";
            enum "disable";
          }
        }
        container isis;
        container ospf;
      }
    }
  }

  grouping ncs_rpc_notif_ip-route-grouping {
    list route {
      tailf:cli-compact-syntax;
      tailf:cli-sequence-commands {
        tailf:cli-reset-siblings;
      }
      tailf:cli-suppress-mode;
      key "ip mask forwarding-router";
      leaf ip {
        type inet:ipv4-address;
      }
      leaf mask {
        type string;
      }
      leaf forwarding-router {
        type inet:ipv4-address;
      }
      leaf distance {
        tailf:cli-drop-node-name;
        tailf:cli-optional-in-sequence;
        type uint8;
      }
      leaf cpu-process {
        tailf:cli-drop-node-name;
        tailf:cli-optional-in-sequence;
        type enumeration {
          enum "cpu-process";
        }
      }
    }
  }

  grouping ncs_rpc_notif_ip-prefix-list-grouping {
    list prefix-list {
      tailf:cli-suppress-mode;
      tailf:cli-compact-syntax;
      key "name seq";
      leaf name {
        type string;
      }
      leaf seq {
        tailf:cli-expose-key-name;
        type uint32;
      }
      choice permit-deny {
        leaf permit {
          type union {
            type enumeration {
              enum "any";
            }
            type tailf:ipv4-address-and-prefix-length;
          }
        }
        leaf deny {
          type union {
            type enumeration {
              enum "any";
            }
            type tailf:ipv4-address-and-prefix-length;
          }
        }
      }
      leaf ge {
        type uint8;
      }
      leaf le {
        type uint8;
      }
    }
  }

  grouping ncs_rpc_notif_ip-grouping {
    container ip {
      list access-list {
        key "name";
        leaf name {
          type string;
        }
        list access-list-rule {
          tailf:cli-suppress-mode;
          tailf:cli-delete-when-empty;
          tailf:cli-drop-node-name;
          ordered-by user;
          key "rule";
          leaf rule {
            tailf:cli-multi-word-key;
            type string;
          }
        }
      }
      list address {
        key "ip";
        tailf:cli-suppress-mode;
        tailf:cli-delete-when-empty;
        tailf:cli-sequence-commands {
          tailf:cli-reset-siblings;
        }
        tailf:cli-compact-syntax;
        leaf ip {
          tailf:cli-drop-node-name;
          type inet:ipv4-address;
        }
        leaf mask {
          tailf:cli-drop-node-name;
          type ncs_rpc_notif_ipv4-mask;
        }
      }
      container anomaly-drop {
        leaf bad-content {
          type uint16;
        }
        leaf drop-all {
          type empty;
        }
        leaf frag {
          type empty;
        }
        leaf ip-option {
          type boolean;
        }
        leaf land-attack {
          type empty;
        }
        leaf out-of-sequence {
          type uint16;
        }
        leaf ping-of-death {
          type empty;
        }
        leaf tcp-no-flag {
          type empty;
        }
        leaf tcp-syn-fin {
          type empty;
        }
        leaf tcp-syn-frag {
          type empty;
        }
        leaf zero-window {
          type uint16;
        }
        container security-attack {
          leaf layer-3 {
            type empty;
          }
          leaf layer-4 {
            type empty;
          }
        }
        list packet-deformity {
          tailf:cli-suppress-mode;
          key "layer";
          leaf layer {
            type enumeration {
              enum "layer-3";
              enum "layer-4";
            }
          }
        }
      }
      container as-path {
        list access-list {
          tailf:cli-suppress-mode;
          key "name action path";
          leaf name {
            type string;
          }
          leaf action {
            type enumeration {
              enum "permit";
              enum "deny";
            }
          }
          leaf path {
            type string;
            tailf:cli-multi-word-key;
          }
        }
      }
      container community-list {
        list standard-number {
          tailf:cli-drop-node-name;
          tailf:cli-suppress-mode;
          key "nr";
          leaf nr {
            type uint8;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list expanded-number {
          tailf:cli-drop-node-name;
          tailf:cli-suppress-mode;
          key "nr";
          leaf nr {
            type uint8;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list word {
          tailf:cli-drop-node-name;
          tailf:cli-suppress-mode;
          key "name";
          leaf name {
            type string;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list expanded {
          tailf:cli-suppress-mode;
          key "name";
          leaf name {
            type string;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list standard {
          tailf:cli-suppress-mode;
          key "name";
          leaf name {
            type string;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
      }
      leaf default-gateway {
        type inet:ipv4-address;
      }
      container dns {
        leaf primary {
          type inet:ipv4-address;
        }
        leaf secondary {
          type inet:ipv4-address;
        }
        leaf suffix {
          type string;
        }
      }
      container extcommunity-list {
        list standard-number {
          tailf:cli-drop-node-name;
          tailf:cli-suppress-mode;
          key "nr";
          leaf nr {
            type uint8;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list expanded-number {
          tailf:cli-drop-node-name;
          tailf:cli-suppress-mode;
          key "nr";
          leaf nr {
            type uint8;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list expanded {
          tailf:cli-suppress-mode;
          key "name";
          leaf name {
            type string;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list standard {
          tailf:cli-suppress-mode;
          key "name";
          leaf name {
            type string;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
      }
      container frag {
        leaf buff {
          type uint32;
        }
        container cpu-threshold {
          tailf:cli-compact-syntax;
          tailf:cli-sequence-commands;
          leaf high {
            type uint8;
          }
          leaf low {
            type uint8;
          }
        }
        leaf max-reassembly-sessions {
          type uint32;
        }
        leaf timeout {
          type uint16;
        }
      }
      container icmp {
        container disable {
          leaf redirect {
            type empty;
          }
          leaf unreachable {
            type empty;
          }
        }
      }
      container mgmt-traffic {
        container snmp {
          uses ncs_rpc_notif_mgmt-source-interface-grouping;
        }
        container ntp {
          uses ncs_rpc_notif_mgmt-source-interface-grouping;
        }
        container syslog {
          uses ncs_rpc_notif_mgmt-source-interface-grouping;
        }
        container ssh {
          uses ncs_rpc_notif_mgmt-source-interface-grouping;
        }
        container telnet {
          uses ncs_rpc_notif_mgmt-source-interface-grouping;
        }
        container ftp {
          uses ncs_rpc_notif_mgmt-source-interface-grouping;
        }
        container tftp {
          uses ncs_rpc_notif_mgmt-source-interface-grouping;
        }
        container rcp {
          uses ncs_rpc_notif_mgmt-source-interface-grouping;
        }
        container web {
          uses ncs_rpc_notif_mgmt-source-interface-grouping;
        }
        container all {
          uses ncs_rpc_notif_mgmt-source-interface-grouping;
        }
      }
      container nat {
        uses ncs_rpc_notif_algs;
        leaf allow-static-host {
          type empty;
        }
        container inside {
          container source {
            list list {
              tailf:cli-suppress-mode;
              key "id";
              leaf id {
                type uint16;
              }
              leaf pool {
                tailf:cli-hide-in-submode;
                mandatory true;
                type string;
              }
            }
            leaf class-list {
              type string;
            }
            list static {
              tailf:cli-suppress-mode;
              tailf:cli-compact-syntax;
              key "source nat";
              leaf source {
                type inet:ipv4-address;
              }
              leaf nat {
                type inet:ipv4-address;
              }
              leaf vrid {
                type uint8;
              }
            }
          }
        }
        list pool {
          tailf:cli-suppress-mode;
          tailf:cli-sequence-commands {
            tailf:cli-reset-all-siblings;
          }
          tailf:cli-compact-syntax;
          key "name";
          leaf name {
            type string;
          }
          leaf ipstart {
            mandatory true;
            tailf:cli-drop-node-name;
            type inet:ipv4-address;
          }
          leaf ipend {
            mandatory true;
            tailf:cli-drop-node-name;
            type inet:ipv4-address;
          }
          leaf netmask {
            mandatory true;
            type union {
              type ncs_rpc_notif_ipv4-mask;
              type string;
            }
          }
          leaf gateway {
            tailf:cli-optional-in-sequence;
            type inet:ipv4-address;
          }
          leaf ha-group-id {
            tailf:cli-optional-in-sequence;
            type uint16;
          }
          leaf ha-use-all-ports {
            tailf:cli-optional-in-sequence;
            type empty;
          }
          leaf vrid {
            tailf:cli-optional-in-sequence;
            type uint16;
          }
          leaf ip-rr {
            tailf:cli-break-sequence-commands;
            type empty;
          }
          leaf lsn {
            type empty;
          }
          leaf max-users-per-ip {
            type uint16;
          }
        }
        list pool-group {
          key "name";
          leaf name {
            type string;
          }
          leaf ha-group-id {
            tailf:cli-hide-in-submode;
            type uint16;
          }
          list member {
            key "member-id";
            tailf:cli-suppress-mode;
            leaf member-id {
              type string;
            }
          }
        }
        container range-list;
        leaf reset-idle-tcp-conn {
          type empty;
        }
        container template {
          list logging {
            key "name";
            leaf name {
              type string;
            }
          }
        }
        container translation {
          leaf icmp-timeout {
            type union {
              type uint16;
              type enumeration {
                enum "fast";
              }
            }
          }
          leaf tcp-timeout {
            type uint16;
          }
          leaf udp-timeout {
            type uint16;
          }
          leaf syn-timeout {
            type uint16;
          }
          list service-timeout {
            tailf:cli-compact-syntax;
            tailf:cli-sequence-commands;
            tailf:cli-suppress-mode;
            key "protocol from";
            leaf protocol {
              type enumeration {
                enum "tcp";
                enum "udp";
              }
            }
            leaf from {
              type uint16;
            }
            leaf to {
              tailf:cli-optional-in-sequence;
              type uint16;
            }
            leaf timeout {
              tailf:cli-drop-node-name;
              type union {
                type uint16;
                type enumeration {
                  enum "fast";
                }
              }
            }
          }
        }
        container lsn {
          container endpoint-independent-mapping {
            container tcp {
              container enable {
                leaf ephemeral {
                  type empty;
                }
                leaf well-known {
                  type empty;
                }
              }
            }
            container udp {
              container enable {
                leaf ephemeral {
                  type empty;
                }
                leaf well-known {
                  type empty;
                }
              }
            }
          }
          container endpoint-independent-filtering {
            container tcp {
              container enable {
                leaf ephemeral {
                  type empty;
                  must '../../../../endpoint-independent-mapping/tcp/enable/ephemeral' {
                    tailf:xpath-root 3;
                    error-message "Endpoint-independent-filtering cannot be enabled when endpoint-independent-mapping is disabled";
                  }
                }
                leaf well-known {
                  type empty;
                  must '../../../../endpoint-independent-mapping/tcp/enable/well-known' {
                    tailf:xpath-root 3;
                    error-message "Endpoint-independent-filtering cannot be enabled when endpoint-independent-mapping is disabled";
                  }
                }
              }
            }
            container udp {
              container enable {
                leaf ephemeral {
                  type empty;
                  must '../../../../endpoint-independent-mapping/udp/enable/ephemeral' {
                    tailf:xpath-root 3;
                    error-message "Endpoint-independent-filtering cannot be enabled when endpoint-independent-mapping is disabled";
                  }
                }
                leaf well-known {
                  type empty;
                  must '../../../../endpoint-independent-mapping/udp/enable/well-known' {
                    tailf:xpath-root 3;
                    error-message "Endpoint-independent-filtering cannot be enabled when endpoint-independent-mapping is disabled";
                  }
                }
              }
            }
          }
          leaf ip-selection {
            type enumeration {
              enum "random";
              enum "round-robin";
              enum "least-used-strict";
              enum "least-udp-used-strict";
              enum "least-tcp-used-strict";
              enum "least-reserved-strict";
              enum "least-udp-reserved-strict";
              enum "least-tcp-reserved-strict";
              enum "least-users-strict";
            }
          }
          leaf attempt-port-preservation {
            type enumeration {
              enum "disable";
              enum "enable";
            }
          }
          uses ncs_rpc_notif_algs;
        }
      }
      uses ncs_rpc_notif_ip-prefix-list-grouping;
      uses ncs_rpc_notif_ip-route-grouping;
      container tcp {
        container syn-cookie {
          leaf threshold {
            type uint8;
          }
        }
      }
    }
  }

  grouping ncs_rpc_notif_resource-usage-grouping {
    leaf class-list-ipv6-addr-count {
      type uint32;
    }
    leaf client-ssl-template-count {
      type uint32;
    }
    leaf conn-reuse-template-count {
      type uint32;
    }
    leaf fast-tcp-template-count {
      type uint32;
    }
    leaf fast-udp-template-count {
      type uint32;
    }
    leaf http-template-count {
      type uint32;
    }
    leaf l4-session-count {
      type uint32;
    }
    leaf nat-pool-addr-count {
      type uint32;
    }
    leaf persist-cookie-template-count {
      type uint32;
    }
    leaf persist-srcip-template-count {
      type uint32;
    }
    leaf proxy-template-count {
      type uint32;
    }
    leaf real-port-count {
      type uint32;
    }
    leaf real-server-count {
      type uint32;
    }
    leaf server-ssl-template-count {
      type uint32;
    }
    leaf service-group-count {
      type uint32;
    }
    leaf stream-template-count {
      type uint32;
    }
    leaf virtual-port-count {
      type uint32;
    }
    leaf virtual-server-count {
      type uint32;
    }
  }

  grouping ncs_rpc_notif_snmp-remote-grouping {
    list remote {
      tailf:cli-suppress-mode;
      tailf:cli-delete-when-empty;
      tailf:cli-compact-syntax;
      key "host";
      leaf host {
        type string;
      }
      leaf mask {
        tailf:cli-drop-node-name;
        type string;
      }
    }
  }

  grouping ncs_rpc_notif_health-grouping {
    container health {
      list monitor {
        key "name";
        leaf name {
          type string;
        }
        container interval {
          tailf:cli-compact-syntax;
          tailf:cli-sequence-commands {
            tailf:cli-reset-all-siblings;
          }
          leaf interval {
            tailf:cli-drop-node-name;
            type uint8;
          }
          leaf timeout {
            type uint8;
          }
        }
        leaf interval-alt {
          tailf:cli-hide-in-submode;
          tailf:alt-name "interval";
          type uint8;
        }
        leaf timeout-alt {
          tailf:cli-hide-in-submode;
          tailf:alt-name "timeout";
          type uint8;
        }
        leaf retry {
          type uint8;
        }
        leaf retry-alt {
          tailf:cli-hide-in-submode;
          tailf:alt-name "retry";
          type uint8;
        }
        leaf up-retry {
          type uint8;
        }
        leaf up-retry-alt {
          tailf:cli-hide-in-submode;
          tailf:alt-name "up-retry";
          type uint8;
        }
        leaf strictly-retry-on-server-error-response {
          type empty;
        }
        leaf disable-after-down {
          type empty;
        }
        leaf override-port {
          type uint16;
        }
        leaf override-ipv4 {
          type inet:ipv4-address;
        }
        leaf override-ipv6 {
          type inet:ipv6-address;
        }
        container method {
          tailf:cli-compact-syntax;
          choice method-choice {
            container icmp {
              leaf transparent {
                type union {
                  type inet:ipv4-address;
                  type inet:ipv6-address;
                }
              }
            }
            container http {
              tailf:cli-compact-syntax;
              presence "true";
              leaf port {
                type uint16;
              }
              // NCS expand uses statement
              leaf username {
                type string;
              }
              leaf password {
                tailf:cli-optional-in-sequence;
                type string;
              }
              leaf url {
                type empty;
              }
              leaf method {
                tailf:cli-drop-node-name;
                type enumeration {
                  enum "GET";
                  enum "POST";
                  enum "HEAD";
                }
              }
              leaf path {
                tailf:cli-drop-node-name;
                type string;
              }
              leaf postdata {
                type string;
              }
              leaf postfile {
                type string;
              }
              container expect {
                tailf:cli-flatten-container;
                choice expect-choice {
                  leaf response-code {
                    type string;
                  }
                  leaf text {
                    tailf:cli-drop-node-name;
                    type string;
                  }
                }
              }
              leaf maintenance-code {
                type string;
              }
              leaf host {
                type string;
              }
            }
            container https {
              tailf:cli-compact-syntax;
              presence "true";
              leaf port {
                type uint16;
              }
              leaf disable-sslv2hello {
                type empty;
              }
              uses ncs_rpc_notif_password-grouping;
              leaf url {
                type empty;
              }
              leaf method {
                tailf:cli-drop-node-name;
                type enumeration {
                  enum "GET";
                  enum "POST";
                  enum "HEAD";
                }
              }
              leaf path {
                tailf:cli-drop-node-name;
                type string;
              }
              container expect {
                tailf:cli-flatten-container;
                choice expect-choice {
                  leaf response-code {
                    type string;
                  }
                  leaf text {
                    tailf:cli-drop-node-name;
                    type string;
                  }
                }
              }
              leaf maintenance-code {
                type string;
              }
              leaf host {
                type string;
              }
              container cert {
                tailf:cli-compact-syntax;
                tailf:cli-flatten-container;
                leaf cert {
                  tailf:cli-drop-node-name;
                  type string;
                }
                leaf key {
                  type string;
                }
              }
            }
            container tcp {
              tailf:cli-compact-syntax;
              tailf:cli-sequence-commands;
              leaf port {
                type uint16;
              }
              leaf method {
                tailf:cli-drop-node-name;
                type enumeration {
                  enum "send";
                  enum "halfopen";
                }
              }
              leaf sendcontent {
                tailf:cli-drop-node-name;
                type string;
              }
              leaf response {
                type empty;
              }
              leaf contains {
                type string;
              }
            }
            container udp {
              leaf port {
                type uint16;
              }
            }
            container ftp {
              presence "present";
              tailf:cli-compact-syntax;
              leaf port {
                type uint16;
              }
              uses ncs_rpc_notif_password-grouping;
            }
            container snmp {
              tailf:cli-compact-syntax;
              presence "present";
              leaf community {
                type string;
              }
              leaf oid {
                type union {
                  type enumeration {
                    enum "sysDescr";
                    enum "sysUpTime";
                    enum "sysName";
                  }
                  type string;
                }
              }
              leaf operation {
                type enumeration {
                  enum "get";
                  enum "getnext";
                }
              }
              leaf port {
                type uint16;
              }
            }
            container smtp {
              tailf:cli-compact-syntax;
              leaf domain {
                type string;
              }
              leaf port {
                type uint16;
              }
            }
            container dns {
              tailf:cli-compact-syntax;
              tailf:cli-sequence-commands;
              choice dns-health-choice {
                leaf domain {
                  type string;
                }
                leaf ipaddress {
                  type inet:ip-address;
                }
              }
              leaf port {
                tailf:cli-optional-in-sequence;
                type uint16;
              }
              leaf expect {
                tailf:cli-optional-in-sequence;
                type empty;
              }
              leaf response-code {
                type string;
              }
              leaf recurse {
                tailf:cli-optional-in-sequence;
                type enumeration {
                  enum "enabled";
                  enum "disabled";
                }
              }
              leaf tcp {
                tailf:cli-optional-in-sequence;
                type empty;
              }
              leaf type {
                type enumeration {
                  enum "A";
                  enum "CNAME";
                  enum "SOA";
                  enum "PTR";
                  enum "MX";
                  enum "TXT";
                  enum "AAAA";
                }
              }
            }
            container pop3 {
              tailf:cli-compact-syntax;
              uses ncs_rpc_notif_password-grouping;
              leaf port {
                type uint16;
              }
            }
            container imap {
              tailf:cli-compact-syntax;
              leaf port {
                type uint16;
              }
              uses ncs_rpc_notif_password-grouping;
              leaf-list auth {
                tailf:cli-flat-list-syntax;
                type enumeration {
                  enum "plain";
                  enum "cram-md5";
                  enum "login";
                }
              }
            }
            container sip {
              tailf:cli-compact-syntax;
              leaf port {
                type uint16;
              }
              leaf register {
                type empty;
              }
              leaf tcp {
                type empty;
              }
              leaf expect-response-code {
                type string;
              }
            }
            container radius {
              tailf:cli-compact-syntax;
              uses ncs_rpc_notif_password-grouping;
              leaf secret {
                mandatory true;
                type string;
              }
              leaf port {
                type uint16;
              }
            }
            container tacplus {
              tailf:cli-compact-syntax;
              uses ncs_rpc_notif_password-grouping;
              leaf secret {
                type string;
              }
              leaf port {
                type uint16;
              }
            }
            container ldap {
              tailf:cli-compact-syntax;
              leaf port {
                type uint16;
              }
              leaf overssl {
                type empty;
              }
              leaf binddn {
                type string;
              }
              leaf password {
                mandatory true;
                type string;
              }
            }
            container rtsp {
              tailf:cli-compact-syntax;
              leaf port {
                type uint16;
              }
              leaf rtspurl {
                type string;
              }
            }
            container database {
              tailf:cli-compact-syntax;
              tailf:cli-sequence-commands {
                tailf:cli-reset-siblings;
              }
              leaf dbtype {
                tailf:cli-drop-node-name;
                type enumeration {
                  enum "mssql";
                  enum "mysql";
                  enum "oracle";
                  enum "postgresql";
                }
              }
              leaf db-name {
                type string;
              }
              uses ncs_rpc_notif_password-grouping;
              leaf send {
                type string;
              }
              leaf receive {
                type string;
              }
              leaf row {
                type uint8;
              }
              leaf column {
                type uint8;
              }
            }
            container external {
              leaf program {
                type string;
              }
            }
            container ntp;
            container compound {
              leaf name {
                tailf:cli-drop-node-name;
                tailf:cli-multi-value;
                type string;
              }
            }
          }
        }
      }
    }
  }

  grouping ncs_rpc_notif_accounting-grouping {
    container accounting {
      container commands {
        tailf:cli-compact-syntax;
        tailf:cli-sequence-commands {
          tailf:cli-reset-all-siblings;
        }
        leaf level {
          tailf:cli-drop-node-name;
          type uint32;
        }
        leaf stop-only {
          type empty;
        }
        leaf tacplus {
          type empty;
        }
      }
      leaf debug {
        type uint8;
      }
      container exec {
        tailf:cli-compact-syntax;
        tailf:cli-sequence-commands {
          tailf:cli-reset-all-siblings;
        }
        choice st-st {
          leaf start-stop {
            type empty;
          }
          leaf stop-only {
            type empty;
          }
        }
        choice service {
          leaf tacplus {
            type empty;
          }
          leaf radius {
            type empty;
          }
        }
      }
    }
  }

  grouping ncs_rpc_notif_acos-events-grouping {
    container acos-events {
      container logdb {
        leaf enable-all {
          type empty;
        }
        leaf enable-cgn {
          type empty;
        }
        leaf enable-http-forward-proxy {
          type empty;
        }
        leaf enable-smtp {
          type empty;
        }
      }
    }
  }

  grouping ncs_rpc_notif_authorization-grouping {
    container authorization {
      container commands {
        tailf:cli-compact-syntax;
        tailf:cli-sequence-commands {
          tailf:cli-reset-all-siblings;
        }
        leaf level {
          tailf:cli-drop-node-name;
          type uint32;
        }
        leaf-list method {
          tailf:cli-flat-list-syntax;
          type enumeration {
            enum "tacplus";
            enum "none";
          }
        }
      }
    }
  }

  grouping ncs_rpc_notif_bgp-grouping {
    container bgp {
      leaf extended-asn-cap {
        type empty;
      }
    }
  }

  grouping ncs_rpc_notif_lacp-grouping {
    container lacp {
      tailf:cli-compact-syntax;
      leaf system-priority {
        type uint32;
      }
    }
  }

  grouping ncs_rpc_notif_slb-grouping {
    container slb {
      container graceful-shutdown {
        tailf:cli-sequence-commands {
          tailf:cli-reset-siblings;
        }
        tailf:cli-compact-syntax;
        leaf timeout {
          tailf:cli-drop-node-name;
          type uint16;
        }
        leaf when {
          must '../timeout' {
            tailf:xpath-root 3;
          }
          tailf:cli-drop-node-name;
          type enumeration {
            enum "after-disable";
            enum "server";
            enum "virtual-server";
          }
        }
      }
      leaf disable-server-auto-reselect {
        type empty;
      }
      container buff-thresh {
        tailf:cli-sequence-commands {
          tailf:cli-reset-siblings;
        }
        tailf:cli-compact-syntax;
        leaf hw-buff {
          type uint32;
        }
        leaf relieve-thresh {
          type uint32;
        }
        leaf sys-buff-low {
          type uint32;
        }
        leaf sys-buff-high {
          type uint32;
        }
      }
      container template {
        list server {
          key "name";
          leaf name {
            type string;
          }
          leaf health-check {
            type boolean;
          }
          container conn-limit {
            tailf:cli-sequence-commands {
              tailf:cli-reset-siblings;
            }
            tailf:cli-compact-syntax;
            leaf limit {
              tailf:cli-drop-node-name;
              type uint32;
            }
            leaf resume {
              must '../limit' {
                tailf:xpath-root 3;
              }
              tailf:cli-optional-in-sequence;
              type uint32;
            }
            leaf no-logging {
              type empty;
            }
          }
          container conn-rate-limit {
            tailf:cli-sequence-commands {
              tailf:cli-reset-siblings;
            }
            tailf:cli-compact-syntax;
            leaf limit {
              tailf:cli-drop-node-name;
              type uint32;
            }
            leaf per {
              must '../limit' {
                tailf:xpath-root 3;
              }
              tailf:cli-optional-in-sequence;
              type enumeration {
                enum "100ms";
                enum "second";
              }
            }
            leaf no-logging {
              type empty;
            }
          }
          leaf dns-query-interval {
            type uint16;
          }
          leaf dynamic-server-prefix {
            type string;
          }
          leaf max-dynamic-server {
            type uint16;
          }
          leaf min-ttl-ratio {
            type uint16;
          }
          container slow-start {
            presence "present";
            tailf:cli-sequence-commands;
            tailf:cli-compact-syntax;
            leaf from {
              tailf:cli-optional-in-sequence;
              type uint16;
            }
            choice slow-start-choice {
              leaf add {
                tailf:cli-optional-in-sequence;
                type uint16;
              }
              leaf times {
                tailf:cli-optional-in-sequence;
                type uint8;
              }
            }
            leaf every {
              tailf:cli-optional-in-sequence;
              type uint8;
            }
            leaf till {
              type uint16;
            }
          }
        }
        list port {
          key "name";
          leaf name {
            type string;
          }
          container health-check {
            presence "true";
            choice mon-choice {
              leaf monitor {
                tailf:cli-drop-node-name;
                type string;
              }
              leaf ping {
                type empty;
              }
            }
          }
          container conn-limit {
            tailf:cli-sequence-commands {
              tailf:cli-reset-siblings;
            }
            tailf:cli-compact-syntax;
            leaf limit {
              tailf:cli-drop-node-name;
              type uint32;
            }
            leaf resume {
              must '../limit' {
                tailf:xpath-root 3;
              }
              tailf:cli-optional-in-sequence;
              type uint32;
            }
            leaf no-logging {
              type empty;
            }
          }
          container conn-rate-limit {
            tailf:cli-sequence-commands {
              tailf:cli-reset-siblings;
            }
            tailf:cli-compact-syntax;
            leaf limit {
              tailf:cli-drop-node-name;
              type uint32;
            }
            leaf per {
              must '../limit' {
                tailf:xpath-root 3;
              }
              tailf:cli-optional-in-sequence;
              type enumeration {
                enum "100ms";
                enum "second";
              }
            }
            leaf no-logging {
              type empty;
            }
          }
          leaf dest-nat {
            type empty;
          }
          leaf down-grace-period {
            type uint32;
          }
          leaf dscp {
            type uint8;
          }
          container dynamic-member-priority {
            tailf:cli-sequence-commands {
              tailf:cli-reset-siblings;
            }
            tailf:cli-compact-syntax;
            leaf priority {
              tailf:cli-drop-node-name;
              type uint8;
            }
            leaf decrement {
              must '../priority' {
                tailf:xpath-root 3;
              }
              type uint8;
            }
          }
          container inband-health-check {
            presence "true";
            tailf:cli-sequence-commands {
              tailf:cli-reset-siblings;
            }
            tailf:cli-compact-syntax;
            leaf retry {
              tailf:cli-optional-in-sequence;
              type uint8;
            }
            leaf reassign {
              type uint8;
            }
          }
          leaf no-ssl {
            type empty;
          }
          container slow-start {
            presence "present";
            tailf:cli-sequence-commands;
            tailf:cli-compact-syntax;
            leaf from {
              tailf:cli-optional-in-sequence;
              type uint16;
            }
            choice slow-start-choice {
              leaf add {
                tailf:cli-optional-in-sequence;
                type uint16;
              }
              leaf times {
                tailf:cli-optional-in-sequence;
                type uint8;
              }
            }
            leaf every {
              tailf:cli-optional-in-sequence;
              type uint8;
            }
            leaf till {
              type uint16;
            }
          }
          leaf source-nat {
            type string;
          }
          leaf weight {
            type uint8;
          }
        }
        container cache;
        list client-ssl {
          key "name";
          leaf name {
            type string;
          }
          container cert {
            tailf:cli-sequence-commands {
              tailf:cli-reset-siblings;
            }
            tailf:cli-compact-syntax;
            leaf cert {
              tailf:cli-drop-node-name;
              type string;
            }
            leaf partition {
              type string;
            }
          }
          container chain-cert {
            tailf:cli-sequence-commands {
              tailf:cli-reset-siblings;
            }
            tailf:cli-compact-syntax;
            leaf chain-cert {
              tailf:cli-drop-node-name;
              type string;
            }
            leaf partition {
              type string;
            }
          }
          list ca-cert {
            tailf:cli-suppress-mode;
            tailf:cli-compact-syntax;
            key "name";
            leaf name {
              type string;
            }
            leaf partition {
              type string;
            }
          }
          container key {
            tailf:cli-sequence-commands;
            tailf:cli-compact-syntax;
            leaf key-name {
              tailf:cli-drop-node-name;
              type string;
            }
            leaf partition {
              tailf:cli-optional-in-sequence;
              type string;
            }
            leaf pass-phrase {
              type empty;
            }
            leaf pass-phrase-value {
              tailf:cli-drop-node-name;
              type string;
            }
          }
          list cipher {
            tailf:cli-suppress-mode;
            key "name";
            leaf name {
              type ncs_rpc_notif_cipher;
            }
          }
          container template {
            container cipher {
              leaf name {
                tailf:cli-drop-node-name;
                type string;
              }
            }
          }
          leaf close-notify {
            type empty;
          }
          leaf renegotiation-disable {
            type empty;
          }
          leaf session-cache-size {
            type uint16;
          }
          leaf session-cache-timeout {
            type uint32;
          }
          leaf session-ticket-lifetime {
            type uint32;
          }
          uses ncs_rpc_notif_slb-template-version-grouping;
          leaf auth-username-attribute {
            type string;
          }
          container certificate {
            tailf:cli-compact-syntax;
            tailf:cli-sequence-commands {
              tailf:cli-reset-siblings;
            }
            leaf name {
              tailf:cli-drop-node-name;
              type string;
            }
            leaf key {
              type string;
            }
            leaf pass-phrase {
              tailf:cli-break-sequence-commands;
              type tailf:aes-cfb-128-encrypted-string;
            }
            leaf chain-cert {
              type string;
            }
          }
          leaf disable-sslv3 {
            type empty;
          }
        }
        list connection-reuse {
          key "name";
          leaf name {
            type string;
          }
          leaf timeout {
            type uint16;
          }
          leaf limit-per-server {
            type uint16;
          }
          container keep-alive-conn {
            tailf:cli-sequence-commands {
              tailf:cli-reset-siblings;
            }
            tailf:cli-compact-syntax;
            presence "present";
            leaf preopen {
              tailf:cli-optional-in-sequence;
              type empty;
            }
            leaf connections {
              tailf:cli-drop-node-name;
              tailf:cli-optional-in-sequence;
              type uint16;
            }
          }
        }
        container diameter;
        list dns {
          key "name";
          leaf name {
            type string;
          }
          leaf max-query-length {
            type uint32;
          }
          leaf max-cache-size {
            type uint32;
          }
          leaf max-cache-entry-size {
            type uint32;
          }
          container dns-log-enable {
            leaf period {
              type uint32;
            }
          }
          leaf query-id-switch {
            type empty;
          }
        }
        list dynamic-service {
          tailf:cli-compact-syntax;
          key "name";
          leaf name {
            type string;
          }
          container dns {
            tailf:cli-compact-syntax;
            list server {
              tailf:cli-suppress-mode;
              key "ip";
              leaf ip {
                type string;
              }
            }
          }
        }
        list http {
          key "name";
          leaf name {
            type string;
          }
          container insert-client-ip {
            tailf:cli-compact-syntax;
            presence "true";
            leaf header-name {
              tailf:cli-drop-node-name;
              type string;
            }
            leaf replace {
              type empty;
            }
          }
          container non-http-bypass {
            leaf service-group {
              type string;
            }
          }
          container url-hash-persist {
            tailf:cli-sequence-commands {
              tailf:cli-reset-siblings;
            }
            tailf:cli-compact-syntax;
            leaf offset {
              tailf:cli-optional-in-sequence;
              type uint8;
            }
            choice hash-choice {
              leaf first {
                type uint8;
              }
              leaf last {
                type uint8;
              }
            }
            leaf use-server-status {
              tailf:cli-optional-in-sequence;
              type empty;
            }
          }
          list host-switching {
            tailf:cli-suppress-mode;
            key "match-type identifier";
            leaf match-type {
              type enumeration {
                enum "contains";
                enum "ends-with";
                enum "equals";
                enum "starts-with";
              }
            }
            leaf identifier {
              type string;
            }
            leaf service-group {
              mandatory true;
              type string;
            }
          }
          list url-switching {
            tailf:cli-suppress-mode;
            key "match-type identifier";
            leaf match-type {
              type enumeration {
                enum "contains";
                enum "ends-with";
                enum "equals";
                enum "starts-with";
              }
            }
            leaf identifier {
              type string;
            }
            leaf service-group {
              mandatory true;
              type string;
            }
          }
          leaf request-line-case-insensitive {
            type empty;
          }
          container redirect-rewrite {
            leaf secure {
              type empty;
            }
          }
          list request-header-insert {
            tailf:cli-suppress-mode;
            key "header";
            leaf header {
              type string;
            }
            leaf insert-mode {
              tailf:cli-drop-node-name;
              type enumeration {
                enum "insert-if-not-exist";
                enum "insert-always";
              }
            }
          }
          list response-header-insert {
            tailf:cli-suppress-mode;
            key "header";
            leaf header {
              type string;
            }
            leaf insert-mode {
              tailf:cli-drop-node-name;
              type enumeration {
                enum "insert-if-not-exist";
                enum "insert-always";
              }
            }
          }
          leaf keep-client-alive {
            type empty;
          }
        }
        container persist {
          list source-ip {
            key "name";
            leaf name {
              type string;
            }
            leaf dont-honor-conn-rules {
              type empty;
            }
            leaf enforce-higher-priority {
              type empty;
            }
            leaf incl-sport {
              type empty;
            }
            container match-type {
              tailf:cli-sequence-commands {
                tailf:cli-reset-siblings;
              }
              tailf:cli-compact-syntax;
              choice match-choice {
                leaf server {
                  type empty;
                }
                leaf service-group {
                  type empty;
                }
              }
              leaf scan-all-members {
                type empty;
              }
            }
            leaf netmask {
              type union {
                type ncs_rpc_notif_ipv4-mask;
                type string;
              }
            }
            leaf netmask6 {
              type uint8;
            }
            leaf timeout {
              type uint16;
            }
          }
          list cookie {
            key "id";
            leaf id {
              type string;
            }
            leaf name {
              type string;
            }
            leaf expire {
              type uint32;
            }
            container match-type {
              tailf:cli-sequence-commands {
                tailf:cli-reset-siblings;
              }
              tailf:cli-compact-syntax;
              leaf server {
                tailf:cli-optional-in-sequence;
                type empty;
              }
              leaf service-group {
                tailf:cli-optional-in-sequence;
                type empty;
              }
              leaf scan-all-members {
                tailf:cli-optional-in-sequence;
                type empty;
              }
            }
            leaf insert-always {
              type empty;
            }
            leaf pass-thru {
              type empty;
            }
          }
          list destination-ip {
            key "name";
            leaf name {
              type string;
            }
          }
          list ssl-sid {
            key "name";
            leaf name {
              type string;
            }
            leaf timeout {
              type uint16;
            }
          }
        }
        list policy {
          key "name";
          leaf name {
            type string;
          }
          leaf proxy-keep-alive {
            type empty;
          }

          grouping stp-class-list-grouping {
            list lid {
              tailf:cli-compact-syntax;
              tailf:cli-delete-when-empty;
              key "limit-id";
              leaf limit-id {
                type uint32;
              }
              leaf class-list-group {
                type string;
              }
              container action {
                tailf:cli-compact-syntax;
                tailf:cli-sequence-commands {
                  tailf:cli-reset-siblings;
                }
                choice action-choice {
                  leaf drop {
                    type empty;
                  }
                  leaf forward-to-internet {
                    type string;
                  }
                  leaf forward-to-service-group {
                    type string;
                  }
                }
                leaf log {
                  type empty;
                }
              }
              leaf conn-limit {
                type uint32;
              }
              container conn-rate-limit {
                tailf:cli-sequence-commands {
                  tailf:cli-reset-siblings;
                }
                tailf:cli-compact-syntax;
                leaf limit {
                  tailf:cli-drop-node-name;
                  type uint32;
                }
                leaf per {
                  must '../limit' {
                    tailf:xpath-root 3;
                  }
                  type uint16;
                }
              }
              leaf request-limit {
                type uint32;
              }
              container request-rate-limit {
                tailf:cli-sequence-commands {
                  tailf:cli-reset-all-siblings;
                }
                tailf:cli-compact-syntax;
                leaf limit {
                  tailf:cli-drop-node-name;
                  type uint32;
                }
                leaf per {
                  must '../limit' {
                    tailf:xpath-root 3;
                  }
                  type uint16;
                }
              }
              container over-limit-action {
                tailf:cli-compact-syntax;
                tailf:cli-sequence-commands {
                  tailf:cli-reset-siblings;
                }
                leaf over-limit-action-choice {
                  tailf:cli-drop-node-name;
                  type enumeration {
                    enum "dns-cache-disable";
                    enum "dns-cache-enable";
                    enum "forward";
                    enum "reset";
                    enum "lockout";
                    enum "log";
                  }
                }
                leaf lockout {
                  tailf:cli-optional-in-sequence;
                  type uint16;
                }
                leaf lockout-val {
                  tailf:cli-optional-in-sequence;
                  tailf:cli-drop-node-name;
                  type uint16;
                }
                leaf log {
                  tailf:cli-optional-in-sequence;
                  type empty;
                }
                leaf log-val {
                  tailf:cli-drop-node-name;
                  tailf:cli-optional-in-sequence;
                  type uint16;
                }
              }
            }
            container client-ip {
              tailf:cli-compact-syntax;
              choice client-ip-choice {
                leaf l3-dest {
                  type empty;
                }
                leaf l7-header {
                  type empty;
                }
              }
              leaf l7-header-string {
                tailf:cli-drop-node-name;
                type string;
              }
            }
          }
          container class-list {
            leaf name {
              type string;
            }
            uses stp-class-list-grouping;
          }
          container class-list-alt {
            tailf:alt-name "class-list";
            tailf:cli-add-mode;
            leaf name {
              tailf:cli-drop-node-name;
              tailf:cli-hide-in-submode;
              type string;
            }
            uses stp-class-list-grouping;
          }
          leaf class-list-group {
            type string;
          }
          container bw-list {
            tailf:cli-compact-syntax;
            leaf name {
              type string;
            }
            list id {
              tailf:cli-compact-syntax;
              tailf:cli-suppress-mode;
              key "id";
              leaf id {
                type uint32;
              }
              leaf service-group {
                type string;
              }
            }
          }
        }
        list server-ssl {
          key "name";
          leaf name {
            type string;
          }
          leaf cert {
            type string;
          }
          leaf ca-cert {
            type string;
          }
          list cipher {
            tailf:cli-suppress-mode;
            key "name";
            leaf name {
              type ncs_rpc_notif_cipher;
            }
          }
          container server-certificate-error {
            tailf:cli-compact-syntax;
            leaf trap {
              type empty;
            }
            leaf email {
              type empty;
            }
            leaf logging {
              type empty;
            }
            leaf ignore {
              type empty;
            }
          }
          leaf close-notify {
            type empty;
          }
          container key {
            tailf:cli-sequence-commands;
            tailf:cli-compact-syntax;
            leaf key-name {
              tailf:cli-drop-node-name;
              type string;
            }
            leaf partition {
              tailf:cli-optional-in-sequence;
              type string;
            }
            leaf pass-phrase {
              type empty;
            }
            leaf pass-phrase-value {
              tailf:cli-drop-node-name;
              type string;
            }
          }
          container template {
            container cipher {
              leaf name {
                tailf:cli-drop-node-name;
                type string;
              }
            }
          }
          uses ncs_rpc_notif_slb-template-version-grouping;
        }
        list sip {
          key "name";
          leaf name {
            type string;
          }
          leaf timeout {
            type uint32;
          }
          leaf call-id-persist-disable {
            type empty;
          }
          leaf insert-client-ip {
            type empty;
          }
        }
        container smtp;
        container streaming-media;
        list tcp {
          key "name";
          leaf name {
            type string;
          }
          leaf idle-timeout {
            type uint32;
          }
          container force-delete-timeout {
            tailf:cli-sequence-commands {
              tailf:cli-reset-siblings;
            }
            tailf:cli-compact-syntax;
            leaf timeout {
              tailf:cli-drop-node-name;
              type uint8;
            }
            leaf alive-if-active {
              must '../timeout' {
                tailf:xpath-root 3;
              }
              type empty;
            }
          }
          leaf half-close-idle-timeout {
            type uint16;
          }
          leaf initial-window-size {
            type uint16;
          }
          leaf lan-fast-ack {
            type empty;
          }
          leaf reset-fwd {
            type empty;
          }
          leaf reset-rev {
            type empty;
          }
        }
        list tcp-proxy {
          key "name";
          leaf name {
            type string;
          }
          leaf idle-timeout {
            type uint32;
          }
          leaf syn-retries {
            type uint8;
          }
          leaf retransmit-retries {
            type uint8;
          }
          leaf half-close-idle-timeout {
            type uint8;
          }
          leaf backend-wscale {
            type uint8;
          }
          leaf reset-fwd {
            type empty;
          }
          leaf reset-rev {
            type empty;
          }
          leaf receive-buffer {
            type uint32;
          }
          leaf transmit-buffer {
            type uint32;
          }
          leaf nagle {
            type empty;
          }
          leaf timewait {
            type uint32;
          }
          leaf reno {
            type empty;
          }
        }
        list udp {
          key "name";
          leaf name {
            type string;
          }
          leaf idle-timeout {
            type uint32;
          }
          container aging {
            choice aging-choice {
              leaf immediate {
                type empty;
              }
              container short {
                presence "present";
                leaf short-value {
                  tailf:cli-drop-node-name;
                  type uint8;
                }
              }
            }
          }
          leaf re-select-if-server-down {
            type empty;
          }
        }
        list virtual-port {
          key "name";
          leaf name {
            type string;
          }
          leaf reset-unknown-conn {
            type empty;
          }
          leaf ignore-tcp-msl {
            type empty;
          }
          leaf allow-syn-otherflags {
            type empty;
          }
          leaf snat-port-preserve {
            type empty;
          }
        }
        list external-service {
          key "name";
          leaf name {
            type string;
          }
          container timeout {
            tailf:cli-compact-syntax;
            leaf time {
              tailf:cli-drop-node-name;
              type uint8;
            }
            leaf action {
              type enumeration {
                enum "continue";
                enum "drop";
                enum "reset";
              }
            }
          }
          leaf service-group {
            type string;
          }
          container template {
            leaf tcp-proxy {
              type string;
            }
          }
        }
        list virtual-server {
          key "name";
          leaf name {
            type string;
          }
          container conn-limit {
            tailf:cli-sequence-commands {
              tailf:cli-reset-siblings;
            }
            tailf:cli-compact-syntax;
            leaf limit {
              tailf:cli-drop-node-name;
              type uint32;
            }
            leaf reset {
              must '../limit' {
                tailf:xpath-root 3;
              }
              tailf:cli-optional-in-sequence;
              type empty;
            }
            leaf no-logging {
              type empty;
            }
          }
          container conn-rate-limit {
            tailf:cli-sequence-commands {
              tailf:cli-reset-siblings;
            }
            tailf:cli-compact-syntax;
            leaf limit {
              tailf:cli-drop-node-name;
              type uint32;
            }
            leaf per {
              must '../limit' {
                tailf:xpath-root 3;
              }
              tailf:cli-optional-in-sequence;
              type enumeration {
                enum "100ms";
                enum "second";
              }
            }
            leaf reset {
              must '../limit' {
                tailf:xpath-root 3;
              }
              tailf:cli-optional-in-sequence;
              type empty;
            }
            leaf no-logging {
              type empty;
            }
          }
          container icmp-rate-limit {
            tailf:cli-sequence-commands {
              tailf:cli-reset-siblings;
            }
            tailf:cli-compact-syntax;
            leaf rate {
              tailf:cli-drop-node-name;
              type uint16;
            }
            leaf lockup {
              must '../rate' {
                tailf:xpath-root 3;
              }
              type uint16;
            }
            leaf lockup-period {
              tailf:cli-drop-node-name;
              must '../lockup' {
                tailf:xpath-root 3;
              }
              type uint16;
            }
          }
          leaf subnet-gratuitous-arp {
            type empty;
          }
        }
        list cipher {
          key "name";
          leaf name {
            type string;
          }

          grouping cipher-prio-grouping {
            leaf priority {
              type uint8;
            }
          }
          container SSL3_RSA_DES_192_CBC3_SHA {
            presence "present";
            uses cipher-prio-grouping;
          }
          container SSL3_RSA_DES_40_CBC_SHA {
            presence "present";
            uses cipher-prio-grouping;
          }
          container SSL3_RSA_DES_64_CBC_SHA {
            presence "present";
            uses cipher-prio-grouping;
          }
          container SSL3_RSA_RC4_128_MD5 {
            presence "present";
            uses cipher-prio-grouping;
          }
          container SSL3_RSA_RC4_128_SHA {
            presence "present";
            uses cipher-prio-grouping;
          }
          container SSL3_RSA_RC4_40_MD5 {
            presence "present";
            uses cipher-prio-grouping;
          }
          container TLS1_RSA_AES_128_SHA {
            presence "present";
            uses cipher-prio-grouping;
          }
          container TLS1_RSA_AES_256_SHA {
            presence "present";
            uses cipher-prio-grouping;
          }
          container TLS1_RSA_EXPORT1024_RC4_56_MD5 {
            presence "present";
            uses cipher-prio-grouping;
          }
          container TLS1_RSA_EXPORT1024_RC4_56_SHA {
            presence "present";
            uses cipher-prio-grouping;
          }
          container TLS1_RSA_AES_128_SHA256 {
            presence "present";
            uses cipher-prio-grouping;
          }
          container TLS1_RSA_AES_256_SHA256 {
            presence "present";
            uses cipher-prio-grouping;
          }
          container TLS1_DHE_RSA_AES_128_GCM_SHA256 {
            presence "present";
            uses cipher-prio-grouping;
          }
          container TLS1_DHE_RSA_AES_128_SHA {
            presence "present";
            uses cipher-prio-grouping;
          }
          container TLS1_DHE_RSA_AES_128_SHA256 {
            presence "present";
            uses cipher-prio-grouping;
          }
          container TLS1_DHE_RSA_AES_256_GCM_SHA384 {
            presence "present";
            uses cipher-prio-grouping;
          }
          container TLS1_DHE_RSA_AES_256_SHA {
            presence "present";
            uses cipher-prio-grouping;
          }
          container TLS1_DHE_RSA_AES_256_SHA256 {
            presence "present";
            uses cipher-prio-grouping;
          }
          container TLS1_ECDHE_ECDSA_AES_128_GCM_SHA256 {
            presence "present";
            uses cipher-prio-grouping;
          }
          container TLS1_ECDHE_ECDSA_AES_128_SHA {
            presence "present";
            uses cipher-prio-grouping;
          }
          container TLS1_ECDHE_ECDSA_AES_128_SHA256 {
            presence "present";
            uses cipher-prio-grouping;
          }
          container TLS1_ECDHE_ECDSA_AES_256_GCM_SHA384 {
            presence "present";
            uses cipher-prio-grouping;
          }
          container TLS1_ECDHE_ECDSA_AES_256_SHA {
            presence "present";
            uses cipher-prio-grouping;
          }
          container TLS1_ECDHE_RSA_AES_128_GCM_SHA256 {
            presence "present";
            uses cipher-prio-grouping;
          }
          container TLS1_ECDHE_RSA_AES_128_SHA {
            presence "present";
            uses cipher-prio-grouping;
          }
          container TLS1_ECDHE_RSA_AES_128_SHA256 {
            presence "present";
            uses cipher-prio-grouping;
          }
          container TLS1_ECDHE_RSA_AES_256_GCM_SHA384 {
            presence "present";
            uses cipher-prio-grouping;
          }
          container TLS1_ECDHE_RSA_AES_256_SHA {
            presence "present";
            uses cipher-prio-grouping;
          }
          container TLS1_RSA_AES_128_GCM_SHA256 {
            presence "present";
            uses cipher-prio-grouping;
          }
          container TLS1_RSA_AES_256_GCM_SHA384 {
            presence "present";
            uses cipher-prio-grouping;
          }
        }
      }
      list server {
        key "name";
        unique "address";
        leaf name {
          type string;
        }
        leaf address {
          tailf:cli-drop-node-name;
          tailf:cli-hide-in-submode;
          mandatory true;
          type union {
            type inet:ipv4-address;
            type inet:ipv6-address;
            type string;
          }
        }
        leaf disable {
          type empty;
        }
        choice hc-choice {
          leaf health-check {
            type boolean;
          }
          container health-check-conf {
            tailf:cli-drop-node-name;
            container health-check {
              choice monitor-choice {
                leaf ping {
                  type empty;
                }
                leaf host {
                  tailf:cli-drop-node-name;
                  type string;
                }
              }
            }
          }
          leaf health-check-disable {
            type empty;
          }
        }
        container conn-limit {
          tailf:cli-sequence-commands {
            tailf:cli-reset-siblings;
          }
          tailf:cli-compact-syntax;
          leaf limit {
            tailf:cli-drop-node-name;
            type uint32;
          }
          leaf resume {
            must '../limit' {
              tailf:xpath-root 3;
            }
            tailf:cli-optional-in-sequence;
            type uint32;
          }
          leaf no-logging {
            type empty;
          }
        }
        leaf conn-resume {
          type uint32;
        }
        leaf extended-stats {
          type empty;
        }
        leaf external-ip {
          type inet:ipv4-address;
        }
        container ha-priority-cost {
          tailf:cli-sequence-commands {
            tailf:cli-reset-siblings;
          }
          tailf:cli-compact-syntax;
          leaf cost {
            tailf:cli-drop-node-name;
            type uint8;
          }
          leaf ha-group {
            type union {
              type enumeration {
                enum "all";
              }
              type uint8;
            }
          }
        }
        leaf ipv6 {
          type inet:ipv6-address;
        }
        leaf slow-start {
          type empty;
        }
        leaf spoofing-cache {
          type empty;
        }
        leaf stats-data-disable {
          type empty;
        }
        leaf weight {
          type uint8;
        }
        list port {
          key "number tcpudp";
          leaf number {
            type uint16;
          }
          leaf tcpudp {
            type enumeration {
              enum "tcp";
              enum "udp";
            }
          }
          container conn-limit {
            tailf:cli-sequence-commands {
              tailf:cli-reset-siblings;
            }
            tailf:cli-compact-syntax;
            leaf limit {
              tailf:cli-drop-node-name;
              type uint32;
            }
            leaf resume {
              must '../limit' {
                tailf:xpath-root 3;
              }
              tailf:cli-optional-in-sequence;
              type uint32;
            }
            leaf no-logging {
              type empty;
            }
          }
          leaf conn-resume {
            type uint32;
          }
          leaf extended-stats {
            type empty;
          }
          container ha-priority-cost {
            tailf:cli-sequence-commands {
              tailf:cli-reset-siblings;
            }
            tailf:cli-compact-syntax;
            leaf cost {
              tailf:cli-drop-node-name;
              type uint8;
            }
            leaf ha-group {
              must '../cost' {
                tailf:xpath-root 3;
              }
              type union {
                type enumeration {
                  enum "all";
                }
                type uint8;
              }
            }
          }
          leaf health-check-disable {
            type empty;
          }
          container template {
            leaf port {
              type string;
            }
          }
          choice hc-choice {
            leaf health-check {
              type boolean;
            }
            container health-check-conf {
              tailf:cli-drop-node-name;
              container health-check {
                choice monitor-choice {
                  leaf ping {
                    type empty;
                  }
                  leaf host {
                    tailf:cli-drop-node-name;
                    type string;
                  }
                  container follow-port {
                    tailf:cli-compact-syntax;
                    tailf:cli-sequence-commands {
                      tailf:cli-reset-siblings;
                    }
                    leaf port {
                      tailf:cli-drop-node-name;
                      type uint16;
                    }
                    leaf tcpudp {
                      tailf:cli-drop-node-name;
                      type enumeration {
                        enum "tcp";
                        enum "udp";
                      }
                    }
                  }
                }
              }
            }
          }
          leaf no-ssl {
            type empty;
          }
          leaf stats-data-disable {
            type empty;
          }
          leaf state {
            tailf:cli-drop-node-name;
            type enumeration {
              enum "enable";
              enum "disable";
            }
          }
        }
        container template {
          leaf server {
            type string;
          }
        }
        leaf state {
          tailf:cli-drop-node-name;
          type enumeration {
            enum "enable";
            enum "disable";
          }
        }
      }
      list service-group {
        key "name tcpudp";
        unique "name";
        leaf name {
          type string;
        }
        leaf tcpudp {
          type enumeration {
            enum "tcp";
            enum "udp";
          }
        }
        leaf backup-server-event-log {
          type empty;
        }
        leaf extended-stats {
          type empty;
        }
        container health-check {
          tailf:cli-compact-syntax;
          tailf:cli-sequence-commands {
            tailf:cli-reset-siblings;
          }
          choice monitor-choice {
            leaf ping {
              type empty;
            }
            leaf host {
              tailf:cli-drop-node-name;
              type string;
            }
          }
          leaf partition {
            type string;
          }
        }
        list member1 {
          tailf:cli-compact-syntax;
          tailf:cli-suppress-mode;
          tailf:alt-name "member";
          key "host port";
          leaf host {
            type string;
          }
          leaf port {
            type uint16;
          }
          leaf partition {
            type string;
          }
          leaf state {
            tailf:cli-drop-node-name;
            type enumeration {
              enum "enable";
              enum "disable";
            }
          }
          leaf priority {
            type uint8;
          }
        }
        list member2 {
          tailf:alt-name "member";
          key "host port";
          leaf host {
            type string;
          }
          leaf port {
            type uint16;
          }
          leaf partition {
            type string;
          }
          leaf state {
            tailf:cli-drop-node-name;
            type enumeration {
              enum "enable";
              enum "disable";
            }
          }
          leaf priority {
            type uint8;
          }
          leaf template {
            type string;
          }
        }
        container method {
          choice method-choice {
            leaf fastest-response {
              type empty;
            }
            container least-connection {
              presence "true";
              leaf pseudo-round-robin {
                type empty;
              }
            }
            leaf least-request {
              type empty;
            }
            leaf round-robin {
              type empty;
            }
            leaf round-robin-strict {
              type empty;
            }
            container service-least-connection {
              presence "true";
              leaf pseudo-round-robin {
                type empty;
              }
            }
            container service-weighted-least-connection {
              presence "true";
              leaf pseudo-round-robin {
                type empty;
              }
            }
            leaf stateless-dst-ip-hash {
              type empty;
            }
            leaf stateless-per-pkt-round-robin {
              type empty;
            }
            leaf stateless-src-dst-ip-hash {
              type empty;
            }
            leaf stateless-src-ip-hash {
              type empty;
            }
            leaf stateless-src-ip-only-hash {
              type empty;
            }
            container weighted-least-connection {
              presence "true";
              leaf pseudo-round-robin {
                type empty;
              }
            }
            leaf weighted-rr {
              type empty;
            }
          }
        }
        container min-active-member {
          tailf:cli-sequence-commands {
            tailf:cli-reset-siblings;
          }
          tailf:cli-compact-syntax;
          leaf min {
            tailf:cli-drop-node-name;
            type uint8;
          }
          leaf method {
            must '../min' {
              tailf:xpath-root 3;
            }
            tailf:cli-drop-node-name;
            type enumeration {
              enum "dynamic-priority";
              enum "skip-pri-set";
            }
          }
        }
        list priority {
          tailf:cli-suppress-mode;
          tailf:cli-delete-when-empty;
          key "prio";
          leaf prio {
            type uint8;
          }
          leaf action {
            tailf:cli-drop-node-name;
            type enumeration {
              enum "drop";
              enum "drop-if-exceed-limit";
              enum "proceed";
              enum "reset";
              enum "reset-if-exceed-limit";
            }
          }
        }
        container priority-affinity {
          presence "true";
        }
        leaf reset-on-server-selection-fail {
          type empty;
        }
        leaf stats-data-disable {
          type empty;
        }
      }
      list virtual-server {
        key "name";
        leaf name {
          type string;
        }
        leaf address {
          tailf:cli-drop-node-name;
          tailf:cli-hide-in-submode;
          mandatory true;
          type union {
            type inet:ipv4-address;
            type inet:ipv6-address;
          }
        }
        leaf netmask {
          tailf:cli-drop-node-name;
          tailf:cli-hide-in-submode;
          type union {
            type ncs_rpc_notif_ipv4-mask;
            type string;
          }
        }
        leaf acl {
          tailf:cli-hide-in-submode;
          type uint16;
        }
        leaf arp-disable {
          type empty;
        }
        leaf disable {
          type empty;
        }
        leaf extended-stats {
          type empty;
        }
        leaf ha-dynamic {
          type uint8;
        }
        choice disable-choice {
          leaf disable-when-any-port-down {
            type empty;
          }
          leaf disable-when-all-ports-down {
            type empty;
          }
        }
        leaf ha-group {
          type uint16;
        }
        leaf redistribution-flagged {
          type empty;
        }
        leaf stats-data-disable {
          type empty;
        }
        leaf vrid {
          type uint8;
        }
        list port {
          key "id type";
          leaf id {
            type uint16;
          }
          leaf type {
            must "(../id = 0 and ../type = 'others') or ../type != 'others' " {
              tailf:xpath-root 3;
            }
            type enumeration {
              enum "diameter";
              enum "dns-udp";
              enum "fast-http";
              enum "ftp";
              enum "http";
              enum "https";
              enum "mms";
              enum "others";
              enum "radius";
              enum "rtsp";
              enum "sip";
              enum "sip-tcp";
              enum "sips";
              enum "smtp";
              enum "ssl-proxy";
              enum "tcp";
              enum "tcp-proxy";
              enum "tftp";
              enum "udp";
            }
          }
          container access-list {
            tailf:cli-sequence-commands {
              tailf:cli-reset-siblings;
            }
            tailf:cli-compact-syntax;
            choice access-list-id {
              leaf acl-id {
                tailf:cli-drop-node-name;
                type uint16;
              }
              leaf name {
                type string;
              }
            }
            choice nat-choice {
              leaf source-nat-pool-alt1 {
                tailf:alt-name "source-nat-pool";
                type string;
              }
              leaf source-nat-pool-alt2 {
                tailf:alt-name "source-nat-pool";
                type string;
              }
              leaf source-nat-pool-alt3 {
                tailf:alt-name "source-nat-pool";
                type string;
              }
            }
            leaf sequence-number {
              type uint8;
            }
          }
          list aflex {
            tailf:cli-suppress-mode;
            key "id";
            leaf id {
              type string;
            }
          }
          container conn-limit {
            tailf:cli-sequence-commands {
              tailf:cli-reset-siblings;
            }
            tailf:cli-compact-syntax;
            leaf limit {
              tailf:cli-drop-node-name;
              type uint32;
            }
            leaf reset {
              must '../limit' {
                tailf:xpath-root 3;
              }
              tailf:cli-optional-in-sequence;
              type empty;
            }
            leaf no-logging {
              type empty;
            }
          }
          leaf def-selection-if-pref-failed-disable {
            type empty;
          }
          leaf disable {
            type empty;
          }
          leaf extended-stats {
            type empty;
          }
          leaf ha-conn-mirror {
            type empty;
            must "../type='tcp' or ../type='diameter' or ../type='ftp' or ../type='mms' or ../type='rtsp' or ../type='sip' or ../type='tftp' or ../type='udp'" {
              tailf:xpath-root 3;
            }
          }
          leaf message-switching {
            type empty;
          }
          leaf name {
            type string;
          }
          container no-dest-nat {
            presence "true";
            leaf port-translation {
              type empty;
            }
          }
          leaf pbslb {
            type empty;
          }
          leaf reset-on-server-selection-fail {
            type empty;
          }
          leaf redirect-to-https {
            type empty;
          }
          leaf support-http2 {
            type empty;
          }
          leaf service-group {
            type string;
          }
          leaf snat-on-vip {
            type empty;
          }
          container source-nat {
            choice source-nat-choice {
              container auto {
                presence "true";
                leaf precedence {
                  type empty;
                }
              }
              leaf class-list {
                type string;
              }
              list pool {
                tailf:cli-suppress-mode;
                tailf:cli-diff-create-before "../../service-group" {
                  tailf:xpath-root 3;
                  tailf:cli-when-target-create;
                }
                key "name";
                leaf name {
                  type string;
                }
              }
            }
          }
          leaf stats-data-disable {
            type empty;
          }
          leaf syn-cookie {
            type empty;
          }
          container use-default-if-no-server {
            presence "true";
            leaf sack {
              type empty;
            }
          }
          leaf use-rcv-hop-for-resp {
            type empty;
          }
          list template {
            tailf:cli-compact-syntax;
            tailf:cli-sequence-commands;
            tailf:cli-suppress-mode;
            tailf:cli-delete-when-empty;
            key "template-type";
            leaf template-type {
              type enumeration {
                enum "client-ssl";
                enum "diameter";
                enum "dynamic-service";
                enum "external-service";
                enum "http";
                enum "persist";
                enum "policy";
                enum "sip";
                enum "server-ssl";
                enum "tcp";
                enum "tcp-proxy";
                enum "udp";
                enum "virtual-port";
              }
            }
            leaf udp {
              tailf:cli-drop-node-name;
              type string;
            }
            leaf sip {
              tailf:cli-drop-node-name;
              type string;
            }
            leaf diameter {
              tailf:cli-drop-node-name;
              type string;
            }
            container persist {
              tailf:cli-drop-node-name;
              leaf source-ip {
                type string;
              }
              leaf destination-ip {
                type string;
              }
              leaf ssl-sid {
                type string;
              }
              leaf cookie {
                type string;
              }
            }
            leaf policy {
              tailf:cli-drop-node-name;
              type string;
            }
            leaf tcp {
              tailf:cli-drop-node-name;
              type string;
            }
            leaf tcp-proxy {
              tailf:cli-drop-node-name;
              type string;
            }
            leaf virtual-port {
              tailf:cli-drop-node-name;
              type string;
            }
            leaf client-ssl {
              tailf:cli-drop-node-name;
              type string;
            }
            leaf server-ssl {
              tailf:cli-drop-node-name;
              type string;
            }
            leaf http {
              tailf:cli-drop-node-name;
              type string;
            }
            leaf external-service {
              tailf:cli-drop-node-name;
              type string;
            }
            leaf dynamic-service {
              tailf:cli-drop-node-name;
              type string;
            }
          }
        }
        container template {
          leaf logging {
            type string;
          }
          leaf policy {
            type string;
          }
          leaf virtual-server {
            type string;
          }
        }
      }
      container resource-usage {
        uses ncs_rpc_notif_resource-usage-grouping;
      }
      leaf transparent-tcp-template {
        type string;
      }
    }
  }

  grouping ncs_rpc_notif_gslb-group-grouping {
    list group {
      key "name";
      leaf name {
        type string;
      }
      leaf config-merge {
        type empty;
      }
      leaf enable {
        type empty;
      }
      list primary {
        tailf:cli-suppress-mode;
        key "ip-address";
        leaf ip-address {
          type inet:ipv4-address;
        }
      }
      leaf priority {
        type uint8;
      }
    }
  }

  grouping ncs_rpc_notif_gslb-service-ip-grouping {
    list service-ip {
      key "name";
      leaf name {
        type string;
      }
      leaf disable {
        type empty;
      }
      leaf ip {
        tailf:cli-drop-node-name;
        tailf:cli-hide-in-submode;
        type union {
          type inet:ipv6-address;
          type inet:ipv4-address;
        }
      }
      leaf health-check {
        type string;
      }
      leaf health-check-protocol-disable {
        type empty;
      }
      leaf health-check-disable {
        type empty;
      }

      grouping service-port-grouping {
        leaf number {
          type uint16;
        }
        leaf udp-tcp {
          tailf:cli-drop-node-name;
          tailf:cli-prefix-key {
            tailf:cli-before-key 2;
          }
          type enumeration {
            enum "tcp";
            enum "udp";
          }
        }
        leaf service-name {
          type string;
        }
        leaf health-check {
          type string;
        }
        leaf health-check-protocol-disable {
          type empty;
        }
        leaf state {
          tailf:cli-drop-node-name;
          type enumeration {
            enum "enable";
            enum "disable";
          }
        }
      }
      list port {
        key "number service-name";
        uses service-port-grouping;
      }
      list service {
        key "number service-name";
        uses service-port-grouping;
      }
      container port-name {
        tailf:cli-drop-node-name;
        list port {
          key "number name";
          leaf number {
            type uint16;
          }
          leaf udp-tcp {
            tailf:cli-prefix-key {
              tailf:cli-before-key 2;
            }
            tailf:cli-drop-node-name;
            type enumeration {
              enum "tcp";
              enum "udp";
            }
          }
          leaf name {
            type string;
          }
          leaf health-check {
            type string;
          }
          leaf health-check-protocol-disable {
            type empty;
          }
          leaf state {
            tailf:cli-drop-node-name;
            type enumeration {
              enum "enable";
              enum "disable";
            }
          }
        }
      }
    }
  }

  grouping ncs_rpc_notif_gslb-site-grouping {
    list site {
      key "name";
      leaf name {
        type string;
      }
      list slb-dev {
        key "name";
        leaf name {
          type string;
        }
        leaf ip-address {
          tailf:cli-drop-node-name;
          tailf:cli-hide-in-submode;
          type inet:ipv4-address;
        }
        list vip-server {
          tailf:cli-suppress-mode;
          key "name";
          leaf name {
            type union {
              type inet:ipv6-address;
              type inet:ipv4-address;
              type string;
            }
          }
        }
      }
    }
  }

  grouping ncs_rpc_notif_gslb-policy-grouping {
    list policy {
      key "name";
      leaf name {
        type string;
      }
      container admin-ip {
        leaf top-only {
          type empty;
        }
      }
      leaf admin-ip-enable {
        type empty;
      }
      leaf geographic {
        type boolean;
      }
      container metric-order {
        tailf:cli-compact-syntax;
        leaf-list options {
          tailf:cli-drop-node-name;
          tailf:cli-flat-list-syntax;
          ordered-by user;
          type enumeration {
            enum "active-rdt";
            enum "active-servers";
            enum "admin-ip";
            enum "admin-preference";
            enum "bw-cost";
            enum "capacity";
            enum "connection-load";
            enum "geographic";
            enum "health-check";
            enum "least-response";
            enum "num-session";
            enum "weighted-ip";
            enum "weighted-site";
          }
        }
      }
      container dns {
        container active-only {
          presence "true";
          leaf fail-safe {
            type empty;
          }
        }
        leaf backup-server {
          type empty;
        }
        container selected-only {
          presence "true";
          leaf number {
            tailf:cli-drop-node-name;
            type uint8;
          }
        }
        leaf ttl {
          type uint32;
        }
        container server {
          choice dns-server-choice {
            leaf any {
              type empty;
            }
            leaf-list records {
              tailf:cli-drop-node-name;
              tailf:cli-flat-list-syntax;
              type enumeration {
                enum "addition-mx";
                enum "any-with-metric";
                enum "authoritative";
                enum "auto-ns";
                enum "auto-ptr";
                enum "cname";
                enum "full-list";
                enum "mx";
                enum "naptr";
                enum "ns";
                enum "ns-list";
                enum "ptr";
                enum "sec";
                enum "server-mode-only";
                enum "srv";
                enum "txt";
              }
            }
          }
        }
        container sticky {
          tailf:cli-compact-syntax;
          leaf ip-mask {
            tailf:cli-drop-node-name;
            type string;
          }
          leaf ipv6-mask {
            type uint8;
          }
          leaf aging-time {
            type uint16;
          }
        }
      }
      container active-rdt {
        leaf enable {
          type empty;
        }
        leaf single-shot {
          type empty;
        }
      }
    }
  }

  grouping ncs_rpc_notif_gslb-zone-grouping {
    list zone {
      key "name";
      leaf name {
        type string;
      }
      container service {
        list service-port {
          tailf:cli-drop-node-name;
          key "port";
          leaf port {
            type uint16;
          }
          uses ncs_rpc_notif_gslb-zone-service-grouping;
        }
        list service-port-name {
          tailf:cli-drop-node-name;
          key "port name";
          leaf port {
            type uint16;
          }
          leaf name {
            type string;
          }
          uses ncs_rpc_notif_gslb-zone-service-grouping;
        }
      }
    }
  }

  grouping ncs_rpc_notif_gslb-grouping {
    container gslb {
      uses ncs_rpc_notif_gslb-service-ip-grouping;
      uses ncs_rpc_notif_gslb-group-grouping;
      uses ncs_rpc_notif_gslb-site-grouping;
      uses ncs_rpc_notif_gslb-policy-grouping;
      uses ncs_rpc_notif_gslb-zone-grouping;
      container protocol {
        container enable {
          leaf controller {
            type empty;
          }
          leaf device {
            type empty;
          }
        }
      }
      container active-rdt {
        leaf icmp {
          type empty;
        }
      }
    }
  }

  grouping ncs_rpc_notif_bw-list-grouping {
    list bw-list {
      tailf:cli-compact-syntax;
      tailf:cli-suppress-mode;
      key "name";
      leaf name {
        type string;
      }
      leaf import-info {
        type string;
      }
    }
    list import-info {
      tailf:cli-suppress-mode;
      tailf:cli-compact-syntax;
      key "name";
      leaf name {
        type string;
      }
      leaf url {
        type string;
      }
      leaf username {
        type string;
      }
      leaf password {
        type string;
      }
    }
  }

  grouping ncs_rpc_notif_aflex-grouping {
    list aflex {
      key "name";
      leaf name {
        type string;
      }
      leaf script {
        type string;
      }
    }
  }

  grouping ncs_rpc_notif_action-grouping {
    list action {
      tailf:cli-suppress-mode;
      key "type";
      leaf type {
        type enumeration {
          enum "dnat";
          enum "drop";
          enum "one-to-one-snat";
          enum "pass-through";
          enum "snat";
        }
      }
      leaf pool {
        type string;
      }
      leaf domain {
        type string;
      }
    }
    leaf no-action {
      type empty;
    }
  }

  grouping ncs_rpc_notif_port-grouping {
    list port {
      tailf:cli-suppress-mode;
      tailf:cli-compact-syntax;
      key "id";
      leaf id {
        type uint16;
      }
      // NCS expand uses statement
      list action {
        tailf:cli-suppress-mode;
        key "type";
        leaf type {
          type enumeration {
            enum "dnat";
            enum "drop";
            enum "one-to-one-snat";
            enum "pass-through";
            enum "snat";
          }
        }
        leaf pool {
          type string;
        }
        leaf domain {
          type string;
        }
      }
      leaf no-action {
        type empty;
      }
    }
  }

  grouping ncs_rpc_notif_system-jumbo-global-grouping {
    container system-jumbo-global {
      leaf enable-jumbo {
        type empty;
      }
    }
  }

  grouping ncs_rpc_notif_hd-monitor-grouping {
    container hd-monitor {
      leaf enable {
        type empty;
      }
    }
  }

  grouping ncs_rpc_notif_timezone-grouping {
    container timezone {
      tailf:cli-compact-syntax;
      tailf:cli-sequence-commands {
        tailf:cli-reset-all-siblings;
      }
      leaf timezone {
        tailf:cli-drop-node-name;
        type enumeration {
          enum "UTC";
          enum "Pacific/Midway";
          enum "Pacific/Honolulu";
          enum "America/Anchorage";
          enum "America/Tijuana";
          enum "America/Los_Angeles";
          enum "America/Vancouver";
          enum "America/Phoenix";
          enum "America/Shiprock";
          enum "America/Chicago";
          enum "America/Mexico_City";
          enum "America/Regina";
          enum "America/Swift_Current";
          enum "America/Kentucky/Monticello";
          enum "America/Indiana/Marengo";
          enum "America/Montreal";
          enum "America/New_York";
          enum "America/Toronto";
          enum "America/Caracas";
          enum "America/Halifax";
          enum "America/Santiago";
          enum "America/St_Johns";
          enum "America/Buenos_Aires";
          enum "America/Godthab";
          enum "Atlantic/South_Georgia";
          enum "Atlantic/Azores";
          enum "Atlantic/Cape_Verde";
          enum "Europe/Dublin";
          enum "Africa/Algiers";
          enum "Europe/Amsterdam";
          enum "Europe/Belgrade";
          enum "Europe/Brussels";
          enum "Europe/Sarajevo";
          enum "Europe/Bucharest";
          enum "Africa/Cairo";
          enum "Europe/Athens";
          enum "Africa/Harare";
          enum "Asia/Jerusalem";
          enum "Europe/Helsinki";
          enum "Africa/Nairobi";
          enum "Asia/Baghdad";
          enum "Asia/Kuwait";
          enum "Europe/Moscow";
          enum "Asia/Tehran";
          enum "Asia/Baku";
          enum "Asia/Muscat";
          enum "Asia/Kabul";
          enum "Asia/Karachi";
          enum "Asia/Yekaterinburg";
          enum "Asia/Calcutta";
          enum "Asia/Katmandu";
          enum "Asia/Almaty";
          enum "Asia/Dhaka";
          enum "Indian/Chagos";
          enum "Asia/Rangoon";
          enum "Asia/Bangkok";
          enum "Asia/Krasnoyarsk";
          enum "Asia/Irkutsk";
          enum "Asia/Kuala_Lumpur";
          enum "Asia/Shanghai";
          enum "Asia/Taipei";
          enum "Australia/Perth";
          enum "Asia/Seoul";
          enum "Asia/Tokyo";
          enum "Asia/Yakutsk";
          enum "Australia/Adelaide";
          enum "Australia/Darwin";
          enum "Australia/Hobart";
          enum "Australia/Brisbane";
          enum "Asia/Vladivostok";
          enum "Australia/Sydney";
          enum "Pacific/Guam";
          enum "Asia/Magadan";
          enum "Pacific/Auckland";
          enum "Pacific/Fiji";
          enum "Pacific/Kwajalein";
          enum "Pacific/Enderbury";
        }
      }
      leaf nodst {
        type empty;
      }
    }
  }

  grouping ncs_rpc_notif_clock-grouping {
    container clock {
      tailf:cli-compact-syntax;
      uses ncs_rpc_notif_timezone-grouping;
      leaf nodst {
        type empty;
      }
    }
  }

  grouping ncs_rpc_notif_timezone-nodst-grouping {
    container timezone-nodst {
      tailf:cli-drop-node-name;
      tailf:cli-compact-syntax;
      tailf:cli-sequence-commands {
        tailf:cli-reset-siblings;
      }
      uses ncs_rpc_notif_timezone-grouping;
      leaf nodst {
        type empty;
      }
    }
  }

  grouping ncs_rpc_notif_ntp-grouping {
    container ntp {
      list server {
        key "name";
        leaf name {
          type string;
        }
        leaf interval {
          tailf:cli-hide-in-submode;
          tailf:cli-drop-node-name;
          type uint32;
        }
        leaf prefer {
          type empty;
        }
      }
    }
  }

  grouping ncs_rpc_notif_netflow-grouping {
    container netflow {
      container common {
        leaf max-packet-queue-time {
          type uint8;
        }
      }
      list monitor {
        key "name";
        leaf name {
          type string;
        }
        container destination {
          leaf ip {
            tailf:cli-drop-node-name;
            type union {
              type inet:ipv4-address;
              type inet:ipv6-address;
            }
          }
          leaf port {
            tailf:cli-drop-node-name;
            type uint16;
          }
        }
        leaf flow-timeout {
          type uint16;
        }
        leaf protocol {
          type enumeration {
            enum "v9";
            enum "v10";
          }
        }
        list record {
          tailf:cli-suppress-mode;
          key "name";
          leaf name {
            type enumeration {
              enum "dslite";
              enum "nat44";
              enum "nat64";
              enum "netflow-v5";
              enum "netflow-v5-ext";
              enum "port-batch-dslite";
              enum "port-batch-nat44";
              enum "port-batch-nat64";
              enum "port-batch-v2-dslite";
              enum "port-batch-v2-nat44";
              enum "port-batch-v2-nat64";
              enum "port-mapping-dslite";
              enum "port-mapping-nat44";
              enum "port-mapping-nat64";
              enum "sesn-event-dslite";
              enum "sesn-event-fw4";
              enum "sesn-event-fw6";
              enum "sesn-event-nat44";
              enum "sesn-event-nat64";
            }
          }
          leaf events {
            tailf:cli-drop-node-name;
            type enumeration {
              enum "both";
              enum "creation";
              enum "deletion";
            }
          }
        }
        container resend-template {
          leaf records {
            type uint32;
          }
          leaf timeout {
            type uint16;
          }
        }

        grouping sample-grouping {
          container sample {
            list ve {
              tailf:cli-suppress-mode;
              key "id";
              leaf id {
                type uint16;
              }
            }
          }
        }
        uses sample-grouping;

        grouping source-address-grouping {
          container source-address {
            leaf ip {
              type inet:ipv4-address;
            }
            leaf ipv6 {
              type inet:ipv6-address;
            }
          }
        }
        uses source-address-grouping;
        leaf source-ip-use-mgmt {
          type empty;
        }
        list device-context {
          key "id";
          leaf id {
            type uint8;
          }
          uses sample-grouping;
          uses source-address-grouping;
        }
      }
    }
  }

  grouping ncs_rpc_notif_trunk-grouping {
    list trunk {
      key "id";
      leaf id {
        type uint16;
      }
      leaf-list ethernet {
        tailf:cli-range-list-syntax;
        type uint8;
      }
      container disable {
        leaf-list ethernet {
          tailf:cli-range-list-syntax;
          type uint8;
        }
      }
      leaf ports-threshold {
        type uint16;
      }
      leaf port-threshold-timer {
        type uint16;
      }
      leaf name {
        type string;
      }
    }
  }

  grouping ncs_rpc_notif_class-list-grouping {
    list class-list {
      key "name";
      leaf name {
        type string;
      }
      leaf cl-type {
        tailf:cli-hide-in-submode;
        tailf:cli-drop-node-name;
        type enumeration {
          enum "ipv4";
          enum "ipv6";
          enum "string";
        }
      }
      choice v4v6str-choice {
        list str {
          tailf:cli-compact-syntax;
          tailf:cli-suppress-mode;
          key "str";
          leaf str {
            type string;
          }
          uses ncs_rpc_notif_lid-grouping;
          leaf string {
            tailf:cli-drop-node-name;
            type string;
          }
        }
        list v4 {
          tailf:cli-compact-syntax;
          tailf:cli-drop-node-name;
          tailf:cli-sequence-commands;
          tailf:cli-suppress-mode;
          key "ip";
          leaf ip {
            type inet:ipv4-prefix;
          }
          uses ncs_rpc_notif_lid-grouping;
        }
        list v6 {
          tailf:cli-compact-syntax;
          tailf:cli-drop-node-name;
          tailf:cli-sequence-commands;
          tailf:cli-suppress-mode;
          key "ip";
          leaf ip {
            type inet:ipv6-prefix;
          }
          uses ncs_rpc_notif_lid-grouping;
        }
      }
    }
  }

  grouping ncs_rpc_notif_class-list-group-grouping {
    list class-list-group {
      tailf:cli-compact-syntax;
      key "name";
      leaf name {
        type string;
      }
      list sequence-number {
        tailf:cli-suppress-mode;
        tailf:cli-compact-syntax;
        tailf:cli-sequence-commands;
        ordered-by user;
        key "id";
        leaf id {
          type uint32;
        }
        leaf host-url {
          tailf:cli-drop-node-name;
          type enumeration {
            enum "HOST";
            enum "URL";
          }
        }
        choice string-choice {
          leaf contains {
            type string;
          }
          leaf ends-with {
            type string;
          }
          leaf equals {
            type string;
          }
          leaf starts-with {
            type string;
          }
        }
        leaf lid {
          type uint32;
        }
      }
    }
  }

  grouping ncs_rpc_notif_tacacs-server-grouping {
    container tacacs-server {
      list host {
        tailf:cli-compact-syntax;
        tailf:cli-sequence-commands;
        tailf:cli-suppress-mode;
        key "name";
        leaf name {
          type union {
            type inet:ipv4-address;
            type inet:ipv4-address;
            type string;
          }
        }
        container secret {
          tailf:cli-compact-syntax;
          tailf:cli-sequence-commands;
          tailf:cli-flatten-container;
          leaf encrypted {
            tailf:cli-optional-in-sequence;
            type empty;
          }
          leaf secret {
            tailf:cli-optional-in-sequence;
            tailf:cli-drop-node-name;
            type string;
          }
        }
        leaf port {
          tailf:cli-break-sequence-commands;
          type uint16;
        }
        leaf timeout {
          type uint8;
        }
      }
    }
  }

  grouping ncs_rpc_notif_radius-server-grouping {
    container radius-server {
      list host {
        tailf:cli-suppress-mode;
        tailf:cli-sequence-commands {
          tailf:cli-reset-siblings;
        }
        tailf:cli-compact-syntax;
        key "name";
        leaf name {
          type union {
            type inet:ipv6-address;
            type string;
          }
        }
        container secret {
          tailf:cli-flatten-container;
          tailf:cli-sequence-commands {
            tailf:cli-reset-siblings;
          }
          tailf:cli-compact-syntax;
          leaf cleartext {
            tailf:cli-drop-node-name;
            tailf:cli-optional-in-sequence;
            type string;
          }
          leaf secret-encrypted {
            type string;
          }
          leaf auth-port {
            type uint32;
          }
          leaf acct-port {
            type uint32;
          }
          leaf timeout {
            type uint32;
          }
        }
      }
    }
  }

  grouping ncs_rpc_notif_authentication-grouping {
    container authentication {
      container enable {
        choice authetication-enable-choice {
          container local {
            leaf tacplus {
              type empty;
            }
          }
          container tacplus {
            presence "true";
            leaf local {
              type empty;
            }
          }
        }
      }
      leaf-list type {
        tailf:cli-flat-list-syntax;
        type enumeration {
          enum "tacplus";
          enum "radius";
          enum "local";
        }
      }
      leaf mode {
        type enumeration {
          enum "multiple";
          enum "single";
        }
      }
      container console {
        leaf-list type {
          tailf:cli-flat-list-syntax;
          type enumeration {
            enum "tacplus";
            enum "radius";
            enum "local";
          }
        }
      }
      leaf disable-local {
        type empty;
      }
      container login {
        leaf privilege-mode {
          type empty;
        }
      }
    }
  }

  grouping ncs_rpc_notif_vlan-grouping {
    list vlan {
      key "id";
      leaf id {
        type ncs_rpc_notif_vlan-index;
      }
      container untagged {
        tailf:cli-compact-syntax;
        leaf-list ethernet {
          tailf:cli-range-list-syntax;
          type uint8;
        }
        leaf trunk {
          type uint8;
        }
      }
      container tagged {
        tailf:cli-compact-syntax;
        leaf-list ethernet {
          tailf:cli-range-list-syntax;
          type uint8;
        }
        leaf trunk {
          type uint8;
        }
      }
      container router-interface {
        leaf ve {
          type ncs_rpc_notif_vlan-index;
        }
      }
      leaf name {
        type string;
      }
    }
  }

  grouping ncs_rpc_notif_ipv6-route-grouping {
    container route {
      list route-no-if {
        tailf:cli-drop-node-name;
        tailf:cli-compact-syntax;
        tailf:cli-suppress-mode;
        key "ip forwarding-router";
        leaf ip {
          type inet:ipv6-prefix;
        }
        leaf forwarding-router {
          tailf:cli-drop-node-name;
          type inet:ipv6-address;
        }
        leaf distance {
          tailf:cli-drop-node-name;
          type uint8;
        }
      }
      list route-if {
        tailf:cli-drop-node-name;
        tailf:cli-compact-syntax;
        tailf:cli-suppress-mode;
        key "ip forwarding-router interface-type interface-nr";
        leaf ip {
          type inet:ipv6-prefix;
        }
        leaf forwarding-router {
          tailf:cli-drop-node-name;
          type inet:ipv6-address;
        }
        leaf interface-type {
          type enumeration {
            enum "ethernet";
            enum "trunk";
            enum "ve";
          }
        }
        leaf interface-nr {
          type uint16;
        }
        leaf distance {
          tailf:cli-drop-node-name;
          type uint8;
        }
      }
    }
  }

  grouping ncs_rpc_notif_ipv6-grouping {
    container ipv6 {
      uses ncs_rpc_notif_ipv6-route-grouping;
      container nat {
        list pool {
          tailf:cli-suppress-mode;
          tailf:cli-compact-syntax;
          tailf:cli-sequence-commands;
          key "name";
          leaf name {
            type string;
          }
          leaf ipstart {
            mandatory true;
            tailf:cli-drop-node-name;
            type inet:ipv6-address;
          }
          leaf ipend {
            mandatory true;
            tailf:cli-drop-node-name;
            type inet:ipv6-address;
          }
          leaf netmask {
            mandatory true;
            type uint8;
          }
        }
      }
      list access-list {
        tailf:cli-delete-when-empty;
        key "id";
        leaf id {
          type string;
        }
        list rules {
          ordered-by user;
          tailf:cli-suppress-mode;
          tailf:cli-drop-node-name;
          key "acc-type txt";
          leaf acc-type {
            type enumeration {
              enum "permit";
              enum "deny";
            }
          }
          leaf txt {
            tailf:cli-multi-word-key;
            type string;
          }
        }
        list remark {
          tailf:cli-suppress-mode;
          key "name";
          leaf name {
            type string;
          }
        }
      }
      list prefix-list {
        tailf:cli-suppress-mode;
        tailf:cli-compact-syntax;
        key "name seq";
        leaf name {
          type string;
        }
        leaf seq {
          tailf:cli-expose-key-name;
          type uint32;
        }
        choice permit-deny {
          leaf permit {
            type union {
              type enumeration {
                enum "any";
              }
              type tailf:ipv6-address-and-prefix-length;
            }
          }
          leaf deny {
            type union {
              type enumeration {
                enum "any";
              }
              type tailf:ipv6-address-and-prefix-length;
            }
          }
        }
      }
    }
  }

  grouping ncs_rpc_notif_nat64-grouping {
    container nat64 {
      uses ncs_rpc_notif_algs;
      leaf user-quota-prefix-length {
        type uint8;
      }
      container inside {
        container source {
          leaf class-list {
            type string;
          }
        }
      }
      leaf prefix {
        type inet:ipv6-prefix;
      }
    }
  }

  grouping ncs_rpc_notif_lsn-lid-grouping {
    list lsn-lid {
      key "lsn-lid-id";
      leaf lsn-lid-id {
        type uint16;
      }
      leaf name {
        type string;
      }
      leaf source-nat-pool {
        type string;
      }
      container user-quota {
        leaf session {
          type uint32;
        }
      }
      leaf respond-to-user-mac {
        type empty;
      }
    }
  }

  grouping ncs_rpc_notif_ha-grouping {
    container ha {
      leaf arp-retry {
        type uint16;
      }
      container check {
        list gateway {
          key "ip";
          tailf:cli-suppress-mode;
          leaf ip {
            type inet:ipv4-address;
          }
        }
        list route {
          key "ip mask gateway distance protocol priority-cost";
          unique "ip mask gateway distance protocol";
          tailf:cli-compact-syntax;
          tailf:cli-suppress-mode;
          leaf ip {
            type union {
              type inet:ipv4-address;
              type inet:ipv6-address;
            }
          }
          leaf mask {
            type ncs_rpc_notif_ipv4-mask;
          }
          leaf gateway {
            tailf:cli-expose-key-name;
            type union {
              type inet:ipv4-address;
              type inet:ipv6-address;
            }
          }
          leaf distance {
            tailf:cli-expose-key-name;
            type uint8;
          }
          leaf protocol {
            tailf:cli-expose-key-name;
            type enumeration {
              enum "any";
              enum "static";
              enum "dynamic";
            }
          }
          leaf priority-cost {
            tailf:cli-expose-key-name;
            type uint8;
          }
        }
        container vlan {
          tailf:cli-sequence-commands;
          tailf:cli-compact-syntax;
          leaf vlan-id {
            tailf:cli-drop-node-name;
            type ncs_rpc_notif_vlan-index;
          }
          leaf timeout {
            must '../vlan-id' {
              tailf:xpath-root 3;
            }
            type uint16;
          }
        }
      }
      container conn-mirror {
        leaf ip {
          type inet:ipv4-address;
        }
      }
      container force-self-standby {
        list HA-group-id {
          key "id persistent";
          tailf:cli-suppress-mode;
          leaf id {
            type uint16;
          }
          leaf persistent {
            type enumeration {
              enum "persistent";
            }
          }
        }
      }
      leaf forward-l4-packet-on-standby {
        type empty;
      }
      container id {
        tailf:cli-sequence-commands {
          tailf:cli-reset-siblings;
        }
        tailf:cli-compact-syntax;
        leaf id {
          tailf:cli-drop-node-name;
          type uint8;
        }
        leaf set-id {
          type uint8;
        }
      }
      list group {
        tailf:cli-suppress-mode;
        key "id";
        tailf:cli-sequence-commands;
        tailf:cli-compact-syntax;
        tailf:cli-delete-when-empty;
        leaf id {
          type uint16;
        }
        leaf priority {
          must '../id' {
            tailf:xpath-root 3;
          }
          type uint16;
        }
      }
      container inline-mode {
        presence "true";
        leaf preferred-port {
          type uint8;
        }
      }
      container interface {
        list ethernet {
          tailf:cli-suppress-mode;
          tailf:cli-compact-syntax;
          tailf:cli-sequence-commands {
            tailf:cli-reset-siblings;
          }
          key "id";
          leaf id {
            type ncs_rpc_notif_ethernet-index;
          }
          leaf type {
            tailf:cli-optional-in-sequence;
            tailf:cli-drop-node-name;
            type enumeration {
              enum "both";
              enum "router-interface";
              enum "server-interface";
            }
          }
          choice xx {
            leaf no-heartbeat {
              tailf:cli-optional-in-sequence;
              type empty;
            }
            leaf vlan {
              tailf:cli-optional-in-sequence;
              type uint16;
            }
          }
        }
      }
      leaf preemption-enable {
        type empty;
      }
      leaf timeout-retry-count {
        type uint8;
      }
    }
  }

  grouping ncs_rpc_notif_floating-ip-grouping {
    container floating-ip {
      list ipv4 {
        tailf:cli-suppress-mode;
        tailf:cli-drop-node-name;
        key "ip ha-group";
        leaf ip {
          type inet:ipv4-address;
        }
        leaf ha-group {
          tailf:cli-expose-key-name;
          type uint16;
        }
      }
      list ipv6 {
        tailf:cli-suppress-mode;
        tailf:cli-drop-node-name;
        key "ip ha-group";
        leaf ip {
          type inet:ipv6-address;
        }
        leaf ha-group {
          tailf:cli-expose-key-name;
          type uint16;
        }
        leaf anycast {
          tailf:cli-prefix-key {
            tailf:cli-before-key 2;
          }
          type empty;
        }
        choice ipv6-interface {
          leaf ethernet {
            must '../../../interface/ethernet/ipv6/address/ip' {
              tailf:xpath-root 3;
            }
            type ncs_rpc_notif_ethernet-index;
          }
          leaf trunk {
            type uint16;
          }
          leaf ve {
            must '../../../interface/ve/ipv6/address/ip' {
              tailf:xpath-root 3;
            }
            type ncs_rpc_notif_vlan-index;
          }
        }
      }
    }
  }

  grouping ncs_rpc_notif_glid-grouping {
    list glid {
      key "limit-id";
      leaf limit-id {
        type uint16;
      }
      container dns {
        leaf cache-leaf {
          tailf:cli-drop-node-name;
          type enumeration {
            enum "cache-enable";
            enum "cache-disable";
          }
        }
        container ttl {
          tailf:cli-compact-syntax;
          leaf ttl-value {
            tailf:cli-drop-node-name;
            type uint16;
          }
          leaf honor-server-response-ttl {
            type empty;
          }
        }
      }
      container over-limit-action {
        tailf:cli-compact-syntax;
        tailf:cli-sequence-commands {
          tailf:cli-reset-siblings;
        }
        leaf over-limit-action-choice {
          tailf:cli-drop-node-name;
          type enumeration {
            enum "dns-cache-disable";
            enum "dns-cache-enable";
            enum "forward";
            enum "reset";
            enum "lockout";
            enum "log";
          }
        }
        leaf lockout {
          tailf:cli-optional-in-sequence;
          type uint16;
        }
        leaf lockout-val {
          tailf:cli-optional-in-sequence;
          tailf:cli-drop-node-name;
          type uint16;
        }
        leaf log {
          tailf:cli-optional-in-sequence;
          type empty;
        }
        leaf log-val {
          tailf:cli-drop-node-name;
          tailf:cli-optional-in-sequence;
          type uint16;
        }
      }
      leaf conn-limit {
        type uint32;
      }
      container conn-rate-limit {
        tailf:cli-sequence-commands {
          tailf:cli-reset-siblings;
        }
        tailf:cli-compact-syntax;
        leaf limit {
          tailf:cli-drop-node-name;
          type uint32;
        }
        leaf per {
          must '../limit' {
            tailf:xpath-root 3;
          }
          type uint16;
        }
      }
      leaf request-limit {
        type uint32;
      }
      container request-rate-limit {
        tailf:cli-sequence-commands {
          tailf:cli-reset-siblings;
        }
        tailf:cli-compact-syntax;
        leaf limit {
          tailf:cli-drop-node-name;
          type uint32;
        }
        leaf per {
          must '../limit' {
            tailf:xpath-root 3;
          }
          type uint16;
        }
      }
      leaf use-nat-pool {
        type string;
      }
    }
  }

  grouping ncs_rpc_notif_gslb-zone-service-grouping {
    leaf policy {
      type string;
    }
    list dns-a-record {
      tailf:cli-suppress-mode;
      tailf:cli-compact-syntax;
      key "name";
      leaf name {
        type union {
          type inet:ipv6-address;
          type inet:ipv4-address;
          type string;
        }
      }
      leaf as-backup {
        tailf:cli-hide-in-submode;
        type empty;
      }
      leaf port-service-name {
        tailf:cli-drop-node-name;
        tailf:cli-hide-in-submode;
        type string;
      }
      leaf weight {
        tailf:cli-hide-in-submode;
        type uint8;
      }
      container static {
        tailf:cli-hide-in-submode;
        tailf:cli-flatten-container;
        tailf:cli-compact-syntax;
        presence "true";
        leaf admin-ip {
          type uint8;
        }
      }
    }
  }

  grouping ncs_rpc_notif_logging-grouping {
    container logging {
      container auditlog {
        tailf:cli-compact-syntax;
        tailf:cli-sequence-commands {
          tailf:cli-reset-all-siblings;
        }
        leaf host {
          type string;
        }
        leaf facility {
          type string;
        }
      }
      container buffered {
        presence "true";
        leaf size {
          tailf:cli-drop-node-name;
          type uint32;
        }
        leaf severity {
          tailf:cli-drop-node-name;
          type enumeration {
            enum "emergency";
            enum "alert";
            enum "critical";
            enum "error";
            enum "warning";
            enum "notification";
            enum "information";
            enum "debugging";
          }
        }
      }
      leaf console {
        type enumeration {
          enum "emergency";
          enum "alert";
          enum "critical";
          enum "error";
          enum "warning";
          enum "notification";
          enum "information";
          enum "debugging";
          enum "disable";
        }
      }
      container email {
        container buffer {
          choice buffer-choice {
            leaf number {
              type uint16;
            }
            leaf time {
              type uint16;
            }
          }
        }
        leaf severity {
          tailf:cli-drop-node-name;
          type enumeration {
            enum "emergency";
            enum "alert";
            enum "critical";
            enum "notification";
          }
        }
      }
      leaf-list email-address {
        tailf:cli-flat-list-syntax;
        type string;
      }
      leaf export {
        type empty;
      }
      leaf facility {
        type enumeration {
          enum "local0";
          enum "local1";
          enum "local2";
          enum "local3";
          enum "local4";
          enum "local5";
          enum "local6";
          enum "local7";
        }
      }
      leaf syslog {
        type enumeration {
          enum "emergency";
          enum "alert";
          enum "critical";
          enum "error";
          enum "warning";
          enum "notification";
          enum "information";
          enum "debugging";
        }
      }
      leaf trap {
        type enumeration {
          enum "emergency";
          enum "alert";
          enum "critical";
        }
      }
      choice host-choice {
        container host-list {
          tailf:cli-drop-node-name;
          list host {
            tailf:cli-suppress-mode;
            tailf:cli-compact-syntax;
            key "hosts";
            leaf hosts {
              type string;
            }
            choice use-mgmt-port-choice {
              container port {
                tailf:cli-compact-syntax;
                tailf:cli-flatten-container;
                tailf:cli-sequence-commands {
                  tailf:cli-reset-siblings;
                }
                leaf number {
                  tailf:cli-drop-node-name;
                  type uint16;
                }
                leaf tcp {
                  type empty;
                }
              }
              container use-mgmt-port {
                tailf:cli-compact-syntax;
                tailf:cli-flatten-container;
                tailf:cli-sequence-commands {
                  tailf:cli-reset-siblings;
                }
                presence "true";
                leaf port {
                  type uint32;
                }
                leaf tcp {
                  type empty;
                }
              }
            }
          }
        }
        container host {
          tailf:cli-sequence-commands {
            tailf:cli-reset-siblings;
          }
          tailf:cli-compact-syntax;
          leaf-list hosts {
            tailf:cli-flat-list-syntax;
            tailf:cli-drop-node-name;
            type string;
          }
          leaf port {
            type uint16;
          }
        }
        container host-alt {
          tailf:cli-drop-node-name;
          container host {
            leaf partition {
              type enumeration {
                enum "shared";
              }
            }
          }
        }
      }
      leaf monitor {
        type enumeration {
          enum "emergency";
          enum "alert";
          enum "critical";
          enum "error";
          enum "warning";
          enum "notification";
          enum "information";
          enum "debugging";
        }
      }
    }
  }

  grouping ncs_rpc_notif_snmp-server-grouping {
    container snmp-server {
      container enable {
        leaf enabled {
          tailf:cli-drop-node-name;
          type empty;
        }
        leaf service {
          type empty;
        }
        container traps {
          leaf enabled {
            tailf:cli-drop-node-name;
            type empty;
          }
          leaf all {
            type empty;
          }
          container routing {
            container ospf {
              choice routing-choice {
                leaf-list ospf-traps {
                  tailf:cli-drop-node-name;
                  type enumeration {
                    enum "ospfIfAuthFailure";
                    enum "ospfIfConfigError";
                    enum "ospfIfRxBadPacket";
                    enum "ospfIfStateChange";
                    enum "ospfLsdbApproachingOverflow";
                    enum "ospfLsdbOverflow";
                    enum "ospfMaxAgeLsa";
                    enum "ospfNbrStateChange";
                    enum "ospfOriginateLsa";
                    enum "ospfTxRetransmit";
                    enum "ospfVirtIfAuthFailure";
                    enum "ospfVirtIfConfigError";
                    enum "ospfVirtIfRxBadPacket";
                    enum "ospfVirtIfStateChange";
                    enum "ospfVirtIfTxRetransmit";
                    enum "ospfVirtNbrStateChange";
                  }
                }
                leaf all {
                  type empty;
                }
              }
            }
            container bgp {
              leaf bgpBackwardTransNotification {
                type empty;
              }
              leaf bgpEstablishedNotification {
                type empty;
              }
            }
          }
          container lsn {
            leaf all {
              type empty;
            }
          }
          container snmp {
            leaf enabled {
              tailf:cli-drop-node-name;
              type empty;
            }
            leaf all {
              type empty;
            }
            leaf linkdown {
              type empty;
            }
            leaf linkup {
              type empty;
            }
          }
          container ha {
            leaf enabled {
              tailf:cli-drop-node-name;
              type empty;
            }
            leaf active {
              type empty;
            }
            leaf active-active {
              type empty;
            }
            leaf standby {
              type empty;
            }
            leaf vrrp {
              type empty;
            }
          }
          container network {
            leaf enabled {
              tailf:cli-drop-node-name;
              type empty;
            }
            leaf trunk-port-threshold {
              type empty;
            }
          }
          container slb {
            leaf enabled {
              tailf:cli-drop-node-name;
              type empty;
            }
            leaf all {
              type empty;
            }
            leaf application-buffer-limit {
              type empty;
            }
            leaf server-conn-limit {
              type empty;
            }
            leaf server-conn-resume {
              type empty;
            }
            leaf server-down {
              type empty;
            }
            leaf server-up {
              type empty;
            }
            leaf service-conn-limit {
              type empty;
            }
            leaf service-conn-resume {
              type empty;
            }
            leaf service-down {
              type empty;
            }
            leaf service-up {
              type empty;
            }
            leaf vip-connlimit {
              type empty;
            }
            leaf vip-connratelimit {
              type empty;
            }
            leaf vip-port-connlimit {
              type empty;
            }
            leaf vip-port-connratelimit {
              type empty;
            }
            leaf vip-port-down {
              type empty;
            }
            leaf vip-port-up {
              type empty;
            }
          }
          container system {
            leaf enabled {
              tailf:cli-drop-node-name;
              type empty;
            }
            leaf all {
              type empty;
            }
            leaf control-cpu-high {
              type empty;
            }
            leaf data-cpu-high {
              type empty;
            }
            leaf fan {
              type empty;
            }
            leaf high-disk-use {
              type empty;
            }
            leaf high-memory-use {
              type empty;
            }
            leaf high-temp {
              type empty;
            }
            leaf packet-drop {
              type empty;
            }
            leaf power {
              type empty;
            }
            leaf pri-disk {
              type empty;
            }
            leaf restart {
              type empty;
            }
            leaf sec-disk {
              type empty;
            }
            leaf shutdown {
              type empty;
            }
            leaf start {
              type empty;
            }
          }
          container vrrp-a {
            leaf active {
              type empty;
            }
            leaf all {
              type empty;
            }
            leaf standby {
              type empty;
            }
          }
        }
      }
      leaf location {
        type string;
      }
      list user {
        tailf:cli-suppress-mode;
        key "name group type";
        leaf name {
          type string;
        }
        leaf group {
          tailf:cli-expose-key-name;
          type string;
        }
        leaf type {
          type enumeration {
            enum "v1";
            enum "v2c";
            enum "v3";
          }
        }
        container auth {
          tailf:cli-compact-syntax;
          tailf:cli-sequence-commands {
            tailf:cli-reset-siblings;
          }
          leaf mac {
            tailf:cli-drop-node-name;
            type enumeration {
              enum "MD5";
              enum "SHA";
            }
          }
          leaf cleartext {
            tailf:cli-drop-node-name;
            tailf:cli-optional-in-sequence;
            type string;
          }
        }
      }
      list view {
        key "name miboid";
        tailf:cli-suppress-mode;
        tailf:cli-compact-syntax;
        leaf name {
          type string;
        }
        leaf miboid {
          type string;
        }
        leaf included-excluded {
          tailf:cli-drop-node-name;
          type enumeration {
            enum "included";
            enum "excluded";
          }
        }
      }
      list group {
        tailf:cli-suppress-mode;
        tailf:cli-compact-syntax;
        key "name";
        leaf name {
          type string;
        }
        container v3 {
          tailf:cli-compact-syntax;
          container auth {
            tailf:cli-compact-syntax;
            leaf read {
              type string;
            }
          }
        }
      }
      container SNMPv1-v2c {
        list user {
          key "name";
          leaf name {
            type string;
          }
          container community {
            leaf read {
              type string;
            }
          }
          uses ncs_rpc_notif_snmp-remote-grouping;
        }
      }
      container SNMPv3 {
        list user {
          tailf:cli-suppress-mode;
          tailf:cli-compact-syntax;
          tailf:cli-sequence-commands {
            tailf:cli-reset-siblings;
          }
          key "name";
          leaf name {
            type string;
          }
          leaf group {
            type string;
          }
          leaf v3 {
            type empty;
          }
          choice smnp-server-v3-user-auth-choice {
            container auth {
              tailf:cli-compact-syntax;
              tailf:cli-flatten-container;
              tailf:cli-sequence-commands {
                tailf:cli-reset-siblings;
              }
              leaf hmac {
                tailf:cli-drop-node-name;
                type enumeration {
                  enum "md5";
                  enum "sha";
                }
              }
              leaf password {
                tailf:cli-drop-node-name;
                type string;
              }
              container priv {
                tailf:cli-compact-syntax;
                tailf:cli-flatten-container;
                tailf:cli-sequence-commands {
                  tailf:cli-reset-siblings;
                }
                leaf algo {
                  tailf:cli-drop-node-name;
                  type enumeration {
                    enum "des";
                    enum "aes";
                  }
                }
                leaf passphrase {
                  tailf:cli-drop-node-name;
                  type string;
                }
              }
            }
            leaf noauth {
              type empty;
            }
          }
        }
      }
      container community-mode {
        tailf:cli-drop-node-name;
        list community {
          key "read";
          leaf read {
            tailf:cli-expose-key-name;
            type string;
          }
          uses ncs_rpc_notif_snmp-remote-grouping;
        }
      }
      list community {
        key "read remote";
        tailf:cli-suppress-mode;
        tailf:cli-compact-syntax;
        leaf read {
          tailf:cli-expose-key-name;
          type string;
        }
        leaf remote {
          tailf:cli-expose-key-name;
          type string;
        }
        leaf oid {
          tailf:cli-prefix-key {
            tailf:cli-before-key 2;
          }
          type string;
        }
        leaf mask {
          tailf:cli-drop-node-name;
          type union {
            type ncs_rpc_notif_ipv4-mask;
            type string;
          }
        }
      }
      leaf contact {
        type string;
      }
      list host {
        tailf:cli-suppress-mode;
        tailf:cli-sequence-commands {
          tailf:cli-reset-siblings;
        }
        tailf:cli-compact-syntax;
        key "ip version";
        leaf ip {
          type string;
        }
        leaf version {
          tailf:cli-expose-key-name;
          type enumeration {
            enum "v1";
            enum "v2c";
          }
        }
        leaf community-string {
          tailf:cli-drop-node-name;
          mandatory true;
          type string;
        }
        leaf udp-port {
          type uint16;
        }
      }
    }
  }

  grouping ncs_rpc_notif_audit-grouping {
    container audit {
      container enable {
        leaf privilege {
          type empty;
        }
      }
      leaf size {
        type uint32;
      }
    }
  }

  grouping ncs_rpc_notif_harmony-controller-grouping {
    container harmony-controller {
      leaf config-replace {
        type enumeration {
          enum "disable";
          enum "enable";
        }
      }
      container profile {
        tailf:cli-add-mode;
        presence "true";
        container host {
          tailf:cli-compact-syntax;
          tailf:cli-sequence-commands;
          leaf host-id {
            tailf:cli-drop-node-name;
            type union {
              type string;
              type inet:ipv4-address;
            }
          }
          leaf use-mgmt-port {
            tailf:cli-optional-in-sequence;
            type empty;
          }
          leaf port {
            type uint16;
          }
        }
        leaf provider {
          type string;
        }
        leaf user-name {
          type string;
        }
        leaf cluster-name {
          type string;
        }
        leaf cluster-id {
          type string;
        }
        leaf password {
          type string;
        }
        leaf region {
          type string;
        }
        leaf availability-zone {
          type string;
        }
        leaf thunder-mgmt-ip {
          type inet:ipv4-address;
        }
        leaf reg-dereg {
          tailf:cli-drop-node-name;
          type enumeration {
            enum "register";
            enum "deregister";
          }
        }
        list device-context {
          key "id";
          leaf id {
            type uint8;
          }
          leaf thunder-mgmt-ip {
            type inet:ipv4-address;
          }
        }
      }
    }
  }

  grouping ncs_rpc_notif_terminal-grouping {
    container terminal {
      leaf auto-size {
        type empty;
      }
      leaf editing {
        type empty;
      }
      container prompt {
        tailf:cli-compact-syntax;
        leaf hostname {
          type empty;
        }
        leaf ha-status {
          type empty;
        }
      }
      container history {
        leaf size {
          type uint16;
        }
      }
      leaf idle-timeout {
        type uint8;
      }
      leaf length {
        type uint16;
      }
      leaf no-ha-prompt {
        type empty;
      }
      leaf width {
        type uint16;
      }
    }
  }

  grouping ncs_rpc_notif_web-service-grouping {
    container web-service {
      leaf auto-redir {
        type boolean;
      }
      container auto-redirt {
        leaf disable {
          type empty;
        }
      }
      container axapi-timeout-policy {
        leaf idle {
          type uint8;
        }
      }
      container timeout-policy {
        leaf idle {
          type uint8;
        }
      }
      leaf gui-session-limit {
        type uint8;
      }
      container gui-timeout-policy {
        leaf idle {
          type uint8;
        }
      }
      leaf login-message {
        type string;
      }
      leaf pre-login-message {
        type string;
      }
    }
  }

  grouping ncs_rpc_notif_multi-config-grouping {
    container multi-config {
      leaf enable {
        type empty;
      }
    }
  }

  grouping ncs_rpc_notif_banner-grouping {
    container banner {
      container login {
        tailf:cli-compact-syntax;
        choice text-multi {
          leaf text {
            tailf:cli-drop-node-name;
            type string;
          }
          leaf multi-line {
            type string;
          }
        }
      }
      container exec {
        tailf:cli-compact-syntax;
        choice text-multi {
          leaf text {
            tailf:cli-drop-node-name;
            type string;
          }
          leaf multi-line {
            type string;
          }
        }
      }
    }
  }

  grouping ncs_rpc_notif_preferred-session-sync-port-grouping {
    container preferred-session-sync-port {
      list trunk {
        tailf:cli-suppress-mode;
        tailf:cli-sequence-commands {
          tailf:cli-reset-siblings;
        }
        tailf:cli-compact-syntax;
        key "id";
        leaf id {
          type uint8;
        }
        leaf vlan {
          type uint16;
        }
      }
      list ethernet {
        tailf:cli-suppress-mode;
        tailf:cli-sequence-commands {
          tailf:cli-reset-siblings;
        }
        tailf:cli-compact-syntax;
        key "id";
        leaf id {
          type ncs_rpc_notif_ethernet-index;
        }
        leaf vlan {
          type uint16;
        }
      }
    }
  }

  grouping ncs_rpc_notif_vrrp-a-grouping {
    container vrrp-a {

      grouping vrrp-a-common-grouping {
        leaf device-id {
          tailf:cli-diff-create-before "/a10-acos:interface" {
            tailf:xpath-root 3;
          }
          tailf:cli-diff-create-before "/a10-acos:vcs" {
            tailf:xpath-root 3;
          }
          type uint8;
        }
        leaf disable-default-vrid {
          type empty;
        }
        leaf set-id {
          tailf:cli-diff-create-before "/a10-acos:interface" {
            tailf:xpath-root 3;
          }
          tailf:cli-diff-create-before "/a10-acos:vcs" {
            tailf:xpath-root 3;
          }
          type uint8;
        }
        leaf hello-interval {
          type uint8;
        }
        leaf preemption-delay {
          type uint8;
        }
        leaf track-event-delay {
          type uint8;
        }
        leaf restart-time {
          type uint8;
        }
        leaf hostid-append-to-vrid {
          type union {
            type uint8;
            type enumeration {
              enum "default";
            }
          }
        }
        leaf enable {
          tailf:cli-drop-node-name;
          type enumeration {
            enum "enable";
            enum "disable";
          }
        }
      }
      uses vrrp-a-common-grouping;
      container common {
        presence "common-presence";
        tailf:cli-add-mode;
        uses vrrp-a-common-grouping;
      }
      list vrid {
        key "id";
        leaf id {
          type union {
            type uint8;
            type enumeration {
              enum "default";
            }
          }
        }

        grouping vrrp-a-vrid-grouping {
          list floating-ip {
            tailf:cli-suppress-mode;
            key "floating-ip-address";
            leaf floating-ip-address {
              tailf:cli-drop-node-name;
              type union {
                type inet:ipv4-address;
                type inet:ipv6-address;
              }
            }
          }
          leaf priority {
            type uint8;
          }
          container preempt-mode {
            choice preempt-choice {
              leaf disable {
                type empty;
              }
              leaf threshold {
                type uint8;
              }
            }
          }
          container blade-parameters {
            tailf:cli-add-mode;
            leaf priority {
              type uint8;
            }
            container tracking-options {
              tailf:cli-add-mode;
              tailf:cli-delete-when-empty;
              list gateway {
                tailf:cli-suppress-mode;
                key "address";
                leaf address {
                  type union {
                    type inet:ipv4-address;
                    type inet:ipv6-address;
                  }
                }
                uses ncs_rpc_notif_priority-cost;
              }
              container interface {
                list ethernet {
                  tailf:cli-suppress-mode;
                  key "id";
                  leaf id {
                    type ncs_rpc_notif_ethernet-index;
                  }
                  leaf priority-cost {
                    mandatory true;
                    type uint8;
                  }
                }
              }
              list route {
                tailf:cli-suppress-mode;
                tailf:cli-compact-syntax;
                key "ip mask";
                leaf ip {
                  type union {
                    type inet:ipv4-address;
                    type inet:ipv6-address;
                  }
                }
                leaf mask {
                  type ncs_rpc_notif_ipv4-mask;
                }
                uses ncs_rpc_notif_priority-cost;
                leaf distance {
                  type uint8;
                }
                leaf gateway {
                  type union {
                    type inet:ipv4-address;
                    type inet:ipv6-address;
                  }
                }
                leaf protocol {
                  type enumeration {
                    enum "any";
                    enum "static";
                    enum "dynamic";
                  }
                }
              }
              list trunk {
                tailf:cli-suppress-mode;
                tailf:cli-sequence-commands {
                  tailf:cli-reset-siblings;
                }
                tailf:cli-compact-syntax;
                key "id";
                leaf id {
                  type uint8;
                }
                uses ncs_rpc_notif_priority-cost;
                leaf per-port-pri {
                  type uint8;
                }
              }
              list vlan {
                tailf:cli-suppress-mode;
                tailf:cli-sequence-commands;
                tailf:cli-compact-syntax;
                key "id";
                leaf id {
                  type ncs_rpc_notif_vlan-index;
                }
                leaf timeout {
                  type uint16;
                }
                uses ncs_rpc_notif_priority-cost;
              }
            }
          }
        }
        // NCS expand uses statement
        list floating-ip {
          tailf:cli-suppress-mode;
          key "floating-ip-address";
          leaf floating-ip-address {
            tailf:cli-drop-node-name;
            type union {
              type inet:ipv4-address;
              type inet:ipv6-address;
            }
          }
        }
        leaf priority {
          type uint8;
        }
        container preempt-mode {
          choice preempt-choice {
            leaf disable {
              type empty;
            }
            leaf threshold {
              type uint8;
            }
          }
        }
        container blade-parameters {
          tailf:cli-add-mode;
          leaf priority {
            type uint8;
          }
          container tracking-options {
            tailf:cli-add-mode;
            tailf:cli-delete-when-empty;
            list gateway {
              tailf:cli-suppress-mode;
              key "address";
              leaf address {
                type union {
                  type inet:ipv4-address;
                  type inet:ipv6-address;
                }
              }
              // NCS expand uses statement
              leaf priority-cost {
                mandatory true;
                type uint8;
              }
            }
            container interface {
              list ethernet {
                tailf:cli-suppress-mode;
                key "id";
                leaf id {
                  type ncs_rpc_notif_ethernet-index;
                }
                leaf priority-cost {
                  mandatory true;
                  type uint8;
                }
              }
            }
            list route {
              tailf:cli-suppress-mode;
              tailf:cli-compact-syntax;
              key "ip mask";
              leaf ip {
                type union {
                  type inet:ipv4-address;
                  type inet:ipv6-address;
                }
              }
              leaf mask {
                type ncs_rpc_notif_ipv4-mask;
              }
              // NCS expand uses statement
              leaf priority-cost {
                mandatory true;
                type uint8;
              }
              leaf distance {
                type uint8;
              }
              leaf gateway {
                type union {
                  type inet:ipv4-address;
                  type inet:ipv6-address;
                }
              }
              leaf protocol {
                type enumeration {
                  enum "any";
                  enum "static";
                  enum "dynamic";
                }
              }
            }
            list trunk {
              tailf:cli-suppress-mode;
              tailf:cli-sequence-commands {
                tailf:cli-reset-siblings;
              }
              tailf:cli-compact-syntax;
              key "id";
              leaf id {
                type uint8;
              }
              // NCS expand uses statement
              leaf priority-cost {
                mandatory true;
                type uint8;
              }
              leaf per-port-pri {
                type uint8;
              }
            }
            list vlan {
              tailf:cli-suppress-mode;
              tailf:cli-sequence-commands;
              tailf:cli-compact-syntax;
              key "id";
              leaf id {
                type ncs_rpc_notif_vlan-index;
              }
              leaf timeout {
                type uint16;
              }
              // NCS expand uses statement
              leaf priority-cost {
                mandatory true;
                type uint8;
              }
            }
          }
        }
        list device-context {
          key "id";
          leaf id {
            type uint8;
          }
          // NCS expand uses statement
          list floating-ip {
            tailf:cli-suppress-mode;
            key "floating-ip-address";
            leaf floating-ip-address {
              tailf:cli-drop-node-name;
              type union {
                type inet:ipv4-address;
                type inet:ipv6-address;
              }
            }
          }
          leaf priority {
            type uint8;
          }
          container preempt-mode {
            choice preempt-choice {
              leaf disable {
                type empty;
              }
              leaf threshold {
                type uint8;
              }
            }
          }
          container blade-parameters {
            tailf:cli-add-mode;
            leaf priority {
              type uint8;
            }
            container tracking-options {
              tailf:cli-add-mode;
              tailf:cli-delete-when-empty;
              list gateway {
                tailf:cli-suppress-mode;
                key "address";
                leaf address {
                  type union {
                    type inet:ipv4-address;
                    type inet:ipv6-address;
                  }
                }
                // NCS expand uses statement
                leaf priority-cost {
                  mandatory true;
                  type uint8;
                }
              }
              container interface {
                list ethernet {
                  tailf:cli-suppress-mode;
                  key "id";
                  leaf id {
                    type ncs_rpc_notif_ethernet-index;
                  }
                  leaf priority-cost {
                    mandatory true;
                    type uint8;
                  }
                }
              }
              list route {
                tailf:cli-suppress-mode;
                tailf:cli-compact-syntax;
                key "ip mask";
                leaf ip {
                  type union {
                    type inet:ipv4-address;
                    type inet:ipv6-address;
                  }
                }
                leaf mask {
                  type ncs_rpc_notif_ipv4-mask;
                }
                // NCS expand uses statement
                leaf priority-cost {
                  mandatory true;
                  type uint8;
                }
                leaf distance {
                  type uint8;
                }
                leaf gateway {
                  type union {
                    type inet:ipv4-address;
                    type inet:ipv6-address;
                  }
                }
                leaf protocol {
                  type enumeration {
                    enum "any";
                    enum "static";
                    enum "dynamic";
                  }
                }
              }
              list trunk {
                tailf:cli-suppress-mode;
                tailf:cli-sequence-commands {
                  tailf:cli-reset-siblings;
                }
                tailf:cli-compact-syntax;
                key "id";
                leaf id {
                  type uint8;
                }
                // NCS expand uses statement
                leaf priority-cost {
                  mandatory true;
                  type uint8;
                }
                leaf per-port-pri {
                  type uint8;
                }
              }
              list vlan {
                tailf:cli-suppress-mode;
                tailf:cli-sequence-commands;
                tailf:cli-compact-syntax;
                key "id";
                leaf id {
                  type ncs_rpc_notif_vlan-index;
                }
                leaf timeout {
                  type uint16;
                }
                // NCS expand uses statement
                leaf priority-cost {
                  mandatory true;
                  type uint8;
                }
              }
            }
          }
        }
      }
      container interface {
        list ethernet {
          tailf:cli-suppress-mode;
          tailf:cli-compact-syntax;
          key "id";
          leaf id {
            type ncs_rpc_notif_ethernet-index;
          }
          choice vrrp-a-ethernet-choice {
            leaf both {
              type empty;
            }
            leaf no-heartbeat {
              type empty;
            }
            container router-interface {
              choice vrrp-a-r-i-choice {
                leaf no-heartbeat {
                  type empty;
                }
                leaf vlan {
                  type uint16;
                }
              }
            }
            container server-interface {
              presence "true";
              choice vrrp-a-s-i-choice {
                leaf no-heartbeat {
                  type empty;
                }
                leaf vlan {
                  type uint16;
                }
              }
            }
            leaf vlan {
              type uint16;
            }
          }
        }
        list trunk {
          tailf:cli-suppress-mode;
          tailf:cli-compact-syntax;
          key "id";
          leaf id {
            type ncs_rpc_notif_ethernet-index;
          }
          choice vrrp-a-trunk-choice {
            leaf both {
              type empty;
            }
            leaf no-heartbeat {
              type empty;
            }
            container router-interface {
              choice vrrp-a-r-i-choice {
                leaf no-heartbeat {
                  type empty;
                }
                leaf vlan {
                  type uint16;
                }
              }
            }
            container server-interface {
              presence "true";
              choice vrrp-a-s-i-choice {
                leaf no-heartbeat {
                  type empty;
                }
                leaf vlan {
                  type uint16;
                }
              }
            }
            leaf vlan {
              type uint16;
            }
          }
        }
      }
      // NCS expand uses statement
      container preferred-session-sync-port {
        list trunk {
          tailf:cli-suppress-mode;
          tailf:cli-sequence-commands {
            tailf:cli-reset-siblings;
          }
          tailf:cli-compact-syntax;
          key "id";
          leaf id {
            type uint8;
          }
          leaf vlan {
            type uint16;
          }
        }
        list ethernet {
          tailf:cli-suppress-mode;
          tailf:cli-sequence-commands {
            tailf:cli-reset-siblings;
          }
          tailf:cli-compact-syntax;
          key "id";
          leaf id {
            type ncs_rpc_notif_ethernet-index;
          }
          leaf vlan {
            type uint16;
          }
        }
      }
    }
  }

  grouping ncs_rpc_notif_router-grouping {
    container router {
      list bgp {
        key "as";
        leaf as {
          type uint32;
        }
        leaf maximum-paths {
          type uint8;
        }
        list network {
          tailf:cli-suppress-mode;
          key "address";
          leaf address {
            type union {
              type inet:ipv4-address;
              type tailf:ipv4-address-and-prefix-length;
            }
          }
        }

        grouping neighbor-grouping {
          list neighbor {
            tailf:cli-suppress-mode;
            tailf:cli-delete-when-empty;
            key "ip";
            leaf ip {
              type union {
                type string;
                type inet:ipv4-address;
                type inet:ipv6-address;
              }
            }
            leaf activate {
              type boolean;
            }
            leaf description {
              tailf:cli-multi-value;
              type string;
            }
            list distribute-list {
              key "direction";
              tailf:cli-suppress-mode;
              leaf name {
                tailf:cli-prefix-key;
                tailf:cli-drop-node-name;
                type string;
              }
              leaf direction {
                type enumeration {
                  enum "in";
                  enum "out";
                }
              }
            }
            container fall-over {
              tailf:cli-compact-syntax;
              tailf:cli-sequence-commands {
                tailf:cli-reset-all-siblings;
              }
              leaf bfd {
                type empty;
              }
              leaf multihop {
                type empty;
              }
            }
            leaf maximum-prefix {
              type uint32;
            }
            leaf next-hop-self {
              type empty;
            }
            leaf password {
              type string;
            }
            container peer-group {
              presence "true";
              leaf name {
                tailf:cli-drop-node-name;
                type union {
                  type string;
                  type inet:ipv4-address;
                  type inet:ipv6-address;
                }
              }
            }
            list prefix-list {
              tailf:cli-suppress-mode;
              key "direction";
              leaf direction {
                type enumeration {
                  enum "in";
                  enum "out";
                }
              }
              leaf name {
                tailf:cli-drop-node-name;
                tailf:cli-prefix-key;
                type string;
              }
            }
            leaf remote-as {
              type uint32;
            }
            leaf remove-private-as {
              type empty;
            }
            list route-map {
              tailf:cli-compact-syntax;
              tailf:cli-suppress-mode;
              key "in-out";
              leaf in-out {
                type enumeration {
                  enum "in";
                  enum "out";
                }
              }
              leaf name {
                tailf:cli-drop-node-name;
                tailf:cli-prefix-key;
                type string;
              }
            }
            container update-source {
              leaf address {
                tailf:cli-drop-node-name;
                type union {
                  type inet:ipv4-address;
                  type inet:ipv6-address;
                }
              }
              leaf ve {
                type uint32;
              }
            }
            leaf soft-reconfiguration {
              type enumeration {
                enum "inbound";
              }
            }
            leaf shutdown {
              type boolean;
            }
          }
        }
        uses neighbor-grouping;

        grouping redistribute-grouping {
          container redistribute {
            container connected {
              presence "true";
              leaf route-map {
                type string;
              }
            }
            container static {
              presence "true";
              leaf route-map {
                type string;
              }
            }
            container ip-nat {
              presence "true";
              leaf route-map {
                type string;
              }
            }
            container vip {
              container only-flagged {
                presence "true";
              }
            }
          }
        }
        uses redistribute-grouping;
        container address-family {
          container ipv6 {
            tailf:cli-add-mode;
            leaf maximum-paths {
              type uint8;
            }
            uses neighbor-grouping;
            uses redistribute-grouping;
          }
        }
        container bgp {
          leaf log-neighbor-changes {
            type empty;
          }
          container bestpath {
            leaf as-path {
              type enumeration {
                enum "ignore";
              }
            }
          }
        }
      }
    }
  }

  grouping ncs_rpc_notif_bfd-grouping {
    container bfd {
      leaf echo {
        type empty;
      }
      leaf enable {
        type empty;
      }
      container interval {
        tailf:cli-compact-syntax;
        tailf:cli-sequence-commands {
          tailf:cli-reset-all-siblings;
        }
        leaf start {
          tailf:cli-drop-node-name;
          type uint32;
        }
        leaf min-rx {
          type uint32;
        }
        leaf multiplier {
          type uint8;
        }
      }
    }
  }

  grouping ncs_rpc_notif_lldp-grouping {
    container lldp {
      leaf system-name {
        type string;
      }
      leaf system-description {
        type string;
      }
      leaf-list enable {
        tailf:cli-flat-list-syntax;
        type enumeration {
          enum "rx";
          enum "tx";
        }
      }
      container management-address {
        list ipv4 {
          tailf:cli-suppress-mode;
          key "address";
          leaf address {
            type inet:ipv4-address;
          }
        }
        list ipv6 {
          tailf:cli-suppress-mode;
          key "address";
          leaf address {
            type inet:ipv6-address;
          }
        }
      }
      container notification {
        leaf interval {
          type uint32;
        }
      }
    }
  }

  grouping ncs_rpc_notif_route-map-grouping {
    list route-map {
      tailf:cli-suppress-mode;
      key "name";
      leaf name {
        type string;
      }

      grouping permit-deny-grouping {
        leaf id {
          type uint16;
        }

        grouping match-set-grouping {
          container ip {
            container address {
              leaf address {
                tailf:cli-drop-node-name;
                type string;
              }
              leaf prefix-list {
                type string;
              }
            }
            leaf next-hop {
              type inet:ipv4-address;
            }
          }
          container ipv6 {
            container address {
              leaf address {
                tailf:cli-drop-node-name;
                type string;
              }
              leaf prefix-list {
                type string;
              }
            }
            leaf next-hop {
              type inet:ipv4-address;
            }
          }
          leaf-list community {
            tailf:cli-flat-list-syntax;
            type string;
          }
        }
        container match {
          uses match-set-grouping;
        }
        container set {
          uses match-set-grouping;
        }
      }
      list permit {
        key "id";
        uses permit-deny-grouping;
      }
      list deny {
        key "id";
        uses permit-deny-grouping;
      }
    }
  }

  grouping ncs_rpc_notif_device-context-grouping {
    list device-context {
      key "id";
      leaf id {
        type uint8;
      }
      uses ncs_rpc_notif_aflex-grouping;
      uses ncs_rpc_notif_hostname-grouping;
      // NCS expand uses statement
      container interface {

        grouping lldp-interface-grouping {
          container lldp {
            container enable {
              tailf:cli-compact-syntax;
              leaf rx {
                type empty;
              }
              leaf tx {
                type empty;
              }
            }
            leaf notification {
              type enumeration {
                enum "enable";
              }
            }
            leaf tx-dot1-tlvs {
              type enumeration {
                enum "link-aggregation";
                enum "vlan";
              }
            }
          }
        }
        container management {
          tailf:cli-add-mode;
          container bcast-rate-limit {
            presence "present";
            leaf rate {
              type uint16;
            }
          }
          container ip {
            // NCS expand uses statement
            list address {
              tailf:cli-suppress-mode;
              key "address mask";
              leaf address {
                type union {
                  type inet:ipv4-address;
                  type enumeration {
                    enum "dhcp";
                  }
                }
              }
              leaf mask {
                type union {
                  type inet:ipv4-address;
                  type string;
                }
              }
            }
            leaf control-apps-use-mgmt-port {
              type empty;
            }
            leaf default-gateway {
              type inet:ipv4-address;
            }
          }
          container ipv6 {
            list address {
              key "ip";
              tailf:cli-suppress-mode;
              tailf:cli-sequence-commands {
                tailf:cli-reset-siblings;
              }
              tailf:cli-compact-syntax;
              leaf ip {
                tailf:cli-drop-node-name;
                type ncs_rpc_notif_ipv6-prefix;
              }
              leaf link-local {
                type empty;
              }
            }
            leaf default-gateway {
              type inet:ipv6-address;
            }
          }
          // NCS expand uses statement
          container lldp {
            container enable {
              tailf:cli-compact-syntax;
              leaf rx {
                type empty;
              }
              leaf tx {
                type empty;
              }
            }
            leaf notification {
              type enumeration {
                enum "enable";
              }
            }
            leaf tx-dot1-tlvs {
              type enumeration {
                enum "link-aggregation";
                enum "vlan";
              }
            }
          }
          leaf flow-control {
            type empty;
          }
          container access-list {
            tailf:cli-sequence-commands {
              tailf:cli-reset-siblings;
            }
            tailf:cli-compact-syntax;
            leaf id {
              tailf:cli-drop-node-name;
              type uint16;
            }
            leaf in {
              must '../id' {
                tailf:xpath-root 3;
              }
              type empty;
            }
          }
          leaf enabled-disabled {
            tailf:cli-drop-node-name;
            type enumeration {
              enum "enable";
              enum "disable";
            }
          }
          leaf duplexity {
            type enumeration {
              enum "full";
              enum "half";
              enum "auto";
            }
          }
          leaf mtu {
            type uint16;
          }
          leaf speed {
            type enumeration {
              enum "10";
              enum "100";
              enum "1000";
              enum "auto";
            }
          }
        }
        list ethernet {
          key "nr";
          leaf nr {
            type ncs_rpc_notif_ethernet-index;
          }
          leaf name {
            type string;
          }
          container ip {
            // NCS expand uses statement
            list address {
              tailf:cli-suppress-mode;
              key "address mask";
              leaf address {
                type union {
                  type inet:ipv4-address;
                  type enumeration {
                    enum "dhcp";
                  }
                }
              }
              leaf mask {
                type union {
                  type inet:ipv4-address;
                  type string;
                }
              }
            }
            leaf cache-spoofing-port {
              type empty;
            }
            leaf helper-address {
              type inet:ipv4-address;
            }
            container nat {
              leaf inside {
                type empty;
              }
              leaf outside {
                type empty;
              }
            }
            container ospf;
            container router {
              container isis {
                presence "true";
                leaf cmds {
                  tailf:cli-drop-node-name;
                  type string;
                }
              }
            }
            leaf allow-promiscuous-vip {
              type empty;
            }
            container tcp {
              leaf syn-cookie {
                type empty;
              }
            }
          }
          container ipv6 {
            container access-list {
              tailf:cli-sequence-commands {
                tailf:cli-reset-siblings;
              }
              tailf:cli-compact-syntax;
              leaf id {
                tailf:cli-drop-node-name;
                type string;
              }
              leaf in {
                must '../id' {
                  tailf:xpath-root 3;
                }
                type empty;
              }
            }
            list address {
              key "ip";
              tailf:cli-suppress-mode;
              tailf:cli-sequence-commands {
                tailf:cli-reset-all-siblings;
              }
              tailf:cli-compact-syntax;
              leaf ip {
                tailf:cli-drop-node-name;
                type ncs_rpc_notif_ipv6-prefix;
              }
              leaf link-local {
                type empty;
                tailf:cli-break-sequence-commands;
              }
              leaf anycast {
                type empty;
                tailf:cli-break-sequence-commands;
              }
            }
            container nat {
              leaf inside {
                type empty;
              }
              leaf outside {
                type empty;
              }
            }
            container ndisc {
              container router-advertisement;
            }
            container ospf;
            container router {
              container isis {
                presence "true";
                leaf cmds {
                  tailf:cli-drop-node-name;
                  type string;
                }
              }
            }
          }
          leaf load-interval {
            type uint16;
          }
          container access-list {
            tailf:cli-sequence-commands {
              tailf:cli-reset-siblings;
            }
            tailf:cli-compact-syntax;
            leaf id {
              tailf:cli-drop-node-name;
              type uint16;
            }
            leaf in {
              must '../id' {
                tailf:xpath-root 3;
              }
              type empty;
            }
          }
          leaf state {
            tailf:cli-drop-node-name;
            type enumeration {
              enum "enable";
              enum "disable";
            }
          }
          leaf state-alt {
            tailf:cli-drop-node-name;
            type enumeration {
              enum "enable";
              enum "disable";
            }
          }
          leaf duplexity {
            type enumeration {
              enum "full";
              enum "half";
              enum "auto";
            }
          }
          leaf cpu-process {
            type empty;
          }
          leaf flow-control {
            type empty;
          }
          container icmp-rate-limit {
            tailf:cli-sequence-commands {
              tailf:cli-reset-siblings;
            }
            tailf:cli-compact-syntax;
            leaf rate {
              tailf:cli-drop-node-name;
              type uint16;
            }
            leaf lockup {
              must '../rate' {
                tailf:xpath-root 3;
              }
              type uint16;
            }
            leaf lockup-period {
              must '../lockup' {
                tailf:xpath-root 3;
              }
              tailf:cli-drop-node-name;
              type uint16;
            }
          }
          container ospf;
          container isis;
          leaf l3-vlan-fwd-disable {
            type empty;
          }
          container lacp {
            leaf port-priority {
              type uint16;
            }
            leaf timeout {
              type enumeration {
                enum "long";
                enum "short";
              }
            }
            container trunk {
              tailf:cli-sequence-commands {
                tailf:cli-reset-all-siblings;
              }
              tailf:cli-compact-syntax;
              leaf number {
                tailf:cli-drop-node-name;
                type uint16;
              }
              leaf admin-key {
                tailf:cli-break-sequence-commands;
                must '../number' {
                  tailf:xpath-root 3;
                }
                type uint16;
              }
              leaf mode {
                must '../number' {
                  tailf:xpath-root 3;
                }
                type enumeration {
                  enum "active";
                  enum "passive";
                }
              }
              leaf unidirectional-detection {
                must '../number' {
                  tailf:xpath-root 3;
                }
                type empty;
              }
            }
            container udld-timeout {
              tailf:cli-sequence-commands {
                tailf:cli-reset-all-siblings;
              }
              tailf:cli-compact-syntax;
              leaf timeout-type {
                tailf:cli-drop-node-name;
                type enumeration {
                  enum "fast";
                  enum "slow";
                }
              }
              leaf milli {
                tailf:cli-drop-node-name;
                type uint16;
              }
              leaf secs {
                tailf:cli-drop-node-name;
                type uint16;
              }
            }
          }
          // NCS expand uses statement
          container lldp {
            container enable {
              tailf:cli-compact-syntax;
              leaf rx {
                type empty;
              }
              leaf tx {
                type empty;
              }
            }
            leaf notification {
              type enumeration {
                enum "enable";
              }
            }
            leaf tx-dot1-tlvs {
              type enumeration {
                enum "link-aggregation";
                enum "vlan";
              }
            }
          }
          leaf mtu {
            type uint16;
          }
          leaf speed {
            type enumeration {
              enum "10";
              enum "100";
              enum "1000";
              enum "auto";
            }
          }
          list trunk-group-list {
            key "trunk-group-key";
            tailf:cli-drop-node-name;
            tailf:cli-compact-syntax;
            tailf:cli-sequence-commands {
              tailf:cli-reset-siblings;
            }
            leaf trunk-group-key {
              type enumeration {
                enum "trunk-group";
              }
            }
            leaf trunk-group-id {
              tailf:cli-drop-node-name;
              tailf:cli-hide-in-submode;
              mandatory true;
              type uint8;
            }
            leaf trunk-group-type {
              tailf:cli-drop-node-name;
              tailf:cli-hide-in-submode;
              type enumeration {
                enum "static";
                enum "lacp";
                enum "lacp-udld";
              }
            }
          }
        }
        list trunk {
          key "nr";
          leaf nr {
            type ncs_rpc_notif_ethernet-index;
          }
          leaf name {
            type string;
          }
          leaf state {
            tailf:cli-drop-node-name;
            type enumeration {
              enum "enable";
              enum "disable";
            }
          }
          container icmp-rate-limit {
            tailf:cli-sequence-commands {
              tailf:cli-reset-siblings;
            }
            tailf:cli-compact-syntax;
            leaf rate {
              tailf:cli-drop-node-name;
              type uint16;
            }
            leaf lockup {
              must '../rate' {
                tailf:xpath-root 3;
              }
              type uint16;
            }
            leaf lockup-period {
              must '../lockup' {
                tailf:xpath-root 3;
              }
              tailf:cli-drop-node-name;
              type uint16;
            }
          }
          list access-list {
            tailf:cli-suppress-mode;
            key "id in-type";
            leaf id {
              type uint16;
            }
            leaf in-type {
              type enumeration {
                enum "in";
              }
            }
          }
          container ip {
            list address {
              key "ip mask";
              tailf:cli-suppress-mode;
              leaf ip {
                type inet:ipv4-address;
              }
              leaf mask {
                type ncs_rpc_notif_ipv4-mask;
              }
            }
            leaf allow-promiscuous-vip {
              type empty;
            }
            leaf cache-spoofing-port {
              type empty;
            }
            container nat {
              leaf inside {
                type empty;
              }
              leaf outside {
                type empty;
              }
            }
          }
        }
        list loopback {
          key "nr";
          leaf nr {
            type ncs_rpc_notif_ethernet-index;
          }
          container ip {
            // NCS expand uses statement
            list address {
              tailf:cli-suppress-mode;
              key "address mask";
              leaf address {
                type union {
                  type inet:ipv4-address;
                  type enumeration {
                    enum "dhcp";
                  }
                }
              }
              leaf mask {
                type union {
                  type inet:ipv4-address;
                  type string;
                }
              }
            }
            container router {
              choice isis-choice {
                container isis-alt {
                  tailf:cli-drop-node-name;
                  leaf isis {
                    type string;
                  }
                }
                leaf isis {
                  type empty;
                }
              }
            }
          }
          container icmp-rate-limit {
            tailf:cli-sequence-commands {
              tailf:cli-reset-siblings;
            }
            tailf:cli-compact-syntax;
            leaf rate {
              tailf:cli-drop-node-name;
              type uint16;
            }
            leaf lockup {
              must '../rate' {
                tailf:xpath-root 3;
              }
              type uint16;
            }
            leaf lockup-period {
              tailf:cli-drop-node-name;
              must '../lockup' {
                tailf:xpath-root 3;
              }
              type uint16;
            }
          }
          leaf state {
            tailf:cli-drop-node-name;
            type enumeration {
              enum "enable";
              enum "disable";
            }
          }
        }
        list ve {
          key "id";
          leaf id {
            type ncs_rpc_notif_vlan-index;
          }
          leaf name {
            type string;
          }
          container bfd {
            container echo {
              presence "true";
            }
          }
          container icmp-rate-limit {
            tailf:cli-sequence-commands {
              tailf:cli-reset-siblings;
            }
            tailf:cli-compact-syntax;
            leaf rate {
              tailf:cli-drop-node-name;
              type uint16;
            }
            leaf lockup {
              must '../rate' {
                tailf:xpath-root 3;
              }
              type uint16;
            }
            leaf lockup-period {
              tailf:cli-drop-node-name;
              must '../lockup' {
                tailf:xpath-root 3;
              }
              type uint16;
            }
          }
          container access-list {
            tailf:cli-sequence-commands {
              tailf:cli-reset-siblings;
            }
            tailf:cli-compact-syntax;
            leaf id {
              tailf:cli-drop-node-name;
              type uint16;
            }
            leaf in {
              must '../id' {
                tailf:xpath-root 3;
              }
              type empty;
            }
          }
          leaf l3-vlan-fwd-disable {
            type empty;
          }
          container ip {
            leaf allow-promiscuous-vip {
              type empty;
            }
            leaf cache-spoofing-port {
              type empty;
            }
            leaf helper-address {
              type inet:ipv4-address;
            }
            container nat {
              leaf inside {
                type empty;
              }
              leaf outside {
                type empty;
              }
            }
            container ospf;
            container router {
              container isis {
                presence "true";
                leaf cmds {
                  tailf:cli-drop-node-name;
                  type string;
                }
              }
            }
            container tcp {
              leaf syn-cookie {
                type empty;
              }
            }
            // NCS expand uses statement
            list address {
              tailf:cli-suppress-mode;
              key "address mask";
              leaf address {
                type union {
                  type inet:ipv4-address;
                  type enumeration {
                    enum "dhcp";
                  }
                }
              }
              leaf mask {
                type union {
                  type inet:ipv4-address;
                  type string;
                }
              }
            }
          }
          container ipv6 {
            container access-list {
              tailf:cli-sequence-commands {
                tailf:cli-reset-siblings;
              }
              tailf:cli-compact-syntax;
              leaf id {
                tailf:cli-drop-node-name;
                type string;
              }
              leaf in {
                must '../id' {
                  tailf:xpath-root 3;
                }
                type empty;
              }
            }
            container nat {
              leaf inside {
                type empty;
              }
              leaf outside {
                type empty;
              }
            }
            container ndisc {
              container router-advertisement;
            }
            container ospf;
            container router {
              container isis {
                presence "true";
                leaf cmds {
                  tailf:cli-drop-node-name;
                  type string;
                }
              }
            }
            list address {
              key "ip";
              tailf:cli-suppress-mode;
              tailf:cli-sequence-commands {
                tailf:cli-reset-all-siblings;
              }
              tailf:cli-compact-syntax;
              leaf ip {
                tailf:cli-drop-node-name;
                type ncs_rpc_notif_ipv6-prefix;
              }
              leaf link-local {
                type empty;
                tailf:cli-break-sequence-commands;
              }
              leaf anycast {
                type empty;
                tailf:cli-break-sequence-commands;
              }
            }
          }
          leaf mtu {
            type uint16;
          }
          leaf state {
            tailf:cli-drop-node-name;
            type enumeration {
              enum "enable";
              enum "disable";
            }
          }
          container isis;
          container ospf;
        }
      }
      container ip {
        uses ncs_rpc_notif_ip-prefix-list-grouping;
        uses ncs_rpc_notif_ip-route-grouping;
      }
      container ipv6 {
        uses ncs_rpc_notif_ipv6-route-grouping;
      }
      uses ncs_rpc_notif_bfd-grouping;
      uses ncs_rpc_notif_clock-grouping;
      uses ncs_rpc_notif_lldp-grouping;
      // NCS expand uses statement
      container vcs {
        leaf state {
          tailf:cli-drop-node-name;
          type enumeration {
            enum "enable";
            enum "disable";
          }
        }
        list device {
          key "id";
          leaf id {
            type uint8;
          }
          leaf priority {
            type uint8;
          }
          container interfaces {
            leaf management {
              type empty;
            }
            list ethernet {
              tailf:cli-suppress-mode;
              key "id";
              leaf id {
                type uint8;
              }
            }
            list trunk {
              tailf:cli-suppress-mode;
              key "id";
              leaf id {
                type uint8;
              }
            }
            list ve {
              tailf:cli-suppress-mode;
              key "id";
              leaf id {
                type uint16;
              }
            }
          }
          leaf enable {
            type empty;
          }
        }
        list floating-ip {
          tailf:cli-suppress-mode;
          tailf:cli-delete-when-empty;
          tailf:cli-compact-syntax;
          key "floating-ip-address";
          leaf floating-ip-address {
            tailf:cli-drop-node-name;
            type inet:ipv4-address;
          }
          leaf mask {
            tailf:cli-drop-node-name;
            type ncs_rpc_notif_ipv4-mask;
          }
        }
        leaf ssl-enable {
          type empty;
        }
        leaf failure-retry-count {
          type union {
            type enumeration {
              enum "forever";
            }
            type uint8;
          }
        }
      }
      uses ncs_rpc_notif_tftp-grouping;
      uses ncs_rpc_notif_enable-management-grouping;
      uses ncs_rpc_notif_disable-management-grouping;
      uses ncs_rpc_notif_lacp-grouping;
      uses ncs_rpc_notif_route-map-grouping;
      uses ncs_rpc_notif_ve-stats-grouping;
      uses ncs_rpc_notif_bgp-grouping;
      uses ncs_rpc_notif_router-grouping;
      uses ncs_rpc_notif_timezone-grouping;
      uses ncs_rpc_notif_sflow-grouping;
      container vrrp-a {
        // NCS expand uses statement
        container preferred-session-sync-port {
          list trunk {
            tailf:cli-suppress-mode;
            tailf:cli-sequence-commands {
              tailf:cli-reset-siblings;
            }
            tailf:cli-compact-syntax;
            key "id";
            leaf id {
              type uint8;
            }
            leaf vlan {
              type uint16;
            }
          }
          list ethernet {
            tailf:cli-suppress-mode;
            tailf:cli-sequence-commands {
              tailf:cli-reset-siblings;
            }
            tailf:cli-compact-syntax;
            key "id";
            leaf id {
              type ncs_rpc_notif_ethernet-index;
            }
            leaf vlan {
              type uint16;
            }
          }
        }
      }
    }
  }

  grouping ncs_rpc_notif_vcs-grouping {
    container vcs {
      leaf state {
        tailf:cli-drop-node-name;
        type enumeration {
          enum "enable";
          enum "disable";
        }
      }
      list device {
        key "id";
        leaf id {
          type uint8;
        }
        leaf priority {
          type uint8;
        }
        container interfaces {
          leaf management {
            type empty;
          }
          list ethernet {
            tailf:cli-suppress-mode;
            key "id";
            leaf id {
              type uint8;
            }
          }
          list trunk {
            tailf:cli-suppress-mode;
            key "id";
            leaf id {
              type uint8;
            }
          }
          list ve {
            tailf:cli-suppress-mode;
            key "id";
            leaf id {
              type uint16;
            }
          }
        }
        leaf enable {
          type empty;
        }
      }
      list floating-ip {
        tailf:cli-suppress-mode;
        tailf:cli-delete-when-empty;
        tailf:cli-compact-syntax;
        key "floating-ip-address";
        leaf floating-ip-address {
          tailf:cli-drop-node-name;
          type inet:ipv4-address;
        }
        leaf mask {
          tailf:cli-drop-node-name;
          type ncs_rpc_notif_ipv4-mask;
        }
      }
      leaf ssl-enable {
        type empty;
      }
      leaf failure-retry-count {
        type union {
          type enumeration {
            enum "forever";
          }
          type uint8;
        }
      }
    }
  }

  grouping ncs_rpc_notif_system-grouping {
    container system {
      container cpu-load-sharing {
        container cpu-usage {
          tailf:cli-compact-syntax;
          leaf low {
            type uint32;
          }
          leaf high {
            type uint32;
          }
        }
      }
      leaf module-ctrl-cpu {
        type enumeration {
          enum "high";
          enum "low";
          enum "medium";
        }
      }
      leaf glid {
        type uint16;
      }
      container all-vlan-limit {
        leaf bcast {
          type uint16;
        }
        leaf ipmcast {
          type uint16;
        }
        leaf mcast {
          type uint16;
        }
        leaf unknown-ucast {
          type uint16;
        }
      }
      container per-vlan-limit {
        leaf bcast {
          type uint16;
        }
        leaf ipmcast {
          type uint16;
        }
        leaf mcast {
          type uint16;
        }
        leaf unknown-ucast {
          type uint16;
        }
      }
      container resource-usage {
        uses ncs_rpc_notif_resource-usage-grouping;
        list template {
          key "name";
          leaf name {
            type string;
          }
          container system-resources {
            tailf:cli-add-mode;
            leaf bw-limit {
              type uint16;
            }
            leaf ssl-throughput-limit {
              type uint16;
            }
            leaf l4cps-limit {
              type uint32;
            }
            leaf natcps-limit {
              type uint32;
            }
            leaf l7cps-limit {
              type uint32;
            }
            leaf sslcps-limit {
              type uint32;
            }
            leaf concurrent-session-limit {
              type uint32;
            }
          }
          container app-resources {
            tailf:cli-add-mode;
            leaf gslb-device-count {
              type uint16;
            }
            leaf gslb-geo-location-count {
              type uint32;
            }
            leaf gslb-ip-list-count {
              type uint16;
            }
            leaf gslb-policy-count {
              type uint16;
            }
            leaf gslb-service-count {
              type uint16;
            }
            leaf gslb-service-ip-count {
              type uint16;
            }
            leaf gslb-service-port-count {
              type uint16;
            }
            leaf gslb-site-count {
              type uint16;
            }
            leaf gslb-svc-group-count {
              type uint16;
            }
            leaf gslb-template-count {
              type uint16;
            }
            leaf gslb-zone-count {
              type uint16;
            }
          }
        }
      }
      container template {
        leaf policy {
          type string;
        }
      }
      container trunk {
        container load-balance {
          tailf:cli-add-mode;
          leaf layer-2 {
            type enumeration {
              enum "use-l3";
              enum "use-l4";
            }
          }
        }
      }
      leaf ve-mac-scheme {
        type enumeration {
          enum "hash-based";
          enum "round-robin";
          enum "system-mac";
        }
      }
      container apps-global {
        leaf log-session-on-established {
          type empty;
        }
        leaf msl-time {
          type uint8;
        }
      }
    }
  }

  grouping ncs_rpc_notif_ve-stats-grouping {
    leaf ve-stats {
      type enumeration {
        enum "enable";
      }
    }
  }

  grouping ncs_rpc_notif_partition-grouping {
    list partition {
      key "name";
      leaf name {
        type string;
      }
      leaf network-partition {
        tailf:cli-hide-in-submode;
        type empty;
      }
      leaf id {
        tailf:cli-hide-in-submode;
        type uint8;
      }
      leaf application-type {
        tailf:cli-hide-in-submode;
        type enumeration {
          enum "adc";
          enum "cgnv6";
        }
      }
      leaf template {
        type string;
      }
    }
  }

  grouping ncs_rpc_notif_partition-group-grouping {
    list partition-group {
      key "name";
      leaf name {
        type string;
      }
      list member {
        tailf:cli-suppress-mode;
        key "partition-name";
        leaf partition-name {
          type string;
        }
      }
    }
  }

  grouping ncs_rpc_notif_access-list-grouping {
    list access-list {
      tailf:cli-suppress-mode;
      tailf:cli-delete-when-empty;
      key "id";
      leaf id {
        type uint16;
      }
      list rules {
        ordered-by user;
        tailf:cli-suppress-mode;
        tailf:cli-drop-node-name;
        key "txt";
        leaf txt {
          tailf:cli-multi-word-key;
          type string;
        }
      }
    }
  }

  grouping ncs_rpc_notif_tftp-grouping {
    container tftp {
      leaf blksize {
        type uint16;
      }
    }
  }

  grouping ncs_rpc_notif_stats-data-disable-grouping {
    leaf stats-data-disable {
      type empty;
    }
  }

  grouping ncs_rpc_notif_syn-cookie-grouping {
    container syn-cookie {
      tailf:cli-compact-syntax;
      tailf:cli-sequence-commands {
        tailf:cli-reset-siblings;
      }
      leaf on-threshold {
        type uint32;
      }
      leaf off-threshold {
        type uint32;
      }
    }
  }

  grouping ncs_rpc_notif_enable-management-grouping {
    container enable-management {
      container service {
        tailf:cli-compact-syntax;

        grouping enable-management-content-grouping {
          leaf-list ethernet {
            tailf:cli-range-list-syntax;
            type uint8;
          }
          list acl {
            key "id";
            leaf id {
              type uint16;
            }
          }
          list acl-v4 {
            key "id";
            leaf id {
              type uint16;
            }
          }
          leaf-list ve {
            tailf:cli-range-list-syntax;
            type uint32;
          }
        }
        container ssh {
          tailf:cli-add-mode;
          uses enable-management-content-grouping;
        }
        container ssh-alt {
          tailf:alt-name "ssh";
          tailf:cli-compact-syntax;
          leaf management {
            type empty;
          }
          uses enable-management-content-grouping;
        }
        container telnet {
          tailf:cli-add-mode;
          uses enable-management-content-grouping;
        }
        container telnet-alt {
          tailf:alt-name "telnet";
          tailf:cli-compact-syntax;
          leaf management {
            type empty;
          }
          uses enable-management-content-grouping;
        }
        container http {
          tailf:cli-add-mode;
          uses enable-management-content-grouping;
        }
        container http-alt {
          tailf:alt-name "http";
          tailf:cli-compact-syntax;
          leaf management {
            type empty;
          }
          uses enable-management-content-grouping;
        }
        container https {
          tailf:cli-add-mode;
          uses enable-management-content-grouping;
        }
        container https-alt {
          tailf:alt-name "https";
          tailf:cli-compact-syntax;
          leaf management {
            type empty;
          }
          uses enable-management-content-grouping;
        }
        container snmp {
          tailf:cli-add-mode;
          uses enable-management-content-grouping;
        }
        container snmp-alt {
          tailf:alt-name "snmp";
          tailf:cli-compact-syntax;
          leaf management {
            type empty;
          }
          uses enable-management-content-grouping;
        }
      }
    }
  }

  grouping ncs_rpc_notif_disable-management-grouping {
    container disable-management {
      container service {
        container http {
          presence "present";
          leaf management {
            type empty;
          }
        }
      }
    }
  }

  grouping ncs_rpc_notif_monitor-grouping {
    container monitor {
      leaf disk {
        type uint8;
      }
      leaf memory {
        type uint8;
      }
      leaf buffer-drop {
        type uint16;
      }
      leaf buffer-usage {
        type uint32;
      }
    }
  }

  grouping ncs_rpc_notif_extended-stats-grouping {
    leaf extended-stats {
      type empty;
    }
  }

  grouping ncs_rpc_notif_admin-grouping {
    container admin {
      container lockout {
        leaf enable {
          type empty;
        }
      }
    }
  }

  grouping ncs_rpc_notif_zone-grouping {
    list zone {
      key "name";
      leaf name {
        type string;
      }
      container interface {
        leaf-list ethernet {
          tailf:cli-range-list-syntax;
          type ncs_rpc_notif_ethernet-index;
        }
      }
    }
  }

  grouping ncs_rpc_notif_object-grouping {
    container object {
      list network {
        key "name";
        leaf name {
          type string;
        }
        leaf ipv4-address {
          tailf:cli-drop-node-name;
          type tailf:ipv4-address-and-prefix-length;
        }
        leaf ipv6-address {
          tailf:cli-drop-node-name;
          type tailf:ipv6-address-and-prefix-length;
        }
      }
    }
  }

  grouping ncs_rpc_notif_icmp-grouping {
    container icmp {
      list type {
        tailf:cli-suppress-mode;
        key "id";
        leaf id {
          type enumeration {
            enum "any-type";
            enum "echo-reply";
            enum "echo-request";
            enum "info-reply";
            enum "info-request";
            enum "mask-reply";
            enum "mask-request";
            enum "parameter-problem";
            enum "redirect";
            enum "source-quench";
            enum "time-exceeded";
            enum "timestamp";
            enum "timestamp-reply";
            enum "dest-unreachable";
          }
        }
      }
    }
  }

  grouping ncs_rpc_notif_object-group-grouping {
    container object-group {
      list service {
        key "service-name";
        leaf service-name {
          type string;
        }
        leaf description {
          type string;
        }
        list tcp {
          tailf:cli-suppress-mode;
          key "op port";
          leaf op {
            type enumeration {
              enum "eq";
              enum "gt";
              enum "lt";
              enum "range";
              enum "source";
            }
          }
          leaf port {
            type uint32;
          }
        }
        uses ncs_rpc_notif_icmp-grouping;
      }
      list network {
        key "name";
        leaf name {
          type string;
        }
        leaf fw {
          tailf:cli-hide-in-submode;
          type enumeration {
            enum "v4";
            enum "v6";
          }
        }
        leaf description {
          type string;
        }
        leaf any {
          type empty;
        }
        leaf host {
          type inet:ipv4-address;
        }
        leaf ipv6-address {
          tailf:cli-drop-node-name;
          type tailf:ipv6-address-and-prefix-length;
        }
      }
    }
  }

  grouping ncs_rpc_notif_rule-set-grouping {
    list rule-set {
      key "rule-name";
      leaf rule-name {
        type string;
      }
      list rule {
        key "name";
        leaf name {
          type string;
        }
        leaf action {
          type enumeration {
            enum "permit";
            enum "deny";
            enum "reset";
          }
        }

        grouping source-dest-grouping {
          list object {
            key "name";
            leaf name {
              type string;
            }
          }
          list object-group {
            key "name";
            leaf name {
              type string;
            }
          }
          leaf zone {
            type string;
          }
        }
        container source {
          uses source-dest-grouping;
        }
        container dest {
          uses source-dest-grouping;
        }
        container service {
          leaf any {
            type empty;
          }
          uses ncs_rpc_notif_icmp-grouping;
          leaf object-group {
            type string;
          }
        }
      }
    }
  }

  grouping ncs_rpc_notif_fw-grouping {
    container fw {
      leaf active-rule-set {
        type string;
      }
    }
  }

  grouping ncs_rpc_notif_enable-core-grouping {
    leaf enable-core {
      type enumeration {
        enum "system";
        enum "a10";
      }
    }
  }

  grouping slb-template-version-grouping {
    container version {
      tailf:cli-compact-syntax;
      tailf:cli-sequence-commands {
        tailf:cli-reset-siblings;
      }
      leaf current {
        tailf:cli-drop-node-name;
        type uint8;
      }
      leaf lower {
        tailf:cli-drop-node-name;
        type uint8;
      }
    }
  }

  grouping ip-list-grouping {
    list ip-list {
      key "name";
      leaf name {
        type string;
      }
    }
  }

  grouping cgnv6-grouping {
    container cgnv6 {
      container logging {
        container nat-quota-exceeded {
          leaf level {
            type enumeration {
              enum "warning";
              enum "critical";
              enum "notice";
            }
          }
        }
        container sampling-enable {
          leaf all {
            type empty;
          }
        }
      }
      list server {
        key "name";
        unique "address";
        leaf name {
          type string;
        }
        leaf address {
          tailf:cli-drop-node-name;
          tailf:cli-hide-in-submode;
          mandatory true;
          type union {
            type inet:ipv4-address;
            type inet:ipv6-address;
            type string;
          }
        }
        leaf health-check-disable {
          type empty;
        }
        list port {
          key "number tcpudp";
          leaf number {
            type uint16;
          }
          leaf tcpudp {
            type enumeration {
              enum "tcp";
              enum "udp";
            }
          }
          leaf health-check-disable {
            type empty;
          }
        }
      }
      list service-group {
        key "name tcpudp";
        unique "name";
        leaf name {
          type string;
        }
        leaf tcpudp {
          type enumeration {
            enum "tcp";
            enum "udp";
          }
        }
        container sampling-enable {
          leaf all {
            type empty;
          }
        }
        list member {
          key "host port";
          leaf host {
            type string;
          }
          leaf port {
            type uint16;
          }
          container sampling-enable {
            leaf all {
              type empty;
            }
          }
        }
        container shared {
          choice group-partition {
            leaf group {
              type string;
            }
            leaf partition {
              type string;
            }
          }
        }
      }
      container translation {
        leaf udp-timeout {
          type uint32;
        }
        leaf tcp-timeout {
          type uint32;
        }
        leaf icmp-timeout {
          type union {
            type uint32;
            type enumeration {
              enum "fast";
            }
          }
        }
        container service-timeout {
          list tcp {
            tailf:cli-compact-syntax;
            tailf:cli-suppress-mode;
            key "port-id";
            leaf port-id {
              type uint32;
            }
            leaf to {
              type uint32;
            }
            leaf timeout {
              tailf:cli-drop-node-name;
              type uint32;
            }
          }
          list udp {
            tailf:cli-compact-syntax;
            tailf:cli-suppress-mode;
            key "port-id";
            leaf port-id {
              type uint32;
            }
            leaf timeout {
              tailf:cli-drop-node-name;
              type uint32;
            }
          }
        }
      }
      container lsn {
        list alg {
          tailf:cli-suppress-mode;
          key "alg-id";
          leaf alg-id {
            type enumeration {
              enum "esp";
              enum "ftp";
              enum "h323";
              enum "mgcp";
              enum "pptp";
              enum "rtp-stun-timeout";
              enum "rtsp";
              enum "sip";
              enum "tftp";
            }
          }
          leaf enable {
            type empty;
          }
        }
        leaf hairpinning {
          type enumeration {
            enum "filter-none";
            enum "filter-self-ip";
            enum "filter-self-ip-port";
          }
        }
        leaf half-close-timeout {
          type uint16;
        }
        container logging {
          leaf default-template {
            type string;
          }
        }
        list endpoint-independent-mapping {
          key "proto";
          leaf proto {
            type enumeration {
              enum "udp";
              enum "tcp";
            }
          }
          container port {
            tailf:cli-compact-syntax;
            leaf from {
              tailf:cli-drop-node-name;
              type uint32;
            }
            leaf to {
              type uint32;
            }
          }
        }
        list endpoint-independent-filtering {
          key "proto";
          leaf proto {
            type enumeration {
              enum "tcp";
              enum "udp";
            }
          }
          container port {
            tailf:cli-compact-syntax;
            leaf from {
              tailf:cli-drop-node-name;
              type uint32;
            }
            leaf to {
              type uint32;
            }
          }
        }
        leaf ip-selection {
          type enumeration {
            enum "random";
            enum "round-robin";
            enum "least-used-strict";
            enum "least-udp-used-strict";
            enum "least-tcp-used-strict";
            enum "least-reserved-strict";
            enum "least-udp-reserved-strict";
            enum "least-tcp-reserved-strict";
            enum "least-users-strict";
          }
        }
        container inside {
          container source {
            leaf class-list {
              type string;
            }
          }
        }
      }
      list lsn-rule-list {
        key "name";
        leaf name {
          type string;
        }
        container default {
          tailf:cli-add-mode;
          container tcp {
            tailf:cli-compact-syntax;
            uses port-grouping;
          }
          container udp {
            tailf:cli-compact-syntax;
            uses port-grouping;
          }
          container icmp {
            tailf:cli-compact-syntax;
            // NCS expand uses statement
            list action {
              tailf:cli-suppress-mode;
              key "type";
              leaf type {
                type enumeration {
                  enum "dnat";
                  enum "drop";
                  enum "one-to-one-snat";
                  enum "pass-through";
                  enum "snat";
                }
              }
              leaf pool {
                type string;
              }
              leaf domain {
                type string;
              }
            }
            leaf no-action {
              type empty;
            }
          }
          container others {
            tailf:cli-compact-syntax;
            // NCS expand uses statement
            list action {
              tailf:cli-suppress-mode;
              key "type";
              leaf type {
                type enumeration {
                  enum "dnat";
                  enum "drop";
                  enum "one-to-one-snat";
                  enum "pass-through";
                  enum "snat";
                }
              }
              leaf pool {
                type string;
              }
              leaf domain {
                type string;
              }
            }
            leaf no-action {
              type empty;
            }
          }
        }
        list ip {
          key "address";
          leaf address {
            type tailf:ipv4-address-and-prefix-length;
          }
          container tcp {
            tailf:cli-compact-syntax;
            uses port-grouping;
          }
          container udp {
            tailf:cli-compact-syntax;
            uses port-grouping;
          }
          container icmp {
            tailf:cli-compact-syntax;
            // NCS expand uses statement
            list action {
              tailf:cli-suppress-mode;
              key "type";
              leaf type {
                type enumeration {
                  enum "dnat";
                  enum "drop";
                  enum "one-to-one-snat";
                  enum "pass-through";
                  enum "snat";
                }
              }
              leaf pool {
                type string;
              }
              leaf domain {
                type string;
              }
            }
            leaf no-action {
              type empty;
            }
          }
          container others {
            tailf:cli-compact-syntax;
            // NCS expand uses statement
            list action {
              tailf:cli-suppress-mode;
              key "type";
              leaf type {
                type enumeration {
                  enum "dnat";
                  enum "drop";
                  enum "one-to-one-snat";
                  enum "pass-through";
                  enum "snat";
                }
              }
              leaf pool {
                type string;
              }
              leaf domain {
                type string;
              }
            }
            leaf no-action {
              type empty;
            }
          }
        }
      }
      container fixed-nat {
        leaf create-port-mapping-file {
          type empty;
        }
      }
      container nat {
        list pool {
          tailf:cli-sequence-commands;
          tailf:cli-compact-syntax;
          tailf:cli-suppress-mode;
          key "name";
          leaf name {
            type string;
          }
          leaf address {
            tailf:cli-drop-node-name;
            type inet:ipv4-address;
          }
          leaf address-end {
            tailf:cli-optional-in-sequence;
            tailf:cli-drop-node-name;
            type inet:ipv4-address;
          }
          leaf netmask {
            type union {
              type inet:ipv4-address;
              type string;
            }
          }
          leaf vrid {
            tailf:cli-optional-in-sequence;
            type union {
              type uint8;
              type enumeration {
                enum "default";
              }
            }
          }
          leaf port-batch-v2-size {
            type enumeration {
              enum "64";
              enum "128";
              enum "256";
              enum "512";
              enum "1024";
              enum "2048";
              enum "4096";
            }
          }
          leaf simultaneous-batch-allocation {
            type empty;
          }
          leaf tcp-time-wait-interval {
            tailf:cli-optional-in-sequence;
            type uint8;
          }
          container usable-nat-ports {
            tailf:cli-compact-syntax;
            tailf:cli-sequence-commands;
            tailf:cli-flatten-container;
            leaf start {
              tailf:cli-drop-node-name;
              type uint16;
            }
            leaf end {
              tailf:cli-drop-node-name;
              type uint16;
            }
          }
        }
        list pool-group {
          key "name";
          leaf name {
            type string;
          }
          leaf vrid {
            tailf:cli-hide-in-submode;
            type union {
              type uint8;
              type enumeration {
                enum "default";
              }
            }
          }
          list member {
            tailf:cli-suppress-mode;
            key "name";
            leaf name {
              type string;
            }
          }
        }
      }
      container resource-usage {
        leaf lsn-nat-addr-count {
          type uint32;
        }
      }
      list lsn-lid {
        key "lid";
        leaf lid {
          type uint32;
        }
        leaf name {
          type string;
        }
        container lsn-rule-list {
          leaf destination {
            type string;
          }
        }
        list user-quota {
          tailf:cli-compact-syntax;
          tailf:cli-suppress-mode;
          key "protocol";
          leaf protocol {
            type enumeration {
              enum "icmp";
              enum "udp";
              enum "tcp";
              enum "session";
              enum "session-tcp";
              enum "session-udp";
            }
          }
          leaf quota {
            tailf:cli-drop-node-name;
            type uint32;
          }
          leaf reserve {
            type uint32;
          }
        }
        leaf source-nat-pool {
          type string;
        }
      }
      container template {
        list logging {
          key "name";
          leaf name {
            type string;
          }
          container log {
            container fixed-nat {
              leaf port-mappings {
                type enumeration {
                  enum "both";
                  enum "creation";
                }
              }
              container sessions {
                presence "true";
                leaf merged-style {
                  type empty;
                }
              }
            }
            leaf port-mappings {
              type enumeration {
                enum "creation";
                enum "disable";
                enum "both";
              }
            }
            container sessions {
              presence "true";
              leaf merged-style {
                type empty;
              }
            }
          }
          leaf facility {
            type union {
              type enumeration {
                enum "kernel";
                enum "user";
                enum "mail";
                enum "daemon";
                enum "security-authorization";
                enum "syslog";
                enum "line-printer";
                enum "news";
                enum "uucp";
                enum "cron";
                enum "security-authorization-private";
                enum "ftp";
                enum "ntp";
                enum "audit";
                enum "alert";
                enum "clock";
                enum "local0";
                enum "local1";
                enum "local2";
                enum "local3";
                enum "local4";
                enum "local5";
                enum "local6";
                enum "local7";
              }
              type string;
            }
          }
          leaf severity {
            type union {
              type enumeration {
                enum "emergency";
                enum "alert";
                enum "critical";
                enum "error";
                enum "warning";
                enum "notice";
                enum "informational";
                enum "debug";
              }
              type uint8;
            }
          }
          container service-group {
            tailf:cli-compact-syntax;
            tailf:cli-sequence-commands {
              tailf:cli-reset-siblings;
            }
            leaf name {
              tailf:cli-drop-node-name;
              type string;
            }
            leaf shared {
              type empty;
            }
          }
          container disable-log-by-destination {
            tailf:cli-add-mode;
            presence "true";
            leaf icmp {
              type empty;
            }
          }
          leaf include-destination {
            type empty;
          }
          leaf format {
            type enumeration {
              enum "binary";
              enum "compact";
              enum "custom";
              enum "default";
              enum "rfc5424";
              enum "cef";
            }
          }
          leaf batched-logging-disable {
            type empty;
          }
        }
      }
    }
  }

  grouping sflow-grouping {
    container sflow {
      container agent {
        leaf address {
          type union {
            type inet:ipv4-address;
            type inet:ipv6-address;
          }
        }
      }
      container setting {
        leaf local-collection {
          type empty;
        }
        leaf source-ip-use-mgmt {
          type empty;
        }
      }
      list collector {
        tailf:cli-suppress-mode;
        key "ip port";
        leaf ip {
          tailf:cli-expose-key-name;
          type inet:ipv4-address;
        }
        leaf port {
          type uint32;
        }
      }
      list collector-alt {
        tailf:cli-suppress-mode;
        tailf:alt-name "collector";
        key "ip port";
        leaf ip {
          type inet:ipv4-address;
        }
        leaf port {
          type uint32;
        }
      }
      container polling {
        leaf cpu-usage {
          type empty;
        }
        leaf-list ve {
          tailf:cli-range-list-syntax;
          type uint16;
        }
      }
      container sampling {
        leaf-list ve {
          tailf:cli-range-list-syntax;
          type uint16;
        }
      }
      container source-address {
        leaf ip {
          type inet:ipv4-address;
        }
        leaf ipv6 {
          type inet:ipv6-address;
        }
      }
    }
  }

  grouping ip-address {
    list address {
      tailf:cli-suppress-mode;
      key "address mask";
      leaf address {
        type union {
          type inet:ipv4-address;
          type enumeration {
            enum "dhcp";
          }
        }
      }
      leaf mask {
        type union {
          type inet:ipv4-address;
          type string;
        }
      }
    }
  }

  grouping algs {
    container alg {
      uses pptp_alg;
      uses tftp_alg;
      uses rtsp_alg;
      uses esp_alg;
    }
  }

  grouping pptp_alg {
    leaf pptp {
      type enumeration {
        enum "disable";
        enum "enable";
      }
    }
  }

  grouping tftp_alg {
    leaf tftp {
      type enumeration {
        enum "disable";
        enum "enable";
      }
    }
  }

  grouping rtsp_alg {
    leaf rtsp {
      type enumeration {
        enum "disable";
        enum "enable";
      }
    }
  }

  grouping esp_alg {
    leaf esp {
      type enumeration {
        enum "disable";
        enum "enable";
      }
    }
  }

  grouping lid-grouping {
    choice lid-choice {
      leaf glid {
        type uint16;
      }
      leaf lid {
        type uint8;
      }
      leaf lsn-lid {
        type uint16;
      }
      leaf lsn-radius-profile {
        type uint8;
      }
    }
  }

  grouping mgmt-source-interface-grouping {
    container source-interface {
      leaf loopback {
        type uint8;
      }
    }
  }

  grouping priority-cost {
    leaf priority-cost {
      mandatory true;
      type uint8;
    }
  }

  grouping hostname-grouping {
    leaf hostname {
      type string;
    }
  }

  grouping password-grouping {
    leaf username {
      type string;
    }
    leaf password {
      tailf:cli-optional-in-sequence;
      type string;
    }
  }

  grouping interface-grouping {
    container interface {

      grouping lldp-interface-grouping {
        container lldp {
          container enable {
            tailf:cli-compact-syntax;
            leaf rx {
              type empty;
            }
            leaf tx {
              type empty;
            }
          }
          leaf notification {
            type enumeration {
              enum "enable";
            }
          }
          leaf tx-dot1-tlvs {
            type enumeration {
              enum "link-aggregation";
              enum "vlan";
            }
          }
        }
      }
      container management {
        tailf:cli-add-mode;
        container bcast-rate-limit {
          presence "present";
          leaf rate {
            type uint16;
          }
        }
        container ip {
          uses ip-address;
          leaf control-apps-use-mgmt-port {
            type empty;
          }
          leaf default-gateway {
            type inet:ipv4-address;
          }
        }
        container ipv6 {
          list address {
            key "ip";
            tailf:cli-suppress-mode;
            tailf:cli-sequence-commands {
              tailf:cli-reset-siblings;
            }
            tailf:cli-compact-syntax;
            leaf ip {
              tailf:cli-drop-node-name;
              type ipv6-prefix;
            }
            leaf link-local {
              type empty;
            }
          }
          leaf default-gateway {
            type inet:ipv6-address;
          }
        }
        uses lldp-interface-grouping;
        leaf flow-control {
          type empty;
        }
        container access-list {
          tailf:cli-sequence-commands {
            tailf:cli-reset-siblings;
          }
          tailf:cli-compact-syntax;
          leaf id {
            tailf:cli-drop-node-name;
            type uint16;
          }
          leaf in {
            must '../id' {
              tailf:xpath-root 3;
            }
            type empty;
          }
        }
        leaf enabled-disabled {
          tailf:cli-drop-node-name;
          type enumeration {
            enum "enable";
            enum "disable";
          }
        }
        leaf duplexity {
          type enumeration {
            enum "full";
            enum "half";
            enum "auto";
          }
        }
        leaf mtu {
          type uint16;
        }
        leaf speed {
          type enumeration {
            enum "10";
            enum "100";
            enum "1000";
            enum "auto";
          }
        }
      }
      list ethernet {
        key "nr";
        leaf nr {
          type ethernet-index;
        }
        leaf name {
          type string;
        }
        container ip {
          uses ip-address;
          leaf cache-spoofing-port {
            type empty;
          }
          leaf helper-address {
            type inet:ipv4-address;
          }
          container nat {
            leaf inside {
              type empty;
            }
            leaf outside {
              type empty;
            }
          }
          container ospf;
          container router {
            container isis {
              presence "true";
              leaf cmds {
                tailf:cli-drop-node-name;
                type string;
              }
            }
          }
          leaf allow-promiscuous-vip {
            type empty;
          }
          container tcp {
            leaf syn-cookie {
              type empty;
            }
          }
        }
        container ipv6 {
          container access-list {
            tailf:cli-sequence-commands {
              tailf:cli-reset-siblings;
            }
            tailf:cli-compact-syntax;
            leaf id {
              tailf:cli-drop-node-name;
              type string;
            }
            leaf in {
              must '../id' {
                tailf:xpath-root 3;
              }
              type empty;
            }
          }
          list address {
            key "ip";
            tailf:cli-suppress-mode;
            tailf:cli-sequence-commands {
              tailf:cli-reset-all-siblings;
            }
            tailf:cli-compact-syntax;
            leaf ip {
              tailf:cli-drop-node-name;
              type ipv6-prefix;
            }
            leaf link-local {
              type empty;
              tailf:cli-break-sequence-commands;
            }
            leaf anycast {
              type empty;
              tailf:cli-break-sequence-commands;
            }
          }
          container nat {
            leaf inside {
              type empty;
            }
            leaf outside {
              type empty;
            }
          }
          container ndisc {
            container router-advertisement;
          }
          container ospf;
          container router {
            container isis {
              presence "true";
              leaf cmds {
                tailf:cli-drop-node-name;
                type string;
              }
            }
          }
        }
        leaf load-interval {
          type uint16;
        }
        container access-list {
          tailf:cli-sequence-commands {
            tailf:cli-reset-siblings;
          }
          tailf:cli-compact-syntax;
          leaf id {
            tailf:cli-drop-node-name;
            type uint16;
          }
          leaf in {
            must '../id' {
              tailf:xpath-root 3;
            }
            type empty;
          }
        }
        leaf state {
          tailf:cli-drop-node-name;
          type enumeration {
            enum "enable";
            enum "disable";
          }
        }
        leaf state-alt {
          tailf:cli-drop-node-name;
          type enumeration {
            enum "enable";
            enum "disable";
          }
        }
        leaf duplexity {
          type enumeration {
            enum "full";
            enum "half";
            enum "auto";
          }
        }
        leaf cpu-process {
          type empty;
        }
        leaf flow-control {
          type empty;
        }
        container icmp-rate-limit {
          tailf:cli-sequence-commands {
            tailf:cli-reset-siblings;
          }
          tailf:cli-compact-syntax;
          leaf rate {
            tailf:cli-drop-node-name;
            type uint16;
          }
          leaf lockup {
            must '../rate' {
              tailf:xpath-root 3;
            }
            type uint16;
          }
          leaf lockup-period {
            must '../lockup' {
              tailf:xpath-root 3;
            }
            tailf:cli-drop-node-name;
            type uint16;
          }
        }
        container ospf;
        container isis;
        leaf l3-vlan-fwd-disable {
          type empty;
        }
        container lacp {
          leaf port-priority {
            type uint16;
          }
          leaf timeout {
            type enumeration {
              enum "long";
              enum "short";
            }
          }
          container trunk {
            tailf:cli-sequence-commands {
              tailf:cli-reset-all-siblings;
            }
            tailf:cli-compact-syntax;
            leaf number {
              tailf:cli-drop-node-name;
              type uint16;
            }
            leaf admin-key {
              tailf:cli-break-sequence-commands;
              must '../number' {
                tailf:xpath-root 3;
              }
              type uint16;
            }
            leaf mode {
              must '../number' {
                tailf:xpath-root 3;
              }
              type enumeration {
                enum "active";
                enum "passive";
              }
            }
            leaf unidirectional-detection {
              must '../number' {
                tailf:xpath-root 3;
              }
              type empty;
            }
          }
          container udld-timeout {
            tailf:cli-sequence-commands {
              tailf:cli-reset-all-siblings;
            }
            tailf:cli-compact-syntax;
            leaf timeout-type {
              tailf:cli-drop-node-name;
              type enumeration {
                enum "fast";
                enum "slow";
              }
            }
            leaf milli {
              tailf:cli-drop-node-name;
              type uint16;
            }
            leaf secs {
              tailf:cli-drop-node-name;
              type uint16;
            }
          }
        }
        uses lldp-interface-grouping;
        leaf mtu {
          type uint16;
        }
        leaf speed {
          type enumeration {
            enum "10";
            enum "100";
            enum "1000";
            enum "auto";
          }
        }
        list trunk-group-list {
          key "trunk-group-key";
          tailf:cli-drop-node-name;
          tailf:cli-compact-syntax;
          tailf:cli-sequence-commands {
            tailf:cli-reset-siblings;
          }
          leaf trunk-group-key {
            type enumeration {
              enum "trunk-group";
            }
          }
          leaf trunk-group-id {
            tailf:cli-drop-node-name;
            tailf:cli-hide-in-submode;
            mandatory true;
            type uint8;
          }
          leaf trunk-group-type {
            tailf:cli-drop-node-name;
            tailf:cli-hide-in-submode;
            type enumeration {
              enum "static";
              enum "lacp";
              enum "lacp-udld";
            }
          }
        }
      }
      list trunk {
        key "nr";
        leaf nr {
          type ethernet-index;
        }
        leaf name {
          type string;
        }
        leaf state {
          tailf:cli-drop-node-name;
          type enumeration {
            enum "enable";
            enum "disable";
          }
        }
        container icmp-rate-limit {
          tailf:cli-sequence-commands {
            tailf:cli-reset-siblings;
          }
          tailf:cli-compact-syntax;
          leaf rate {
            tailf:cli-drop-node-name;
            type uint16;
          }
          leaf lockup {
            must '../rate' {
              tailf:xpath-root 3;
            }
            type uint16;
          }
          leaf lockup-period {
            must '../lockup' {
              tailf:xpath-root 3;
            }
            tailf:cli-drop-node-name;
            type uint16;
          }
        }
        list access-list {
          tailf:cli-suppress-mode;
          key "id in-type";
          leaf id {
            type uint16;
          }
          leaf in-type {
            type enumeration {
              enum "in";
            }
          }
        }
        container ip {
          list address {
            key "ip mask";
            tailf:cli-suppress-mode;
            leaf ip {
              type inet:ipv4-address;
            }
            leaf mask {
              type ipv4-mask;
            }
          }
          leaf allow-promiscuous-vip {
            type empty;
          }
          leaf cache-spoofing-port {
            type empty;
          }
          container nat {
            leaf inside {
              type empty;
            }
            leaf outside {
              type empty;
            }
          }
        }
      }
      list loopback {
        key "nr";
        leaf nr {
          type ethernet-index;
        }
        container ip {
          uses ip-address;
          container router {
            choice isis-choice {
              container isis-alt {
                tailf:cli-drop-node-name;
                leaf isis {
                  type string;
                }
              }
              leaf isis {
                type empty;
              }
            }
          }
        }
        container icmp-rate-limit {
          tailf:cli-sequence-commands {
            tailf:cli-reset-siblings;
          }
          tailf:cli-compact-syntax;
          leaf rate {
            tailf:cli-drop-node-name;
            type uint16;
          }
          leaf lockup {
            must '../rate' {
              tailf:xpath-root 3;
            }
            type uint16;
          }
          leaf lockup-period {
            tailf:cli-drop-node-name;
            must '../lockup' {
              tailf:xpath-root 3;
            }
            type uint16;
          }
        }
        leaf state {
          tailf:cli-drop-node-name;
          type enumeration {
            enum "enable";
            enum "disable";
          }
        }
      }
      list ve {
        key "id";
        leaf id {
          type vlan-index;
        }
        leaf name {
          type string;
        }
        container bfd {
          container echo {
            presence "true";
          }
        }
        container icmp-rate-limit {
          tailf:cli-sequence-commands {
            tailf:cli-reset-siblings;
          }
          tailf:cli-compact-syntax;
          leaf rate {
            tailf:cli-drop-node-name;
            type uint16;
          }
          leaf lockup {
            must '../rate' {
              tailf:xpath-root 3;
            }
            type uint16;
          }
          leaf lockup-period {
            tailf:cli-drop-node-name;
            must '../lockup' {
              tailf:xpath-root 3;
            }
            type uint16;
          }
        }
        container access-list {
          tailf:cli-sequence-commands {
            tailf:cli-reset-siblings;
          }
          tailf:cli-compact-syntax;
          leaf id {
            tailf:cli-drop-node-name;
            type uint16;
          }
          leaf in {
            must '../id' {
              tailf:xpath-root 3;
            }
            type empty;
          }
        }
        leaf l3-vlan-fwd-disable {
          type empty;
        }
        container ip {
          leaf allow-promiscuous-vip {
            type empty;
          }
          leaf cache-spoofing-port {
            type empty;
          }
          leaf helper-address {
            type inet:ipv4-address;
          }
          container nat {
            leaf inside {
              type empty;
            }
            leaf outside {
              type empty;
            }
          }
          container ospf;
          container router {
            container isis {
              presence "true";
              leaf cmds {
                tailf:cli-drop-node-name;
                type string;
              }
            }
          }
          container tcp {
            leaf syn-cookie {
              type empty;
            }
          }
          uses ip-address;
        }
        container ipv6 {
          container access-list {
            tailf:cli-sequence-commands {
              tailf:cli-reset-siblings;
            }
            tailf:cli-compact-syntax;
            leaf id {
              tailf:cli-drop-node-name;
              type string;
            }
            leaf in {
              must '../id' {
                tailf:xpath-root 3;
              }
              type empty;
            }
          }
          container nat {
            leaf inside {
              type empty;
            }
            leaf outside {
              type empty;
            }
          }
          container ndisc {
            container router-advertisement;
          }
          container ospf;
          container router {
            container isis {
              presence "true";
              leaf cmds {
                tailf:cli-drop-node-name;
                type string;
              }
            }
          }
          list address {
            key "ip";
            tailf:cli-suppress-mode;
            tailf:cli-sequence-commands {
              tailf:cli-reset-all-siblings;
            }
            tailf:cli-compact-syntax;
            leaf ip {
              tailf:cli-drop-node-name;
              type ipv6-prefix;
            }
            leaf link-local {
              type empty;
              tailf:cli-break-sequence-commands;
            }
            leaf anycast {
              type empty;
              tailf:cli-break-sequence-commands;
            }
          }
        }
        leaf mtu {
          type uint16;
        }
        leaf state {
          tailf:cli-drop-node-name;
          type enumeration {
            enum "enable";
            enum "disable";
          }
        }
        container isis;
        container ospf;
      }
    }
  }

  grouping ip-route-grouping {
    list route {
      tailf:cli-compact-syntax;
      tailf:cli-sequence-commands {
        tailf:cli-reset-siblings;
      }
      tailf:cli-suppress-mode;
      key "ip mask forwarding-router";
      leaf ip {
        type inet:ipv4-address;
      }
      leaf mask {
        type string;
      }
      leaf forwarding-router {
        type inet:ipv4-address;
      }
      leaf distance {
        tailf:cli-drop-node-name;
        tailf:cli-optional-in-sequence;
        type uint8;
      }
      leaf cpu-process {
        tailf:cli-drop-node-name;
        tailf:cli-optional-in-sequence;
        type enumeration {
          enum "cpu-process";
        }
      }
    }
  }

  grouping ip-prefix-list-grouping {
    list prefix-list {
      tailf:cli-suppress-mode;
      tailf:cli-compact-syntax;
      key "name seq";
      leaf name {
        type string;
      }
      leaf seq {
        tailf:cli-expose-key-name;
        type uint32;
      }
      choice permit-deny {
        leaf permit {
          type union {
            type enumeration {
              enum "any";
            }
            type tailf:ipv4-address-and-prefix-length;
          }
        }
        leaf deny {
          type union {
            type enumeration {
              enum "any";
            }
            type tailf:ipv4-address-and-prefix-length;
          }
        }
      }
      leaf ge {
        type uint8;
      }
      leaf le {
        type uint8;
      }
    }
  }

  grouping ip-grouping {
    container ip {
      list access-list {
        key "name";
        leaf name {
          type string;
        }
        list access-list-rule {
          tailf:cli-suppress-mode;
          tailf:cli-delete-when-empty;
          tailf:cli-drop-node-name;
          ordered-by user;
          key "rule";
          leaf rule {
            tailf:cli-multi-word-key;
            type string;
          }
        }
      }
      list address {
        key "ip";
        tailf:cli-suppress-mode;
        tailf:cli-delete-when-empty;
        tailf:cli-sequence-commands {
          tailf:cli-reset-siblings;
        }
        tailf:cli-compact-syntax;
        leaf ip {
          tailf:cli-drop-node-name;
          type inet:ipv4-address;
        }
        leaf mask {
          tailf:cli-drop-node-name;
          type ipv4-mask;
        }
      }
      container anomaly-drop {
        leaf bad-content {
          type uint16;
        }
        leaf drop-all {
          type empty;
        }
        leaf frag {
          type empty;
        }
        leaf ip-option {
          type boolean;
        }
        leaf land-attack {
          type empty;
        }
        leaf out-of-sequence {
          type uint16;
        }
        leaf ping-of-death {
          type empty;
        }
        leaf tcp-no-flag {
          type empty;
        }
        leaf tcp-syn-fin {
          type empty;
        }
        leaf tcp-syn-frag {
          type empty;
        }
        leaf zero-window {
          type uint16;
        }
        container security-attack {
          leaf layer-3 {
            type empty;
          }
          leaf layer-4 {
            type empty;
          }
        }
        list packet-deformity {
          tailf:cli-suppress-mode;
          key "layer";
          leaf layer {
            type enumeration {
              enum "layer-3";
              enum "layer-4";
            }
          }
        }
      }
      container as-path {
        list access-list {
          tailf:cli-suppress-mode;
          key "name action path";
          leaf name {
            type string;
          }
          leaf action {
            type enumeration {
              enum "permit";
              enum "deny";
            }
          }
          leaf path {
            type string;
            tailf:cli-multi-word-key;
          }
        }
      }
      container community-list {
        list standard-number {
          tailf:cli-drop-node-name;
          tailf:cli-suppress-mode;
          key "nr";
          leaf nr {
            type uint8;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list expanded-number {
          tailf:cli-drop-node-name;
          tailf:cli-suppress-mode;
          key "nr";
          leaf nr {
            type uint8;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list word {
          tailf:cli-drop-node-name;
          tailf:cli-suppress-mode;
          key "name";
          leaf name {
            type string;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list expanded {
          tailf:cli-suppress-mode;
          key "name";
          leaf name {
            type string;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list standard {
          tailf:cli-suppress-mode;
          key "name";
          leaf name {
            type string;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
      }
      leaf default-gateway {
        type inet:ipv4-address;
      }
      container dns {
        leaf primary {
          type inet:ipv4-address;
        }
        leaf secondary {
          type inet:ipv4-address;
        }
        leaf suffix {
          type string;
        }
      }
      container extcommunity-list {
        list standard-number {
          tailf:cli-drop-node-name;
          tailf:cli-suppress-mode;
          key "nr";
          leaf nr {
            type uint8;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list expanded-number {
          tailf:cli-drop-node-name;
          tailf:cli-suppress-mode;
          key "nr";
          leaf nr {
            type uint8;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list expanded {
          tailf:cli-suppress-mode;
          key "name";
          leaf name {
            type string;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list standard {
          tailf:cli-suppress-mode;
          key "name";
          leaf name {
            type string;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
      }
      container frag {
        leaf buff {
          type uint32;
        }
        container cpu-threshold {
          tailf:cli-compact-syntax;
          tailf:cli-sequence-commands;
          leaf high {
            type uint8;
          }
          leaf low {
            type uint8;
          }
        }
        leaf max-reassembly-sessions {
          type uint32;
        }
        leaf timeout {
          type uint16;
        }
      }
      container icmp {
        container disable {
          leaf redirect {
            type empty;
          }
          leaf unreachable {
            type empty;
          }
        }
      }
      container mgmt-traffic {
        container snmp {
          uses mgmt-source-interface-grouping;
        }
        container ntp {
          uses mgmt-source-interface-grouping;
        }
        container syslog {
          uses mgmt-source-interface-grouping;
        }
        container ssh {
          uses mgmt-source-interface-grouping;
        }
        container telnet {
          uses mgmt-source-interface-grouping;
        }
        container ftp {
          uses mgmt-source-interface-grouping;
        }
        container tftp {
          uses mgmt-source-interface-grouping;
        }
        container rcp {
          uses mgmt-source-interface-grouping;
        }
        container web {
          uses mgmt-source-interface-grouping;
        }
        container all {
          uses mgmt-source-interface-grouping;
        }
      }
      container nat {
        uses algs;
        leaf allow-static-host {
          type empty;
        }
        container inside {
          container source {
            list list {
              tailf:cli-suppress-mode;
              key "id";
              leaf id {
                type uint16;
              }
              leaf pool {
                tailf:cli-hide-in-submode;
                mandatory true;
                type string;
              }
            }
            leaf class-list {
              type string;
            }
            list static {
              tailf:cli-suppress-mode;
              tailf:cli-compact-syntax;
              key "source nat";
              leaf source {
                type inet:ipv4-address;
              }
              leaf nat {
                type inet:ipv4-address;
              }
              leaf vrid {
                type uint8;
              }
            }
          }
        }
        list pool {
          tailf:cli-suppress-mode;
          tailf:cli-sequence-commands {
            tailf:cli-reset-all-siblings;
          }
          tailf:cli-compact-syntax;
          key "name";
          leaf name {
            type string;
          }
          leaf ipstart {
            mandatory true;
            tailf:cli-drop-node-name;
            type inet:ipv4-address;
          }
          leaf ipend {
            mandatory true;
            tailf:cli-drop-node-name;
            type inet:ipv4-address;
          }
          leaf netmask {
            mandatory true;
            type union {
              type ipv4-mask;
              type string;
            }
          }
          leaf gateway {
            tailf:cli-optional-in-sequence;
            type inet:ipv4-address;
          }
          leaf ha-group-id {
            tailf:cli-optional-in-sequence;
            type uint16;
          }
          leaf ha-use-all-ports {
            tailf:cli-optional-in-sequence;
            type empty;
          }
          leaf vrid {
            tailf:cli-optional-in-sequence;
            type uint16;
          }
          leaf ip-rr {
            tailf:cli-break-sequence-commands;
            type empty;
          }
          leaf lsn {
            type empty;
          }
          leaf max-users-per-ip {
            type uint16;
          }
        }
        list pool-group {
          key "name";
          leaf name {
            type string;
          }
          leaf ha-group-id {
            tailf:cli-hide-in-submode;
            type uint16;
          }
          list member {
            key "member-id";
            tailf:cli-suppress-mode;
            leaf member-id {
              type string;
            }
          }
        }
        container range-list;
        leaf reset-idle-tcp-conn {
          type empty;
        }
        container template {
          list logging {
            key "name";
            leaf name {
              type string;
            }
          }
        }
        container translation {
          leaf icmp-timeout {
            type union {
              type uint16;
              type enumeration {
                enum "fast";
              }
            }
          }
          leaf tcp-timeout {
            type uint16;
          }
          leaf udp-timeout {
            type uint16;
          }
          leaf syn-timeout {
            type uint16;
          }
          list service-timeout {
            tailf:cli-compact-syntax;
            tailf:cli-sequence-commands;
            tailf:cli-suppress-mode;
            key "protocol from";
            leaf protocol {
              type enumeration {
                enum "tcp";
                enum "udp";
              }
            }
            leaf from {
              type uint16;
            }
            leaf to {
              tailf:cli-optional-in-sequence;
              type uint16;
            }
            leaf timeout {
              tailf:cli-drop-node-name;
              type union {
                type uint16;
                type enumeration {
                  enum "fast";
                }
              }
            }
          }
        }
        container lsn {
          container endpoint-independent-mapping {
            container tcp {
              container enable {
                leaf ephemeral {
                  type empty;
                }
                leaf well-known {
                  type empty;
                }
              }
            }
            container udp {
              container enable {
                leaf ephemeral {
                  type empty;
                }
                leaf well-known {
                  type empty;
                }
              }
            }
          }
          container endpoint-independent-filtering {
            container tcp {
              container enable {
                leaf ephemeral {
                  type empty;
                  must '../../../../endpoint-independent-mapping/tcp/enable/ephemeral' {
                    tailf:xpath-root 3;
                    error-message "Endpoint-independent-filtering cannot be enabled when endpoint-independent-mapping is disabled";
                  }
                }
                leaf well-known {
                  type empty;
                  must '../../../../endpoint-independent-mapping/tcp/enable/well-known' {
                    tailf:xpath-root 3;
                    error-message "Endpoint-independent-filtering cannot be enabled when endpoint-independent-mapping is disabled";
                  }
                }
              }
            }
            container udp {
              container enable {
                leaf ephemeral {
                  type empty;
                  must '../../../../endpoint-independent-mapping/udp/enable/ephemeral' {
                    tailf:xpath-root 3;
                    error-message "Endpoint-independent-filtering cannot be enabled when endpoint-independent-mapping is disabled";
                  }
                }
                leaf well-known {
                  type empty;
                  must '../../../../endpoint-independent-mapping/udp/enable/well-known' {
                    tailf:xpath-root 3;
                    error-message "Endpoint-independent-filtering cannot be enabled when endpoint-independent-mapping is disabled";
                  }
                }
              }
            }
          }
          leaf ip-selection {
            type enumeration {
              enum "random";
              enum "round-robin";
              enum "least-used-strict";
              enum "least-udp-used-strict";
              enum "least-tcp-used-strict";
              enum "least-reserved-strict";
              enum "least-udp-reserved-strict";
              enum "least-tcp-reserved-strict";
              enum "least-users-strict";
            }
          }
          leaf attempt-port-preservation {
            type enumeration {
              enum "disable";
              enum "enable";
            }
          }
          uses algs;
        }
      }
      uses ip-prefix-list-grouping;
      uses ip-route-grouping;
      container tcp {
        container syn-cookie {
          leaf threshold {
            type uint8;
          }
        }
      }
    }
  }

  grouping resource-usage-grouping {
    leaf class-list-ipv6-addr-count {
      type uint32;
    }
    leaf client-ssl-template-count {
      type uint32;
    }
    leaf conn-reuse-template-count {
      type uint32;
    }
    leaf fast-tcp-template-count {
      type uint32;
    }
    leaf fast-udp-template-count {
      type uint32;
    }
    leaf http-template-count {
      type uint32;
    }
    leaf l4-session-count {
      type uint32;
    }
    leaf nat-pool-addr-count {
      type uint32;
    }
    leaf persist-cookie-template-count {
      type uint32;
    }
    leaf persist-srcip-template-count {
      type uint32;
    }
    leaf proxy-template-count {
      type uint32;
    }
    leaf real-port-count {
      type uint32;
    }
    leaf real-server-count {
      type uint32;
    }
    leaf server-ssl-template-count {
      type uint32;
    }
    leaf service-group-count {
      type uint32;
    }
    leaf stream-template-count {
      type uint32;
    }
    leaf virtual-port-count {
      type uint32;
    }
    leaf virtual-server-count {
      type uint32;
    }
  }

  grouping snmp-remote-grouping {
    list remote {
      tailf:cli-suppress-mode;
      tailf:cli-delete-when-empty;
      tailf:cli-compact-syntax;
      key "host";
      leaf host {
        type string;
      }
      leaf mask {
        tailf:cli-drop-node-name;
        type string;
      }
    }
  }

  grouping health-grouping {
    container health {
      list monitor {
        key "name";
        leaf name {
          type string;
        }
        container interval {
          tailf:cli-compact-syntax;
          tailf:cli-sequence-commands {
            tailf:cli-reset-all-siblings;
          }
          leaf interval {
            tailf:cli-drop-node-name;
            type uint8;
          }
          leaf timeout {
            type uint8;
          }
        }
        leaf interval-alt {
          tailf:cli-hide-in-submode;
          tailf:alt-name "interval";
          type uint8;
        }
        leaf timeout-alt {
          tailf:cli-hide-in-submode;
          tailf:alt-name "timeout";
          type uint8;
        }
        leaf retry {
          type uint8;
        }
        leaf retry-alt {
          tailf:cli-hide-in-submode;
          tailf:alt-name "retry";
          type uint8;
        }
        leaf up-retry {
          type uint8;
        }
        leaf up-retry-alt {
          tailf:cli-hide-in-submode;
          tailf:alt-name "up-retry";
          type uint8;
        }
        leaf strictly-retry-on-server-error-response {
          type empty;
        }
        leaf disable-after-down {
          type empty;
        }
        leaf override-port {
          type uint16;
        }
        leaf override-ipv4 {
          type inet:ipv4-address;
        }
        leaf override-ipv6 {
          type inet:ipv6-address;
        }
        container method {
          tailf:cli-compact-syntax;
          choice method-choice {
            container icmp {
              leaf transparent {
                type union {
                  type inet:ipv4-address;
                  type inet:ipv6-address;
                }
              }
            }
            container http {
              tailf:cli-compact-syntax;
              presence "true";
              leaf port {
                type uint16;
              }
              // NCS expand uses statement
              leaf username {
                type string;
              }
              leaf password {
                tailf:cli-optional-in-sequence;
                type string;
              }
              leaf url {
                type empty;
              }
              leaf method {
                tailf:cli-drop-node-name;
                type enumeration {
                  enum "GET";
                  enum "POST";
                  enum "HEAD";
                }
              }
              leaf path {
                tailf:cli-drop-node-name;
                type string;
              }
              leaf postdata {
                type string;
              }
              leaf postfile {
                type string;
              }
              container expect {
                tailf:cli-flatten-container;
                choice expect-choice {
                  leaf response-code {
                    type string;
                  }
                  leaf text {
                    tailf:cli-drop-node-name;
                    type string;
                  }
                }
              }
              leaf maintenance-code {
                type string;
              }
              leaf host {
                type string;
              }
            }
            container https {
              tailf:cli-compact-syntax;
              presence "true";
              leaf port {
                type uint16;
              }
              leaf disable-sslv2hello {
                type empty;
              }
              uses password-grouping;
              leaf url {
                type empty;
              }
              leaf method {
                tailf:cli-drop-node-name;
                type enumeration {
                  enum "GET";
                  enum "POST";
                  enum "HEAD";
                }
              }
              leaf path {
                tailf:cli-drop-node-name;
                type string;
              }
              container expect {
                tailf:cli-flatten-container;
                choice expect-choice {
                  leaf response-code {
                    type string;
                  }
                  leaf text {
                    tailf:cli-drop-node-name;
                    type string;
                  }
                }
              }
              leaf maintenance-code {
                type string;
              }
              leaf host {
                type string;
              }
              container cert {
                tailf:cli-compact-syntax;
                tailf:cli-flatten-container;
                leaf cert {
                  tailf:cli-drop-node-name;
                  type string;
                }
                leaf key {
                  type string;
                }
              }
            }
            container tcp {
              tailf:cli-compact-syntax;
              tailf:cli-sequence-commands;
              leaf port {
                type uint16;
              }
              leaf method {
                tailf:cli-drop-node-name;
                type enumeration {
                  enum "send";
                  enum "halfopen";
                }
              }
              leaf sendcontent {
                tailf:cli-drop-node-name;
                type string;
              }
              leaf response {
                type empty;
              }
              leaf contains {
                type string;
              }
            }
            container udp {
              leaf port {
                type uint16;
              }
            }
            container ftp {
              presence "present";
              tailf:cli-compact-syntax;
              leaf port {
                type uint16;
              }
              uses password-grouping;
            }
            container snmp {
              tailf:cli-compact-syntax;
              presence "present";
              leaf community {
                type string;
              }
              leaf oid {
                type union {
                  type enumeration {
                    enum "sysDescr";
                    enum "sysUpTime";
                    enum "sysName";
                  }
                  type string;
                }
              }
              leaf operation {
                type enumeration {
                  enum "get";
                  enum "getnext";
                }
              }
              leaf port {
                type uint16;
              }
            }
            container smtp {
              tailf:cli-compact-syntax;
              leaf domain {
                type string;
              }
              leaf port {
                type uint16;
              }
            }
            container dns {
              tailf:cli-compact-syntax;
              tailf:cli-sequence-commands;
              choice dns-health-choice {
                leaf domain {
                  type string;
                }
                leaf ipaddress {
                  type inet:ip-address;
                }
              }
              leaf port {
                tailf:cli-optional-in-sequence;
                type uint16;
              }
              leaf expect {
                tailf:cli-optional-in-sequence;
                type empty;
              }
              leaf response-code {
                type string;
              }
              leaf recurse {
                tailf:cli-optional-in-sequence;
                type enumeration {
                  enum "enabled";
                  enum "disabled";
                }
              }
              leaf tcp {
                tailf:cli-optional-in-sequence;
                type empty;
              }
              leaf type {
                type enumeration {
                  enum "A";
                  enum "CNAME";
                  enum "SOA";
                  enum "PTR";
                  enum "MX";
                  enum "TXT";
                  enum "AAAA";
                }
              }
            }
            container pop3 {
              tailf:cli-compact-syntax;
              uses password-grouping;
              leaf port {
                type uint16;
              }
            }
            container imap {
              tailf:cli-compact-syntax;
              leaf port {
                type uint16;
              }
              uses password-grouping;
              leaf-list auth {
                tailf:cli-flat-list-syntax;
                type enumeration {
                  enum "plain";
                  enum "cram-md5";
                  enum "login";
                }
              }
            }
            container sip {
              tailf:cli-compact-syntax;
              leaf port {
                type uint16;
              }
              leaf register {
                type empty;
              }
              leaf tcp {
                type empty;
              }
              leaf expect-response-code {
                type string;
              }
            }
            container radius {
              tailf:cli-compact-syntax;
              uses password-grouping;
              leaf secret {
                mandatory true;
                type string;
              }
              leaf port {
                type uint16;
              }
            }
            container tacplus {
              tailf:cli-compact-syntax;
              uses password-grouping;
              leaf secret {
                type string;
              }
              leaf port {
                type uint16;
              }
            }
            container ldap {
              tailf:cli-compact-syntax;
              leaf port {
                type uint16;
              }
              leaf overssl {
                type empty;
              }
              leaf binddn {
                type string;
              }
              leaf password {
                mandatory true;
                type string;
              }
            }
            container rtsp {
              tailf:cli-compact-syntax;
              leaf port {
                type uint16;
              }
              leaf rtspurl {
                type string;
              }
            }
            container database {
              tailf:cli-compact-syntax;
              tailf:cli-sequence-commands {
                tailf:cli-reset-siblings;
              }
              leaf dbtype {
                tailf:cli-drop-node-name;
                type enumeration {
                  enum "mssql";
                  enum "mysql";
                  enum "oracle";
                  enum "postgresql";
                }
              }
              leaf db-name {
                type string;
              }
              uses password-grouping;
              leaf send {
                type string;
              }
              leaf receive {
                type string;
              }
              leaf row {
                type uint8;
              }
              leaf column {
                type uint8;
              }
            }
            container external {
              leaf program {
                type string;
              }
            }
            container ntp;
            container compound {
              leaf name {
                tailf:cli-drop-node-name;
                tailf:cli-multi-value;
                type string;
              }
            }
          }
        }
      }
    }
  }

  grouping accounting-grouping {
    container accounting {
      container commands {
        tailf:cli-compact-syntax;
        tailf:cli-sequence-commands {
          tailf:cli-reset-all-siblings;
        }
        leaf level {
          tailf:cli-drop-node-name;
          type uint32;
        }
        leaf stop-only {
          type empty;
        }
        leaf tacplus {
          type empty;
        }
      }
      leaf debug {
        type uint8;
      }
      container exec {
        tailf:cli-compact-syntax;
        tailf:cli-sequence-commands {
          tailf:cli-reset-all-siblings;
        }
        choice st-st {
          leaf start-stop {
            type empty;
          }
          leaf stop-only {
            type empty;
          }
        }
        choice service {
          leaf tacplus {
            type empty;
          }
          leaf radius {
            type empty;
          }
        }
      }
    }
  }

  grouping acos-events-grouping {
    container acos-events {
      container logdb {
        leaf enable-all {
          type empty;
        }
        leaf enable-cgn {
          type empty;
        }
        leaf enable-http-forward-proxy {
          type empty;
        }
        leaf enable-smtp {
          type empty;
        }
      }
    }
  }

  grouping authorization-grouping {
    container authorization {
      container commands {
        tailf:cli-compact-syntax;
        tailf:cli-sequence-commands {
          tailf:cli-reset-all-siblings;
        }
        leaf level {
          tailf:cli-drop-node-name;
          type uint32;
        }
        leaf-list method {
          tailf:cli-flat-list-syntax;
          type enumeration {
            enum "tacplus";
            enum "none";
          }
        }
      }
    }
  }

  grouping bgp-grouping {
    container bgp {
      leaf extended-asn-cap {
        type empty;
      }
    }
  }

  grouping lacp-grouping {
    container lacp {
      tailf:cli-compact-syntax;
      leaf system-priority {
        type uint32;
      }
    }
  }

  grouping slb-grouping {
    container slb {
      container graceful-shutdown {
        tailf:cli-sequence-commands {
          tailf:cli-reset-siblings;
        }
        tailf:cli-compact-syntax;
        leaf timeout {
          tailf:cli-drop-node-name;
          type uint16;
        }
        leaf when {
          must '../timeout' {
            tailf:xpath-root 3;
          }
          tailf:cli-drop-node-name;
          type enumeration {
            enum "after-disable";
            enum "server";
            enum "virtual-server";
          }
        }
      }
      leaf disable-server-auto-reselect {
        type empty;
      }
      container buff-thresh {
        tailf:cli-sequence-commands {
          tailf:cli-reset-siblings;
        }
        tailf:cli-compact-syntax;
        leaf hw-buff {
          type uint32;
        }
        leaf relieve-thresh {
          type uint32;
        }
        leaf sys-buff-low {
          type uint32;
        }
        leaf sys-buff-high {
          type uint32;
        }
      }
      container template {
        list server {
          key "name";
          leaf name {
            type string;
          }
          leaf health-check {
            type boolean;
          }
          container conn-limit {
            tailf:cli-sequence-commands {
              tailf:cli-reset-siblings;
            }
            tailf:cli-compact-syntax;
            leaf limit {
              tailf:cli-drop-node-name;
              type uint32;
            }
            leaf resume {
              must '../limit' {
                tailf:xpath-root 3;
              }
              tailf:cli-optional-in-sequence;
              type uint32;
            }
            leaf no-logging {
              type empty;
            }
          }
          container conn-rate-limit {
            tailf:cli-sequence-commands {
              tailf:cli-reset-siblings;
            }
            tailf:cli-compact-syntax;
            leaf limit {
              tailf:cli-drop-node-name;
              type uint32;
            }
            leaf per {
              must '../limit' {
                tailf:xpath-root 3;
              }
              tailf:cli-optional-in-sequence;
              type enumeration {
                enum "100ms";
                enum "second";
              }
            }
            leaf no-logging {
              type empty;
            }
          }
          leaf dns-query-interval {
            type uint16;
          }
          leaf dynamic-server-prefix {
            type string;
          }
          leaf max-dynamic-server {
            type uint16;
          }
          leaf min-ttl-ratio {
            type uint16;
          }
          container slow-start {
            presence "present";
            tailf:cli-sequence-commands;
            tailf:cli-compact-syntax;
            leaf from {
              tailf:cli-optional-in-sequence;
              type uint16;
            }
            choice slow-start-choice {
              leaf add {
                tailf:cli-optional-in-sequence;
                type uint16;
              }
              leaf times {
                tailf:cli-optional-in-sequence;
                type uint8;
              }
            }
            leaf every {
              tailf:cli-optional-in-sequence;
              type uint8;
            }
            leaf till {
              type uint16;
            }
          }
        }
        list port {
          key "name";
          leaf name {
            type string;
          }
          container health-check {
            presence "true";
            choice mon-choice {
              leaf monitor {
                tailf:cli-drop-node-name;
                type string;
              }
              leaf ping {
                type empty;
              }
            }
          }
          container conn-limit {
            tailf:cli-sequence-commands {
              tailf:cli-reset-siblings;
            }
            tailf:cli-compact-syntax;
            leaf limit {
              tailf:cli-drop-node-name;
              type uint32;
            }
            leaf resume {
              must '../limit' {
                tailf:xpath-root 3;
              }
              tailf:cli-optional-in-sequence;
              type uint32;
            }
            leaf no-logging {
              type empty;
            }
          }
          container conn-rate-limit {
            tailf:cli-sequence-commands {
              tailf:cli-reset-siblings;
            }
            tailf:cli-compact-syntax;
            leaf limit {
              tailf:cli-drop-node-name;
              type uint32;
            }
            leaf per {
              must '../limit' {
                tailf:xpath-root 3;
              }
              tailf:cli-optional-in-sequence;
              type enumeration {
                enum "100ms";
                enum "second";
              }
            }
            leaf no-logging {
              type empty;
            }
          }
          leaf dest-nat {
            type empty;
          }
          leaf down-grace-period {
            type uint32;
          }
          leaf dscp {
            type uint8;
          }
          container dynamic-member-priority {
            tailf:cli-sequence-commands {
              tailf:cli-reset-siblings;
            }
            tailf:cli-compact-syntax;
            leaf priority {
              tailf:cli-drop-node-name;
              type uint8;
            }
            leaf decrement {
              must '../priority' {
                tailf:xpath-root 3;
              }
              type uint8;
            }
          }
          container inband-health-check {
            presence "true";
            tailf:cli-sequence-commands {
              tailf:cli-reset-siblings;
            }
            tailf:cli-compact-syntax;
            leaf retry {
              tailf:cli-optional-in-sequence;
              type uint8;
            }
            leaf reassign {
              type uint8;
            }
          }
          leaf no-ssl {
            type empty;
          }
          container slow-start {
            presence "present";
            tailf:cli-sequence-commands;
            tailf:cli-compact-syntax;
            leaf from {
              tailf:cli-optional-in-sequence;
              type uint16;
            }
            choice slow-start-choice {
              leaf add {
                tailf:cli-optional-in-sequence;
                type uint16;
              }
              leaf times {
                tailf:cli-optional-in-sequence;
                type uint8;
              }
            }
            leaf every {
              tailf:cli-optional-in-sequence;
              type uint8;
            }
            leaf till {
              type uint16;
            }
          }
          leaf source-nat {
            type string;
          }
          leaf weight {
            type uint8;
          }
        }
        container cache;
        list client-ssl {
          key "name";
          leaf name {
            type string;
          }
          container cert {
            tailf:cli-sequence-commands {
              tailf:cli-reset-siblings;
            }
            tailf:cli-compact-syntax;
            leaf cert {
              tailf:cli-drop-node-name;
              type string;
            }
            leaf partition {
              type string;
            }
          }
          container chain-cert {
            tailf:cli-sequence-commands {
              tailf:cli-reset-siblings;
            }
            tailf:cli-compact-syntax;
            leaf chain-cert {
              tailf:cli-drop-node-name;
              type string;
            }
            leaf partition {
              type string;
            }
          }
          list ca-cert {
            tailf:cli-suppress-mode;
            tailf:cli-compact-syntax;
            key "name";
            leaf name {
              type string;
            }
            leaf partition {
              type string;
            }
          }
          container key {
            tailf:cli-sequence-commands;
            tailf:cli-compact-syntax;
            leaf key-name {
              tailf:cli-drop-node-name;
              type string;
            }
            leaf partition {
              tailf:cli-optional-in-sequence;
              type string;
            }
            leaf pass-phrase {
              type empty;
            }
            leaf pass-phrase-value {
              tailf:cli-drop-node-name;
              type string;
            }
          }
          list cipher {
            tailf:cli-suppress-mode;
            key "name";
            leaf name {
              type cipher;
            }
          }
          container template {
            container cipher {
              leaf name {
                tailf:cli-drop-node-name;
                type string;
              }
            }
          }
          leaf close-notify {
            type empty;
          }
          leaf renegotiation-disable {
            type empty;
          }
          leaf session-cache-size {
            type uint16;
          }
          leaf session-cache-timeout {
            type uint32;
          }
          leaf session-ticket-lifetime {
            type uint32;
          }
          uses slb-template-version-grouping;
          leaf auth-username-attribute {
            type string;
          }
          container certificate {
            tailf:cli-compact-syntax;
            tailf:cli-sequence-commands {
              tailf:cli-reset-siblings;
            }
            leaf name {
              tailf:cli-drop-node-name;
              type string;
            }
            leaf key {
              type string;
            }
            leaf pass-phrase {
              tailf:cli-break-sequence-commands;
              type tailf:aes-cfb-128-encrypted-string;
            }
            leaf chain-cert {
              type string;
            }
          }
          leaf disable-sslv3 {
            type empty;
          }
        }
        list connection-reuse {
          key "name";
          leaf name {
            type string;
          }
          leaf timeout {
            type uint16;
          }
          leaf limit-per-server {
            type uint16;
          }
          container keep-alive-conn {
            tailf:cli-sequence-commands {
              tailf:cli-reset-siblings;
            }
            tailf:cli-compact-syntax;
            presence "present";
            leaf preopen {
              tailf:cli-optional-in-sequence;
              type empty;
            }
            leaf connections {
              tailf:cli-drop-node-name;
              tailf:cli-optional-in-sequence;
              type uint16;
            }
          }
        }
        container diameter;
        list dns {
          key "name";
          leaf name {
            type string;
          }
          leaf max-query-length {
            type uint32;
          }
          leaf max-cache-size {
            type uint32;
          }
          leaf max-cache-entry-size {
            type uint32;
          }
          container dns-log-enable {
            leaf period {
              type uint32;
            }
          }
          leaf query-id-switch {
            type empty;
          }
        }
        list dynamic-service {
          tailf:cli-compact-syntax;
          key "name";
          leaf name {
            type string;
          }
          container dns {
            tailf:cli-compact-syntax;
            list server {
              tailf:cli-suppress-mode;
              key "ip";
              leaf ip {
                type string;
              }
            }
          }
        }
        list http {
          key "name";
          leaf name {
            type string;
          }
          container insert-client-ip {
            tailf:cli-compact-syntax;
            presence "true";
            leaf header-name {
              tailf:cli-drop-node-name;
              type string;
            }
            leaf replace {
              type empty;
            }
          }
          container non-http-bypass {
            leaf service-group {
              type string;
            }
          }
          container url-hash-persist {
            tailf:cli-sequence-commands {
              tailf:cli-reset-siblings;
            }
            tailf:cli-compact-syntax;
            leaf offset {
              tailf:cli-optional-in-sequence;
              type uint8;
            }
            choice hash-choice {
              leaf first {
                type uint8;
              }
              leaf last {
                type uint8;
              }
            }
            leaf use-server-status {
              tailf:cli-optional-in-sequence;
              type empty;
            }
          }
          list host-switching {
            tailf:cli-suppress-mode;
            key "match-type identifier";
            leaf match-type {
              type enumeration {
                enum "contains";
                enum "ends-with";
                enum "equals";
                enum "starts-with";
              }
            }
            leaf identifier {
              type string;
            }
            leaf service-group {
              mandatory true;
              type string;
            }
          }
          list url-switching {
            tailf:cli-suppress-mode;
            key "match-type identifier";
            leaf match-type {
              type enumeration {
                enum "contains";
                enum "ends-with";
                enum "equals";
                enum "starts-with";
              }
            }
            leaf identifier {
              type string;
            }
            leaf service-group {
              mandatory true;
              type string;
            }
          }
          leaf request-line-case-insensitive {
            type empty;
          }
          container redirect-rewrite {
            leaf secure {
              type empty;
            }
          }
          list request-header-insert {
            tailf:cli-suppress-mode;
            key "header";
            leaf header {
              type string;
            }
            leaf insert-mode {
              tailf:cli-drop-node-name;
              type enumeration {
                enum "insert-if-not-exist";
                enum "insert-always";
              }
            }
          }
          list response-header-insert {
            tailf:cli-suppress-mode;
            key "header";
            leaf header {
              type string;
            }
            leaf insert-mode {
              tailf:cli-drop-node-name;
              type enumeration {
                enum "insert-if-not-exist";
                enum "insert-always";
              }
            }
          }
          leaf keep-client-alive {
            type empty;
          }
        }
        container persist {
          list source-ip {
            key "name";
            leaf name {
              type string;
            }
            leaf dont-honor-conn-rules {
              type empty;
            }
            leaf enforce-higher-priority {
              type empty;
            }
            leaf incl-sport {
              type empty;
            }
            container match-type {
              tailf:cli-sequence-commands {
                tailf:cli-reset-siblings;
              }
              tailf:cli-compact-syntax;
              choice match-choice {
                leaf server {
                  type empty;
                }
                leaf service-group {
                  type empty;
                }
              }
              leaf scan-all-members {
                type empty;
              }
            }
            leaf netmask {
              type union {
                type ipv4-mask;
                type string;
              }
            }
            leaf netmask6 {
              type uint8;
            }
            leaf timeout {
              type uint16;
            }
          }
          list cookie {
            key "id";
            leaf id {
              type string;
            }
            leaf name {
              type string;
            }
            leaf expire {
              type uint32;
            }
            container match-type {
              tailf:cli-sequence-commands {
                tailf:cli-reset-siblings;
              }
              tailf:cli-compact-syntax;
              leaf server {
                tailf:cli-optional-in-sequence;
                type empty;
              }
              leaf service-group {
                tailf:cli-optional-in-sequence;
                type empty;
              }
              leaf scan-all-members {
                tailf:cli-optional-in-sequence;
                type empty;
              }
            }
            leaf insert-always {
              type empty;
            }
            leaf pass-thru {
              type empty;
            }
          }
          list destination-ip {
            key "name";
            leaf name {
              type string;
            }
          }
          list ssl-sid {
            key "name";
            leaf name {
              type string;
            }
            leaf timeout {
              type uint16;
            }
          }
        }
        list policy {
          key "name";
          leaf name {
            type string;
          }
          leaf proxy-keep-alive {
            type empty;
          }

          grouping stp-class-list-grouping {
            list lid {
              tailf:cli-compact-syntax;
              tailf:cli-delete-when-empty;
              key "limit-id";
              leaf limit-id {
                type uint32;
              }
              leaf class-list-group {
                type string;
              }
              container action {
                tailf:cli-compact-syntax;
                tailf:cli-sequence-commands {
                  tailf:cli-reset-siblings;
                }
                choice action-choice {
                  leaf drop {
                    type empty;
                  }
                  leaf forward-to-internet {
                    type string;
                  }
                  leaf forward-to-service-group {
                    type string;
                  }
                }
                leaf log {
                  type empty;
                }
              }
              leaf conn-limit {
                type uint32;
              }
              container conn-rate-limit {
                tailf:cli-sequence-commands {
                  tailf:cli-reset-siblings;
                }
                tailf:cli-compact-syntax;
                leaf limit {
                  tailf:cli-drop-node-name;
                  type uint32;
                }
                leaf per {
                  must '../limit' {
                    tailf:xpath-root 3;
                  }
                  type uint16;
                }
              }
              leaf request-limit {
                type uint32;
              }
              container request-rate-limit {
                tailf:cli-sequence-commands {
                  tailf:cli-reset-all-siblings;
                }
                tailf:cli-compact-syntax;
                leaf limit {
                  tailf:cli-drop-node-name;
                  type uint32;
                }
                leaf per {
                  must '../limit' {
                    tailf:xpath-root 3;
                  }
                  type uint16;
                }
              }
              container over-limit-action {
                tailf:cli-compact-syntax;
                tailf:cli-sequence-commands {
                  tailf:cli-reset-siblings;
                }
                leaf over-limit-action-choice {
                  tailf:cli-drop-node-name;
                  type enumeration {
                    enum "dns-cache-disable";
                    enum "dns-cache-enable";
                    enum "forward";
                    enum "reset";
                    enum "lockout";
                    enum "log";
                  }
                }
                leaf lockout {
                  tailf:cli-optional-in-sequence;
                  type uint16;
                }
                leaf lockout-val {
                  tailf:cli-optional-in-sequence;
                  tailf:cli-drop-node-name;
                  type uint16;
                }
                leaf log {
                  tailf:cli-optional-in-sequence;
                  type empty;
                }
                leaf log-val {
                  tailf:cli-drop-node-name;
                  tailf:cli-optional-in-sequence;
                  type uint16;
                }
              }
            }
            container client-ip {
              tailf:cli-compact-syntax;
              choice client-ip-choice {
                leaf l3-dest {
                  type empty;
                }
                leaf l7-header {
                  type empty;
                }
              }
              leaf l7-header-string {
                tailf:cli-drop-node-name;
                type string;
              }
            }
          }
          container class-list {
            leaf name {
              type string;
            }
            uses stp-class-list-grouping;
          }
          container class-list-alt {
            tailf:alt-name "class-list";
            tailf:cli-add-mode;
            leaf name {
              tailf:cli-drop-node-name;
              tailf:cli-hide-in-submode;
              type string;
            }
            uses stp-class-list-grouping;
          }
          leaf class-list-group {
            type string;
          }
          container bw-list {
            tailf:cli-compact-syntax;
            leaf name {
              type string;
            }
            list id {
              tailf:cli-compact-syntax;
              tailf:cli-suppress-mode;
              key "id";
              leaf id {
                type uint32;
              }
              leaf service-group {
                type string;
              }
            }
          }
        }
        list server-ssl {
          key "name";
          leaf name {
            type string;
          }
          leaf cert {
            type string;
          }
          leaf ca-cert {
            type string;
          }
          list cipher {
            tailf:cli-suppress-mode;
            key "name";
            leaf name {
              type cipher;
            }
          }
          container server-certificate-error {
            tailf:cli-compact-syntax;
            leaf trap {
              type empty;
            }
            leaf email {
              type empty;
            }
            leaf logging {
              type empty;
            }
            leaf ignore {
              type empty;
            }
          }
          leaf close-notify {
            type empty;
          }
          container key {
            tailf:cli-sequence-commands;
            tailf:cli-compact-syntax;
            leaf key-name {
              tailf:cli-drop-node-name;
              type string;
            }
            leaf partition {
              tailf:cli-optional-in-sequence;
              type string;
            }
            leaf pass-phrase {
              type empty;
            }
            leaf pass-phrase-value {
              tailf:cli-drop-node-name;
              type string;
            }
          }
          container template {
            container cipher {
              leaf name {
                tailf:cli-drop-node-name;
                type string;
              }
            }
          }
          uses slb-template-version-grouping;
        }
        list sip {
          key "name";
          leaf name {
            type string;
          }
          leaf timeout {
            type uint32;
          }
          leaf call-id-persist-disable {
            type empty;
          }
          leaf insert-client-ip {
            type empty;
          }
        }
        container smtp;
        container streaming-media;
        list tcp {
          key "name";
          leaf name {
            type string;
          }
          leaf idle-timeout {
            type uint32;
          }
          container force-delete-timeout {
            tailf:cli-sequence-commands {
              tailf:cli-reset-siblings;
            }
            tailf:cli-compact-syntax;
            leaf timeout {
              tailf:cli-drop-node-name;
              type uint8;
            }
            leaf alive-if-active {
              must '../timeout' {
                tailf:xpath-root 3;
              }
              type empty;
            }
          }
          leaf half-close-idle-timeout {
            type uint16;
          }
          leaf initial-window-size {
            type uint16;
          }
          leaf lan-fast-ack {
            type empty;
          }
          leaf reset-fwd {
            type empty;
          }
          leaf reset-rev {
            type empty;
          }
        }
        list tcp-proxy {
          key "name";
          leaf name {
            type string;
          }
          leaf idle-timeout {
            type uint32;
          }
          leaf syn-retries {
            type uint8;
          }
          leaf retransmit-retries {
            type uint8;
          }
          leaf half-close-idle-timeout {
            type uint8;
          }
          leaf backend-wscale {
            type uint8;
          }
          leaf reset-fwd {
            type empty;
          }
          leaf reset-rev {
            type empty;
          }
          leaf receive-buffer {
            type uint32;
          }
          leaf transmit-buffer {
            type uint32;
          }
          leaf nagle {
            type empty;
          }
          leaf timewait {
            type uint32;
          }
          leaf reno {
            type empty;
          }
        }
        list udp {
          key "name";
          leaf name {
            type string;
          }
          leaf idle-timeout {
            type uint32;
          }
          container aging {
            choice aging-choice {
              leaf immediate {
                type empty;
              }
              container short {
                presence "present";
                leaf short-value {
                  tailf:cli-drop-node-name;
                  type uint8;
                }
              }
            }
          }
          leaf re-select-if-server-down {
            type empty;
          }
        }
        list virtual-port {
          key "name";
          leaf name {
            type string;
          }
          leaf reset-unknown-conn {
            type empty;
          }
          leaf ignore-tcp-msl {
            type empty;
          }
          leaf allow-syn-otherflags {
            type empty;
          }
          leaf snat-port-preserve {
            type empty;
          }
        }
        list external-service {
          key "name";
          leaf name {
            type string;
          }
          container timeout {
            tailf:cli-compact-syntax;
            leaf time {
              tailf:cli-drop-node-name;
              type uint8;
            }
            leaf action {
              type enumeration {
                enum "continue";
                enum "drop";
                enum "reset";
              }
            }
          }
          leaf service-group {
            type string;
          }
          container template {
            leaf tcp-proxy {
              type string;
            }
          }
        }
        list virtual-server {
          key "name";
          leaf name {
            type string;
          }
          container conn-limit {
            tailf:cli-sequence-commands {
              tailf:cli-reset-siblings;
            }
            tailf:cli-compact-syntax;
            leaf limit {
              tailf:cli-drop-node-name;
              type uint32;
            }
            leaf reset {
              must '../limit' {
                tailf:xpath-root 3;
              }
              tailf:cli-optional-in-sequence;
              type empty;
            }
            leaf no-logging {
              type empty;
            }
          }
          container conn-rate-limit {
            tailf:cli-sequence-commands {
              tailf:cli-reset-siblings;
            }
            tailf:cli-compact-syntax;
            leaf limit {
              tailf:cli-drop-node-name;
              type uint32;
            }
            leaf per {
              must '../limit' {
                tailf:xpath-root 3;
              }
              tailf:cli-optional-in-sequence;
              type enumeration {
                enum "100ms";
                enum "second";
              }
            }
            leaf reset {
              must '../limit' {
                tailf:xpath-root 3;
              }
              tailf:cli-optional-in-sequence;
              type empty;
            }
            leaf no-logging {
              type empty;
            }
          }
          container icmp-rate-limit {
            tailf:cli-sequence-commands {
              tailf:cli-reset-siblings;
            }
            tailf:cli-compact-syntax;
            leaf rate {
              tailf:cli-drop-node-name;
              type uint16;
            }
            leaf lockup {
              must '../rate' {
                tailf:xpath-root 3;
              }
              type uint16;
            }
            leaf lockup-period {
              tailf:cli-drop-node-name;
              must '../lockup' {
                tailf:xpath-root 3;
              }
              type uint16;
            }
          }
          leaf subnet-gratuitous-arp {
            type empty;
          }
        }
        list cipher {
          key "name";
          leaf name {
            type string;
          }

          grouping cipher-prio-grouping {
            leaf priority {
              type uint8;
            }
          }
          container SSL3_RSA_DES_192_CBC3_SHA {
            presence "present";
            uses cipher-prio-grouping;
          }
          container SSL3_RSA_DES_40_CBC_SHA {
            presence "present";
            uses cipher-prio-grouping;
          }
          container SSL3_RSA_DES_64_CBC_SHA {
            presence "present";
            uses cipher-prio-grouping;
          }
          container SSL3_RSA_RC4_128_MD5 {
            presence "present";
            uses cipher-prio-grouping;
          }
          container SSL3_RSA_RC4_128_SHA {
            presence "present";
            uses cipher-prio-grouping;
          }
          container SSL3_RSA_RC4_40_MD5 {
            presence "present";
            uses cipher-prio-grouping;
          }
          container TLS1_RSA_AES_128_SHA {
            presence "present";
            uses cipher-prio-grouping;
          }
          container TLS1_RSA_AES_256_SHA {
            presence "present";
            uses cipher-prio-grouping;
          }
          container TLS1_RSA_EXPORT1024_RC4_56_MD5 {
            presence "present";
            uses cipher-prio-grouping;
          }
          container TLS1_RSA_EXPORT1024_RC4_56_SHA {
            presence "present";
            uses cipher-prio-grouping;
          }
          container TLS1_RSA_AES_128_SHA256 {
            presence "present";
            uses cipher-prio-grouping;
          }
          container TLS1_RSA_AES_256_SHA256 {
            presence "present";
            uses cipher-prio-grouping;
          }
          container TLS1_DHE_RSA_AES_128_GCM_SHA256 {
            presence "present";
            uses cipher-prio-grouping;
          }
          container TLS1_DHE_RSA_AES_128_SHA {
            presence "present";
            uses cipher-prio-grouping;
          }
          container TLS1_DHE_RSA_AES_128_SHA256 {
            presence "present";
            uses cipher-prio-grouping;
          }
          container TLS1_DHE_RSA_AES_256_GCM_SHA384 {
            presence "present";
            uses cipher-prio-grouping;
          }
          container TLS1_DHE_RSA_AES_256_SHA {
            presence "present";
            uses cipher-prio-grouping;
          }
          container TLS1_DHE_RSA_AES_256_SHA256 {
            presence "present";
            uses cipher-prio-grouping;
          }
          container TLS1_ECDHE_ECDSA_AES_128_GCM_SHA256 {
            presence "present";
            uses cipher-prio-grouping;
          }
          container TLS1_ECDHE_ECDSA_AES_128_SHA {
            presence "present";
            uses cipher-prio-grouping;
          }
          container TLS1_ECDHE_ECDSA_AES_128_SHA256 {
            presence "present";
            uses cipher-prio-grouping;
          }
          container TLS1_ECDHE_ECDSA_AES_256_GCM_SHA384 {
            presence "present";
            uses cipher-prio-grouping;
          }
          container TLS1_ECDHE_ECDSA_AES_256_SHA {
            presence "present";
            uses cipher-prio-grouping;
          }
          container TLS1_ECDHE_RSA_AES_128_GCM_SHA256 {
            presence "present";
            uses cipher-prio-grouping;
          }
          container TLS1_ECDHE_RSA_AES_128_SHA {
            presence "present";
            uses cipher-prio-grouping;
          }
          container TLS1_ECDHE_RSA_AES_128_SHA256 {
            presence "present";
            uses cipher-prio-grouping;
          }
          container TLS1_ECDHE_RSA_AES_256_GCM_SHA384 {
            presence "present";
            uses cipher-prio-grouping;
          }
          container TLS1_ECDHE_RSA_AES_256_SHA {
            presence "present";
            uses cipher-prio-grouping;
          }
          container TLS1_RSA_AES_128_GCM_SHA256 {
            presence "present";
            uses cipher-prio-grouping;
          }
          container TLS1_RSA_AES_256_GCM_SHA384 {
            presence "present";
            uses cipher-prio-grouping;
          }
        }
      }
      list server {
        key "name";
        unique "address";
        leaf name {
          type string;
        }
        leaf address {
          tailf:cli-drop-node-name;
          tailf:cli-hide-in-submode;
          mandatory true;
          type union {
            type inet:ipv4-address;
            type inet:ipv6-address;
            type string;
          }
        }
        leaf disable {
          type empty;
        }
        choice hc-choice {
          leaf health-check {
            type boolean;
          }
          container health-check-conf {
            tailf:cli-drop-node-name;
            container health-check {
              choice monitor-choice {
                leaf ping {
                  type empty;
                }
                leaf host {
                  tailf:cli-drop-node-name;
                  type string;
                }
              }
            }
          }
          leaf health-check-disable {
            type empty;
          }
        }
        container conn-limit {
          tailf:cli-sequence-commands {
            tailf:cli-reset-siblings;
          }
          tailf:cli-compact-syntax;
          leaf limit {
            tailf:cli-drop-node-name;
            type uint32;
          }
          leaf resume {
            must '../limit' {
              tailf:xpath-root 3;
            }
            tailf:cli-optional-in-sequence;
            type uint32;
          }
          leaf no-logging {
            type empty;
          }
        }
        leaf conn-resume {
          type uint32;
        }
        leaf extended-stats {
          type empty;
        }
        leaf external-ip {
          type inet:ipv4-address;
        }
        container ha-priority-cost {
          tailf:cli-sequence-commands {
            tailf:cli-reset-siblings;
          }
          tailf:cli-compact-syntax;
          leaf cost {
            tailf:cli-drop-node-name;
            type uint8;
          }
          leaf ha-group {
            type union {
              type enumeration {
                enum "all";
              }
              type uint8;
            }
          }
        }
        leaf ipv6 {
          type inet:ipv6-address;
        }
        leaf slow-start {
          type empty;
        }
        leaf spoofing-cache {
          type empty;
        }
        leaf stats-data-disable {
          type empty;
        }
        leaf weight {
          type uint8;
        }
        list port {
          key "number tcpudp";
          leaf number {
            type uint16;
          }
          leaf tcpudp {
            type enumeration {
              enum "tcp";
              enum "udp";
            }
          }
          container conn-limit {
            tailf:cli-sequence-commands {
              tailf:cli-reset-siblings;
            }
            tailf:cli-compact-syntax;
            leaf limit {
              tailf:cli-drop-node-name;
              type uint32;
            }
            leaf resume {
              must '../limit' {
                tailf:xpath-root 3;
              }
              tailf:cli-optional-in-sequence;
              type uint32;
            }
            leaf no-logging {
              type empty;
            }
          }
          leaf conn-resume {
            type uint32;
          }
          leaf extended-stats {
            type empty;
          }
          container ha-priority-cost {
            tailf:cli-sequence-commands {
              tailf:cli-reset-siblings;
            }
            tailf:cli-compact-syntax;
            leaf cost {
              tailf:cli-drop-node-name;
              type uint8;
            }
            leaf ha-group {
              must '../cost' {
                tailf:xpath-root 3;
              }
              type union {
                type enumeration {
                  enum "all";
                }
                type uint8;
              }
            }
          }
          leaf health-check-disable {
            type empty;
          }
          container template {
            leaf port {
              type string;
            }
          }
          choice hc-choice {
            leaf health-check {
              type boolean;
            }
            container health-check-conf {
              tailf:cli-drop-node-name;
              container health-check {
                choice monitor-choice {
                  leaf ping {
                    type empty;
                  }
                  leaf host {
                    tailf:cli-drop-node-name;
                    type string;
                  }
                  container follow-port {
                    tailf:cli-compact-syntax;
                    tailf:cli-sequence-commands {
                      tailf:cli-reset-siblings;
                    }
                    leaf port {
                      tailf:cli-drop-node-name;
                      type uint16;
                    }
                    leaf tcpudp {
                      tailf:cli-drop-node-name;
                      type enumeration {
                        enum "tcp";
                        enum "udp";
                      }
                    }
                  }
                }
              }
            }
          }
          leaf no-ssl {
            type empty;
          }
          leaf stats-data-disable {
            type empty;
          }
          leaf state {
            tailf:cli-drop-node-name;
            type enumeration {
              enum "enable";
              enum "disable";
            }
          }
        }
        container template {
          leaf server {
            type string;
          }
        }
        leaf state {
          tailf:cli-drop-node-name;
          type enumeration {
            enum "enable";
            enum "disable";
          }
        }
      }
      list service-group {
        key "name tcpudp";
        unique "name";
        leaf name {
          type string;
        }
        leaf tcpudp {
          type enumeration {
            enum "tcp";
            enum "udp";
          }
        }
        leaf backup-server-event-log {
          type empty;
        }
        leaf extended-stats {
          type empty;
        }
        container health-check {
          tailf:cli-compact-syntax;
          tailf:cli-sequence-commands {
            tailf:cli-reset-siblings;
          }
          choice monitor-choice {
            leaf ping {
              type empty;
            }
            leaf host {
              tailf:cli-drop-node-name;
              type string;
            }
          }
          leaf partition {
            type string;
          }
        }
        list member1 {
          tailf:cli-compact-syntax;
          tailf:cli-suppress-mode;
          tailf:alt-name "member";
          key "host port";
          leaf host {
            type string;
          }
          leaf port {
            type uint16;
          }
          leaf partition {
            type string;
          }
          leaf state {
            tailf:cli-drop-node-name;
            type enumeration {
              enum "enable";
              enum "disable";
            }
          }
          leaf priority {
            type uint8;
          }
        }
        list member2 {
          tailf:alt-name "member";
          key "host port";
          leaf host {
            type string;
          }
          leaf port {
            type uint16;
          }
          leaf partition {
            type string;
          }
          leaf state {
            tailf:cli-drop-node-name;
            type enumeration {
              enum "enable";
              enum "disable";
            }
          }
          leaf priority {
            type uint8;
          }
          leaf template {
            type string;
          }
        }
        container method {
          choice method-choice {
            leaf fastest-response {
              type empty;
            }
            container least-connection {
              presence "true";
              leaf pseudo-round-robin {
                type empty;
              }
            }
            leaf least-request {
              type empty;
            }
            leaf round-robin {
              type empty;
            }
            leaf round-robin-strict {
              type empty;
            }
            container service-least-connection {
              presence "true";
              leaf pseudo-round-robin {
                type empty;
              }
            }
            container service-weighted-least-connection {
              presence "true";
              leaf pseudo-round-robin {
                type empty;
              }
            }
            leaf stateless-dst-ip-hash {
              type empty;
            }
            leaf stateless-per-pkt-round-robin {
              type empty;
            }
            leaf stateless-src-dst-ip-hash {
              type empty;
            }
            leaf stateless-src-ip-hash {
              type empty;
            }
            leaf stateless-src-ip-only-hash {
              type empty;
            }
            container weighted-least-connection {
              presence "true";
              leaf pseudo-round-robin {
                type empty;
              }
            }
            leaf weighted-rr {
              type empty;
            }
          }
        }
        container min-active-member {
          tailf:cli-sequence-commands {
            tailf:cli-reset-siblings;
          }
          tailf:cli-compact-syntax;
          leaf min {
            tailf:cli-drop-node-name;
            type uint8;
          }
          leaf method {
            must '../min' {
              tailf:xpath-root 3;
            }
            tailf:cli-drop-node-name;
            type enumeration {
              enum "dynamic-priority";
              enum "skip-pri-set";
            }
          }
        }
        list priority {
          tailf:cli-suppress-mode;
          tailf:cli-delete-when-empty;
          key "prio";
          leaf prio {
            type uint8;
          }
          leaf action {
            tailf:cli-drop-node-name;
            type enumeration {
              enum "drop";
              enum "drop-if-exceed-limit";
              enum "proceed";
              enum "reset";
              enum "reset-if-exceed-limit";
            }
          }
        }
        container priority-affinity {
          presence "true";
        }
        leaf reset-on-server-selection-fail {
          type empty;
        }
        leaf stats-data-disable {
          type empty;
        }
      }
      list virtual-server {
        key "name";
        leaf name {
          type string;
        }
        leaf address {
          tailf:cli-drop-node-name;
          tailf:cli-hide-in-submode;
          mandatory true;
          type union {
            type inet:ipv4-address;
            type inet:ipv6-address;
          }
        }
        leaf netmask {
          tailf:cli-drop-node-name;
          tailf:cli-hide-in-submode;
          type union {
            type ipv4-mask;
            type string;
          }
        }
        leaf acl {
          tailf:cli-hide-in-submode;
          type uint16;
        }
        leaf arp-disable {
          type empty;
        }
        leaf disable {
          type empty;
        }
        leaf extended-stats {
          type empty;
        }
        leaf ha-dynamic {
          type uint8;
        }
        choice disable-choice {
          leaf disable-when-any-port-down {
            type empty;
          }
          leaf disable-when-all-ports-down {
            type empty;
          }
        }
        leaf ha-group {
          type uint16;
        }
        leaf redistribution-flagged {
          type empty;
        }
        leaf stats-data-disable {
          type empty;
        }
        leaf vrid {
          type uint8;
        }
        list port {
          key "id type";
          leaf id {
            type uint16;
          }
          leaf type {
            must "(../id = 0 and ../type = 'others') or ../type != 'others' " {
              tailf:xpath-root 3;
            }
            type enumeration {
              enum "diameter";
              enum "dns-udp";
              enum "fast-http";
              enum "ftp";
              enum "http";
              enum "https";
              enum "mms";
              enum "others";
              enum "radius";
              enum "rtsp";
              enum "sip";
              enum "sip-tcp";
              enum "sips";
              enum "smtp";
              enum "ssl-proxy";
              enum "tcp";
              enum "tcp-proxy";
              enum "tftp";
              enum "udp";
            }
          }
          container access-list {
            tailf:cli-sequence-commands {
              tailf:cli-reset-siblings;
            }
            tailf:cli-compact-syntax;
            choice access-list-id {
              leaf acl-id {
                tailf:cli-drop-node-name;
                type uint16;
              }
              leaf name {
                type string;
              }
            }
            choice nat-choice {
              leaf source-nat-pool-alt1 {
                tailf:alt-name "source-nat-pool";
                type string;
              }
              leaf source-nat-pool-alt2 {
                tailf:alt-name "source-nat-pool";
                type string;
              }
              leaf source-nat-pool-alt3 {
                tailf:alt-name "source-nat-pool";
                type string;
              }
            }
            leaf sequence-number {
              type uint8;
            }
          }
          list aflex {
            tailf:cli-suppress-mode;
            key "id";
            leaf id {
              type string;
            }
          }
          container conn-limit {
            tailf:cli-sequence-commands {
              tailf:cli-reset-siblings;
            }
            tailf:cli-compact-syntax;
            leaf limit {
              tailf:cli-drop-node-name;
              type uint32;
            }
            leaf reset {
              must '../limit' {
                tailf:xpath-root 3;
              }
              tailf:cli-optional-in-sequence;
              type empty;
            }
            leaf no-logging {
              type empty;
            }
          }
          leaf def-selection-if-pref-failed-disable {
            type empty;
          }
          leaf disable {
            type empty;
          }
          leaf extended-stats {
            type empty;
          }
          leaf ha-conn-mirror {
            type empty;
            must "../type='tcp' or ../type='diameter' or ../type='ftp' or ../type='mms' or ../type='rtsp' or ../type='sip' or ../type='tftp' or ../type='udp'" {
              tailf:xpath-root 3;
            }
          }
          leaf message-switching {
            type empty;
          }
          leaf name {
            type string;
          }
          container no-dest-nat {
            presence "true";
            leaf port-translation {
              type empty;
            }
          }
          leaf pbslb {
            type empty;
          }
          leaf reset-on-server-selection-fail {
            type empty;
          }
          leaf redirect-to-https {
            type empty;
          }
          leaf support-http2 {
            type empty;
          }
          leaf service-group {
            type string;
          }
          leaf snat-on-vip {
            type empty;
          }
          container source-nat {
            choice source-nat-choice {
              container auto {
                presence "true";
                leaf precedence {
                  type empty;
                }
              }
              leaf class-list {
                type string;
              }
              list pool {
                tailf:cli-suppress-mode;
                tailf:cli-diff-create-before "../../service-group" {
                  tailf:xpath-root 3;
                  tailf:cli-when-target-create;
                }
                key "name";
                leaf name {
                  type string;
                }
              }
            }
          }
          leaf stats-data-disable {
            type empty;
          }
          leaf syn-cookie {
            type empty;
          }
          container use-default-if-no-server {
            presence "true";
            leaf sack {
              type empty;
            }
          }
          leaf use-rcv-hop-for-resp {
            type empty;
          }
          list template {
            tailf:cli-compact-syntax;
            tailf:cli-sequence-commands;
            tailf:cli-suppress-mode;
            tailf:cli-delete-when-empty;
            key "template-type";
            leaf template-type {
              type enumeration {
                enum "client-ssl";
                enum "diameter";
                enum "dynamic-service";
                enum "external-service";
                enum "http";
                enum "persist";
                enum "policy";
                enum "sip";
                enum "server-ssl";
                enum "tcp";
                enum "tcp-proxy";
                enum "udp";
                enum "virtual-port";
              }
            }
            leaf udp {
              tailf:cli-drop-node-name;
              type string;
            }
            leaf sip {
              tailf:cli-drop-node-name;
              type string;
            }
            leaf diameter {
              tailf:cli-drop-node-name;
              type string;
            }
            container persist {
              tailf:cli-drop-node-name;
              leaf source-ip {
                type string;
              }
              leaf destination-ip {
                type string;
              }
              leaf ssl-sid {
                type string;
              }
              leaf cookie {
                type string;
              }
            }
            leaf policy {
              tailf:cli-drop-node-name;
              type string;
            }
            leaf tcp {
              tailf:cli-drop-node-name;
              type string;
            }
            leaf tcp-proxy {
              tailf:cli-drop-node-name;
              type string;
            }
            leaf virtual-port {
              tailf:cli-drop-node-name;
              type string;
            }
            leaf client-ssl {
              tailf:cli-drop-node-name;
              type string;
            }
            leaf server-ssl {
              tailf:cli-drop-node-name;
              type string;
            }
            leaf http {
              tailf:cli-drop-node-name;
              type string;
            }
            leaf external-service {
              tailf:cli-drop-node-name;
              type string;
            }
            leaf dynamic-service {
              tailf:cli-drop-node-name;
              type string;
            }
          }
        }
        container template {
          leaf logging {
            type string;
          }
          leaf policy {
            type string;
          }
          leaf virtual-server {
            type string;
          }
        }
      }
      container resource-usage {
        uses resource-usage-grouping;
      }
      leaf transparent-tcp-template {
        type string;
      }
    }
  }

  grouping gslb-group-grouping {
    list group {
      key "name";
      leaf name {
        type string;
      }
      leaf config-merge {
        type empty;
      }
      leaf enable {
        type empty;
      }
      list primary {
        tailf:cli-suppress-mode;
        key "ip-address";
        leaf ip-address {
          type inet:ipv4-address;
        }
      }
      leaf priority {
        type uint8;
      }
    }
  }

  grouping gslb-service-ip-grouping {
    list service-ip {
      key "name";
      leaf name {
        type string;
      }
      leaf disable {
        type empty;
      }
      leaf ip {
        tailf:cli-drop-node-name;
        tailf:cli-hide-in-submode;
        type union {
          type inet:ipv6-address;
          type inet:ipv4-address;
        }
      }
      leaf health-check {
        type string;
      }
      leaf health-check-protocol-disable {
        type empty;
      }
      leaf health-check-disable {
        type empty;
      }

      grouping service-port-grouping {
        leaf number {
          type uint16;
        }
        leaf udp-tcp {
          tailf:cli-drop-node-name;
          tailf:cli-prefix-key {
            tailf:cli-before-key 2;
          }
          type enumeration {
            enum "tcp";
            enum "udp";
          }
        }
        leaf service-name {
          type string;
        }
        leaf health-check {
          type string;
        }
        leaf health-check-protocol-disable {
          type empty;
        }
        leaf state {
          tailf:cli-drop-node-name;
          type enumeration {
            enum "enable";
            enum "disable";
          }
        }
      }
      list port {
        key "number service-name";
        uses service-port-grouping;
      }
      list service {
        key "number service-name";
        uses service-port-grouping;
      }
      container port-name {
        tailf:cli-drop-node-name;
        list port {
          key "number name";
          leaf number {
            type uint16;
          }
          leaf udp-tcp {
            tailf:cli-prefix-key {
              tailf:cli-before-key 2;
            }
            tailf:cli-drop-node-name;
            type enumeration {
              enum "tcp";
              enum "udp";
            }
          }
          leaf name {
            type string;
          }
          leaf health-check {
            type string;
          }
          leaf health-check-protocol-disable {
            type empty;
          }
          leaf state {
            tailf:cli-drop-node-name;
            type enumeration {
              enum "enable";
              enum "disable";
            }
          }
        }
      }
    }
  }

  grouping gslb-site-grouping {
    list site {
      key "name";
      leaf name {
        type string;
      }
      list slb-dev {
        key "name";
        leaf name {
          type string;
        }
        leaf ip-address {
          tailf:cli-drop-node-name;
          tailf:cli-hide-in-submode;
          type inet:ipv4-address;
        }
        list vip-server {
          tailf:cli-suppress-mode;
          key "name";
          leaf name {
            type union {
              type inet:ipv6-address;
              type inet:ipv4-address;
              type string;
            }
          }
        }
      }
    }
  }

  grouping gslb-policy-grouping {
    list policy {
      key "name";
      leaf name {
        type string;
      }
      container admin-ip {
        leaf top-only {
          type empty;
        }
      }
      leaf admin-ip-enable {
        type empty;
      }
      leaf geographic {
        type boolean;
      }
      container metric-order {
        tailf:cli-compact-syntax;
        leaf-list options {
          tailf:cli-drop-node-name;
          tailf:cli-flat-list-syntax;
          ordered-by user;
          type enumeration {
            enum "active-rdt";
            enum "active-servers";
            enum "admin-ip";
            enum "admin-preference";
            enum "bw-cost";
            enum "capacity";
            enum "connection-load";
            enum "geographic";
            enum "health-check";
            enum "least-response";
            enum "num-session";
            enum "weighted-ip";
            enum "weighted-site";
          }
        }
      }
      container dns {
        container active-only {
          presence "true";
          leaf fail-safe {
            type empty;
          }
        }
        leaf backup-server {
          type empty;
        }
        container selected-only {
          presence "true";
          leaf number {
            tailf:cli-drop-node-name;
            type uint8;
          }
        }
        leaf ttl {
          type uint32;
        }
        container server {
          choice dns-server-choice {
            leaf any {
              type empty;
            }
            leaf-list records {
              tailf:cli-drop-node-name;
              tailf:cli-flat-list-syntax;
              type enumeration {
                enum "addition-mx";
                enum "any-with-metric";
                enum "authoritative";
                enum "auto-ns";
                enum "auto-ptr";
                enum "cname";
                enum "full-list";
                enum "mx";
                enum "naptr";
                enum "ns";
                enum "ns-list";
                enum "ptr";
                enum "sec";
                enum "server-mode-only";
                enum "srv";
                enum "txt";
              }
            }
          }
        }
        container sticky {
          tailf:cli-compact-syntax;
          leaf ip-mask {
            tailf:cli-drop-node-name;
            type string;
          }
          leaf ipv6-mask {
            type uint8;
          }
          leaf aging-time {
            type uint16;
          }
        }
      }
      container active-rdt {
        leaf enable {
          type empty;
        }
        leaf single-shot {
          type empty;
        }
      }
    }
  }

  grouping gslb-zone-grouping {
    list zone {
      key "name";
      leaf name {
        type string;
      }
      container service {
        list service-port {
          tailf:cli-drop-node-name;
          key "port";
          leaf port {
            type uint16;
          }
          uses gslb-zone-service-grouping;
        }
        list service-port-name {
          tailf:cli-drop-node-name;
          key "port name";
          leaf port {
            type uint16;
          }
          leaf name {
            type string;
          }
          uses gslb-zone-service-grouping;
        }
      }
    }
  }

  grouping gslb-grouping {
    container gslb {
      uses gslb-service-ip-grouping;
      uses gslb-group-grouping;
      uses gslb-site-grouping;
      uses gslb-policy-grouping;
      uses gslb-zone-grouping;
      container protocol {
        container enable {
          leaf controller {
            type empty;
          }
          leaf device {
            type empty;
          }
        }
      }
      container active-rdt {
        leaf icmp {
          type empty;
        }
      }
    }
  }

  grouping bw-list-grouping {
    list bw-list {
      tailf:cli-compact-syntax;
      tailf:cli-suppress-mode;
      key "name";
      leaf name {
        type string;
      }
      leaf import-info {
        type string;
      }
    }
    list import-info {
      tailf:cli-suppress-mode;
      tailf:cli-compact-syntax;
      key "name";
      leaf name {
        type string;
      }
      leaf url {
        type string;
      }
      leaf username {
        type string;
      }
      leaf password {
        type string;
      }
    }
  }

  grouping aflex-grouping {
    list aflex {
      key "name";
      leaf name {
        type string;
      }
      leaf script {
        type string;
      }
    }
  }

  grouping action-grouping {
    list action {
      tailf:cli-suppress-mode;
      key "type";
      leaf type {
        type enumeration {
          enum "dnat";
          enum "drop";
          enum "one-to-one-snat";
          enum "pass-through";
          enum "snat";
        }
      }
      leaf pool {
        type string;
      }
      leaf domain {
        type string;
      }
    }
    leaf no-action {
      type empty;
    }
  }

  grouping port-grouping {
    list port {
      tailf:cli-suppress-mode;
      tailf:cli-compact-syntax;
      key "id";
      leaf id {
        type uint16;
      }
      // NCS expand uses statement
      list action {
        tailf:cli-suppress-mode;
        key "type";
        leaf type {
          type enumeration {
            enum "dnat";
            enum "drop";
            enum "one-to-one-snat";
            enum "pass-through";
            enum "snat";
          }
        }
        leaf pool {
          type string;
        }
        leaf domain {
          type string;
        }
      }
      leaf no-action {
        type empty;
      }
    }
  }

  grouping system-jumbo-global-grouping {
    container system-jumbo-global {
      leaf enable-jumbo {
        type empty;
      }
    }
  }

  grouping hd-monitor-grouping {
    container hd-monitor {
      leaf enable {
        type empty;
      }
    }
  }

  grouping timezone-grouping {
    container timezone {
      tailf:cli-compact-syntax;
      tailf:cli-sequence-commands {
        tailf:cli-reset-all-siblings;
      }
      leaf timezone {
        tailf:cli-drop-node-name;
        type enumeration {
          enum "UTC";
          enum "Pacific/Midway";
          enum "Pacific/Honolulu";
          enum "America/Anchorage";
          enum "America/Tijuana";
          enum "America/Los_Angeles";
          enum "America/Vancouver";
          enum "America/Phoenix";
          enum "America/Shiprock";
          enum "America/Chicago";
          enum "America/Mexico_City";
          enum "America/Regina";
          enum "America/Swift_Current";
          enum "America/Kentucky/Monticello";
          enum "America/Indiana/Marengo";
          enum "America/Montreal";
          enum "America/New_York";
          enum "America/Toronto";
          enum "America/Caracas";
          enum "America/Halifax";
          enum "America/Santiago";
          enum "America/St_Johns";
          enum "America/Buenos_Aires";
          enum "America/Godthab";
          enum "Atlantic/South_Georgia";
          enum "Atlantic/Azores";
          enum "Atlantic/Cape_Verde";
          enum "Europe/Dublin";
          enum "Africa/Algiers";
          enum "Europe/Amsterdam";
          enum "Europe/Belgrade";
          enum "Europe/Brussels";
          enum "Europe/Sarajevo";
          enum "Europe/Bucharest";
          enum "Africa/Cairo";
          enum "Europe/Athens";
          enum "Africa/Harare";
          enum "Asia/Jerusalem";
          enum "Europe/Helsinki";
          enum "Africa/Nairobi";
          enum "Asia/Baghdad";
          enum "Asia/Kuwait";
          enum "Europe/Moscow";
          enum "Asia/Tehran";
          enum "Asia/Baku";
          enum "Asia/Muscat";
          enum "Asia/Kabul";
          enum "Asia/Karachi";
          enum "Asia/Yekaterinburg";
          enum "Asia/Calcutta";
          enum "Asia/Katmandu";
          enum "Asia/Almaty";
          enum "Asia/Dhaka";
          enum "Indian/Chagos";
          enum "Asia/Rangoon";
          enum "Asia/Bangkok";
          enum "Asia/Krasnoyarsk";
          enum "Asia/Irkutsk";
          enum "Asia/Kuala_Lumpur";
          enum "Asia/Shanghai";
          enum "Asia/Taipei";
          enum "Australia/Perth";
          enum "Asia/Seoul";
          enum "Asia/Tokyo";
          enum "Asia/Yakutsk";
          enum "Australia/Adelaide";
          enum "Australia/Darwin";
          enum "Australia/Hobart";
          enum "Australia/Brisbane";
          enum "Asia/Vladivostok";
          enum "Australia/Sydney";
          enum "Pacific/Guam";
          enum "Asia/Magadan";
          enum "Pacific/Auckland";
          enum "Pacific/Fiji";
          enum "Pacific/Kwajalein";
          enum "Pacific/Enderbury";
        }
      }
      leaf nodst {
        type empty;
      }
    }
  }

  grouping clock-grouping {
    container clock {
      tailf:cli-compact-syntax;
      uses timezone-grouping;
      leaf nodst {
        type empty;
      }
    }
  }

  grouping timezone-nodst-grouping {
    container timezone-nodst {
      tailf:cli-drop-node-name;
      tailf:cli-compact-syntax;
      tailf:cli-sequence-commands {
        tailf:cli-reset-siblings;
      }
      uses timezone-grouping;
      leaf nodst {
        type empty;
      }
    }
  }

  grouping ntp-grouping {
    container ntp {
      list server {
        key "name";
        leaf name {
          type string;
        }
        leaf interval {
          tailf:cli-hide-in-submode;
          tailf:cli-drop-node-name;
          type uint32;
        }
        leaf prefer {
          type empty;
        }
      }
    }
  }

  grouping netflow-grouping {
    container netflow {
      container common {
        leaf max-packet-queue-time {
          type uint8;
        }
      }
      list monitor {
        key "name";
        leaf name {
          type string;
        }
        container destination {
          leaf ip {
            tailf:cli-drop-node-name;
            type union {
              type inet:ipv4-address;
              type inet:ipv6-address;
            }
          }
          leaf port {
            tailf:cli-drop-node-name;
            type uint16;
          }
        }
        leaf flow-timeout {
          type uint16;
        }
        leaf protocol {
          type enumeration {
            enum "v9";
            enum "v10";
          }
        }
        list record {
          tailf:cli-suppress-mode;
          key "name";
          leaf name {
            type enumeration {
              enum "dslite";
              enum "nat44";
              enum "nat64";
              enum "netflow-v5";
              enum "netflow-v5-ext";
              enum "port-batch-dslite";
              enum "port-batch-nat44";
              enum "port-batch-nat64";
              enum "port-batch-v2-dslite";
              enum "port-batch-v2-nat44";
              enum "port-batch-v2-nat64";
              enum "port-mapping-dslite";
              enum "port-mapping-nat44";
              enum "port-mapping-nat64";
              enum "sesn-event-dslite";
              enum "sesn-event-fw4";
              enum "sesn-event-fw6";
              enum "sesn-event-nat44";
              enum "sesn-event-nat64";
            }
          }
          leaf events {
            tailf:cli-drop-node-name;
            type enumeration {
              enum "both";
              enum "creation";
              enum "deletion";
            }
          }
        }
        container resend-template {
          leaf records {
            type uint32;
          }
          leaf timeout {
            type uint16;
          }
        }

        grouping sample-grouping {
          container sample {
            list ve {
              tailf:cli-suppress-mode;
              key "id";
              leaf id {
                type uint16;
              }
            }
          }
        }
        uses sample-grouping;

        grouping source-address-grouping {
          container source-address {
            leaf ip {
              type inet:ipv4-address;
            }
            leaf ipv6 {
              type inet:ipv6-address;
            }
          }
        }
        uses source-address-grouping;
        leaf source-ip-use-mgmt {
          type empty;
        }
        list device-context {
          key "id";
          leaf id {
            type uint8;
          }
          uses sample-grouping;
          uses source-address-grouping;
        }
      }
    }
  }

  grouping trunk-grouping {
    list trunk {
      key "id";
      leaf id {
        type uint16;
      }
      leaf-list ethernet {
        tailf:cli-range-list-syntax;
        type uint8;
      }
      container disable {
        leaf-list ethernet {
          tailf:cli-range-list-syntax;
          type uint8;
        }
      }
      leaf ports-threshold {
        type uint16;
      }
      leaf port-threshold-timer {
        type uint16;
      }
      leaf name {
        type string;
      }
    }
  }

  grouping class-list-grouping {
    list class-list {
      key "name";
      leaf name {
        type string;
      }
      leaf cl-type {
        tailf:cli-hide-in-submode;
        tailf:cli-drop-node-name;
        type enumeration {
          enum "ipv4";
          enum "ipv6";
          enum "string";
        }
      }
      choice v4v6str-choice {
        list str {
          tailf:cli-compact-syntax;
          tailf:cli-suppress-mode;
          key "str";
          leaf str {
            type string;
          }
          uses lid-grouping;
          leaf string {
            tailf:cli-drop-node-name;
            type string;
          }
        }
        list v4 {
          tailf:cli-compact-syntax;
          tailf:cli-drop-node-name;
          tailf:cli-sequence-commands;
          tailf:cli-suppress-mode;
          key "ip";
          leaf ip {
            type inet:ipv4-prefix;
          }
          uses lid-grouping;
        }
        list v6 {
          tailf:cli-compact-syntax;
          tailf:cli-drop-node-name;
          tailf:cli-sequence-commands;
          tailf:cli-suppress-mode;
          key "ip";
          leaf ip {
            type inet:ipv6-prefix;
          }
          uses lid-grouping;
        }
      }
    }
  }

  grouping class-list-group-grouping {
    list class-list-group {
      tailf:cli-compact-syntax;
      key "name";
      leaf name {
        type string;
      }
      list sequence-number {
        tailf:cli-suppress-mode;
        tailf:cli-compact-syntax;
        tailf:cli-sequence-commands;
        ordered-by user;
        key "id";
        leaf id {
          type uint32;
        }
        leaf host-url {
          tailf:cli-drop-node-name;
          type enumeration {
            enum "HOST";
            enum "URL";
          }
        }
        choice string-choice {
          leaf contains {
            type string;
          }
          leaf ends-with {
            type string;
          }
          leaf equals {
            type string;
          }
          leaf starts-with {
            type string;
          }
        }
        leaf lid {
          type uint32;
        }
      }
    }
  }

  grouping tacacs-server-grouping {
    container tacacs-server {
      list host {
        tailf:cli-compact-syntax;
        tailf:cli-sequence-commands;
        tailf:cli-suppress-mode;
        key "name";
        leaf name {
          type union {
            type inet:ipv4-address;
            type inet:ipv4-address;
            type string;
          }
        }
        container secret {
          tailf:cli-compact-syntax;
          tailf:cli-sequence-commands;
          tailf:cli-flatten-container;
          leaf encrypted {
            tailf:cli-optional-in-sequence;
            type empty;
          }
          leaf secret {
            tailf:cli-optional-in-sequence;
            tailf:cli-drop-node-name;
            type string;
          }
        }
        leaf port {
          tailf:cli-break-sequence-commands;
          type uint16;
        }
        leaf timeout {
          type uint8;
        }
      }
    }
  }

  grouping radius-server-grouping {
    container radius-server {
      list host {
        tailf:cli-suppress-mode;
        tailf:cli-sequence-commands {
          tailf:cli-reset-siblings;
        }
        tailf:cli-compact-syntax;
        key "name";
        leaf name {
          type union {
            type inet:ipv6-address;
            type string;
          }
        }
        container secret {
          tailf:cli-flatten-container;
          tailf:cli-sequence-commands {
            tailf:cli-reset-siblings;
          }
          tailf:cli-compact-syntax;
          leaf cleartext {
            tailf:cli-drop-node-name;
            tailf:cli-optional-in-sequence;
            type string;
          }
          leaf secret-encrypted {
            type string;
          }
          leaf auth-port {
            type uint32;
          }
          leaf acct-port {
            type uint32;
          }
          leaf timeout {
            type uint32;
          }
        }
      }
    }
  }

  grouping authentication-grouping {
    container authentication {
      container enable {
        choice authetication-enable-choice {
          container local {
            leaf tacplus {
              type empty;
            }
          }
          container tacplus {
            presence "true";
            leaf local {
              type empty;
            }
          }
        }
      }
      leaf-list type {
        tailf:cli-flat-list-syntax;
        type enumeration {
          enum "tacplus";
          enum "radius";
          enum "local";
        }
      }
      leaf mode {
        type enumeration {
          enum "multiple";
          enum "single";
        }
      }
      container console {
        leaf-list type {
          tailf:cli-flat-list-syntax;
          type enumeration {
            enum "tacplus";
            enum "radius";
            enum "local";
          }
        }
      }
      leaf disable-local {
        type empty;
      }
      container login {
        leaf privilege-mode {
          type empty;
        }
      }
    }
  }

  grouping vlan-grouping {
    list vlan {
      key "id";
      leaf id {
        type vlan-index;
      }
      container untagged {
        tailf:cli-compact-syntax;
        leaf-list ethernet {
          tailf:cli-range-list-syntax;
          type uint8;
        }
        leaf trunk {
          type uint8;
        }
      }
      container tagged {
        tailf:cli-compact-syntax;
        leaf-list ethernet {
          tailf:cli-range-list-syntax;
          type uint8;
        }
        leaf trunk {
          type uint8;
        }
      }
      container router-interface {
        leaf ve {
          type vlan-index;
        }
      }
      leaf name {
        type string;
      }
    }
  }

  grouping ipv6-route-grouping {
    container route {
      list route-no-if {
        tailf:cli-drop-node-name;
        tailf:cli-compact-syntax;
        tailf:cli-suppress-mode;
        key "ip forwarding-router";
        leaf ip {
          type inet:ipv6-prefix;
        }
        leaf forwarding-router {
          tailf:cli-drop-node-name;
          type inet:ipv6-address;
        }
        leaf distance {
          tailf:cli-drop-node-name;
          type uint8;
        }
      }
      list route-if {
        tailf:cli-drop-node-name;
        tailf:cli-compact-syntax;
        tailf:cli-suppress-mode;
        key "ip forwarding-router interface-type interface-nr";
        leaf ip {
          type inet:ipv6-prefix;
        }
        leaf forwarding-router {
          tailf:cli-drop-node-name;
          type inet:ipv6-address;
        }
        leaf interface-type {
          type enumeration {
            enum "ethernet";
            enum "trunk";
            enum "ve";
          }
        }
        leaf interface-nr {
          type uint16;
        }
        leaf distance {
          tailf:cli-drop-node-name;
          type uint8;
        }
      }
    }
  }

  grouping ipv6-grouping {
    container ipv6 {
      uses ipv6-route-grouping;
      container nat {
        list pool {
          tailf:cli-suppress-mode;
          tailf:cli-compact-syntax;
          tailf:cli-sequence-commands;
          key "name";
          leaf name {
            type string;
          }
          leaf ipstart {
            mandatory true;
            tailf:cli-drop-node-name;
            type inet:ipv6-address;
          }
          leaf ipend {
            mandatory true;
            tailf:cli-drop-node-name;
            type inet:ipv6-address;
          }
          leaf netmask {
            mandatory true;
            type uint8;
          }
        }
      }
      list access-list {
        tailf:cli-delete-when-empty;
        key "id";
        leaf id {
          type string;
        }
        list rules {
          ordered-by user;
          tailf:cli-suppress-mode;
          tailf:cli-drop-node-name;
          key "acc-type txt";
          leaf acc-type {
            type enumeration {
              enum "permit";
              enum "deny";
            }
          }
          leaf txt {
            tailf:cli-multi-word-key;
            type string;
          }
        }
        list remark {
          tailf:cli-suppress-mode;
          key "name";
          leaf name {
            type string;
          }
        }
      }
      list prefix-list {
        tailf:cli-suppress-mode;
        tailf:cli-compact-syntax;
        key "name seq";
        leaf name {
          type string;
        }
        leaf seq {
          tailf:cli-expose-key-name;
          type uint32;
        }
        choice permit-deny {
          leaf permit {
            type union {
              type enumeration {
                enum "any";
              }
              type tailf:ipv6-address-and-prefix-length;
            }
          }
          leaf deny {
            type union {
              type enumeration {
                enum "any";
              }
              type tailf:ipv6-address-and-prefix-length;
            }
          }
        }
      }
    }
  }

  grouping nat64-grouping {
    container nat64 {
      uses algs;
      leaf user-quota-prefix-length {
        type uint8;
      }
      container inside {
        container source {
          leaf class-list {
            type string;
          }
        }
      }
      leaf prefix {
        type inet:ipv6-prefix;
      }
    }
  }

  grouping lsn-lid-grouping {
    list lsn-lid {
      key "lsn-lid-id";
      leaf lsn-lid-id {
        type uint16;
      }
      leaf name {
        type string;
      }
      leaf source-nat-pool {
        type string;
      }
      container user-quota {
        leaf session {
          type uint32;
        }
      }
      leaf respond-to-user-mac {
        type empty;
      }
    }
  }

  grouping ha-grouping {
    container ha {
      leaf arp-retry {
        type uint16;
      }
      container check {
        list gateway {
          key "ip";
          tailf:cli-suppress-mode;
          leaf ip {
            type inet:ipv4-address;
          }
        }
        list route {
          key "ip mask gateway distance protocol priority-cost";
          unique "ip mask gateway distance protocol";
          tailf:cli-compact-syntax;
          tailf:cli-suppress-mode;
          leaf ip {
            type union {
              type inet:ipv4-address;
              type inet:ipv6-address;
            }
          }
          leaf mask {
            type ipv4-mask;
          }
          leaf gateway {
            tailf:cli-expose-key-name;
            type union {
              type inet:ipv4-address;
              type inet:ipv6-address;
            }
          }
          leaf distance {
            tailf:cli-expose-key-name;
            type uint8;
          }
          leaf protocol {
            tailf:cli-expose-key-name;
            type enumeration {
              enum "any";
              enum "static";
              enum "dynamic";
            }
          }
          leaf priority-cost {
            tailf:cli-expose-key-name;
            type uint8;
          }
        }
        container vlan {
          tailf:cli-sequence-commands;
          tailf:cli-compact-syntax;
          leaf vlan-id {
            tailf:cli-drop-node-name;
            type vlan-index;
          }
          leaf timeout {
            must '../vlan-id' {
              tailf:xpath-root 3;
            }
            type uint16;
          }
        }
      }
      container conn-mirror {
        leaf ip {
          type inet:ipv4-address;
        }
      }
      container force-self-standby {
        list HA-group-id {
          key "id persistent";
          tailf:cli-suppress-mode;
          leaf id {
            type uint16;
          }
          leaf persistent {
            type enumeration {
              enum "persistent";
            }
          }
        }
      }
      leaf forward-l4-packet-on-standby {
        type empty;
      }
      container id {
        tailf:cli-sequence-commands {
          tailf:cli-reset-siblings;
        }
        tailf:cli-compact-syntax;
        leaf id {
          tailf:cli-drop-node-name;
          type uint8;
        }
        leaf set-id {
          type uint8;
        }
      }
      list group {
        tailf:cli-suppress-mode;
        key "id";
        tailf:cli-sequence-commands;
        tailf:cli-compact-syntax;
        tailf:cli-delete-when-empty;
        leaf id {
          type uint16;
        }
        leaf priority {
          must '../id' {
            tailf:xpath-root 3;
          }
          type uint16;
        }
      }
      container inline-mode {
        presence "true";
        leaf preferred-port {
          type uint8;
        }
      }
      container interface {
        list ethernet {
          tailf:cli-suppress-mode;
          tailf:cli-compact-syntax;
          tailf:cli-sequence-commands {
            tailf:cli-reset-siblings;
          }
          key "id";
          leaf id {
            type ethernet-index;
          }
          leaf type {
            tailf:cli-optional-in-sequence;
            tailf:cli-drop-node-name;
            type enumeration {
              enum "both";
              enum "router-interface";
              enum "server-interface";
            }
          }
          choice xx {
            leaf no-heartbeat {
              tailf:cli-optional-in-sequence;
              type empty;
            }
            leaf vlan {
              tailf:cli-optional-in-sequence;
              type uint16;
            }
          }
        }
      }
      leaf preemption-enable {
        type empty;
      }
      leaf timeout-retry-count {
        type uint8;
      }
    }
  }

  grouping floating-ip-grouping {
    container floating-ip {
      list ipv4 {
        tailf:cli-suppress-mode;
        tailf:cli-drop-node-name;
        key "ip ha-group";
        leaf ip {
          type inet:ipv4-address;
        }
        leaf ha-group {
          tailf:cli-expose-key-name;
          type uint16;
        }
      }
      list ipv6 {
        tailf:cli-suppress-mode;
        tailf:cli-drop-node-name;
        key "ip ha-group";
        leaf ip {
          type inet:ipv6-address;
        }
        leaf ha-group {
          tailf:cli-expose-key-name;
          type uint16;
        }
        leaf anycast {
          tailf:cli-prefix-key {
            tailf:cli-before-key 2;
          }
          type empty;
        }
        choice ipv6-interface {
          leaf ethernet {
            must '../../../interface/ethernet/ipv6/address/ip' {
              tailf:xpath-root 3;
            }
            type ethernet-index;
          }
          leaf trunk {
            type uint16;
          }
          leaf ve {
            must '../../../interface/ve/ipv6/address/ip' {
              tailf:xpath-root 3;
            }
            type vlan-index;
          }
        }
      }
    }
  }

  grouping glid-grouping {
    list glid {
      key "limit-id";
      leaf limit-id {
        type uint16;
      }
      container dns {
        leaf cache-leaf {
          tailf:cli-drop-node-name;
          type enumeration {
            enum "cache-enable";
            enum "cache-disable";
          }
        }
        container ttl {
          tailf:cli-compact-syntax;
          leaf ttl-value {
            tailf:cli-drop-node-name;
            type uint16;
          }
          leaf honor-server-response-ttl {
            type empty;
          }
        }
      }
      container over-limit-action {
        tailf:cli-compact-syntax;
        tailf:cli-sequence-commands {
          tailf:cli-reset-siblings;
        }
        leaf over-limit-action-choice {
          tailf:cli-drop-node-name;
          type enumeration {
            enum "dns-cache-disable";
            enum "dns-cache-enable";
            enum "forward";
            enum "reset";
            enum "lockout";
            enum "log";
          }
        }
        leaf lockout {
          tailf:cli-optional-in-sequence;
          type uint16;
        }
        leaf lockout-val {
          tailf:cli-optional-in-sequence;
          tailf:cli-drop-node-name;
          type uint16;
        }
        leaf log {
          tailf:cli-optional-in-sequence;
          type empty;
        }
        leaf log-val {
          tailf:cli-drop-node-name;
          tailf:cli-optional-in-sequence;
          type uint16;
        }
      }
      leaf conn-limit {
        type uint32;
      }
      container conn-rate-limit {
        tailf:cli-sequence-commands {
          tailf:cli-reset-siblings;
        }
        tailf:cli-compact-syntax;
        leaf limit {
          tailf:cli-drop-node-name;
          type uint32;
        }
        leaf per {
          must '../limit' {
            tailf:xpath-root 3;
          }
          type uint16;
        }
      }
      leaf request-limit {
        type uint32;
      }
      container request-rate-limit {
        tailf:cli-sequence-commands {
          tailf:cli-reset-siblings;
        }
        tailf:cli-compact-syntax;
        leaf limit {
          tailf:cli-drop-node-name;
          type uint32;
        }
        leaf per {
          must '../limit' {
            tailf:xpath-root 3;
          }
          type uint16;
        }
      }
      leaf use-nat-pool {
        type string;
      }
    }
  }

  grouping gslb-zone-service-grouping {
    leaf policy {
      type string;
    }
    list dns-a-record {
      tailf:cli-suppress-mode;
      tailf:cli-compact-syntax;
      key "name";
      leaf name {
        type union {
          type inet:ipv6-address;
          type inet:ipv4-address;
          type string;
        }
      }
      leaf as-backup {
        tailf:cli-hide-in-submode;
        type empty;
      }
      leaf port-service-name {
        tailf:cli-drop-node-name;
        tailf:cli-hide-in-submode;
        type string;
      }
      leaf weight {
        tailf:cli-hide-in-submode;
        type uint8;
      }
      container static {
        tailf:cli-hide-in-submode;
        tailf:cli-flatten-container;
        tailf:cli-compact-syntax;
        presence "true";
        leaf admin-ip {
          type uint8;
        }
      }
    }
  }

  grouping logging-grouping {
    container logging {
      container auditlog {
        tailf:cli-compact-syntax;
        tailf:cli-sequence-commands {
          tailf:cli-reset-all-siblings;
        }
        leaf host {
          type string;
        }
        leaf facility {
          type string;
        }
      }
      container buffered {
        presence "true";
        leaf size {
          tailf:cli-drop-node-name;
          type uint32;
        }
        leaf severity {
          tailf:cli-drop-node-name;
          type enumeration {
            enum "emergency";
            enum "alert";
            enum "critical";
            enum "error";
            enum "warning";
            enum "notification";
            enum "information";
            enum "debugging";
          }
        }
      }
      leaf console {
        type enumeration {
          enum "emergency";
          enum "alert";
          enum "critical";
          enum "error";
          enum "warning";
          enum "notification";
          enum "information";
          enum "debugging";
          enum "disable";
        }
      }
      container email {
        container buffer {
          choice buffer-choice {
            leaf number {
              type uint16;
            }
            leaf time {
              type uint16;
            }
          }
        }
        leaf severity {
          tailf:cli-drop-node-name;
          type enumeration {
            enum "emergency";
            enum "alert";
            enum "critical";
            enum "notification";
          }
        }
      }
      leaf-list email-address {
        tailf:cli-flat-list-syntax;
        type string;
      }
      leaf export {
        type empty;
      }
      leaf facility {
        type enumeration {
          enum "local0";
          enum "local1";
          enum "local2";
          enum "local3";
          enum "local4";
          enum "local5";
          enum "local6";
          enum "local7";
        }
      }
      leaf syslog {
        type enumeration {
          enum "emergency";
          enum "alert";
          enum "critical";
          enum "error";
          enum "warning";
          enum "notification";
          enum "information";
          enum "debugging";
        }
      }
      leaf trap {
        type enumeration {
          enum "emergency";
          enum "alert";
          enum "critical";
        }
      }
      choice host-choice {
        container host-list {
          tailf:cli-drop-node-name;
          list host {
            tailf:cli-suppress-mode;
            tailf:cli-compact-syntax;
            key "hosts";
            leaf hosts {
              type string;
            }
            choice use-mgmt-port-choice {
              container port {
                tailf:cli-compact-syntax;
                tailf:cli-flatten-container;
                tailf:cli-sequence-commands {
                  tailf:cli-reset-siblings;
                }
                leaf number {
                  tailf:cli-drop-node-name;
                  type uint16;
                }
                leaf tcp {
                  type empty;
                }
              }
              container use-mgmt-port {
                tailf:cli-compact-syntax;
                tailf:cli-flatten-container;
                tailf:cli-sequence-commands {
                  tailf:cli-reset-siblings;
                }
                presence "true";
                leaf port {
                  type uint32;
                }
                leaf tcp {
                  type empty;
                }
              }
            }
          }
        }
        container host {
          tailf:cli-sequence-commands {
            tailf:cli-reset-siblings;
          }
          tailf:cli-compact-syntax;
          leaf-list hosts {
            tailf:cli-flat-list-syntax;
            tailf:cli-drop-node-name;
            type string;
          }
          leaf port {
            type uint16;
          }
        }
        container host-alt {
          tailf:cli-drop-node-name;
          container host {
            leaf partition {
              type enumeration {
                enum "shared";
              }
            }
          }
        }
      }
      leaf monitor {
        type enumeration {
          enum "emergency";
          enum "alert";
          enum "critical";
          enum "error";
          enum "warning";
          enum "notification";
          enum "information";
          enum "debugging";
        }
      }
    }
  }

  grouping snmp-server-grouping {
    container snmp-server {
      container enable {
        leaf enabled {
          tailf:cli-drop-node-name;
          type empty;
        }
        leaf service {
          type empty;
        }
        container traps {
          leaf enabled {
            tailf:cli-drop-node-name;
            type empty;
          }
          leaf all {
            type empty;
          }
          container routing {
            container ospf {
              choice routing-choice {
                leaf-list ospf-traps {
                  tailf:cli-drop-node-name;
                  type enumeration {
                    enum "ospfIfAuthFailure";
                    enum "ospfIfConfigError";
                    enum "ospfIfRxBadPacket";
                    enum "ospfIfStateChange";
                    enum "ospfLsdbApproachingOverflow";
                    enum "ospfLsdbOverflow";
                    enum "ospfMaxAgeLsa";
                    enum "ospfNbrStateChange";
                    enum "ospfOriginateLsa";
                    enum "ospfTxRetransmit";
                    enum "ospfVirtIfAuthFailure";
                    enum "ospfVirtIfConfigError";
                    enum "ospfVirtIfRxBadPacket";
                    enum "ospfVirtIfStateChange";
                    enum "ospfVirtIfTxRetransmit";
                    enum "ospfVirtNbrStateChange";
                  }
                }
                leaf all {
                  type empty;
                }
              }
            }
            container bgp {
              leaf bgpBackwardTransNotification {
                type empty;
              }
              leaf bgpEstablishedNotification {
                type empty;
              }
            }
          }
          container lsn {
            leaf all {
              type empty;
            }
          }
          container snmp {
            leaf enabled {
              tailf:cli-drop-node-name;
              type empty;
            }
            leaf all {
              type empty;
            }
            leaf linkdown {
              type empty;
            }
            leaf linkup {
              type empty;
            }
          }
          container ha {
            leaf enabled {
              tailf:cli-drop-node-name;
              type empty;
            }
            leaf active {
              type empty;
            }
            leaf active-active {
              type empty;
            }
            leaf standby {
              type empty;
            }
            leaf vrrp {
              type empty;
            }
          }
          container network {
            leaf enabled {
              tailf:cli-drop-node-name;
              type empty;
            }
            leaf trunk-port-threshold {
              type empty;
            }
          }
          container slb {
            leaf enabled {
              tailf:cli-drop-node-name;
              type empty;
            }
            leaf all {
              type empty;
            }
            leaf application-buffer-limit {
              type empty;
            }
            leaf server-conn-limit {
              type empty;
            }
            leaf server-conn-resume {
              type empty;
            }
            leaf server-down {
              type empty;
            }
            leaf server-up {
              type empty;
            }
            leaf service-conn-limit {
              type empty;
            }
            leaf service-conn-resume {
              type empty;
            }
            leaf service-down {
              type empty;
            }
            leaf service-up {
              type empty;
            }
            leaf vip-connlimit {
              type empty;
            }
            leaf vip-connratelimit {
              type empty;
            }
            leaf vip-port-connlimit {
              type empty;
            }
            leaf vip-port-connratelimit {
              type empty;
            }
            leaf vip-port-down {
              type empty;
            }
            leaf vip-port-up {
              type empty;
            }
          }
          container system {
            leaf enabled {
              tailf:cli-drop-node-name;
              type empty;
            }
            leaf all {
              type empty;
            }
            leaf control-cpu-high {
              type empty;
            }
            leaf data-cpu-high {
              type empty;
            }
            leaf fan {
              type empty;
            }
            leaf high-disk-use {
              type empty;
            }
            leaf high-memory-use {
              type empty;
            }
            leaf high-temp {
              type empty;
            }
            leaf packet-drop {
              type empty;
            }
            leaf power {
              type empty;
            }
            leaf pri-disk {
              type empty;
            }
            leaf restart {
              type empty;
            }
            leaf sec-disk {
              type empty;
            }
            leaf shutdown {
              type empty;
            }
            leaf start {
              type empty;
            }
          }
          container vrrp-a {
            leaf active {
              type empty;
            }
            leaf all {
              type empty;
            }
            leaf standby {
              type empty;
            }
          }
        }
      }
      leaf location {
        type string;
      }
      list user {
        tailf:cli-suppress-mode;
        key "name group type";
        leaf name {
          type string;
        }
        leaf group {
          tailf:cli-expose-key-name;
          type string;
        }
        leaf type {
          type enumeration {
            enum "v1";
            enum "v2c";
            enum "v3";
          }
        }
        container auth {
          tailf:cli-compact-syntax;
          tailf:cli-sequence-commands {
            tailf:cli-reset-siblings;
          }
          leaf mac {
            tailf:cli-drop-node-name;
            type enumeration {
              enum "MD5";
              enum "SHA";
            }
          }
          leaf cleartext {
            tailf:cli-drop-node-name;
            tailf:cli-optional-in-sequence;
            type string;
          }
        }
      }
      list view {
        key "name miboid";
        tailf:cli-suppress-mode;
        tailf:cli-compact-syntax;
        leaf name {
          type string;
        }
        leaf miboid {
          type string;
        }
        leaf included-excluded {
          tailf:cli-drop-node-name;
          type enumeration {
            enum "included";
            enum "excluded";
          }
        }
      }
      list group {
        tailf:cli-suppress-mode;
        tailf:cli-compact-syntax;
        key "name";
        leaf name {
          type string;
        }
        container v3 {
          tailf:cli-compact-syntax;
          container auth {
            tailf:cli-compact-syntax;
            leaf read {
              type string;
            }
          }
        }
      }
      container SNMPv1-v2c {
        list user {
          key "name";
          leaf name {
            type string;
          }
          container community {
            leaf read {
              type string;
            }
          }
          uses snmp-remote-grouping;
        }
      }
      container SNMPv3 {
        list user {
          tailf:cli-suppress-mode;
          tailf:cli-compact-syntax;
          tailf:cli-sequence-commands {
            tailf:cli-reset-siblings;
          }
          key "name";
          leaf name {
            type string;
          }
          leaf group {
            type string;
          }
          leaf v3 {
            type empty;
          }
          choice smnp-server-v3-user-auth-choice {
            container auth {
              tailf:cli-compact-syntax;
              tailf:cli-flatten-container;
              tailf:cli-sequence-commands {
                tailf:cli-reset-siblings;
              }
              leaf hmac {
                tailf:cli-drop-node-name;
                type enumeration {
                  enum "md5";
                  enum "sha";
                }
              }
              leaf password {
                tailf:cli-drop-node-name;
                type string;
              }
              container priv {
                tailf:cli-compact-syntax;
                tailf:cli-flatten-container;
                tailf:cli-sequence-commands {
                  tailf:cli-reset-siblings;
                }
                leaf algo {
                  tailf:cli-drop-node-name;
                  type enumeration {
                    enum "des";
                    enum "aes";
                  }
                }
                leaf passphrase {
                  tailf:cli-drop-node-name;
                  type string;
                }
              }
            }
            leaf noauth {
              type empty;
            }
          }
        }
      }
      container community-mode {
        tailf:cli-drop-node-name;
        list community {
          key "read";
          leaf read {
            tailf:cli-expose-key-name;
            type string;
          }
          uses snmp-remote-grouping;
        }
      }
      list community {
        key "read remote";
        tailf:cli-suppress-mode;
        tailf:cli-compact-syntax;
        leaf read {
          tailf:cli-expose-key-name;
          type string;
        }
        leaf remote {
          tailf:cli-expose-key-name;
          type string;
        }
        leaf oid {
          tailf:cli-prefix-key {
            tailf:cli-before-key 2;
          }
          type string;
        }
        leaf mask {
          tailf:cli-drop-node-name;
          type union {
            type ipv4-mask;
            type string;
          }
        }
      }
      leaf contact {
        type string;
      }
      list host {
        tailf:cli-suppress-mode;
        tailf:cli-sequence-commands {
          tailf:cli-reset-siblings;
        }
        tailf:cli-compact-syntax;
        key "ip version";
        leaf ip {
          type string;
        }
        leaf version {
          tailf:cli-expose-key-name;
          type enumeration {
            enum "v1";
            enum "v2c";
          }
        }
        leaf community-string {
          tailf:cli-drop-node-name;
          mandatory true;
          type string;
        }
        leaf udp-port {
          type uint16;
        }
      }
    }
  }

  grouping audit-grouping {
    container audit {
      container enable {
        leaf privilege {
          type empty;
        }
      }
      leaf size {
        type uint32;
      }
    }
  }

  grouping harmony-controller-grouping {
    container harmony-controller {
      leaf config-replace {
        type enumeration {
          enum "disable";
          enum "enable";
        }
      }
      container profile {
        tailf:cli-add-mode;
        presence "true";
        container host {
          tailf:cli-compact-syntax;
          tailf:cli-sequence-commands;
          leaf host-id {
            tailf:cli-drop-node-name;
            type union {
              type string;
              type inet:ipv4-address;
            }
          }
          leaf use-mgmt-port {
            tailf:cli-optional-in-sequence;
            type empty;
          }
          leaf port {
            type uint16;
          }
        }
        leaf provider {
          type string;
        }
        leaf user-name {
          type string;
        }
        leaf cluster-name {
          type string;
        }
        leaf cluster-id {
          type string;
        }
        leaf password {
          type string;
        }
        leaf region {
          type string;
        }
        leaf availability-zone {
          type string;
        }
        leaf thunder-mgmt-ip {
          type inet:ipv4-address;
        }
        leaf reg-dereg {
          tailf:cli-drop-node-name;
          type enumeration {
            enum "register";
            enum "deregister";
          }
        }
        list device-context {
          key "id";
          leaf id {
            type uint8;
          }
          leaf thunder-mgmt-ip {
            type inet:ipv4-address;
          }
        }
      }
    }
  }

  grouping terminal-grouping {
    container terminal {
      leaf auto-size {
        type empty;
      }
      leaf editing {
        type empty;
      }
      container prompt {
        tailf:cli-compact-syntax;
        leaf hostname {
          type empty;
        }
        leaf ha-status {
          type empty;
        }
      }
      container history {
        leaf size {
          type uint16;
        }
      }
      leaf idle-timeout {
        type uint8;
      }
      leaf length {
        type uint16;
      }
      leaf no-ha-prompt {
        type empty;
      }
      leaf width {
        type uint16;
      }
    }
  }

  grouping web-service-grouping {
    container web-service {
      leaf auto-redir {
        type boolean;
      }
      container auto-redirt {
        leaf disable {
          type empty;
        }
      }
      container axapi-timeout-policy {
        leaf idle {
          type uint8;
        }
      }
      container timeout-policy {
        leaf idle {
          type uint8;
        }
      }
      leaf gui-session-limit {
        type uint8;
      }
      container gui-timeout-policy {
        leaf idle {
          type uint8;
        }
      }
      leaf login-message {
        type string;
      }
      leaf pre-login-message {
        type string;
      }
    }
  }

  grouping multi-config-grouping {
    container multi-config {
      leaf enable {
        type empty;
      }
    }
  }

  grouping banner-grouping {
    container banner {
      container login {
        tailf:cli-compact-syntax;
        choice text-multi {
          leaf text {
            tailf:cli-drop-node-name;
            type string;
          }
          leaf multi-line {
            type string;
          }
        }
      }
      container exec {
        tailf:cli-compact-syntax;
        choice text-multi {
          leaf text {
            tailf:cli-drop-node-name;
            type string;
          }
          leaf multi-line {
            type string;
          }
        }
      }
    }
  }

  grouping preferred-session-sync-port-grouping {
    container preferred-session-sync-port {
      list trunk {
        tailf:cli-suppress-mode;
        tailf:cli-sequence-commands {
          tailf:cli-reset-siblings;
        }
        tailf:cli-compact-syntax;
        key "id";
        leaf id {
          type uint8;
        }
        leaf vlan {
          type uint16;
        }
      }
      list ethernet {
        tailf:cli-suppress-mode;
        tailf:cli-sequence-commands {
          tailf:cli-reset-siblings;
        }
        tailf:cli-compact-syntax;
        key "id";
        leaf id {
          type ethernet-index;
        }
        leaf vlan {
          type uint16;
        }
      }
    }
  }

  grouping vrrp-a-grouping {
    container vrrp-a {

      grouping vrrp-a-common-grouping {
        leaf device-id {
          tailf:cli-diff-create-before "/a10-acos:interface" {
            tailf:xpath-root 3;
          }
          tailf:cli-diff-create-before "/a10-acos:vcs" {
            tailf:xpath-root 3;
          }
          type uint8;
        }
        leaf disable-default-vrid {
          type empty;
        }
        leaf set-id {
          tailf:cli-diff-create-before "/a10-acos:interface" {
            tailf:xpath-root 3;
          }
          tailf:cli-diff-create-before "/a10-acos:vcs" {
            tailf:xpath-root 3;
          }
          type uint8;
        }
        leaf hello-interval {
          type uint8;
        }
        leaf preemption-delay {
          type uint8;
        }
        leaf track-event-delay {
          type uint8;
        }
        leaf restart-time {
          type uint8;
        }
        leaf hostid-append-to-vrid {
          type union {
            type uint8;
            type enumeration {
              enum "default";
            }
          }
        }
        leaf enable {
          tailf:cli-drop-node-name;
          type enumeration {
            enum "enable";
            enum "disable";
          }
        }
      }
      uses vrrp-a-common-grouping;
      container common {
        presence "common-presence";
        tailf:cli-add-mode;
        uses vrrp-a-common-grouping;
      }
      list vrid {
        key "id";
        leaf id {
          type union {
            type uint8;
            type enumeration {
              enum "default";
            }
          }
        }

        grouping vrrp-a-vrid-grouping {
          list floating-ip {
            tailf:cli-suppress-mode;
            key "floating-ip-address";
            leaf floating-ip-address {
              tailf:cli-drop-node-name;
              type union {
                type inet:ipv4-address;
                type inet:ipv6-address;
              }
            }
          }
          leaf priority {
            type uint8;
          }
          container preempt-mode {
            choice preempt-choice {
              leaf disable {
                type empty;
              }
              leaf threshold {
                type uint8;
              }
            }
          }
          container blade-parameters {
            tailf:cli-add-mode;
            leaf priority {
              type uint8;
            }
            container tracking-options {
              tailf:cli-add-mode;
              tailf:cli-delete-when-empty;
              list gateway {
                tailf:cli-suppress-mode;
                key "address";
                leaf address {
                  type union {
                    type inet:ipv4-address;
                    type inet:ipv6-address;
                  }
                }
                uses priority-cost;
              }
              container interface {
                list ethernet {
                  tailf:cli-suppress-mode;
                  key "id";
                  leaf id {
                    type ethernet-index;
                  }
                  leaf priority-cost {
                    mandatory true;
                    type uint8;
                  }
                }
              }
              list route {
                tailf:cli-suppress-mode;
                tailf:cli-compact-syntax;
                key "ip mask";
                leaf ip {
                  type union {
                    type inet:ipv4-address;
                    type inet:ipv6-address;
                  }
                }
                leaf mask {
                  type ipv4-mask;
                }
                uses priority-cost;
                leaf distance {
                  type uint8;
                }
                leaf gateway {
                  type union {
                    type inet:ipv4-address;
                    type inet:ipv6-address;
                  }
                }
                leaf protocol {
                  type enumeration {
                    enum "any";
                    enum "static";
                    enum "dynamic";
                  }
                }
              }
              list trunk {
                tailf:cli-suppress-mode;
                tailf:cli-sequence-commands {
                  tailf:cli-reset-siblings;
                }
                tailf:cli-compact-syntax;
                key "id";
                leaf id {
                  type uint8;
                }
                uses priority-cost;
                leaf per-port-pri {
                  type uint8;
                }
              }
              list vlan {
                tailf:cli-suppress-mode;
                tailf:cli-sequence-commands;
                tailf:cli-compact-syntax;
                key "id";
                leaf id {
                  type vlan-index;
                }
                leaf timeout {
                  type uint16;
                }
                uses priority-cost;
              }
            }
          }
        }
        // NCS expand uses statement
        list floating-ip {
          tailf:cli-suppress-mode;
          key "floating-ip-address";
          leaf floating-ip-address {
            tailf:cli-drop-node-name;
            type union {
              type inet:ipv4-address;
              type inet:ipv6-address;
            }
          }
        }
        leaf priority {
          type uint8;
        }
        container preempt-mode {
          choice preempt-choice {
            leaf disable {
              type empty;
            }
            leaf threshold {
              type uint8;
            }
          }
        }
        container blade-parameters {
          tailf:cli-add-mode;
          leaf priority {
            type uint8;
          }
          container tracking-options {
            tailf:cli-add-mode;
            tailf:cli-delete-when-empty;
            list gateway {
              tailf:cli-suppress-mode;
              key "address";
              leaf address {
                type union {
                  type inet:ipv4-address;
                  type inet:ipv6-address;
                }
              }
              // NCS expand uses statement
              leaf priority-cost {
                mandatory true;
                type uint8;
              }
            }
            container interface {
              list ethernet {
                tailf:cli-suppress-mode;
                key "id";
                leaf id {
                  type ethernet-index;
                }
                leaf priority-cost {
                  mandatory true;
                  type uint8;
                }
              }
            }
            list route {
              tailf:cli-suppress-mode;
              tailf:cli-compact-syntax;
              key "ip mask";
              leaf ip {
                type union {
                  type inet:ipv4-address;
                  type inet:ipv6-address;
                }
              }
              leaf mask {
                type ipv4-mask;
              }
              // NCS expand uses statement
              leaf priority-cost {
                mandatory true;
                type uint8;
              }
              leaf distance {
                type uint8;
              }
              leaf gateway {
                type union {
                  type inet:ipv4-address;
                  type inet:ipv6-address;
                }
              }
              leaf protocol {
                type enumeration {
                  enum "any";
                  enum "static";
                  enum "dynamic";
                }
              }
            }
            list trunk {
              tailf:cli-suppress-mode;
              tailf:cli-sequence-commands {
                tailf:cli-reset-siblings;
              }
              tailf:cli-compact-syntax;
              key "id";
              leaf id {
                type uint8;
              }
              // NCS expand uses statement
              leaf priority-cost {
                mandatory true;
                type uint8;
              }
              leaf per-port-pri {
                type uint8;
              }
            }
            list vlan {
              tailf:cli-suppress-mode;
              tailf:cli-sequence-commands;
              tailf:cli-compact-syntax;
              key "id";
              leaf id {
                type vlan-index;
              }
              leaf timeout {
                type uint16;
              }
              // NCS expand uses statement
              leaf priority-cost {
                mandatory true;
                type uint8;
              }
            }
          }
        }
        list device-context {
          key "id";
          leaf id {
            type uint8;
          }
          // NCS expand uses statement
          list floating-ip {
            tailf:cli-suppress-mode;
            key "floating-ip-address";
            leaf floating-ip-address {
              tailf:cli-drop-node-name;
              type union {
                type inet:ipv4-address;
                type inet:ipv6-address;
              }
            }
          }
          leaf priority {
            type uint8;
          }
          container preempt-mode {
            choice preempt-choice {
              leaf disable {
                type empty;
              }
              leaf threshold {
                type uint8;
              }
            }
          }
          container blade-parameters {
            tailf:cli-add-mode;
            leaf priority {
              type uint8;
            }
            container tracking-options {
              tailf:cli-add-mode;
              tailf:cli-delete-when-empty;
              list gateway {
                tailf:cli-suppress-mode;
                key "address";
                leaf address {
                  type union {
                    type inet:ipv4-address;
                    type inet:ipv6-address;
                  }
                }
                // NCS expand uses statement
                leaf priority-cost {
                  mandatory true;
                  type uint8;
                }
              }
              container interface {
                list ethernet {
                  tailf:cli-suppress-mode;
                  key "id";
                  leaf id {
                    type ethernet-index;
                  }
                  leaf priority-cost {
                    mandatory true;
                    type uint8;
                  }
                }
              }
              list route {
                tailf:cli-suppress-mode;
                tailf:cli-compact-syntax;
                key "ip mask";
                leaf ip {
                  type union {
                    type inet:ipv4-address;
                    type inet:ipv6-address;
                  }
                }
                leaf mask {
                  type ipv4-mask;
                }
                // NCS expand uses statement
                leaf priority-cost {
                  mandatory true;
                  type uint8;
                }
                leaf distance {
                  type uint8;
                }
                leaf gateway {
                  type union {
                    type inet:ipv4-address;
                    type inet:ipv6-address;
                  }
                }
                leaf protocol {
                  type enumeration {
                    enum "any";
                    enum "static";
                    enum "dynamic";
                  }
                }
              }
              list trunk {
                tailf:cli-suppress-mode;
                tailf:cli-sequence-commands {
                  tailf:cli-reset-siblings;
                }
                tailf:cli-compact-syntax;
                key "id";
                leaf id {
                  type uint8;
                }
                // NCS expand uses statement
                leaf priority-cost {
                  mandatory true;
                  type uint8;
                }
                leaf per-port-pri {
                  type uint8;
                }
              }
              list vlan {
                tailf:cli-suppress-mode;
                tailf:cli-sequence-commands;
                tailf:cli-compact-syntax;
                key "id";
                leaf id {
                  type vlan-index;
                }
                leaf timeout {
                  type uint16;
                }
                // NCS expand uses statement
                leaf priority-cost {
                  mandatory true;
                  type uint8;
                }
              }
            }
          }
        }
      }
      container interface {
        list ethernet {
          tailf:cli-suppress-mode;
          tailf:cli-compact-syntax;
          key "id";
          leaf id {
            type ethernet-index;
          }
          choice vrrp-a-ethernet-choice {
            leaf both {
              type empty;
            }
            leaf no-heartbeat {
              type empty;
            }
            container router-interface {
              choice vrrp-a-r-i-choice {
                leaf no-heartbeat {
                  type empty;
                }
                leaf vlan {
                  type uint16;
                }
              }
            }
            container server-interface {
              presence "true";
              choice vrrp-a-s-i-choice {
                leaf no-heartbeat {
                  type empty;
                }
                leaf vlan {
                  type uint16;
                }
              }
            }
            leaf vlan {
              type uint16;
            }
          }
        }
        list trunk {
          tailf:cli-suppress-mode;
          tailf:cli-compact-syntax;
          key "id";
          leaf id {
            type ethernet-index;
          }
          choice vrrp-a-trunk-choice {
            leaf both {
              type empty;
            }
            leaf no-heartbeat {
              type empty;
            }
            container router-interface {
              choice vrrp-a-r-i-choice {
                leaf no-heartbeat {
                  type empty;
                }
                leaf vlan {
                  type uint16;
                }
              }
            }
            container server-interface {
              presence "true";
              choice vrrp-a-s-i-choice {
                leaf no-heartbeat {
                  type empty;
                }
                leaf vlan {
                  type uint16;
                }
              }
            }
            leaf vlan {
              type uint16;
            }
          }
        }
      }
      // NCS expand uses statement
      container preferred-session-sync-port {
        list trunk {
          tailf:cli-suppress-mode;
          tailf:cli-sequence-commands {
            tailf:cli-reset-siblings;
          }
          tailf:cli-compact-syntax;
          key "id";
          leaf id {
            type uint8;
          }
          leaf vlan {
            type uint16;
          }
        }
        list ethernet {
          tailf:cli-suppress-mode;
          tailf:cli-sequence-commands {
            tailf:cli-reset-siblings;
          }
          tailf:cli-compact-syntax;
          key "id";
          leaf id {
            type ethernet-index;
          }
          leaf vlan {
            type uint16;
          }
        }
      }
    }
  }

  grouping router-grouping {
    container router {
      list bgp {
        key "as";
        leaf as {
          type uint32;
        }
        leaf maximum-paths {
          type uint8;
        }
        list network {
          tailf:cli-suppress-mode;
          key "address";
          leaf address {
            type union {
              type inet:ipv4-address;
              type tailf:ipv4-address-and-prefix-length;
            }
          }
        }

        grouping neighbor-grouping {
          list neighbor {
            tailf:cli-suppress-mode;
            tailf:cli-delete-when-empty;
            key "ip";
            leaf ip {
              type union {
                type string;
                type inet:ipv4-address;
                type inet:ipv6-address;
              }
            }
            leaf activate {
              type boolean;
            }
            leaf description {
              tailf:cli-multi-value;
              type string;
            }
            list distribute-list {
              key "direction";
              tailf:cli-suppress-mode;
              leaf name {
                tailf:cli-prefix-key;
                tailf:cli-drop-node-name;
                type string;
              }
              leaf direction {
                type enumeration {
                  enum "in";
                  enum "out";
                }
              }
            }
            container fall-over {
              tailf:cli-compact-syntax;
              tailf:cli-sequence-commands {
                tailf:cli-reset-all-siblings;
              }
              leaf bfd {
                type empty;
              }
              leaf multihop {
                type empty;
              }
            }
            leaf maximum-prefix {
              type uint32;
            }
            leaf next-hop-self {
              type empty;
            }
            leaf password {
              type string;
            }
            container peer-group {
              presence "true";
              leaf name {
                tailf:cli-drop-node-name;
                type union {
                  type string;
                  type inet:ipv4-address;
                  type inet:ipv6-address;
                }
              }
            }
            list prefix-list {
              tailf:cli-suppress-mode;
              key "direction";
              leaf direction {
                type enumeration {
                  enum "in";
                  enum "out";
                }
              }
              leaf name {
                tailf:cli-drop-node-name;
                tailf:cli-prefix-key;
                type string;
              }
            }
            leaf remote-as {
              type uint32;
            }
            leaf remove-private-as {
              type empty;
            }
            list route-map {
              tailf:cli-compact-syntax;
              tailf:cli-suppress-mode;
              key "in-out";
              leaf in-out {
                type enumeration {
                  enum "in";
                  enum "out";
                }
              }
              leaf name {
                tailf:cli-drop-node-name;
                tailf:cli-prefix-key;
                type string;
              }
            }
            container update-source {
              leaf address {
                tailf:cli-drop-node-name;
                type union {
                  type inet:ipv4-address;
                  type inet:ipv6-address;
                }
              }
              leaf ve {
                type uint32;
              }
            }
            leaf soft-reconfiguration {
              type enumeration {
                enum "inbound";
              }
            }
            leaf shutdown {
              type boolean;
            }
          }
        }
        uses neighbor-grouping;

        grouping redistribute-grouping {
          container redistribute {
            container connected {
              presence "true";
              leaf route-map {
                type string;
              }
            }
            container static {
              presence "true";
              leaf route-map {
                type string;
              }
            }
            container ip-nat {
              presence "true";
              leaf route-map {
                type string;
              }
            }
            container vip {
              container only-flagged {
                presence "true";
              }
            }
          }
        }
        uses redistribute-grouping;
        container address-family {
          container ipv6 {
            tailf:cli-add-mode;
            leaf maximum-paths {
              type uint8;
            }
            uses neighbor-grouping;
            uses redistribute-grouping;
          }
        }
        container bgp {
          leaf log-neighbor-changes {
            type empty;
          }
          container bestpath {
            leaf as-path {
              type enumeration {
                enum "ignore";
              }
            }
          }
        }
      }
    }
  }

  grouping bfd-grouping {
    container bfd {
      leaf echo {
        type empty;
      }
      leaf enable {
        type empty;
      }
      container interval {
        tailf:cli-compact-syntax;
        tailf:cli-sequence-commands {
          tailf:cli-reset-all-siblings;
        }
        leaf start {
          tailf:cli-drop-node-name;
          type uint32;
        }
        leaf min-rx {
          type uint32;
        }
        leaf multiplier {
          type uint8;
        }
      }
    }
  }

  grouping lldp-grouping {
    container lldp {
      leaf system-name {
        type string;
      }
      leaf system-description {
        type string;
      }
      leaf-list enable {
        tailf:cli-flat-list-syntax;
        type enumeration {
          enum "rx";
          enum "tx";
        }
      }
      container management-address {
        list ipv4 {
          tailf:cli-suppress-mode;
          key "address";
          leaf address {
            type inet:ipv4-address;
          }
        }
        list ipv6 {
          tailf:cli-suppress-mode;
          key "address";
          leaf address {
            type inet:ipv6-address;
          }
        }
      }
      container notification {
        leaf interval {
          type uint32;
        }
      }
    }
  }

  grouping route-map-grouping {
    list route-map {
      tailf:cli-suppress-mode;
      key "name";
      leaf name {
        type string;
      }

      grouping permit-deny-grouping {
        leaf id {
          type uint16;
        }

        grouping match-set-grouping {
          container ip {
            container address {
              leaf address {
                tailf:cli-drop-node-name;
                type string;
              }
              leaf prefix-list {
                type string;
              }
            }
            leaf next-hop {
              type inet:ipv4-address;
            }
          }
          container ipv6 {
            container address {
              leaf address {
                tailf:cli-drop-node-name;
                type string;
              }
              leaf prefix-list {
                type string;
              }
            }
            leaf next-hop {
              type inet:ipv4-address;
            }
          }
          leaf-list community {
            tailf:cli-flat-list-syntax;
            type string;
          }
        }
        container match {
          uses match-set-grouping;
        }
        container set {
          uses match-set-grouping;
        }
      }
      list permit {
        key "id";
        uses permit-deny-grouping;
      }
      list deny {
        key "id";
        uses permit-deny-grouping;
      }
    }
  }

  grouping device-context-grouping {
    list device-context {
      key "id";
      leaf id {
        type uint8;
      }
      uses aflex-grouping;
      uses hostname-grouping;
      // NCS expand uses statement
      container interface {

        grouping lldp-interface-grouping {
          container lldp {
            container enable {
              tailf:cli-compact-syntax;
              leaf rx {
                type empty;
              }
              leaf tx {
                type empty;
              }
            }
            leaf notification {
              type enumeration {
                enum "enable";
              }
            }
            leaf tx-dot1-tlvs {
              type enumeration {
                enum "link-aggregation";
                enum "vlan";
              }
            }
          }
        }
        container management {
          tailf:cli-add-mode;
          container bcast-rate-limit {
            presence "present";
            leaf rate {
              type uint16;
            }
          }
          container ip {
            // NCS expand uses statement
            list address {
              tailf:cli-suppress-mode;
              key "address mask";
              leaf address {
                type union {
                  type inet:ipv4-address;
                  type enumeration {
                    enum "dhcp";
                  }
                }
              }
              leaf mask {
                type union {
                  type inet:ipv4-address;
                  type string;
                }
              }
            }
            leaf control-apps-use-mgmt-port {
              type empty;
            }
            leaf default-gateway {
              type inet:ipv4-address;
            }
          }
          container ipv6 {
            list address {
              key "ip";
              tailf:cli-suppress-mode;
              tailf:cli-sequence-commands {
                tailf:cli-reset-siblings;
              }
              tailf:cli-compact-syntax;
              leaf ip {
                tailf:cli-drop-node-name;
                type ipv6-prefix;
              }
              leaf link-local {
                type empty;
              }
            }
            leaf default-gateway {
              type inet:ipv6-address;
            }
          }
          // NCS expand uses statement
          container lldp {
            container enable {
              tailf:cli-compact-syntax;
              leaf rx {
                type empty;
              }
              leaf tx {
                type empty;
              }
            }
            leaf notification {
              type enumeration {
                enum "enable";
              }
            }
            leaf tx-dot1-tlvs {
              type enumeration {
                enum "link-aggregation";
                enum "vlan";
              }
            }
          }
          leaf flow-control {
            type empty;
          }
          container access-list {
            tailf:cli-sequence-commands {
              tailf:cli-reset-siblings;
            }
            tailf:cli-compact-syntax;
            leaf id {
              tailf:cli-drop-node-name;
              type uint16;
            }
            leaf in {
              must '../id' {
                tailf:xpath-root 3;
              }
              type empty;
            }
          }
          leaf enabled-disabled {
            tailf:cli-drop-node-name;
            type enumeration {
              enum "enable";
              enum "disable";
            }
          }
          leaf duplexity {
            type enumeration {
              enum "full";
              enum "half";
              enum "auto";
            }
          }
          leaf mtu {
            type uint16;
          }
          leaf speed {
            type enumeration {
              enum "10";
              enum "100";
              enum "1000";
              enum "auto";
            }
          }
        }
        list ethernet {
          key "nr";
          leaf nr {
            type ethernet-index;
          }
          leaf name {
            type string;
          }
          container ip {
            // NCS expand uses statement
            list address {
              tailf:cli-suppress-mode;
              key "address mask";
              leaf address {
                type union {
                  type inet:ipv4-address;
                  type enumeration {
                    enum "dhcp";
                  }
                }
              }
              leaf mask {
                type union {
                  type inet:ipv4-address;
                  type string;
                }
              }
            }
            leaf cache-spoofing-port {
              type empty;
            }
            leaf helper-address {
              type inet:ipv4-address;
            }
            container nat {
              leaf inside {
                type empty;
              }
              leaf outside {
                type empty;
              }
            }
            container ospf;
            container router {
              container isis {
                presence "true";
                leaf cmds {
                  tailf:cli-drop-node-name;
                  type string;
                }
              }
            }
            leaf allow-promiscuous-vip {
              type empty;
            }
            container tcp {
              leaf syn-cookie {
                type empty;
              }
            }
          }
          container ipv6 {
            container access-list {
              tailf:cli-sequence-commands {
                tailf:cli-reset-siblings;
              }
              tailf:cli-compact-syntax;
              leaf id {
                tailf:cli-drop-node-name;
                type string;
              }
              leaf in {
                must '../id' {
                  tailf:xpath-root 3;
                }
                type empty;
              }
            }
            list address {
              key "ip";
              tailf:cli-suppress-mode;
              tailf:cli-sequence-commands {
                tailf:cli-reset-all-siblings;
              }
              tailf:cli-compact-syntax;
              leaf ip {
                tailf:cli-drop-node-name;
                type ipv6-prefix;
              }
              leaf link-local {
                type empty;
                tailf:cli-break-sequence-commands;
              }
              leaf anycast {
                type empty;
                tailf:cli-break-sequence-commands;
              }
            }
            container nat {
              leaf inside {
                type empty;
              }
              leaf outside {
                type empty;
              }
            }
            container ndisc {
              container router-advertisement;
            }
            container ospf;
            container router {
              container isis {
                presence "true";
                leaf cmds {
                  tailf:cli-drop-node-name;
                  type string;
                }
              }
            }
          }
          leaf load-interval {
            type uint16;
          }
          container access-list {
            tailf:cli-sequence-commands {
              tailf:cli-reset-siblings;
            }
            tailf:cli-compact-syntax;
            leaf id {
              tailf:cli-drop-node-name;
              type uint16;
            }
            leaf in {
              must '../id' {
                tailf:xpath-root 3;
              }
              type empty;
            }
          }
          leaf state {
            tailf:cli-drop-node-name;
            type enumeration {
              enum "enable";
              enum "disable";
            }
          }
          leaf state-alt {
            tailf:cli-drop-node-name;
            type enumeration {
              enum "enable";
              enum "disable";
            }
          }
          leaf duplexity {
            type enumeration {
              enum "full";
              enum "half";
              enum "auto";
            }
          }
          leaf cpu-process {
            type empty;
          }
          leaf flow-control {
            type empty;
          }
          container icmp-rate-limit {
            tailf:cli-sequence-commands {
              tailf:cli-reset-siblings;
            }
            tailf:cli-compact-syntax;
            leaf rate {
              tailf:cli-drop-node-name;
              type uint16;
            }
            leaf lockup {
              must '../rate' {
                tailf:xpath-root 3;
              }
              type uint16;
            }
            leaf lockup-period {
              must '../lockup' {
                tailf:xpath-root 3;
              }
              tailf:cli-drop-node-name;
              type uint16;
            }
          }
          container ospf;
          container isis;
          leaf l3-vlan-fwd-disable {
            type empty;
          }
          container lacp {
            leaf port-priority {
              type uint16;
            }
            leaf timeout {
              type enumeration {
                enum "long";
                enum "short";
              }
            }
            container trunk {
              tailf:cli-sequence-commands {
                tailf:cli-reset-all-siblings;
              }
              tailf:cli-compact-syntax;
              leaf number {
                tailf:cli-drop-node-name;
                type uint16;
              }
              leaf admin-key {
                tailf:cli-break-sequence-commands;
                must '../number' {
                  tailf:xpath-root 3;
                }
                type uint16;
              }
              leaf mode {
                must '../number' {
                  tailf:xpath-root 3;
                }
                type enumeration {
                  enum "active";
                  enum "passive";
                }
              }
              leaf unidirectional-detection {
                must '../number' {
                  tailf:xpath-root 3;
                }
                type empty;
              }
            }
            container udld-timeout {
              tailf:cli-sequence-commands {
                tailf:cli-reset-all-siblings;
              }
              tailf:cli-compact-syntax;
              leaf timeout-type {
                tailf:cli-drop-node-name;
                type enumeration {
                  enum "fast";
                  enum "slow";
                }
              }
              leaf milli {
                tailf:cli-drop-node-name;
                type uint16;
              }
              leaf secs {
                tailf:cli-drop-node-name;
                type uint16;
              }
            }
          }
          // NCS expand uses statement
          container lldp {
            container enable {
              tailf:cli-compact-syntax;
              leaf rx {
                type empty;
              }
              leaf tx {
                type empty;
              }
            }
            leaf notification {
              type enumeration {
                enum "enable";
              }
            }
            leaf tx-dot1-tlvs {
              type enumeration {
                enum "link-aggregation";
                enum "vlan";
              }
            }
          }
          leaf mtu {
            type uint16;
          }
          leaf speed {
            type enumeration {
              enum "10";
              enum "100";
              enum "1000";
              enum "auto";
            }
          }
          list trunk-group-list {
            key "trunk-group-key";
            tailf:cli-drop-node-name;
            tailf:cli-compact-syntax;
            tailf:cli-sequence-commands {
              tailf:cli-reset-siblings;
            }
            leaf trunk-group-key {
              type enumeration {
                enum "trunk-group";
              }
            }
            leaf trunk-group-id {
              tailf:cli-drop-node-name;
              tailf:cli-hide-in-submode;
              mandatory true;
              type uint8;
            }
            leaf trunk-group-type {
              tailf:cli-drop-node-name;
              tailf:cli-hide-in-submode;
              type enumeration {
                enum "static";
                enum "lacp";
                enum "lacp-udld";
              }
            }
          }
        }
        list trunk {
          key "nr";
          leaf nr {
            type ethernet-index;
          }
          leaf name {
            type string;
          }
          leaf state {
            tailf:cli-drop-node-name;
            type enumeration {
              enum "enable";
              enum "disable";
            }
          }
          container icmp-rate-limit {
            tailf:cli-sequence-commands {
              tailf:cli-reset-siblings;
            }
            tailf:cli-compact-syntax;
            leaf rate {
              tailf:cli-drop-node-name;
              type uint16;
            }
            leaf lockup {
              must '../rate' {
                tailf:xpath-root 3;
              }
              type uint16;
            }
            leaf lockup-period {
              must '../lockup' {
                tailf:xpath-root 3;
              }
              tailf:cli-drop-node-name;
              type uint16;
            }
          }
          list access-list {
            tailf:cli-suppress-mode;
            key "id in-type";
            leaf id {
              type uint16;
            }
            leaf in-type {
              type enumeration {
                enum "in";
              }
            }
          }
          container ip {
            list address {
              key "ip mask";
              tailf:cli-suppress-mode;
              leaf ip {
                type inet:ipv4-address;
              }
              leaf mask {
                type ipv4-mask;
              }
            }
            leaf allow-promiscuous-vip {
              type empty;
            }
            leaf cache-spoofing-port {
              type empty;
            }
            container nat {
              leaf inside {
                type empty;
              }
              leaf outside {
                type empty;
              }
            }
          }
        }
        list loopback {
          key "nr";
          leaf nr {
            type ethernet-index;
          }
          container ip {
            // NCS expand uses statement
            list address {
              tailf:cli-suppress-mode;
              key "address mask";
              leaf address {
                type union {
                  type inet:ipv4-address;
                  type enumeration {
                    enum "dhcp";
                  }
                }
              }
              leaf mask {
                type union {
                  type inet:ipv4-address;
                  type string;
                }
              }
            }
            container router {
              choice isis-choice {
                container isis-alt {
                  tailf:cli-drop-node-name;
                  leaf isis {
                    type string;
                  }
                }
                leaf isis {
                  type empty;
                }
              }
            }
          }
          container icmp-rate-limit {
            tailf:cli-sequence-commands {
              tailf:cli-reset-siblings;
            }
            tailf:cli-compact-syntax;
            leaf rate {
              tailf:cli-drop-node-name;
              type uint16;
            }
            leaf lockup {
              must '../rate' {
                tailf:xpath-root 3;
              }
              type uint16;
            }
            leaf lockup-period {
              tailf:cli-drop-node-name;
              must '../lockup' {
                tailf:xpath-root 3;
              }
              type uint16;
            }
          }
          leaf state {
            tailf:cli-drop-node-name;
            type enumeration {
              enum "enable";
              enum "disable";
            }
          }
        }
        list ve {
          key "id";
          leaf id {
            type vlan-index;
          }
          leaf name {
            type string;
          }
          container bfd {
            container echo {
              presence "true";
            }
          }
          container icmp-rate-limit {
            tailf:cli-sequence-commands {
              tailf:cli-reset-siblings;
            }
            tailf:cli-compact-syntax;
            leaf rate {
              tailf:cli-drop-node-name;
              type uint16;
            }
            leaf lockup {
              must '../rate' {
                tailf:xpath-root 3;
              }
              type uint16;
            }
            leaf lockup-period {
              tailf:cli-drop-node-name;
              must '../lockup' {
                tailf:xpath-root 3;
              }
              type uint16;
            }
          }
          container access-list {
            tailf:cli-sequence-commands {
              tailf:cli-reset-siblings;
            }
            tailf:cli-compact-syntax;
            leaf id {
              tailf:cli-drop-node-name;
              type uint16;
            }
            leaf in {
              must '../id' {
                tailf:xpath-root 3;
              }
              type empty;
            }
          }
          leaf l3-vlan-fwd-disable {
            type empty;
          }
          container ip {
            leaf allow-promiscuous-vip {
              type empty;
            }
            leaf cache-spoofing-port {
              type empty;
            }
            leaf helper-address {
              type inet:ipv4-address;
            }
            container nat {
              leaf inside {
                type empty;
              }
              leaf outside {
                type empty;
              }
            }
            container ospf;
            container router {
              container isis {
                presence "true";
                leaf cmds {
                  tailf:cli-drop-node-name;
                  type string;
                }
              }
            }
            container tcp {
              leaf syn-cookie {
                type empty;
              }
            }
            // NCS expand uses statement
            list address {
              tailf:cli-suppress-mode;
              key "address mask";
              leaf address {
                type union {
                  type inet:ipv4-address;
                  type enumeration {
                    enum "dhcp";
                  }
                }
              }
              leaf mask {
                type union {
                  type inet:ipv4-address;
                  type string;
                }
              }
            }
          }
          container ipv6 {
            container access-list {
              tailf:cli-sequence-commands {
                tailf:cli-reset-siblings;
              }
              tailf:cli-compact-syntax;
              leaf id {
                tailf:cli-drop-node-name;
                type string;
              }
              leaf in {
                must '../id' {
                  tailf:xpath-root 3;
                }
                type empty;
              }
            }
            container nat {
              leaf inside {
                type empty;
              }
              leaf outside {
                type empty;
              }
            }
            container ndisc {
              container router-advertisement;
            }
            container ospf;
            container router {
              container isis {
                presence "true";
                leaf cmds {
                  tailf:cli-drop-node-name;
                  type string;
                }
              }
            }
            list address {
              key "ip";
              tailf:cli-suppress-mode;
              tailf:cli-sequence-commands {
                tailf:cli-reset-all-siblings;
              }
              tailf:cli-compact-syntax;
              leaf ip {
                tailf:cli-drop-node-name;
                type ipv6-prefix;
              }
              leaf link-local {
                type empty;
                tailf:cli-break-sequence-commands;
              }
              leaf anycast {
                type empty;
                tailf:cli-break-sequence-commands;
              }
            }
          }
          leaf mtu {
            type uint16;
          }
          leaf state {
            tailf:cli-drop-node-name;
            type enumeration {
              enum "enable";
              enum "disable";
            }
          }
          container isis;
          container ospf;
        }
      }
      container ip {
        uses ip-prefix-list-grouping;
        uses ip-route-grouping;
      }
      container ipv6 {
        uses ipv6-route-grouping;
      }
      uses bfd-grouping;
      uses clock-grouping;
      uses lldp-grouping;
      // NCS expand uses statement
      container vcs {
        leaf state {
          tailf:cli-drop-node-name;
          type enumeration {
            enum "enable";
            enum "disable";
          }
        }
        list device {
          key "id";
          leaf id {
            type uint8;
          }
          leaf priority {
            type uint8;
          }
          container interfaces {
            leaf management {
              type empty;
            }
            list ethernet {
              tailf:cli-suppress-mode;
              key "id";
              leaf id {
                type uint8;
              }
            }
            list trunk {
              tailf:cli-suppress-mode;
              key "id";
              leaf id {
                type uint8;
              }
            }
            list ve {
              tailf:cli-suppress-mode;
              key "id";
              leaf id {
                type uint16;
              }
            }
          }
          leaf enable {
            type empty;
          }
        }
        list floating-ip {
          tailf:cli-suppress-mode;
          tailf:cli-delete-when-empty;
          tailf:cli-compact-syntax;
          key "floating-ip-address";
          leaf floating-ip-address {
            tailf:cli-drop-node-name;
            type inet:ipv4-address;
          }
          leaf mask {
            tailf:cli-drop-node-name;
            type ipv4-mask;
          }
        }
        leaf ssl-enable {
          type empty;
        }
        leaf failure-retry-count {
          type union {
            type enumeration {
              enum "forever";
            }
            type uint8;
          }
        }
      }
      uses tftp-grouping;
      uses enable-management-grouping;
      uses disable-management-grouping;
      uses lacp-grouping;
      uses route-map-grouping;
      uses ve-stats-grouping;
      uses bgp-grouping;
      uses router-grouping;
      uses timezone-grouping;
      uses sflow-grouping;
      container vrrp-a {
        // NCS expand uses statement
        container preferred-session-sync-port {
          list trunk {
            tailf:cli-suppress-mode;
            tailf:cli-sequence-commands {
              tailf:cli-reset-siblings;
            }
            tailf:cli-compact-syntax;
            key "id";
            leaf id {
              type uint8;
            }
            leaf vlan {
              type uint16;
            }
          }
          list ethernet {
            tailf:cli-suppress-mode;
            tailf:cli-sequence-commands {
              tailf:cli-reset-siblings;
            }
            tailf:cli-compact-syntax;
            key "id";
            leaf id {
              type ethernet-index;
            }
            leaf vlan {
              type uint16;
            }
          }
        }
      }
    }
  }

  grouping vcs-grouping {
    container vcs {
      leaf state {
        tailf:cli-drop-node-name;
        type enumeration {
          enum "enable";
          enum "disable";
        }
      }
      list device {
        key "id";
        leaf id {
          type uint8;
        }
        leaf priority {
          type uint8;
        }
        container interfaces {
          leaf management {
            type empty;
          }
          list ethernet {
            tailf:cli-suppress-mode;
            key "id";
            leaf id {
              type uint8;
            }
          }
          list trunk {
            tailf:cli-suppress-mode;
            key "id";
            leaf id {
              type uint8;
            }
          }
          list ve {
            tailf:cli-suppress-mode;
            key "id";
            leaf id {
              type uint16;
            }
          }
        }
        leaf enable {
          type empty;
        }
      }
      list floating-ip {
        tailf:cli-suppress-mode;
        tailf:cli-delete-when-empty;
        tailf:cli-compact-syntax;
        key "floating-ip-address";
        leaf floating-ip-address {
          tailf:cli-drop-node-name;
          type inet:ipv4-address;
        }
        leaf mask {
          tailf:cli-drop-node-name;
          type ipv4-mask;
        }
      }
      leaf ssl-enable {
        type empty;
      }
      leaf failure-retry-count {
        type union {
          type enumeration {
            enum "forever";
          }
          type uint8;
        }
      }
    }
  }

  grouping system-grouping {
    container system {
      container cpu-load-sharing {
        container cpu-usage {
          tailf:cli-compact-syntax;
          leaf low {
            type uint32;
          }
          leaf high {
            type uint32;
          }
        }
      }
      leaf module-ctrl-cpu {
        type enumeration {
          enum "high";
          enum "low";
          enum "medium";
        }
      }
      leaf glid {
        type uint16;
      }
      container all-vlan-limit {
        leaf bcast {
          type uint16;
        }
        leaf ipmcast {
          type uint16;
        }
        leaf mcast {
          type uint16;
        }
        leaf unknown-ucast {
          type uint16;
        }
      }
      container per-vlan-limit {
        leaf bcast {
          type uint16;
        }
        leaf ipmcast {
          type uint16;
        }
        leaf mcast {
          type uint16;
        }
        leaf unknown-ucast {
          type uint16;
        }
      }
      container resource-usage {
        uses resource-usage-grouping;
        list template {
          key "name";
          leaf name {
            type string;
          }
          container system-resources {
            tailf:cli-add-mode;
            leaf bw-limit {
              type uint16;
            }
            leaf ssl-throughput-limit {
              type uint16;
            }
            leaf l4cps-limit {
              type uint32;
            }
            leaf natcps-limit {
              type uint32;
            }
            leaf l7cps-limit {
              type uint32;
            }
            leaf sslcps-limit {
              type uint32;
            }
            leaf concurrent-session-limit {
              type uint32;
            }
          }
          container app-resources {
            tailf:cli-add-mode;
            leaf gslb-device-count {
              type uint16;
            }
            leaf gslb-geo-location-count {
              type uint32;
            }
            leaf gslb-ip-list-count {
              type uint16;
            }
            leaf gslb-policy-count {
              type uint16;
            }
            leaf gslb-service-count {
              type uint16;
            }
            leaf gslb-service-ip-count {
              type uint16;
            }
            leaf gslb-service-port-count {
              type uint16;
            }
            leaf gslb-site-count {
              type uint16;
            }
            leaf gslb-svc-group-count {
              type uint16;
            }
            leaf gslb-template-count {
              type uint16;
            }
            leaf gslb-zone-count {
              type uint16;
            }
          }
        }
      }
      container template {
        leaf policy {
          type string;
        }
      }
      container trunk {
        container load-balance {
          tailf:cli-add-mode;
          leaf layer-2 {
            type enumeration {
              enum "use-l3";
              enum "use-l4";
            }
          }
        }
      }
      leaf ve-mac-scheme {
        type enumeration {
          enum "hash-based";
          enum "round-robin";
          enum "system-mac";
        }
      }
      container apps-global {
        leaf log-session-on-established {
          type empty;
        }
        leaf msl-time {
          type uint8;
        }
      }
    }
  }

  grouping ve-stats-grouping {
    leaf ve-stats {
      type enumeration {
        enum "enable";
      }
    }
  }

  grouping partition-grouping {
    list partition {
      key "name";
      leaf name {
        type string;
      }
      leaf network-partition {
        tailf:cli-hide-in-submode;
        type empty;
      }
      leaf id {
        tailf:cli-hide-in-submode;
        type uint8;
      }
      leaf application-type {
        tailf:cli-hide-in-submode;
        type enumeration {
          enum "adc";
          enum "cgnv6";
        }
      }
      leaf template {
        type string;
      }
    }
  }

  grouping partition-group-grouping {
    list partition-group {
      key "name";
      leaf name {
        type string;
      }
      list member {
        tailf:cli-suppress-mode;
        key "partition-name";
        leaf partition-name {
          type string;
        }
      }
    }
  }

  grouping access-list-grouping {
    list access-list {
      tailf:cli-suppress-mode;
      tailf:cli-delete-when-empty;
      key "id";
      leaf id {
        type uint16;
      }
      list rules {
        ordered-by user;
        tailf:cli-suppress-mode;
        tailf:cli-drop-node-name;
        key "txt";
        leaf txt {
          tailf:cli-multi-word-key;
          type string;
        }
      }
    }
  }

  grouping tftp-grouping {
    container tftp {
      leaf blksize {
        type uint16;
      }
    }
  }

  grouping stats-data-disable-grouping {
    leaf stats-data-disable {
      type empty;
    }
  }

  grouping syn-cookie-grouping {
    container syn-cookie {
      tailf:cli-compact-syntax;
      tailf:cli-sequence-commands {
        tailf:cli-reset-siblings;
      }
      leaf on-threshold {
        type uint32;
      }
      leaf off-threshold {
        type uint32;
      }
    }
  }

  grouping enable-management-grouping {
    container enable-management {
      container service {
        tailf:cli-compact-syntax;

        grouping enable-management-content-grouping {
          leaf-list ethernet {
            tailf:cli-range-list-syntax;
            type uint8;
          }
          list acl {
            key "id";
            leaf id {
              type uint16;
            }
          }
          list acl-v4 {
            key "id";
            leaf id {
              type uint16;
            }
          }
          leaf-list ve {
            tailf:cli-range-list-syntax;
            type uint32;
          }
        }
        container ssh {
          tailf:cli-add-mode;
          uses enable-management-content-grouping;
        }
        container ssh-alt {
          tailf:alt-name "ssh";
          tailf:cli-compact-syntax;
          leaf management {
            type empty;
          }
          uses enable-management-content-grouping;
        }
        container telnet {
          tailf:cli-add-mode;
          uses enable-management-content-grouping;
        }
        container telnet-alt {
          tailf:alt-name "telnet";
          tailf:cli-compact-syntax;
          leaf management {
            type empty;
          }
          uses enable-management-content-grouping;
        }
        container http {
          tailf:cli-add-mode;
          uses enable-management-content-grouping;
        }
        container http-alt {
          tailf:alt-name "http";
          tailf:cli-compact-syntax;
          leaf management {
            type empty;
          }
          uses enable-management-content-grouping;
        }
        container https {
          tailf:cli-add-mode;
          uses enable-management-content-grouping;
        }
        container https-alt {
          tailf:alt-name "https";
          tailf:cli-compact-syntax;
          leaf management {
            type empty;
          }
          uses enable-management-content-grouping;
        }
        container snmp {
          tailf:cli-add-mode;
          uses enable-management-content-grouping;
        }
        container snmp-alt {
          tailf:alt-name "snmp";
          tailf:cli-compact-syntax;
          leaf management {
            type empty;
          }
          uses enable-management-content-grouping;
        }
      }
    }
  }

  grouping disable-management-grouping {
    container disable-management {
      container service {
        container http {
          presence "present";
          leaf management {
            type empty;
          }
        }
      }
    }
  }

  grouping monitor-grouping {
    container monitor {
      leaf disk {
        type uint8;
      }
      leaf memory {
        type uint8;
      }
      leaf buffer-drop {
        type uint16;
      }
      leaf buffer-usage {
        type uint32;
      }
    }
  }

  grouping extended-stats-grouping {
    leaf extended-stats {
      type empty;
    }
  }

  grouping admin-grouping {
    container admin {
      container lockout {
        leaf enable {
          type empty;
        }
      }
    }
  }

  grouping zone-grouping {
    list zone {
      key "name";
      leaf name {
        type string;
      }
      container interface {
        leaf-list ethernet {
          tailf:cli-range-list-syntax;
          type ethernet-index;
        }
      }
    }
  }

  grouping object-grouping {
    container object {
      list network {
        key "name";
        leaf name {
          type string;
        }
        leaf ipv4-address {
          tailf:cli-drop-node-name;
          type tailf:ipv4-address-and-prefix-length;
        }
        leaf ipv6-address {
          tailf:cli-drop-node-name;
          type tailf:ipv6-address-and-prefix-length;
        }
      }
    }
  }

  grouping icmp-grouping {
    container icmp {
      list type {
        tailf:cli-suppress-mode;
        key "id";
        leaf id {
          type enumeration {
            enum "any-type";
            enum "echo-reply";
            enum "echo-request";
            enum "info-reply";
            enum "info-request";
            enum "mask-reply";
            enum "mask-request";
            enum "parameter-problem";
            enum "redirect";
            enum "source-quench";
            enum "time-exceeded";
            enum "timestamp";
            enum "timestamp-reply";
            enum "dest-unreachable";
          }
        }
      }
    }
  }

  grouping object-group-grouping {
    container object-group {
      list service {
        key "service-name";
        leaf service-name {
          type string;
        }
        leaf description {
          type string;
        }
        list tcp {
          tailf:cli-suppress-mode;
          key "op port";
          leaf op {
            type enumeration {
              enum "eq";
              enum "gt";
              enum "lt";
              enum "range";
              enum "source";
            }
          }
          leaf port {
            type uint32;
          }
        }
        uses icmp-grouping;
      }
      list network {
        key "name";
        leaf name {
          type string;
        }
        leaf fw {
          tailf:cli-hide-in-submode;
          type enumeration {
            enum "v4";
            enum "v6";
          }
        }
        leaf description {
          type string;
        }
        leaf any {
          type empty;
        }
        leaf host {
          type inet:ipv4-address;
        }
        leaf ipv6-address {
          tailf:cli-drop-node-name;
          type tailf:ipv6-address-and-prefix-length;
        }
      }
    }
  }

  grouping rule-set-grouping {
    list rule-set {
      key "rule-name";
      leaf rule-name {
        type string;
      }
      list rule {
        key "name";
        leaf name {
          type string;
        }
        leaf action {
          type enumeration {
            enum "permit";
            enum "deny";
            enum "reset";
          }
        }

        grouping source-dest-grouping {
          list object {
            key "name";
            leaf name {
              type string;
            }
          }
          list object-group {
            key "name";
            leaf name {
              type string;
            }
          }
          leaf zone {
            type string;
          }
        }
        container source {
          uses source-dest-grouping;
        }
        container dest {
          uses source-dest-grouping;
        }
        container service {
          leaf any {
            type empty;
          }
          uses icmp-grouping;
          leaf object-group {
            type string;
          }
        }
      }
    }
  }

  grouping fw-grouping {
    container fw {
      leaf active-rule-set {
        type string;
      }
    }
  }

  grouping enable-core-grouping {
    leaf enable-core {
      type enumeration {
        enum "system";
        enum "a10";
      }
    }
  }

  augment "/ncs:devices/ncs:device/ncs:rpc" {
    container rpc-slb-ssl-delete {
      tailf:ncs-device-type "cli-ned";
      tailf:display-when "not(../../ncs:module) or ../../ncs:module[ncs:name='netsim-ned-a10-acos']";
      tailf:action slb-ssl-delete {
        tailf:actionpoint ncsproxy {
          tailf:internal;
        }
        input {
          leaf-list args {
            tailf:cli-drop-node-name;
            tailf:cli-flat-list-syntax;
            type string;
          }
        }
        output {
          leaf result {
            type string;
          }
        }
      }
    }
  }
  augment "/ncs:devices/ncs:device-group/ncs:ned-id/ncs:rpc" {
    container rpc-slb-ssl-delete {
      tailf:ncs-device-type "cli-ned";
      tailf:display-when "../../ncs:id = 'a10-acos-netsim-cli-1.0:a10-acos-netsim-cli-1.0'";
      tailf:action slb-ssl-delete {
        tailf:actionpoint ncsproxy {
          tailf:internal;
        }
        input {
          leaf-list args {
            tailf:cli-drop-node-name;
            tailf:cli-flat-list-syntax;
            type string;
          }
        }
        output {
          container "device" {
            leaf "name" {
              type string;
            }
            leaf "info" {
              type string;
            }
            container "result" {
              leaf result {
                type string;
              }
            }
          }
        }
      }
    }
  }
  augment "/ncs:devices/ncs:device/ncs:rpc" {
    container rpc-slb-ssl-load {
      tailf:ncs-device-type "cli-ned";
      tailf:display-when "not(../../ncs:module) or ../../ncs:module[ncs:name='netsim-ned-a10-acos']";
      tailf:action slb-ssl-load {
        tailf:actionpoint ncsproxy {
          tailf:internal;
        }
        input {
          leaf-list args {
            tailf:cli-drop-node-name;
            tailf:cli-flat-list-syntax;
            type string;
          }
        }
        output {
          leaf result {
            type string;
          }
        }
      }
    }
  }
  augment "/ncs:devices/ncs:device-group/ncs:ned-id/ncs:rpc" {
    container rpc-slb-ssl-load {
      tailf:ncs-device-type "cli-ned";
      tailf:display-when "../../ncs:id = 'a10-acos-netsim-cli-1.0:a10-acos-netsim-cli-1.0'";
      tailf:action slb-ssl-load {
        tailf:actionpoint ncsproxy {
          tailf:internal;
        }
        input {
          leaf-list args {
            tailf:cli-drop-node-name;
            tailf:cli-flat-list-syntax;
            type string;
          }
        }
        output {
          container "device" {
            leaf "name" {
              type string;
            }
            leaf "info" {
              type string;
            }
            container "result" {
              leaf result {
                type string;
              }
            }
          }
        }
      }
    }
  }
  augment "/ncs:devices/ncs:device/ncs:rpc" {
    container rpc-backup {
      tailf:ncs-device-type "cli-ned";
      tailf:display-when "not(../../ncs:module) or ../../ncs:module[ncs:name='netsim-ned-a10-acos']";
      tailf:action backup {
        tailf:actionpoint ncsproxy {
          tailf:internal;
        }
        input {
          leaf-list args {
            tailf:cli-drop-node-name;
            tailf:cli-flat-list-syntax;
            type string;
          }
        }
        output {
          leaf result {
            type string;
          }
        }
      }
    }
  }
  augment "/ncs:devices/ncs:device-group/ncs:ned-id/ncs:rpc" {
    container rpc-backup {
      tailf:ncs-device-type "cli-ned";
      tailf:display-when "../../ncs:id = 'a10-acos-netsim-cli-1.0:a10-acos-netsim-cli-1.0'";
      tailf:action backup {
        tailf:actionpoint ncsproxy {
          tailf:internal;
        }
        input {
          leaf-list args {
            tailf:cli-drop-node-name;
            tailf:cli-flat-list-syntax;
            type string;
          }
        }
        output {
          container "device" {
            leaf "name" {
              type string;
            }
            leaf "info" {
              type string;
            }
            container "result" {
              leaf result {
                type string;
              }
            }
          }
        }
      }
    }
  }
  augment "/ncs:devices/ncs:device/ncs:config" {
    leaf os-major {
      tailf:ncs-device-type "cli-ned";
      tailf:display-when "not(../../ncs:module) or ../../ncs:module[ncs:name='netsim-ned-a10-acos']";
      type uint32;
    }
    leaf os-minor {
      tailf:ncs-device-type "cli-ned";
      tailf:display-when "not(../../ncs:module) or ../../ncs:module[ncs:name='netsim-ned-a10-acos']";
      type uint32;
    }
    uses ip-list-grouping {
      refine ip-list {
        tailf:ncs-device-type "cli-ned";
        tailf:display-when "not(../ncs:module) or ../ncs:module[ncs:name='netsim-ned-a10-acos']";
      }
    }
    uses cgnv6-grouping {
      refine cgnv6 {
        tailf:ncs-device-type "cli-ned";
        tailf:display-when "not(../../ncs:module) or ../../ncs:module[ncs:name='netsim-ned-a10-acos']";
      }
    }
    uses sflow-grouping {
      refine sflow {
        tailf:ncs-device-type "cli-ned";
        tailf:display-when "not(../../ncs:module) or ../../ncs:module[ncs:name='netsim-ned-a10-acos']";
      }
    }
    uses accounting-grouping {
      refine accounting {
        tailf:ncs-device-type "cli-ned";
        tailf:display-when "not(../../ncs:module) or ../../ncs:module[ncs:name='netsim-ned-a10-acos']";
      }
    }
    uses acos-events-grouping {
      refine acos-events {
        tailf:ncs-device-type "cli-ned";
        tailf:display-when "not(../../ncs:module) or ../../ncs:module[ncs:name='netsim-ned-a10-acos']";
      }
    }
    uses authorization-grouping {
      refine authorization {
        tailf:ncs-device-type "cli-ned";
        tailf:display-when "not(../../ncs:module) or ../../ncs:module[ncs:name='netsim-ned-a10-acos']";
      }
    }
    uses bgp-grouping {
      refine bgp {
        tailf:ncs-device-type "cli-ned";
        tailf:display-when "not(../../ncs:module) or ../../ncs:module[ncs:name='netsim-ned-a10-acos']";
      }
    }
    uses lacp-grouping {
      refine lacp {
        tailf:ncs-device-type "cli-ned";
        tailf:display-when "not(../../ncs:module) or ../../ncs:module[ncs:name='netsim-ned-a10-acos']";
      }
    }
    uses aflex-grouping {
      refine aflex {
        tailf:ncs-device-type "cli-ned";
        tailf:display-when "not(../ncs:module) or ../ncs:module[ncs:name='netsim-ned-a10-acos']";
      }
    }
    container EXEC {
      tailf:ncs-device-type "cli-ned";
      tailf:display-when "not(../../ncs:module) or ../../ncs:module[ncs:name='netsim-ned-a10-acos']";
      tailf:cli-drop-node-name;
    }
    uses system-jumbo-global-grouping {
      refine system-jumbo-global {
        tailf:ncs-device-type "cli-ned";
        tailf:display-when "not(../../ncs:module) or ../../ncs:module[ncs:name='netsim-ned-a10-acos']";
      }
    }
    uses hostname-grouping {
      refine hostname {
        tailf:ncs-device-type "cli-ned";
        tailf:display-when "not(../../ncs:module) or ../../ncs:module[ncs:name='netsim-ned-a10-acos']";
      }
    }
    uses hd-monitor-grouping {
      refine hd-monitor {
        tailf:ncs-device-type "cli-ned";
        tailf:display-when "not(../../ncs:module) or ../../ncs:module[ncs:name='netsim-ned-a10-acos']";
      }
    }
    uses timezone-nodst-grouping {
      refine timezone-nodst {
        tailf:ncs-device-type "cli-ned";
        tailf:display-when "not(../../ncs:module) or ../../ncs:module[ncs:name='netsim-ned-a10-acos']";
      }
    }
    uses clock-grouping {
      refine clock {
        tailf:ncs-device-type "cli-ned";
        tailf:display-when "not(../../ncs:module) or ../../ncs:module[ncs:name='netsim-ned-a10-acos']";
      }
    }
    uses ntp-grouping {
      refine ntp {
        tailf:ncs-device-type "cli-ned";
        tailf:display-when "not(../../ncs:module) or ../../ncs:module[ncs:name='netsim-ned-a10-acos']";
      }
    }
    uses netflow-grouping {
      refine netflow {
        tailf:ncs-device-type "cli-ned";
        tailf:display-when "not(../../ncs:module) or ../../ncs:module[ncs:name='netsim-ned-a10-acos']";
      }
    }
    uses trunk-grouping {
      refine trunk {
        tailf:ncs-device-type "cli-ned";
        tailf:display-when "not(../ncs:module) or ../ncs:module[ncs:name='netsim-ned-a10-acos']";
      }
    }
    uses class-list-grouping {
      refine class-list {
        tailf:ncs-device-type "cli-ned";
        tailf:display-when "not(../ncs:module) or ../ncs:module[ncs:name='netsim-ned-a10-acos']";
      }
    }
    uses class-list-group-grouping {
      refine class-list-group {
        tailf:ncs-device-type "cli-ned";
        tailf:display-when "not(../ncs:module) or ../ncs:module[ncs:name='netsim-ned-a10-acos']";
      }
    }
    uses tacacs-server-grouping {
      refine tacacs-server {
        tailf:ncs-device-type "cli-ned";
        tailf:display-when "not(../../ncs:module) or ../../ncs:module[ncs:name='netsim-ned-a10-acos']";
      }
    }
    uses radius-server-grouping {
      refine radius-server {
        tailf:ncs-device-type "cli-ned";
        tailf:display-when "not(../../ncs:module) or ../../ncs:module[ncs:name='netsim-ned-a10-acos']";
      }
    }
    uses authentication-grouping {
      refine authentication {
        tailf:ncs-device-type "cli-ned";
        tailf:display-when "not(../../ncs:module) or ../../ncs:module[ncs:name='netsim-ned-a10-acos']";
      }
    }
    // NCS expand uses statement
    container interface {
      tailf:ncs-device-type "cli-ned";
      tailf:display-when "not(../../ncs:module) or ../../ncs:module[ncs:name='netsim-ned-a10-acos']";

      grouping lldp-interface-grouping {
        container lldp {
          container enable {
            tailf:cli-compact-syntax;
            leaf rx {
              type empty;
            }
            leaf tx {
              type empty;
            }
          }
          leaf notification {
            type enumeration {
              enum "enable";
            }
          }
          leaf tx-dot1-tlvs {
            type enumeration {
              enum "link-aggregation";
              enum "vlan";
            }
          }
        }
      }
      container management {
        tailf:cli-add-mode;
        container bcast-rate-limit {
          presence "present";
          leaf rate {
            type uint16;
          }
        }
        container ip {
          // NCS expand uses statement
          list address {
            tailf:cli-suppress-mode;
            key "address mask";
            leaf address {
              type union {
                type inet:ipv4-address;
                type enumeration {
                  enum "dhcp";
                }
              }
            }
            leaf mask {
              type union {
                type inet:ipv4-address;
                type string;
              }
            }
          }
          leaf control-apps-use-mgmt-port {
            type empty;
          }
          leaf default-gateway {
            type inet:ipv4-address;
          }
        }
        container ipv6 {
          list address {
            key "ip";
            tailf:cli-suppress-mode;
            tailf:cli-sequence-commands {
              tailf:cli-reset-siblings;
            }
            tailf:cli-compact-syntax;
            leaf ip {
              tailf:cli-drop-node-name;
              type ipv6-prefix;
            }
            leaf link-local {
              type empty;
            }
          }
          leaf default-gateway {
            type inet:ipv6-address;
          }
        }
        // NCS expand uses statement
        container lldp {
          container enable {
            tailf:cli-compact-syntax;
            leaf rx {
              type empty;
            }
            leaf tx {
              type empty;
            }
          }
          leaf notification {
            type enumeration {
              enum "enable";
            }
          }
          leaf tx-dot1-tlvs {
            type enumeration {
              enum "link-aggregation";
              enum "vlan";
            }
          }
        }
        leaf flow-control {
          type empty;
        }
        container access-list {
          tailf:cli-sequence-commands {
            tailf:cli-reset-siblings;
          }
          tailf:cli-compact-syntax;
          leaf id {
            tailf:cli-drop-node-name;
            type uint16;
          }
          leaf in {
            must '../id' {
              tailf:xpath-root 3;
            }
            type empty;
          }
        }
        leaf enabled-disabled {
          tailf:cli-drop-node-name;
          type enumeration {
            enum "enable";
            enum "disable";
          }
        }
        leaf duplexity {
          type enumeration {
            enum "full";
            enum "half";
            enum "auto";
          }
        }
        leaf mtu {
          type uint16;
        }
        leaf speed {
          type enumeration {
            enum "10";
            enum "100";
            enum "1000";
            enum "auto";
          }
        }
      }
      list ethernet {
        key "nr";
        leaf nr {
          type ethernet-index;
        }
        leaf name {
          type string;
        }
        container ip {
          // NCS expand uses statement
          list address {
            tailf:cli-suppress-mode;
            key "address mask";
            leaf address {
              type union {
                type inet:ipv4-address;
                type enumeration {
                  enum "dhcp";
                }
              }
            }
            leaf mask {
              type union {
                type inet:ipv4-address;
                type string;
              }
            }
          }
          leaf cache-spoofing-port {
            type empty;
          }
          leaf helper-address {
            type inet:ipv4-address;
          }
          container nat {
            leaf inside {
              type empty;
            }
            leaf outside {
              type empty;
            }
          }
          container ospf;
          container router {
            container isis {
              presence "true";
              leaf cmds {
                tailf:cli-drop-node-name;
                type string;
              }
            }
          }
          leaf allow-promiscuous-vip {
            type empty;
          }
          container tcp {
            leaf syn-cookie {
              type empty;
            }
          }
        }
        container ipv6 {
          container access-list {
            tailf:cli-sequence-commands {
              tailf:cli-reset-siblings;
            }
            tailf:cli-compact-syntax;
            leaf id {
              tailf:cli-drop-node-name;
              type string;
            }
            leaf in {
              must '../id' {
                tailf:xpath-root 3;
              }
              type empty;
            }
          }
          list address {
            key "ip";
            tailf:cli-suppress-mode;
            tailf:cli-sequence-commands {
              tailf:cli-reset-all-siblings;
            }
            tailf:cli-compact-syntax;
            leaf ip {
              tailf:cli-drop-node-name;
              type ipv6-prefix;
            }
            leaf link-local {
              type empty;
              tailf:cli-break-sequence-commands;
            }
            leaf anycast {
              type empty;
              tailf:cli-break-sequence-commands;
            }
          }
          container nat {
            leaf inside {
              type empty;
            }
            leaf outside {
              type empty;
            }
          }
          container ndisc {
            container router-advertisement;
          }
          container ospf;
          container router {
            container isis {
              presence "true";
              leaf cmds {
                tailf:cli-drop-node-name;
                type string;
              }
            }
          }
        }
        leaf load-interval {
          type uint16;
        }
        container access-list {
          tailf:cli-sequence-commands {
            tailf:cli-reset-siblings;
          }
          tailf:cli-compact-syntax;
          leaf id {
            tailf:cli-drop-node-name;
            type uint16;
          }
          leaf in {
            must '../id' {
              tailf:xpath-root 3;
            }
            type empty;
          }
        }
        leaf state {
          tailf:cli-drop-node-name;
          type enumeration {
            enum "enable";
            enum "disable";
          }
        }
        leaf state-alt {
          tailf:cli-drop-node-name;
          type enumeration {
            enum "enable";
            enum "disable";
          }
        }
        leaf duplexity {
          type enumeration {
            enum "full";
            enum "half";
            enum "auto";
          }
        }
        leaf cpu-process {
          type empty;
        }
        leaf flow-control {
          type empty;
        }
        container icmp-rate-limit {
          tailf:cli-sequence-commands {
            tailf:cli-reset-siblings;
          }
          tailf:cli-compact-syntax;
          leaf rate {
            tailf:cli-drop-node-name;
            type uint16;
          }
          leaf lockup {
            must '../rate' {
              tailf:xpath-root 3;
            }
            type uint16;
          }
          leaf lockup-period {
            must '../lockup' {
              tailf:xpath-root 3;
            }
            tailf:cli-drop-node-name;
            type uint16;
          }
        }
        container ospf;
        container isis;
        leaf l3-vlan-fwd-disable {
          type empty;
        }
        container lacp {
          leaf port-priority {
            type uint16;
          }
          leaf timeout {
            type enumeration {
              enum "long";
              enum "short";
            }
          }
          container trunk {
            tailf:cli-sequence-commands {
              tailf:cli-reset-all-siblings;
            }
            tailf:cli-compact-syntax;
            leaf number {
              tailf:cli-drop-node-name;
              type uint16;
            }
            leaf admin-key {
              tailf:cli-break-sequence-commands;
              must '../number' {
                tailf:xpath-root 3;
              }
              type uint16;
            }
            leaf mode {
              must '../number' {
                tailf:xpath-root 3;
              }
              type enumeration {
                enum "active";
                enum "passive";
              }
            }
            leaf unidirectional-detection {
              must '../number' {
                tailf:xpath-root 3;
              }
              type empty;
            }
          }
          container udld-timeout {
            tailf:cli-sequence-commands {
              tailf:cli-reset-all-siblings;
            }
            tailf:cli-compact-syntax;
            leaf timeout-type {
              tailf:cli-drop-node-name;
              type enumeration {
                enum "fast";
                enum "slow";
              }
            }
            leaf milli {
              tailf:cli-drop-node-name;
              type uint16;
            }
            leaf secs {
              tailf:cli-drop-node-name;
              type uint16;
            }
          }
        }
        // NCS expand uses statement
        container lldp {
          container enable {
            tailf:cli-compact-syntax;
            leaf rx {
              type empty;
            }
            leaf tx {
              type empty;
            }
          }
          leaf notification {
            type enumeration {
              enum "enable";
            }
          }
          leaf tx-dot1-tlvs {
            type enumeration {
              enum "link-aggregation";
              enum "vlan";
            }
          }
        }
        leaf mtu {
          type uint16;
        }
        leaf speed {
          type enumeration {
            enum "10";
            enum "100";
            enum "1000";
            enum "auto";
          }
        }
        list trunk-group-list {
          key "trunk-group-key";
          tailf:cli-drop-node-name;
          tailf:cli-compact-syntax;
          tailf:cli-sequence-commands {
            tailf:cli-reset-siblings;
          }
          leaf trunk-group-key {
            type enumeration {
              enum "trunk-group";
            }
          }
          leaf trunk-group-id {
            tailf:cli-drop-node-name;
            tailf:cli-hide-in-submode;
            mandatory true;
            type uint8;
          }
          leaf trunk-group-type {
            tailf:cli-drop-node-name;
            tailf:cli-hide-in-submode;
            type enumeration {
              enum "static";
              enum "lacp";
              enum "lacp-udld";
            }
          }
        }
      }
      list trunk {
        key "nr";
        leaf nr {
          type ethernet-index;
        }
        leaf name {
          type string;
        }
        leaf state {
          tailf:cli-drop-node-name;
          type enumeration {
            enum "enable";
            enum "disable";
          }
        }
        container icmp-rate-limit {
          tailf:cli-sequence-commands {
            tailf:cli-reset-siblings;
          }
          tailf:cli-compact-syntax;
          leaf rate {
            tailf:cli-drop-node-name;
            type uint16;
          }
          leaf lockup {
            must '../rate' {
              tailf:xpath-root 3;
            }
            type uint16;
          }
          leaf lockup-period {
            must '../lockup' {
              tailf:xpath-root 3;
            }
            tailf:cli-drop-node-name;
            type uint16;
          }
        }
        list access-list {
          tailf:cli-suppress-mode;
          key "id in-type";
          leaf id {
            type uint16;
          }
          leaf in-type {
            type enumeration {
              enum "in";
            }
          }
        }
        container ip {
          list address {
            key "ip mask";
            tailf:cli-suppress-mode;
            leaf ip {
              type inet:ipv4-address;
            }
            leaf mask {
              type ipv4-mask;
            }
          }
          leaf allow-promiscuous-vip {
            type empty;
          }
          leaf cache-spoofing-port {
            type empty;
          }
          container nat {
            leaf inside {
              type empty;
            }
            leaf outside {
              type empty;
            }
          }
        }
      }
      list loopback {
        key "nr";
        leaf nr {
          type ethernet-index;
        }
        container ip {
          // NCS expand uses statement
          list address {
            tailf:cli-suppress-mode;
            key "address mask";
            leaf address {
              type union {
                type inet:ipv4-address;
                type enumeration {
                  enum "dhcp";
                }
              }
            }
            leaf mask {
              type union {
                type inet:ipv4-address;
                type string;
              }
            }
          }
          container router {
            choice isis-choice {
              container isis-alt {
                tailf:cli-drop-node-name;
                leaf isis {
                  type string;
                }
              }
              leaf isis {
                type empty;
              }
            }
          }
        }
        container icmp-rate-limit {
          tailf:cli-sequence-commands {
            tailf:cli-reset-siblings;
          }
          tailf:cli-compact-syntax;
          leaf rate {
            tailf:cli-drop-node-name;
            type uint16;
          }
          leaf lockup {
            must '../rate' {
              tailf:xpath-root 3;
            }
            type uint16;
          }
          leaf lockup-period {
            tailf:cli-drop-node-name;
            must '../lockup' {
              tailf:xpath-root 3;
            }
            type uint16;
          }
        }
        leaf state {
          tailf:cli-drop-node-name;
          type enumeration {
            enum "enable";
            enum "disable";
          }
        }
      }
      list ve {
        key "id";
        leaf id {
          type vlan-index;
        }
        leaf name {
          type string;
        }
        container bfd {
          container echo {
            presence "true";
          }
        }
        container icmp-rate-limit {
          tailf:cli-sequence-commands {
            tailf:cli-reset-siblings;
          }
          tailf:cli-compact-syntax;
          leaf rate {
            tailf:cli-drop-node-name;
            type uint16;
          }
          leaf lockup {
            must '../rate' {
              tailf:xpath-root 3;
            }
            type uint16;
          }
          leaf lockup-period {
            tailf:cli-drop-node-name;
            must '../lockup' {
              tailf:xpath-root 3;
            }
            type uint16;
          }
        }
        container access-list {
          tailf:cli-sequence-commands {
            tailf:cli-reset-siblings;
          }
          tailf:cli-compact-syntax;
          leaf id {
            tailf:cli-drop-node-name;
            type uint16;
          }
          leaf in {
            must '../id' {
              tailf:xpath-root 3;
            }
            type empty;
          }
        }
        leaf l3-vlan-fwd-disable {
          type empty;
        }
        container ip {
          leaf allow-promiscuous-vip {
            type empty;
          }
          leaf cache-spoofing-port {
            type empty;
          }
          leaf helper-address {
            type inet:ipv4-address;
          }
          container nat {
            leaf inside {
              type empty;
            }
            leaf outside {
              type empty;
            }
          }
          container ospf;
          container router {
            container isis {
              presence "true";
              leaf cmds {
                tailf:cli-drop-node-name;
                type string;
              }
            }
          }
          container tcp {
            leaf syn-cookie {
              type empty;
            }
          }
          // NCS expand uses statement
          list address {
            tailf:cli-suppress-mode;
            key "address mask";
            leaf address {
              type union {
                type inet:ipv4-address;
                type enumeration {
                  enum "dhcp";
                }
              }
            }
            leaf mask {
              type union {
                type inet:ipv4-address;
                type string;
              }
            }
          }
        }
        container ipv6 {
          container access-list {
            tailf:cli-sequence-commands {
              tailf:cli-reset-siblings;
            }
            tailf:cli-compact-syntax;
            leaf id {
              tailf:cli-drop-node-name;
              type string;
            }
            leaf in {
              must '../id' {
                tailf:xpath-root 3;
              }
              type empty;
            }
          }
          container nat {
            leaf inside {
              type empty;
            }
            leaf outside {
              type empty;
            }
          }
          container ndisc {
            container router-advertisement;
          }
          container ospf;
          container router {
            container isis {
              presence "true";
              leaf cmds {
                tailf:cli-drop-node-name;
                type string;
              }
            }
          }
          list address {
            key "ip";
            tailf:cli-suppress-mode;
            tailf:cli-sequence-commands {
              tailf:cli-reset-all-siblings;
            }
            tailf:cli-compact-syntax;
            leaf ip {
              tailf:cli-drop-node-name;
              type ipv6-prefix;
            }
            leaf link-local {
              type empty;
              tailf:cli-break-sequence-commands;
            }
            leaf anycast {
              type empty;
              tailf:cli-break-sequence-commands;
            }
          }
        }
        leaf mtu {
          type uint16;
        }
        leaf state {
          tailf:cli-drop-node-name;
          type enumeration {
            enum "enable";
            enum "disable";
          }
        }
        container isis;
        container ospf;
      }
    }
    uses vlan-grouping {
      refine vlan {
        tailf:ncs-device-type "cli-ned";
        tailf:display-when "not(../ncs:module) or ../ncs:module[ncs:name='netsim-ned-a10-acos']";
      }
    }
    // NCS expand uses statement
    container ip {
      tailf:ncs-device-type "cli-ned";
      tailf:display-when "not(../../ncs:module) or ../../ncs:module[ncs:name='netsim-ned-a10-acos']";
      list access-list {
        key "name";
        leaf name {
          type string;
        }
        list access-list-rule {
          tailf:cli-suppress-mode;
          tailf:cli-delete-when-empty;
          tailf:cli-drop-node-name;
          ordered-by user;
          key "rule";
          leaf rule {
            tailf:cli-multi-word-key;
            type string;
          }
        }
      }
      list address {
        key "ip";
        tailf:cli-suppress-mode;
        tailf:cli-delete-when-empty;
        tailf:cli-sequence-commands {
          tailf:cli-reset-siblings;
        }
        tailf:cli-compact-syntax;
        leaf ip {
          tailf:cli-drop-node-name;
          type inet:ipv4-address;
        }
        leaf mask {
          tailf:cli-drop-node-name;
          type ipv4-mask;
        }
      }
      container anomaly-drop {
        leaf bad-content {
          type uint16;
        }
        leaf drop-all {
          type empty;
        }
        leaf frag {
          type empty;
        }
        leaf ip-option {
          type boolean;
        }
        leaf land-attack {
          type empty;
        }
        leaf out-of-sequence {
          type uint16;
        }
        leaf ping-of-death {
          type empty;
        }
        leaf tcp-no-flag {
          type empty;
        }
        leaf tcp-syn-fin {
          type empty;
        }
        leaf tcp-syn-frag {
          type empty;
        }
        leaf zero-window {
          type uint16;
        }
        container security-attack {
          leaf layer-3 {
            type empty;
          }
          leaf layer-4 {
            type empty;
          }
        }
        list packet-deformity {
          tailf:cli-suppress-mode;
          key "layer";
          leaf layer {
            type enumeration {
              enum "layer-3";
              enum "layer-4";
            }
          }
        }
      }
      container as-path {
        list access-list {
          tailf:cli-suppress-mode;
          key "name action path";
          leaf name {
            type string;
          }
          leaf action {
            type enumeration {
              enum "permit";
              enum "deny";
            }
          }
          leaf path {
            type string;
            tailf:cli-multi-word-key;
          }
        }
      }
      container community-list {
        list standard-number {
          tailf:cli-drop-node-name;
          tailf:cli-suppress-mode;
          key "nr";
          leaf nr {
            type uint8;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list expanded-number {
          tailf:cli-drop-node-name;
          tailf:cli-suppress-mode;
          key "nr";
          leaf nr {
            type uint8;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list word {
          tailf:cli-drop-node-name;
          tailf:cli-suppress-mode;
          key "name";
          leaf name {
            type string;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list expanded {
          tailf:cli-suppress-mode;
          key "name";
          leaf name {
            type string;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list standard {
          tailf:cli-suppress-mode;
          key "name";
          leaf name {
            type string;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
      }
      leaf default-gateway {
        type inet:ipv4-address;
      }
      container dns {
        leaf primary {
          type inet:ipv4-address;
        }
        leaf secondary {
          type inet:ipv4-address;
        }
        leaf suffix {
          type string;
        }
      }
      container extcommunity-list {
        list standard-number {
          tailf:cli-drop-node-name;
          tailf:cli-suppress-mode;
          key "nr";
          leaf nr {
            type uint8;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list expanded-number {
          tailf:cli-drop-node-name;
          tailf:cli-suppress-mode;
          key "nr";
          leaf nr {
            type uint8;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list expanded {
          tailf:cli-suppress-mode;
          key "name";
          leaf name {
            type string;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
        list standard {
          tailf:cli-suppress-mode;
          key "name";
          leaf name {
            type string;
          }
          list rules {
            tailf:cli-drop-node-name;
            tailf:cli-suppress-mode;
            key "action expr";
            leaf action {
              type enumeration {
                enum "deny";
                enum "permit";
              }
            }
            leaf expr {
              type string;
              tailf:cli-multi-word-key;
            }
          }
        }
      }
      container frag {
        leaf buff {
          type uint32;
        }
        container cpu-threshold {
          tailf:cli-compact-syntax;
          tailf:cli-sequence-commands;
          leaf high {
            type uint8;
          }
          leaf low {
            type uint8;
          }
        }
        leaf max-reassembly-sessions {
          type uint32;
        }
        leaf timeout {
          type uint16;
        }
      }
      container icmp {
        container disable {
          leaf redirect {
            type empty;
          }
          leaf unreachable {
            type empty;
          }
        }
      }
      container mgmt-traffic {
        container snmp {
          // NCS expand uses statement
          container source-interface {
            leaf loopback {
              type uint8;
            }
          }
        }
        container ntp {
          // NCS expand uses statement
          container source-interface {
            leaf loopback {
              type uint8;
            }
          }
        }
        container syslog {
          // NCS expand uses statement
          container source-interface {
            leaf loopback {
              type uint8;
            }
          }
        }
        container ssh {
          // NCS expand uses statement
          container source-interface {
            leaf loopback {
              type uint8;
            }
          }
        }
        container telnet {
          // NCS expand uses statement
          container source-interface {
            leaf loopback {
              type uint8;
            }
          }
        }
        container ftp {
          // NCS expand uses statement
          container source-interface {
            leaf loopback {
              type uint8;
            }
          }
        }
        container tftp {
          // NCS expand uses statement
          container source-interface {
            leaf loopback {
              type uint8;
            }
          }
        }
        container rcp {
          // NCS expand uses statement
          container source-interface {
            leaf loopback {
              type uint8;
            }
          }
        }
        container web {
          // NCS expand uses statement
          container source-interface {
            leaf loopback {
              type uint8;
            }
          }
        }
        container all {
          // NCS expand uses statement
          container source-interface {
            leaf loopback {
              type uint8;
            }
          }
        }
      }
      container nat {
        // NCS expand uses statement
        container alg {
          // NCS expand uses statement
          leaf pptp {
            type enumeration {
              enum "disable";
              enum "enable";
            }
          }
          // NCS expand uses statement
          leaf tftp {
            type enumeration {
              enum "disable";
              enum "enable";
            }
          }
          // NCS expand uses statement
          leaf rtsp {
            type enumeration {
              enum "disable";
              enum "enable";
            }
          }
          // NCS expand uses statement
          leaf esp {
            type enumeration {
              enum "disable";
              enum "enable";
            }
          }
        }
        leaf allow-static-host {
          type empty;
        }
        container inside {
          container source {
            list list {
              tailf:cli-suppress-mode;
              key "id";
              leaf id {
                type uint16;
              }
              leaf pool {
                tailf:cli-hide-in-submode;
                mandatory true;
                type string;
              }
            }
            leaf class-list {
              type string;
            }
            list static {
              tailf:cli-suppress-mode;
              tailf:cli-compact-syntax;
              key "source nat";
              leaf source {
                type inet:ipv4-address;
              }
              leaf nat {
                type inet:ipv4-address;
              }
              leaf vrid {
                type uint8;
              }
            }
          }
        }
        list pool {
          tailf:cli-suppress-mode;
          tailf:cli-sequence-commands {
            tailf:cli-reset-all-siblings;
          }
          tailf:cli-compact-syntax;
          key "name";
          leaf name {
            type string;
          }
          leaf ipstart {
            mandatory true;
            tailf:cli-drop-node-name;
            type inet:ipv4-address;
          }
          leaf ipend {
            mandatory true;
            tailf:cli-drop-node-name;
            type inet:ipv4-address;
          }
          leaf netmask {
            mandatory true;
            type union {
              type ipv4-mask;
              type string;
            }
          }
          leaf gateway {
            tailf:cli-optional-in-sequence;
            type inet:ipv4-address;
          }
          leaf ha-group-id {
            tailf:cli-optional-in-sequence;
            type uint16;
          }
          leaf ha-use-all-ports {
            tailf:cli-optional-in-sequence;
            type empty;
          }
          leaf vrid {
            tailf:cli-optional-in-sequence;
            type uint16;
          }
          leaf ip-rr {
            tailf:cli-break-sequence-commands;
            type empty;
          }
          leaf lsn {
            type empty;
          }
          leaf max-users-per-ip {
            type uint16;
          }
        }
        list pool-group {
          key "name";
          leaf name {
            type string;
          }
          leaf ha-group-id {
            tailf:cli-hide-in-submode;
            type uint16;
          }
          list member {
            key "member-id";
            tailf:cli-suppress-mode;
            leaf member-id {
              type string;
            }
          }
        }
        container range-list;
        leaf reset-idle-tcp-conn {
          type empty;
        }
        container template {
          list logging {
            key "name";
            leaf name {
              type string;
            }
          }
        }
        container translation {
          leaf icmp-timeout {
            type union {
              type uint16;
              type enumeration {
                enum "fast";
              }
            }
          }
          leaf tcp-timeout {
            type uint16;
          }
          leaf udp-timeout {
            type uint16;
          }
          leaf syn-timeout {
            type uint16;
          }
          list service-timeout {
            tailf:cli-compact-syntax;
            tailf:cli-sequence-commands;
            tailf:cli-suppress-mode;
            key "protocol from";
            leaf protocol {
              type enumeration {
                enum "tcp";
                enum "udp";
              }
            }
            leaf from {
              type uint16;
            }
            leaf to {
              tailf:cli-optional-in-sequence;
              type uint16;
            }
            leaf timeout {
              tailf:cli-drop-node-name;
              type union {
                type uint16;
                type enumeration {
                  enum "fast";
                }
              }
            }
          }
        }
        container lsn {
          container endpoint-independent-mapping {
            container tcp {
              container enable {
                leaf ephemeral {
                  type empty;
                }
                leaf well-known {
                  type empty;
                }
              }
            }
            container udp {
              container enable {
                leaf ephemeral {
                  type empty;
                }
                leaf well-known {
                  type empty;
                }
              }
            }
          }
          container endpoint-independent-filtering {
            container tcp {
              container enable {
                leaf ephemeral {
                  type empty;
                  must '../../../../endpoint-independent-mapping/tcp/enable/ephemeral' {
                    tailf:xpath-root 3;
                    error-message "Endpoint-independent-filtering cannot be enabled when endpoint-independent-mapping is disabled";
                  }
                }
                leaf well-known {
                  type empty;
                  must '../../../../endpoint-independent-mapping/tcp/enable/well-known' {
                    tailf:xpath-root 3;
                    error-message "Endpoint-independent-filtering cannot be enabled when endpoint-independent-mapping is disabled";
                  }
                }
              }
            }
            container udp {
              container enable {
                leaf ephemeral {
                  type empty;
                  must '../../../../endpoint-independent-mapping/udp/enable/ephemeral' {
                    tailf:xpath-root 3;
                    error-message "Endpoint-independent-filtering cannot be enabled when endpoint-independent-mapping is disabled";
                  }
                }
                leaf well-known {
                  type empty;
                  must '../../../../endpoint-independent-mapping/udp/enable/well-known' {
                    tailf:xpath-root 3;
                    error-message "Endpoint-independent-filtering cannot be enabled when endpoint-independent-mapping is disabled";
                  }
                }
              }
            }
          }
          leaf ip-selection {
            type enumeration {
              enum "random";
              enum "round-robin";
              enum "least-used-strict";
              enum "least-udp-used-strict";
              enum "least-tcp-used-strict";
              enum "least-reserved-strict";
              enum "least-udp-reserved-strict";
              enum "least-tcp-reserved-strict";
              enum "least-users-strict";
            }
          }
          leaf attempt-port-preservation {
            type enumeration {
              enum "disable";
              enum "enable";
            }
          }
          // NCS expand uses statement
          container alg {
            // NCS expand uses statement
            leaf pptp {
              type enumeration {
                enum "disable";
                enum "enable";
              }
            }
            // NCS expand uses statement
            leaf tftp {
              type enumeration {
                enum "disable";
                enum "enable";
              }
            }
            // NCS expand uses statement
            leaf rtsp {
              type enumeration {
                enum "disable";
                enum "enable";
              }
            }
            // NCS expand uses statement
            leaf esp {
              type enumeration {
                enum "disable";
                enum "enable";
              }
            }
          }
        }
      }
      // NCS expand uses statement
      list prefix-list {
        tailf:cli-suppress-mode;
        tailf:cli-compact-syntax;
        key "name seq";
        leaf name {
          type string;
        }
        leaf seq {
          tailf:cli-expose-key-name;
          type uint32;
        }
        choice permit-deny {
          leaf permit {
            type union {
              type enumeration {
                enum "any";
              }
              type tailf:ipv4-address-and-prefix-length;
            }
          }
          leaf deny {
            type union {
              type enumeration {
                enum "any";
              }
              type tailf:ipv4-address-and-prefix-length;
            }
          }
        }
        leaf ge {
          type uint8;
        }
        leaf le {
          type uint8;
        }
      }
      // NCS expand uses statement
      list route {
        tailf:cli-compact-syntax;
        tailf:cli-sequence-commands {
          tailf:cli-reset-siblings;
        }
        tailf:cli-suppress-mode;
        key "ip mask forwarding-router";
        leaf ip {
          type inet:ipv4-address;
        }
        leaf mask {
          type string;
        }
        leaf forwarding-router {
          type inet:ipv4-address;
        }
        leaf distance {
          tailf:cli-drop-node-name;
          tailf:cli-optional-in-sequence;
          type uint8;
        }
        leaf cpu-process {
          tailf:cli-drop-node-name;
          tailf:cli-optional-in-sequence;
          type enumeration {
            enum "cpu-process";
          }
        }
      }
      container tcp {
        container syn-cookie {
          leaf threshold {
            type uint8;
          }
        }
      }
    }
    uses ipv6-grouping {
      refine ipv6 {
        tailf:ncs-device-type "cli-ned";
        tailf:display-when "not(../../ncs:module) or ../../ncs:module[ncs:name='netsim-ned-a10-acos']";
      }
    }
    uses nat64-grouping {
      refine nat64 {
        tailf:ncs-device-type "cli-ned";
        tailf:display-when "not(../../ncs:module) or ../../ncs:module[ncs:name='netsim-ned-a10-acos']";
      }
    }
    uses lsn-lid-grouping {
      refine lsn-lid {
        tailf:ncs-device-type "cli-ned";
        tailf:display-when "not(../ncs:module) or ../ncs:module[ncs:name='netsim-ned-a10-acos']";
      }
    }
    uses ha-grouping {
      refine ha {
        tailf:ncs-device-type "cli-ned";
        tailf:display-when "not(../../ncs:module) or ../../ncs:module[ncs:name='netsim-ned-a10-acos']";
      }
    }
    uses floating-ip-grouping {
      refine floating-ip {
        tailf:ncs-device-type "cli-ned";
        tailf:display-when "not(../../ncs:module) or ../../ncs:module[ncs:name='netsim-ned-a10-acos']";
      }
    }
    uses glid-grouping {
      refine glid {
        tailf:ncs-device-type "cli-ned";
        tailf:display-when "not(../ncs:module) or ../ncs:module[ncs:name='netsim-ned-a10-acos']";
      }
    }
    uses slb-grouping {
      refine slb {
        tailf:ncs-device-type "cli-ned";
        tailf:display-when "not(../../ncs:module) or ../../ncs:module[ncs:name='netsim-ned-a10-acos']";
      }
    }
    uses gslb-grouping {
      refine gslb {
        tailf:ncs-device-type "cli-ned";
        tailf:display-when "not(../../ncs:module) or ../../ncs:module[ncs:name='netsim-ned-a10-acos']";
      }
    }
    uses logging-grouping {
      refine logging {
        tailf:ncs-device-type "cli-ned";
        tailf:display-when "not(../../ncs:module) or ../../ncs:module[ncs:name='netsim-ned-a10-acos']";
      }
    }
    uses snmp-server-grouping {
      refine snmp-server {
        tailf:ncs-device-type "cli-ned";
        tailf:display-when "not(../../ncs:module) or ../../ncs:module[ncs:name='netsim-ned-a10-acos']";
      }
    }
    uses audit-grouping {
      refine audit {
        tailf:ncs-device-type "cli-ned";
        tailf:display-when "not(../../ncs:module) or ../../ncs:module[ncs:name='netsim-ned-a10-acos']";
      }
    }
    uses harmony-controller-grouping {
      refine harmony-controller {
        tailf:ncs-device-type "cli-ned";
        tailf:display-when "not(../../ncs:module) or ../../ncs:module[ncs:name='netsim-ned-a10-acos']";
      }
    }
    uses terminal-grouping {
      refine terminal {
        tailf:ncs-device-type "cli-ned";
        tailf:display-when "not(../../ncs:module) or ../../ncs:module[ncs:name='netsim-ned-a10-acos']";
      }
    }
    uses web-service-grouping {
      refine web-service {
        tailf:ncs-device-type "cli-ned";
        tailf:display-when "not(../../ncs:module) or ../../ncs:module[ncs:name='netsim-ned-a10-acos']";
      }
    }
    uses multi-config-grouping {
      refine multi-config {
        tailf:ncs-device-type "cli-ned";
        tailf:display-when "not(../../ncs:module) or ../../ncs:module[ncs:name='netsim-ned-a10-acos']";
      }
    }
    uses banner-grouping {
      refine banner {
        tailf:ncs-device-type "cli-ned";
        tailf:display-when "not(../../ncs:module) or ../../ncs:module[ncs:name='netsim-ned-a10-acos']";
      }
    }
    uses vrrp-a-grouping {
      refine vrrp-a {
        tailf:ncs-device-type "cli-ned";
        tailf:display-when "not(../../ncs:module) or ../../ncs:module[ncs:name='netsim-ned-a10-acos']";
      }
    }
    uses router-grouping {
      refine router {
        tailf:ncs-device-type "cli-ned";
        tailf:display-when "not(../../ncs:module) or ../../ncs:module[ncs:name='netsim-ned-a10-acos']";
      }
    }
    uses bfd-grouping {
      refine bfd {
        tailf:ncs-device-type "cli-ned";
        tailf:display-when "not(../../ncs:module) or ../../ncs:module[ncs:name='netsim-ned-a10-acos']";
      }
    }
    uses lldp-grouping {
      refine lldp {
        tailf:ncs-device-type "cli-ned";
        tailf:display-when "not(../../ncs:module) or ../../ncs:module[ncs:name='netsim-ned-a10-acos']";
      }
    }
    uses route-map-grouping {
      refine route-map {
        tailf:ncs-device-type "cli-ned";
        tailf:display-when "not(../ncs:module) or ../ncs:module[ncs:name='netsim-ned-a10-acos']";
      }
    }
    uses device-context-grouping {
      refine device-context {
        tailf:ncs-device-type "cli-ned";
        tailf:display-when "not(../ncs:module) or ../ncs:module[ncs:name='netsim-ned-a10-acos']";
      }
    }
    // NCS expand uses statement
    container vcs {
      tailf:ncs-device-type "cli-ned";
      tailf:display-when "not(../../ncs:module) or ../../ncs:module[ncs:name='netsim-ned-a10-acos']";
      leaf state {
        tailf:cli-drop-node-name;
        type enumeration {
          enum "enable";
          enum "disable";
        }
      }
      list device {
        key "id";
        leaf id {
          type uint8;
        }
        leaf priority {
          type uint8;
        }
        container interfaces {
          leaf management {
            type empty;
          }
          list ethernet {
            tailf:cli-suppress-mode;
            key "id";
            leaf id {
              type uint8;
            }
          }
          list trunk {
            tailf:cli-suppress-mode;
            key "id";
            leaf id {
              type uint8;
            }
          }
          list ve {
            tailf:cli-suppress-mode;
            key "id";
            leaf id {
              type uint16;
            }
          }
        }
        leaf enable {
          type empty;
        }
      }
      list floating-ip {
        tailf:cli-suppress-mode;
        tailf:cli-delete-when-empty;
        tailf:cli-compact-syntax;
        key "floating-ip-address";
        leaf floating-ip-address {
          tailf:cli-drop-node-name;
          type inet:ipv4-address;
        }
        leaf mask {
          tailf:cli-drop-node-name;
          type ipv4-mask;
        }
      }
      leaf ssl-enable {
        type empty;
      }
      leaf failure-retry-count {
        type union {
          type enumeration {
            enum "forever";
          }
          type uint8;
        }
      }
    }
    uses system-grouping {
      refine system {
        tailf:ncs-device-type "cli-ned";
        tailf:display-when "not(../../ncs:module) or ../../ncs:module[ncs:name='netsim-ned-a10-acos']";
      }
    }
    uses ve-stats-grouping {
      refine ve-stats {
        tailf:ncs-device-type "cli-ned";
        tailf:display-when "not(../../ncs:module) or ../../ncs:module[ncs:name='netsim-ned-a10-acos']";
      }
    }
    uses partition-grouping {
      refine partition {
        tailf:ncs-device-type "cli-ned";
        tailf:display-when "not(../ncs:module) or ../ncs:module[ncs:name='netsim-ned-a10-acos']";
      }
    }
    uses partition-group-grouping {
      refine partition-group {
        tailf:ncs-device-type "cli-ned";
        tailf:display-when "not(../ncs:module) or ../ncs:module[ncs:name='netsim-ned-a10-acos']";
      }
    }
    uses access-list-grouping {
      refine access-list {
        tailf:ncs-device-type "cli-ned";
        tailf:display-when "not(../ncs:module) or ../ncs:module[ncs:name='netsim-ned-a10-acos']";
      }
    }
    uses tftp-grouping {
      refine tftp {
        tailf:ncs-device-type "cli-ned";
        tailf:display-when "not(../../ncs:module) or ../../ncs:module[ncs:name='netsim-ned-a10-acos']";
      }
    }
    uses health-grouping {
      refine health {
        tailf:ncs-device-type "cli-ned";
        tailf:display-when "not(../../ncs:module) or ../../ncs:module[ncs:name='netsim-ned-a10-acos']";
      }
    }
    uses stats-data-disable-grouping {
      refine stats-data-disable {
        tailf:ncs-device-type "cli-ned";
        tailf:display-when "not(../../ncs:module) or ../../ncs:module[ncs:name='netsim-ned-a10-acos']";
      }
    }
    uses syn-cookie-grouping {
      refine syn-cookie {
        tailf:ncs-device-type "cli-ned";
        tailf:display-when "not(../../ncs:module) or ../../ncs:module[ncs:name='netsim-ned-a10-acos']";
      }
    }
    uses enable-management-grouping {
      refine enable-management {
        tailf:ncs-device-type "cli-ned";
        tailf:display-when "not(../../ncs:module) or ../../ncs:module[ncs:name='netsim-ned-a10-acos']";
      }
    }
    uses disable-management-grouping {
      refine disable-management {
        tailf:ncs-device-type "cli-ned";
        tailf:display-when "not(../../ncs:module) or ../../ncs:module[ncs:name='netsim-ned-a10-acos']";
      }
    }
    uses monitor-grouping {
      refine monitor {
        tailf:ncs-device-type "cli-ned";
        tailf:display-when "not(../../ncs:module) or ../../ncs:module[ncs:name='netsim-ned-a10-acos']";
      }
    }
    uses extended-stats-grouping {
      refine extended-stats {
        tailf:ncs-device-type "cli-ned";
        tailf:display-when "not(../../ncs:module) or ../../ncs:module[ncs:name='netsim-ned-a10-acos']";
      }
    }
    uses admin-grouping {
      refine admin {
        tailf:ncs-device-type "cli-ned";
        tailf:display-when "not(../../ncs:module) or ../../ncs:module[ncs:name='netsim-ned-a10-acos']";
      }
    }
    uses zone-grouping {
      refine zone {
        tailf:ncs-device-type "cli-ned";
        tailf:display-when "not(../ncs:module) or ../ncs:module[ncs:name='netsim-ned-a10-acos']";
      }
    }
    uses object-grouping {
      refine object {
        tailf:ncs-device-type "cli-ned";
        tailf:display-when "not(../../ncs:module) or ../../ncs:module[ncs:name='netsim-ned-a10-acos']";
      }
    }
    uses object-group-grouping {
      refine object-group {
        tailf:ncs-device-type "cli-ned";
        tailf:display-when "not(../../ncs:module) or ../../ncs:module[ncs:name='netsim-ned-a10-acos']";
      }
    }
    uses rule-set-grouping {
      refine rule-set {
        tailf:ncs-device-type "cli-ned";
        tailf:display-when "not(../ncs:module) or ../ncs:module[ncs:name='netsim-ned-a10-acos']";
      }
    }
    uses fw-grouping {
      refine fw {
        tailf:ncs-device-type "cli-ned";
        tailf:display-when "not(../../ncs:module) or ../../ncs:module[ncs:name='netsim-ned-a10-acos']";
      }
    }
    uses enable-core-grouping {
      refine enable-core {
        tailf:ncs-device-type "cli-ned";
        tailf:display-when "not(../../ncs:module) or ../../ncs:module[ncs:name='netsim-ned-a10-acos']";
      }
    }
    uses bw-list-grouping {
      refine import-info {
        tailf:ncs-device-type "cli-ned";
        tailf:display-when "not(../ncs:module) or ../ncs:module[ncs:name='netsim-ned-a10-acos']";
      }
      refine bw-list {
        tailf:ncs-device-type "cli-ned";
        tailf:display-when "not(../ncs:module) or ../ncs:module[ncs:name='netsim-ned-a10-acos']";
      }
    }
    list active-partition {
      tailf:ncs-device-type "cli-ned";
      tailf:display-when "not(../ncs:module) or ../ncs:module[ncs:name='netsim-ned-a10-acos']";
      key "name";
      leaf name {
        type string;
      }
      uses aflex-grouping;
      uses hostname-grouping;
      // NCS expand uses statement
      container interface {

        grouping lldp-interface-grouping {
          container lldp {
            container enable {
              tailf:cli-compact-syntax;
              leaf rx {
                type empty;
              }
              leaf tx {
                type empty;
              }
            }
            leaf notification {
              type enumeration {
                enum "enable";
              }
            }
            leaf tx-dot1-tlvs {
              type enumeration {
                enum "link-aggregation";
                enum "vlan";
              }
            }
          }
        }
        container management {
          tailf:cli-add-mode;
          container bcast-rate-limit {
            presence "present";
            leaf rate {
              type uint16;
            }
          }
          container ip {
            // NCS expand uses statement
            list address {
              tailf:cli-suppress-mode;
              key "address mask";
              leaf address {
                type union {
                  type inet:ipv4-address;
                  type enumeration {
                    enum "dhcp";
                  }
                }
              }
              leaf mask {
                type union {
                  type inet:ipv4-address;
                  type string;
                }
              }
            }
            leaf control-apps-use-mgmt-port {
              type empty;
            }
            leaf default-gateway {
              type inet:ipv4-address;
            }
          }
          container ipv6 {
            list address {
              key "ip";
              tailf:cli-suppress-mode;
              tailf:cli-sequence-commands {
                tailf:cli-reset-siblings;
              }
              tailf:cli-compact-syntax;
              leaf ip {
                tailf:cli-drop-node-name;
                type ipv6-prefix;
              }
              leaf link-local {
                type empty;
              }
            }
            leaf default-gateway {
              type inet:ipv6-address;
            }
          }
          // NCS expand uses statement
          container lldp {
            container enable {
              tailf:cli-compact-syntax;
              leaf rx {
                type empty;
              }
              leaf tx {
                type empty;
              }
            }
            leaf notification {
              type enumeration {
                enum "enable";
              }
            }
            leaf tx-dot1-tlvs {
              type enumeration {
                enum "link-aggregation";
                enum "vlan";
              }
            }
          }
          leaf flow-control {
            type empty;
          }
          container access-list {
            tailf:cli-sequence-commands {
              tailf:cli-reset-siblings;
            }
            tailf:cli-compact-syntax;
            leaf id {
              tailf:cli-drop-node-name;
              type uint16;
            }
            leaf in {
              must '../id' {
                tailf:xpath-root 3;
              }
              type empty;
            }
          }
          leaf enabled-disabled {
            tailf:cli-drop-node-name;
            type enumeration {
              enum "enable";
              enum "disable";
            }
          }
          leaf duplexity {
            type enumeration {
              enum "full";
              enum "half";
              enum "auto";
            }
          }
          leaf mtu {
            type uint16;
          }
          leaf speed {
            type enumeration {
              enum "10";
              enum "100";
              enum "1000";
              enum "auto";
            }
          }
        }
        list ethernet {
          key "nr";
          leaf nr {
            type ethernet-index;
          }
          leaf name {
            type string;
          }
          container ip {
            // NCS expand uses statement
            list address {
              tailf:cli-suppress-mode;
              key "address mask";
              leaf address {
                type union {
                  type inet:ipv4-address;
                  type enumeration {
                    enum "dhcp";
                  }
                }
              }
              leaf mask {
                type union {
                  type inet:ipv4-address;
                  type string;
                }
              }
            }
            leaf cache-spoofing-port {
              type empty;
            }
            leaf helper-address {
              type inet:ipv4-address;
            }
            container nat {
              leaf inside {
                type empty;
              }
              leaf outside {
                type empty;
              }
            }
            container ospf;
            container router {
              container isis {
                presence "true";
                leaf cmds {
                  tailf:cli-drop-node-name;
                  type string;
                }
              }
            }
            leaf allow-promiscuous-vip {
              type empty;
            }
            container tcp {
              leaf syn-cookie {
                type empty;
              }
            }
          }
          container ipv6 {
            container access-list {
              tailf:cli-sequence-commands {
                tailf:cli-reset-siblings;
              }
              tailf:cli-compact-syntax;
              leaf id {
                tailf:cli-drop-node-name;
                type string;
              }
              leaf in {
                must '../id' {
                  tailf:xpath-root 3;
                }
                type empty;
              }
            }
            list address {
              key "ip";
              tailf:cli-suppress-mode;
              tailf:cli-sequence-commands {
                tailf:cli-reset-all-siblings;
              }
              tailf:cli-compact-syntax;
              leaf ip {
                tailf:cli-drop-node-name;
                type ipv6-prefix;
              }
              leaf link-local {
                type empty;
                tailf:cli-break-sequence-commands;
              }
              leaf anycast {
                type empty;
                tailf:cli-break-sequence-commands;
              }
            }
            container nat {
              leaf inside {
                type empty;
              }
              leaf outside {
                type empty;
              }
            }
            container ndisc {
              container router-advertisement;
            }
            container ospf;
            container router {
              container isis {
                presence "true";
                leaf cmds {
                  tailf:cli-drop-node-name;
                  type string;
                }
              }
            }
          }
          leaf load-interval {
            type uint16;
          }
          container access-list {
            tailf:cli-sequence-commands {
              tailf:cli-reset-siblings;
            }
            tailf:cli-compact-syntax;
            leaf id {
              tailf:cli-drop-node-name;
              type uint16;
            }
            leaf in {
              must '../id' {
                tailf:xpath-root 3;
              }
              type empty;
            }
          }
          leaf state {
            tailf:cli-drop-node-name;
            type enumeration {
              enum "enable";
              enum "disable";
            }
          }
          leaf state-alt {
            tailf:cli-drop-node-name;
            type enumeration {
              enum "enable";
              enum "disable";
            }
          }
          leaf duplexity {
            type enumeration {
              enum "full";
              enum "half";
              enum "auto";
            }
          }
          leaf cpu-process {
            type empty;
          }
          leaf flow-control {
            type empty;
          }
          container icmp-rate-limit {
            tailf:cli-sequence-commands {
              tailf:cli-reset-siblings;
            }
            tailf:cli-compact-syntax;
            leaf rate {
              tailf:cli-drop-node-name;
              type uint16;
            }
            leaf lockup {
              must '../rate' {
                tailf:xpath-root 3;
              }
              type uint16;
            }
            leaf lockup-period {
              must '../lockup' {
                tailf:xpath-root 3;
              }
              tailf:cli-drop-node-name;
              type uint16;
            }
          }
          container ospf;
          container isis;
          leaf l3-vlan-fwd-disable {
            type empty;
          }
          container lacp {
            leaf port-priority {
              type uint16;
            }
            leaf timeout {
              type enumeration {
                enum "long";
                enum "short";
              }
            }
            container trunk {
              tailf:cli-sequence-commands {
                tailf:cli-reset-all-siblings;
              }
              tailf:cli-compact-syntax;
              leaf number {
                tailf:cli-drop-node-name;
                type uint16;
              }
              leaf admin-key {
                tailf:cli-break-sequence-commands;
                must '../number' {
                  tailf:xpath-root 3;
                }
                type uint16;
              }
              leaf mode {
                must '../number' {
                  tailf:xpath-root 3;
                }
                type enumeration {
                  enum "active";
                  enum "passive";
                }
              }
              leaf unidirectional-detection {
                must '../number' {
                  tailf:xpath-root 3;
                }
                type empty;
              }
            }
            container udld-timeout {
              tailf:cli-sequence-commands {
                tailf:cli-reset-all-siblings;
              }
              tailf:cli-compact-syntax;
              leaf timeout-type {
                tailf:cli-drop-node-name;
                type enumeration {
                  enum "fast";
                  enum "slow";
                }
              }
              leaf milli {
                tailf:cli-drop-node-name;
                type uint16;
              }
              leaf secs {
                tailf:cli-drop-node-name;
                type uint16;
              }
            }
          }
          // NCS expand uses statement
          container lldp {
            container enable {
              tailf:cli-compact-syntax;
              leaf rx {
                type empty;
              }
              leaf tx {
                type empty;
              }
            }
            leaf notification {
              type enumeration {
                enum "enable";
              }
            }
            leaf tx-dot1-tlvs {
              type enumeration {
                enum "link-aggregation";
                enum "vlan";
              }
            }
          }
          leaf mtu {
            type uint16;
          }
          leaf speed {
            type enumeration {
              enum "10";
              enum "100";
              enum "1000";
              enum "auto";
            }
          }
          list trunk-group-list {
            key "trunk-group-key";
            tailf:cli-drop-node-name;
            tailf:cli-compact-syntax;
            tailf:cli-sequence-commands {
              tailf:cli-reset-siblings;
            }
            leaf trunk-group-key {
              type enumeration {
                enum "trunk-group";
              }
            }
            leaf trunk-group-id {
              tailf:cli-drop-node-name;
              tailf:cli-hide-in-submode;
              mandatory true;
              type uint8;
            }
            leaf trunk-group-type {
              tailf:cli-drop-node-name;
              tailf:cli-hide-in-submode;
              type enumeration {
                enum "static";
                enum "lacp";
                enum "lacp-udld";
              }
            }
          }
        }
        list trunk {
          key "nr";
          leaf nr {
            type ethernet-index;
          }
          leaf name {
            type string;
          }
          leaf state {
            tailf:cli-drop-node-name;
            type enumeration {
              enum "enable";
              enum "disable";
            }
          }
          container icmp-rate-limit {
            tailf:cli-sequence-commands {
              tailf:cli-reset-siblings;
            }
            tailf:cli-compact-syntax;
            leaf rate {
              tailf:cli-drop-node-name;
              type uint16;
            }
            leaf lockup {
              must '../rate' {
                tailf:xpath-root 3;
              }
              type uint16;
            }
            leaf lockup-period {
              must '../lockup' {
                tailf:xpath-root 3;
              }
              tailf:cli-drop-node-name;
              type uint16;
            }
          }
          list access-list {
            tailf:cli-suppress-mode;
            key "id in-type";
            leaf id {
              type uint16;
            }
            leaf in-type {
              type enumeration {
                enum "in";
              }
            }
          }
          container ip {
            list address {
              key "ip mask";
              tailf:cli-suppress-mode;
              leaf ip {
                type inet:ipv4-address;
              }
              leaf mask {
                type ipv4-mask;
              }
            }
            leaf allow-promiscuous-vip {
              type empty;
            }
            leaf cache-spoofing-port {
              type empty;
            }
            container nat {
              leaf inside {
                type empty;
              }
              leaf outside {
                type empty;
              }
            }
          }
        }
        list loopback {
          key "nr";
          leaf nr {
            type ethernet-index;
          }
          container ip {
            // NCS expand uses statement
            list address {
              tailf:cli-suppress-mode;
              key "address mask";
              leaf address {
                type union {
                  type inet:ipv4-address;
                  type enumeration {
                    enum "dhcp";
                  }
                }
              }
              leaf mask {
                type union {
                  type inet:ipv4-address;
                  type string;
                }
              }
            }
            container router {
              choice isis-choice {
                container isis-alt {
                  tailf:cli-drop-node-name;
                  leaf isis {
                    type string;
                  }
                }
                leaf isis {
                  type empty;
                }
              }
            }
          }
          container icmp-rate-limit {
            tailf:cli-sequence-commands {
              tailf:cli-reset-siblings;
            }
            tailf:cli-compact-syntax;
            leaf rate {
              tailf:cli-drop-node-name;
              type uint16;
            }
            leaf lockup {
              must '../rate' {
                tailf:xpath-root 3;
              }
              type uint16;
            }
            leaf lockup-period {
              tailf:cli-drop-node-name;
              must '../lockup' {
                tailf:xpath-root 3;
              }
              type uint16;
            }
          }
          leaf state {
            tailf:cli-drop-node-name;
            type enumeration {
              enum "enable";
              enum "disable";
            }
          }
        }
        list ve {
          key "id";
          leaf id {
            type vlan-index;
          }
          leaf name {
            type string;
          }
          container bfd {
            container echo {
              presence "true";
            }
          }
          container icmp-rate-limit {
            tailf:cli-sequence-commands {
              tailf:cli-reset-siblings;
            }
            tailf:cli-compact-syntax;
            leaf rate {
              tailf:cli-drop-node-name;
              type uint16;
            }
            leaf lockup {
              must '../rate' {
                tailf:xpath-root 3;
              }
              type uint16;
            }
            leaf lockup-period {
              tailf:cli-drop-node-name;
              must '../lockup' {
                tailf:xpath-root 3;
              }
              type uint16;
            }
          }
          container access-list {
            tailf:cli-sequence-commands {
              tailf:cli-reset-siblings;
            }
            tailf:cli-compact-syntax;
            leaf id {
              tailf:cli-drop-node-name;
              type uint16;
            }
            leaf in {
              must '../id' {
                tailf:xpath-root 3;
              }
              type empty;
            }
          }
          leaf l3-vlan-fwd-disable {
            type empty;
          }
          container ip {
            leaf allow-promiscuous-vip {
              type empty;
            }
            leaf cache-spoofing-port {
              type empty;
            }
            leaf helper-address {
              type inet:ipv4-address;
            }
            container nat {
              leaf inside {
                type empty;
              }
              leaf outside {
                type empty;
              }
            }
            container ospf;
            container router {
              container isis {
                presence "true";
                leaf cmds {
                  tailf:cli-drop-node-name;
                  type string;
                }
              }
            }
            container tcp {
              leaf syn-cookie {
                type empty;
              }
            }
            // NCS expand uses statement
            list address {
              tailf:cli-suppress-mode;
              key "address mask";
              leaf address {
                type union {
                  type inet:ipv4-address;
                  type enumeration {
                    enum "dhcp";
                  }
                }
              }
              leaf mask {
                type union {
                  type inet:ipv4-address;
                  type string;
                }
              }
            }
          }
          container ipv6 {
            container access-list {
              tailf:cli-sequence-commands {
                tailf:cli-reset-siblings;
              }
              tailf:cli-compact-syntax;
              leaf id {
                tailf:cli-drop-node-name;
                type string;
              }
              leaf in {
                must '../id' {
                  tailf:xpath-root 3;
                }
                type empty;
              }
            }
            container nat {
              leaf inside {
                type empty;
              }
              leaf outside {
                type empty;
              }
            }
            container ndisc {
              container router-advertisement;
            }
            container ospf;
            container router {
              container isis {
                presence "true";
                leaf cmds {
                  tailf:cli-drop-node-name;
                  type string;
                }
              }
            }
            list address {
              key "ip";
              tailf:cli-suppress-mode;
              tailf:cli-sequence-commands {
                tailf:cli-reset-all-siblings;
              }
              tailf:cli-compact-syntax;
              leaf ip {
                tailf:cli-drop-node-name;
                type ipv6-prefix;
              }
              leaf link-local {
                type empty;
                tailf:cli-break-sequence-commands;
              }
              leaf anycast {
                type empty;
                tailf:cli-break-sequence-commands;
              }
            }
          }
          leaf mtu {
            type uint16;
          }
          leaf state {
            tailf:cli-drop-node-name;
            type enumeration {
              enum "enable";
              enum "disable";
            }
          }
          container isis;
          container ospf;
        }
      }
      // NCS expand uses statement
      container ip {
        list access-list {
          key "name";
          leaf name {
            type string;
          }
          list access-list-rule {
            tailf:cli-suppress-mode;
            tailf:cli-delete-when-empty;
            tailf:cli-drop-node-name;
            ordered-by user;
            key "rule";
            leaf rule {
              tailf:cli-multi-word-key;
              type string;
            }
          }
        }
        list address {
          key "ip";
          tailf:cli-suppress-mode;
          tailf:cli-delete-when-empty;
          tailf:cli-sequence-commands {
            tailf:cli-reset-siblings;
          }
          tailf:cli-compact-syntax;
          leaf ip {
            tailf:cli-drop-node-name;
            type inet:ipv4-address;
          }
          leaf mask {
            tailf:cli-drop-node-name;
            type ipv4-mask;
          }
        }
        container anomaly-drop {
          leaf bad-content {
            type uint16;
          }
          leaf drop-all {
            type empty;
          }
          leaf frag {
            type empty;
          }
          leaf ip-option {
            type boolean;
          }
          leaf land-attack {
            type empty;
          }
          leaf out-of-sequence {
            type uint16;
          }
          leaf ping-of-death {
            type empty;
          }
          leaf tcp-no-flag {
            type empty;
          }
          leaf tcp-syn-fin {
            type empty;
          }
          leaf tcp-syn-frag {
            type empty;
          }
          leaf zero-window {
            type uint16;
          }
          container security-attack {
            leaf layer-3 {
              type empty;
            }
            leaf layer-4 {
              type empty;
            }
          }
          list packet-deformity {
            tailf:cli-suppress-mode;
            key "layer";
            leaf layer {
              type enumeration {
                enum "layer-3";
                enum "layer-4";
              }
            }
          }
        }
        container as-path {
          list access-list {
            tailf:cli-suppress-mode;
            key "name action path";
            leaf name {
              type string;
            }
            leaf action {
              type enumeration {
                enum "permit";
                enum "deny";
              }
            }
            leaf path {
              type string;
              tailf:cli-multi-word-key;
            }
          }
        }
        container community-list {
          list standard-number {
            tailf:cli-drop-node-name;
            tailf:cli-suppress-mode;
            key "nr";
            leaf nr {
              type uint8;
            }
            list rules {
              tailf:cli-drop-node-name;
              tailf:cli-suppress-mode;
              key "action expr";
              leaf action {
                type enumeration {
                  enum "deny";
                  enum "permit";
                }
              }
              leaf expr {
                type string;
                tailf:cli-multi-word-key;
              }
            }
          }
          list expanded-number {
            tailf:cli-drop-node-name;
            tailf:cli-suppress-mode;
            key "nr";
            leaf nr {
              type uint8;
            }
            list rules {
              tailf:cli-drop-node-name;
              tailf:cli-suppress-mode;
              key "action expr";
              leaf action {
                type enumeration {
                  enum "deny";
                  enum "permit";
                }
              }
              leaf expr {
                type string;
                tailf:cli-multi-word-key;
              }
            }
          }
          list word {
            tailf:cli-drop-node-name;
            tailf:cli-suppress-mode;
            key "name";
            leaf name {
              type string;
            }
            list rules {
              tailf:cli-drop-node-name;
              tailf:cli-suppress-mode;
              key "action expr";
              leaf action {
                type enumeration {
                  enum "deny";
                  enum "permit";
                }
              }
              leaf expr {
                type string;
                tailf:cli-multi-word-key;
              }
            }
          }
          list expanded {
            tailf:cli-suppress-mode;
            key "name";
            leaf name {
              type string;
            }
            list rules {
              tailf:cli-drop-node-name;
              tailf:cli-suppress-mode;
              key "action expr";
              leaf action {
                type enumeration {
                  enum "deny";
                  enum "permit";
                }
              }
              leaf expr {
                type string;
                tailf:cli-multi-word-key;
              }
            }
          }
          list standard {
            tailf:cli-suppress-mode;
            key "name";
            leaf name {
              type string;
            }
            list rules {
              tailf:cli-drop-node-name;
              tailf:cli-suppress-mode;
              key "action expr";
              leaf action {
                type enumeration {
                  enum "deny";
                  enum "permit";
                }
              }
              leaf expr {
                type string;
                tailf:cli-multi-word-key;
              }
            }
          }
        }
        leaf default-gateway {
          type inet:ipv4-address;
        }
        container dns {
          leaf primary {
            type inet:ipv4-address;
          }
          leaf secondary {
            type inet:ipv4-address;
          }
          leaf suffix {
            type string;
          }
        }
        container extcommunity-list {
          list standard-number {
            tailf:cli-drop-node-name;
            tailf:cli-suppress-mode;
            key "nr";
            leaf nr {
              type uint8;
            }
            list rules {
              tailf:cli-drop-node-name;
              tailf:cli-suppress-mode;
              key "action expr";
              leaf action {
                type enumeration {
                  enum "deny";
                  enum "permit";
                }
              }
              leaf expr {
                type string;
                tailf:cli-multi-word-key;
              }
            }
          }
          list expanded-number {
            tailf:cli-drop-node-name;
            tailf:cli-suppress-mode;
            key "nr";
            leaf nr {
              type uint8;
            }
            list rules {
              tailf:cli-drop-node-name;
              tailf:cli-suppress-mode;
              key "action expr";
              leaf action {
                type enumeration {
                  enum "deny";
                  enum "permit";
                }
              }
              leaf expr {
                type string;
                tailf:cli-multi-word-key;
              }
            }
          }
          list expanded {
            tailf:cli-suppress-mode;
            key "name";
            leaf name {
              type string;
            }
            list rules {
              tailf:cli-drop-node-name;
              tailf:cli-suppress-mode;
              key "action expr";
              leaf action {
                type enumeration {
                  enum "deny";
                  enum "permit";
                }
              }
              leaf expr {
                type string;
                tailf:cli-multi-word-key;
              }
            }
          }
          list standard {
            tailf:cli-suppress-mode;
            key "name";
            leaf name {
              type string;
            }
            list rules {
              tailf:cli-drop-node-name;
              tailf:cli-suppress-mode;
              key "action expr";
              leaf action {
                type enumeration {
                  enum "deny";
                  enum "permit";
                }
              }
              leaf expr {
                type string;
                tailf:cli-multi-word-key;
              }
            }
          }
        }
        container frag {
          leaf buff {
            type uint32;
          }
          container cpu-threshold {
            tailf:cli-compact-syntax;
            tailf:cli-sequence-commands;
            leaf high {
              type uint8;
            }
            leaf low {
              type uint8;
            }
          }
          leaf max-reassembly-sessions {
            type uint32;
          }
          leaf timeout {
            type uint16;
          }
        }
        container icmp {
          container disable {
            leaf redirect {
              type empty;
            }
            leaf unreachable {
              type empty;
            }
          }
        }
        container mgmt-traffic {
          container snmp {
            // NCS expand uses statement
            container source-interface {
              leaf loopback {
                type uint8;
              }
            }
          }
          container ntp {
            // NCS expand uses statement
            container source-interface {
              leaf loopback {
                type uint8;
              }
            }
          }
          container syslog {
            // NCS expand uses statement
            container source-interface {
              leaf loopback {
                type uint8;
              }
            }
          }
          container ssh {
            // NCS expand uses statement
            container source-interface {
              leaf loopback {
                type uint8;
              }
            }
          }
          container telnet {
            // NCS expand uses statement
            container source-interface {
              leaf loopback {
                type uint8;
              }
            }
          }
          container ftp {
            // NCS expand uses statement
            container source-interface {
              leaf loopback {
                type uint8;
              }
            }
          }
          container tftp {
            // NCS expand uses statement
            container source-interface {
              leaf loopback {
                type uint8;
              }
            }
          }
          container rcp {
            // NCS expand uses statement
            container source-interface {
              leaf loopback {
                type uint8;
              }
            }
          }
          container web {
            // NCS expand uses statement
            container source-interface {
              leaf loopback {
                type uint8;
              }
            }
          }
          container all {
            // NCS expand uses statement
            container source-interface {
              leaf loopback {
                type uint8;
              }
            }
          }
        }
        container nat {
          // NCS expand uses statement
          container alg {
            // NCS expand uses statement
            leaf pptp {
              type enumeration {
                enum "disable";
                enum "enable";
              }
            }
            // NCS expand uses statement
            leaf tftp {
              type enumeration {
                enum "disable";
                enum "enable";
              }
            }
            // NCS expand uses statement
            leaf rtsp {
              type enumeration {
                enum "disable";
                enum "enable";
              }
            }
            // NCS expand uses statement
            leaf esp {
              type enumeration {
                enum "disable";
                enum "enable";
              }
            }
          }
          leaf allow-static-host {
            type empty;
          }
          container inside {
            container source {
              list list {
                tailf:cli-suppress-mode;
                key "id";
                leaf id {
                  type uint16;
                }
                leaf pool {
                  tailf:cli-hide-in-submode;
                  mandatory true;
                  type string;
                }
              }
              leaf class-list {
                type string;
              }
              list static {
                tailf:cli-suppress-mode;
                tailf:cli-compact-syntax;
                key "source nat";
                leaf source {
                  type inet:ipv4-address;
                }
                leaf nat {
                  type inet:ipv4-address;
                }
                leaf vrid {
                  type uint8;
                }
              }
            }
          }
          list pool {
            tailf:cli-suppress-mode;
            tailf:cli-sequence-commands {
              tailf:cli-reset-all-siblings;
            }
            tailf:cli-compact-syntax;
            key "name";
            leaf name {
              type string;
            }
            leaf ipstart {
              mandatory true;
              tailf:cli-drop-node-name;
              type inet:ipv4-address;
            }
            leaf ipend {
              mandatory true;
              tailf:cli-drop-node-name;
              type inet:ipv4-address;
            }
            leaf netmask {
              mandatory true;
              type union {
                type ipv4-mask;
                type string;
              }
            }
            leaf gateway {
              tailf:cli-optional-in-sequence;
              type inet:ipv4-address;
            }
            leaf ha-group-id {
              tailf:cli-optional-in-sequence;
              type uint16;
            }
            leaf ha-use-all-ports {
              tailf:cli-optional-in-sequence;
              type empty;
            }
            leaf vrid {
              tailf:cli-optional-in-sequence;
              type uint16;
            }
            leaf ip-rr {
              tailf:cli-break-sequence-commands;
              type empty;
            }
            leaf lsn {
              type empty;
            }
            leaf max-users-per-ip {
              type uint16;
            }
          }
          list pool-group {
            key "name";
            leaf name {
              type string;
            }
            leaf ha-group-id {
              tailf:cli-hide-in-submode;
              type uint16;
            }
            list member {
              key "member-id";
              tailf:cli-suppress-mode;
              leaf member-id {
                type string;
              }
            }
          }
          container range-list;
          leaf reset-idle-tcp-conn {
            type empty;
          }
          container template {
            list logging {
              key "name";
              leaf name {
                type string;
              }
            }
          }
          container translation {
            leaf icmp-timeout {
              type union {
                type uint16;
                type enumeration {
                  enum "fast";
                }
              }
            }
            leaf tcp-timeout {
              type uint16;
            }
            leaf udp-timeout {
              type uint16;
            }
            leaf syn-timeout {
              type uint16;
            }
            list service-timeout {
              tailf:cli-compact-syntax;
              tailf:cli-sequence-commands;
              tailf:cli-suppress-mode;
              key "protocol from";
              leaf protocol {
                type enumeration {
                  enum "tcp";
                  enum "udp";
                }
              }
              leaf from {
                type uint16;
              }
              leaf to {
                tailf:cli-optional-in-sequence;
                type uint16;
              }
              leaf timeout {
                tailf:cli-drop-node-name;
                type union {
                  type uint16;
                  type enumeration {
                    enum "fast";
                  }
                }
              }
            }
          }
          container lsn {
            container endpoint-independent-mapping {
              container tcp {
                container enable {
                  leaf ephemeral {
                    type empty;
                  }
                  leaf well-known {
                    type empty;
                  }
                }
              }
              container udp {
                container enable {
                  leaf ephemeral {
                    type empty;
                  }
                  leaf well-known {
                    type empty;
                  }
                }
              }
            }
            container endpoint-independent-filtering {
              container tcp {
                container enable {
                  leaf ephemeral {
                    type empty;
                    must '../../../../endpoint-independent-mapping/tcp/enable/ephemeral' {
                      tailf:xpath-root 3;
                      error-message "Endpoint-independent-filtering cannot be enabled when endpoint-independent-mapping is disabled";
                    }
                  }
                  leaf well-known {
                    type empty;
                    must '../../../../endpoint-independent-mapping/tcp/enable/well-known' {
                      tailf:xpath-root 3;
                      error-message "Endpoint-independent-filtering cannot be enabled when endpoint-independent-mapping is disabled";
                    }
                  }
                }
              }
              container udp {
                container enable {
                  leaf ephemeral {
                    type empty;
                    must '../../../../endpoint-independent-mapping/udp/enable/ephemeral' {
                      tailf:xpath-root 3;
                      error-message "Endpoint-independent-filtering cannot be enabled when endpoint-independent-mapping is disabled";
                    }
                  }
                  leaf well-known {
                    type empty;
                    must '../../../../endpoint-independent-mapping/udp/enable/well-known' {
                      tailf:xpath-root 3;
                      error-message "Endpoint-independent-filtering cannot be enabled when endpoint-independent-mapping is disabled";
                    }
                  }
                }
              }
            }
            leaf ip-selection {
              type enumeration {
                enum "random";
                enum "round-robin";
                enum "least-used-strict";
                enum "least-udp-used-strict";
                enum "least-tcp-used-strict";
                enum "least-reserved-strict";
                enum "least-udp-reserved-strict";
                enum "least-tcp-reserved-strict";
                enum "least-users-strict";
              }
            }
            leaf attempt-port-preservation {
              type enumeration {
                enum "disable";
                enum "enable";
              }
            }
            // NCS expand uses statement
            container alg {
              // NCS expand uses statement
              leaf pptp {
                type enumeration {
                  enum "disable";
                  enum "enable";
                }
              }
              // NCS expand uses statement
              leaf tftp {
                type enumeration {
                  enum "disable";
                  enum "enable";
                }
              }
              // NCS expand uses statement
              leaf rtsp {
                type enumeration {
                  enum "disable";
                  enum "enable";
                }
              }
              // NCS expand uses statement
              leaf esp {
                type enumeration {
                  enum "disable";
                  enum "enable";
                }
              }
            }
          }
        }
        // NCS expand uses statement
        list prefix-list {
          tailf:cli-suppress-mode;
          tailf:cli-compact-syntax;
          key "name seq";
          leaf name {
            type string;
          }
          leaf seq {
            tailf:cli-expose-key-name;
            type uint32;
          }
          choice permit-deny {
            leaf permit {
              type union {
                type enumeration {
                  enum "any";
                }
                type tailf:ipv4-address-and-prefix-length;
              }
            }
            leaf deny {
              type union {
                type enumeration {
                  enum "any";
                }
                type tailf:ipv4-address-and-prefix-length;
              }
            }
          }
          leaf ge {
            type uint8;
          }
          leaf le {
            type uint8;
          }
        }
        // NCS expand uses statement
        list route {
          tailf:cli-compact-syntax;
          tailf:cli-sequence-commands {
            tailf:cli-reset-siblings;
          }
          tailf:cli-suppress-mode;
          key "ip mask forwarding-router";
          leaf ip {
            type inet:ipv4-address;
          }
          leaf mask {
            type string;
          }
          leaf forwarding-router {
            type inet:ipv4-address;
          }
          leaf distance {
            tailf:cli-drop-node-name;
            tailf:cli-optional-in-sequence;
            type uint8;
          }
          leaf cpu-process {
            tailf:cli-drop-node-name;
            tailf:cli-optional-in-sequence;
            type enumeration {
              enum "cpu-process";
            }
          }
        }
        container tcp {
          container syn-cookie {
            leaf threshold {
              type uint8;
            }
          }
        }
      }
      uses bfd-grouping;
      uses health-grouping;
      uses glid-grouping;
      uses class-list-grouping;
      uses class-list-group-grouping;
      uses slb-grouping;
      uses gslb-grouping;
      uses vrrp-a-grouping;
      uses vlan-grouping;
      uses logging-grouping;
      uses bw-list-grouping;
      uses ip-list-grouping;
      uses cgnv6-grouping;
      uses router-grouping;
      uses system-jumbo-global-grouping;
      uses hd-monitor-grouping;
      uses clock-grouping;
      uses ntp-grouping;
      uses netflow-grouping;
      uses tacacs-server-grouping;
      uses radius-server-grouping;
      uses authentication-grouping;
      uses ipv6-grouping;
      uses nat64-grouping;
      uses lsn-lid-grouping;
      uses ha-grouping;
      uses floating-ip-grouping;
      uses snmp-server-grouping;
      uses audit-grouping;
      uses terminal-grouping;
      uses web-service-grouping;
      uses multi-config-grouping;
      uses lldp-grouping;
      uses banner-grouping;
      uses device-context-grouping;
      uses system-grouping;
      uses partition-grouping;
      uses partition-group-grouping;
      uses access-list-grouping;
      uses tftp-grouping;
      uses stats-data-disable-grouping;
      uses syn-cookie-grouping;
      uses enable-management-grouping;
      uses disable-management-grouping;
      uses monitor-grouping;
      uses extended-stats-grouping;
      uses admin-grouping;
      uses enable-core-grouping;
      uses trunk-grouping;
      uses lacp-grouping;
      uses sflow-grouping;
      uses zone-grouping;
      uses object-grouping;
      uses object-group-grouping;
      uses rule-set-grouping;
      uses fw-grouping;
      uses route-map-grouping;
      uses accounting-grouping;
      uses ve-stats-grouping;
      uses acos-events-grouping;
      uses bgp-grouping;
      uses harmony-controller-grouping;
      // NCS expand uses statement
      container vcs {
        leaf state {
          tailf:cli-drop-node-name;
          type enumeration {
            enum "enable";
            enum "disable";
          }
        }
        list device {
          key "id";
          leaf id {
            type uint8;
          }
          leaf priority {
            type uint8;
          }
          container interfaces {
            leaf management {
              type empty;
            }
            list ethernet {
              tailf:cli-suppress-mode;
              key "id";
              leaf id {
                type uint8;
              }
            }
            list trunk {
              tailf:cli-suppress-mode;
              key "id";
              leaf id {
                type uint8;
              }
            }
            list ve {
              tailf:cli-suppress-mode;
              key "id";
              leaf id {
                type uint16;
              }
            }
          }
          leaf enable {
            type empty;
          }
        }
        list floating-ip {
          tailf:cli-suppress-mode;
          tailf:cli-delete-when-empty;
          tailf:cli-compact-syntax;
          key "floating-ip-address";
          leaf floating-ip-address {
            tailf:cli-drop-node-name;
            type inet:ipv4-address;
          }
          leaf mask {
            tailf:cli-drop-node-name;
            type ipv4-mask;
          }
        }
        leaf ssl-enable {
          type empty;
        }
        leaf failure-retry-count {
          type union {
            type enumeration {
              enum "forever";
            }
            type uint8;
          }
        }
      }
    }
  }
  augment "/ncs:devices/ncs:template/ncs:ned-id/ncs:config" {
    leaf os-major {
      type string;
    }
    leaf os-minor {
      type string;
    }
    uses ncs_template_ip-list-grouping;
    uses ncs_template_cgnv6-grouping;
    uses ncs_template_sflow-grouping;
    uses ncs_template_accounting-grouping;
    uses ncs_template_acos-events-grouping;
    uses ncs_template_authorization-grouping;
    uses ncs_template_bgp-grouping;
    uses ncs_template_lacp-grouping;
    uses ncs_template_aflex-grouping;
    container EXEC {
      tailf:cli-drop-node-name;
    }
    uses ncs_template_system-jumbo-global-grouping;
    uses ncs_template_hostname-grouping;
    uses ncs_template_hd-monitor-grouping;
    uses ncs_template_timezone-nodst-grouping;
    uses ncs_template_clock-grouping;
    uses ncs_template_ntp-grouping;
    uses ncs_template_netflow-grouping;
    uses ncs_template_trunk-grouping;
    uses ncs_template_class-list-grouping;
    uses ncs_template_class-list-group-grouping;
    uses ncs_template_tacacs-server-grouping;
    uses ncs_template_radius-server-grouping;
    uses ncs_template_authentication-grouping;
    // NCS expand uses statement
    container interface {

      grouping lldp-interface-grouping {
        container lldp {
          container enable {
            leaf rx {
              type empty;
            }
            leaf tx {
              type empty;
            }
          }
          leaf notification {
            type string;
          }
          leaf tx-dot1-tlvs {
            type string;
          }
        }
      }
      container management {
        container bcast-rate-limit {
          presence "present";
          leaf rate {
            type string;
          }
        }
        container ip {
          // NCS expand uses statement
          list address {
            // NCS patched for predictable order
            ordered-by user;
            tailf:cli-suppress-mode;
            key "address mask";
            leaf address {
              type string;
            }
            leaf mask {
              type string;
            }
          }
          leaf control-apps-use-mgmt-port {
            type empty;
          }
          leaf default-gateway {
            type string;
          }
        }
        container ipv6 {
          list address {
            // NCS patched for predictable order
            ordered-by user;
            key "ip";
            tailf:cli-suppress-mode;
            leaf ip {
              tailf:cli-drop-node-name;
              type ncs_template_ipv6-prefix;
            }
            leaf link-local {
              type empty;
            }
          }
          leaf default-gateway {
            type string;
          }
        }
        // NCS expand uses statement
        container lldp {
          container enable {
            leaf rx {
              type empty;
            }
            leaf tx {
              type empty;
            }
          }
          leaf notification {
            type string;
          }
          leaf tx-dot1-tlvs {
            type string;
          }
        }
        leaf flow-control {
          type empty;
        }
        container access-list {
          leaf id {
            tailf:cli-drop-node-name;
            type string;
          }
          leaf in {
            // NCS drop must statement
            type empty;
          }
        }
        leaf enabled-disabled {
          tailf:cli-drop-node-name;
          type string;
        }
        leaf duplexity {
          type string;
        }
        leaf mtu {
          type string;
        }
        leaf speed {
          type string;
        }
      }
      list ethernet {
        // NCS patched for predictable order
        ordered-by user;
        key "nr";
        leaf nr {
          type ncs_template_ethernet-index;
        }
        leaf name {
          type string;
        }
        container ip {
          // NCS expand uses statement
          list address {
            // NCS patched for predictable order
            ordered-by user;
            tailf:cli-suppress-mode;
            key "address mask";
            leaf address {
              type string;
            }
            leaf mask {
              type string;
            }
          }
          leaf cache-spoofing-port {
            type empty;
          }
          leaf helper-address {
            type string;
          }
          container nat {
            leaf inside {
              type empty;
            }
            leaf outside {
              type empty;
            }
          }
          container ospf;
          container router {
            container isis {
              presence "true";
              leaf cmds {
                tailf:cli-drop-node-name;
                type string;
              }
            }
          }
          leaf allow-promiscuous-vip {
            type empty;
          }
          container tcp {
            leaf syn-cookie {
              type empty;
            }
          }
        }
        container ipv6 {
          container access-list {
            leaf id {
              tailf:cli-drop-node-name;
              type string;
            }
            leaf in {
              // NCS drop must statement
              type empty;
            }
          }
          list address {
            // NCS patched for predictable order
            ordered-by user;
            key "ip";
            tailf:cli-suppress-mode;
            leaf ip {
              tailf:cli-drop-node-name;
              type ncs_template_ipv6-prefix;
            }
            leaf link-local {
              type empty;
            }
            leaf anycast {
              type empty;
            }
          }
          container nat {
            leaf inside {
              type empty;
            }
            leaf outside {
              type empty;
            }
          }
          container ndisc {
            container router-advertisement;
          }
          container ospf;
          container router {
            container isis {
              presence "true";
              leaf cmds {
                tailf:cli-drop-node-name;
                type string;
              }
            }
          }
        }
        leaf load-interval {
          type string;
        }
        container access-list {
          leaf id {
            tailf:cli-drop-node-name;
            type string;
          }
          leaf in {
            // NCS drop must statement
            type empty;
          }
        }
        leaf state {
          tailf:cli-drop-node-name;
          type string;
        }
        leaf state-alt {
          tailf:cli-drop-node-name;
          type string;
        }
        leaf duplexity {
          type string;
        }
        leaf cpu-process {
          type empty;
        }
        leaf flow-control {
          type empty;
        }
        container icmp-rate-limit {
          leaf rate {
            tailf:cli-drop-node-name;
            type string;
          }
          leaf lockup {
            // NCS drop must statement
            type string;
          }
          leaf lockup-period {
            // NCS drop must statement
            tailf:cli-drop-node-name;
            type string;
          }
        }
        container ospf;
        container isis;
        leaf l3-vlan-fwd-disable {
          type empty;
        }
        container lacp {
          leaf port-priority {
            type string;
          }
          leaf timeout {
            type string;
          }
          container trunk {
            leaf number {
              tailf:cli-drop-node-name;
              type string;
            }
            leaf admin-key {
              // NCS drop must statement
              type string;
            }
            leaf mode {
              // NCS drop must statement
              type string;
            }
            leaf unidirectional-detection {
              // NCS drop must statement
              type empty;
            }
          }
          container udld-timeout {
            leaf timeout-type {
              tailf:cli-drop-node-name;
              type string;
            }
            leaf milli {
              tailf:cli-drop-node-name;
              type string;
            }
            leaf secs {
              tailf:cli-drop-node-name;
              type string;
            }
          }
        }
        // NCS expand uses statement
        container lldp {
          container enable {
            leaf rx {
              type empty;
            }
            leaf tx {
              type empty;
            }
          }
          leaf notification {
            type string;
          }
          leaf tx-dot1-tlvs {
            type string;
          }
        }
        leaf mtu {
          type string;
        }
        leaf speed {
          type string;
        }
        list trunk-group-list {
          // NCS patched for predictable order
          ordered-by user;
          key "trunk-group-key";
          tailf:cli-drop-node-name;
          leaf trunk-group-key {
            type string;
          }
          leaf trunk-group-id {
            tailf:cli-drop-node-name;
            // NCS drop mandatory statement
            type string;
          }
          leaf trunk-group-type {
            tailf:cli-drop-node-name;
            type string;
          }
        }
      }
      list trunk {
        // NCS patched for predictable order
        ordered-by user;
        key "nr";
        leaf nr {
          type ncs_template_ethernet-index;
        }
        leaf name {
          type string;
        }
        leaf state {
          tailf:cli-drop-node-name;
          type string;
        }
        container icmp-rate-limit {
          leaf rate {
            tailf:cli-drop-node-name;
            type string;
          }
          leaf lockup {
            // NCS drop must statement
            type string;
          }
          leaf lockup-period {
            // NCS drop must statement
            tailf:cli-drop-node-name;
            type string;
          }
        }
        list access-list {
          // NCS patched for predictable order
          ordered-by user;
          tailf:cli-suppress-mode;
          key "id in-type";
          leaf id {
            type string;
          }
          leaf in-type {
            type string;
          }
        }
        container ip {
          list address {
            // NCS patched for predictable order
            ordered-by user;
            key "ip mask";
            tailf:cli-suppress-mode;
            leaf ip {
              type string;
            }
            leaf mask {
              type ncs_template_ipv4-mask;
            }
          }
          leaf allow-promiscuous-vip {
            type empty;
          }
          leaf cache-spoofing-port {
            type empty;
          }
          container nat {
            leaf inside {
              type empty;
            }
            leaf outside {
              type empty;
            }
          }
        }
      }
      list loopback {
        // NCS patched for predictable order
        ordered-by user;
        key "nr";
        leaf nr {
          type ncs_template_ethernet-index;
        }
        container ip {
          // NCS expand uses statement
          list address {
            // NCS patched for predictable order
            ordered-by user;
            tailf:cli-suppress-mode;
            key "address mask";
            leaf address {
              type string;
            }
            leaf mask {
              type string;
            }
          }
          container router {
            choice isis-choice {
              container isis-alt {
                tailf:cli-drop-node-name;
                leaf isis {
                  type string;
                }
              }
              leaf isis {
                type empty;
              }
            }
          }
        }
        container icmp-rate-limit {
          leaf rate {
            tailf:cli-drop-node-name;
            type string;
          }
          leaf lockup {
            // NCS drop must statement
            type string;
          }
          leaf lockup-period {
            tailf:cli-drop-node-name;
            // NCS drop must statement
            type string;
          }
        }
        leaf state {
          tailf:cli-drop-node-name;
          type string;
        }
      }
      list ve {
        // NCS patched for predictable order
        ordered-by user;
        key "id";
        leaf id {
          type ncs_template_vlan-index;
        }
        leaf name {
          type string;
        }
        container bfd {
          container echo {
            presence "true";
          }
        }
        container icmp-rate-limit {
          leaf rate {
            tailf:cli-drop-node-name;
            type string;
          }
          leaf lockup {
            // NCS drop must statement
            type string;
          }
          leaf lockup-period {
            tailf:cli-drop-node-name;
            // NCS drop must statement
            type string;
          }
        }
        container access-list {
          leaf id {
            tailf:cli-drop-node-name;
            type string;
          }
          leaf in {
            // NCS drop must statement
            type empty;
          }
        }
        leaf l3-vlan-fwd-disable {
          type empty;
        }
        container ip {
          leaf allow-promiscuous-vip {
            type empty;
          }
          leaf cache-spoofing-port {
            type empty;
          }
          leaf helper-address {
            type string;
          }
          container nat {
            leaf inside {
              type empty;
            }
            leaf outside {
              type empty;
            }
          }
          container ospf;
          container router {
            container isis {
              presence "true";
              leaf cmds {
                tailf:cli-drop-node-name;
                type string;
              }
            }
          }
          container tcp {
            leaf syn-cookie {
              type empty;
            }
          }
          // NCS expand uses statement
          list address {
            // NCS patched for predictable order
            ordered-by user;
            tailf:cli-suppress-mode;
            key "address mask";
            leaf address {
              type string;
            }
            leaf mask {
              type string;
            }
          }
        }
        container ipv6 {
          container access-list {
            leaf id {
              tailf:cli-drop-node-name;
              type string;
            }
            leaf in {
              // NCS drop must statement
              type empty;
            }
          }
          container nat {
            leaf inside {
              type empty;
            }
            leaf outside {
              type empty;
            }
          }
          container ndisc {
            container router-advertisement;
          }
          container ospf;
          container router {
            container isis {
              presence "true";
              leaf cmds {
                tailf:cli-drop-node-name;
                type string;
              }
            }
          }
          list address {
            // NCS patched for predictable order
            ordered-by user;
            key "ip";
            tailf:cli-suppress-mode;
            leaf ip {
              tailf:cli-drop-node-name;
              type ncs_template_ipv6-prefix;
            }
            leaf link-local {
              type empty;
            }
            leaf anycast {
              type empty;
            }
          }
        }
        leaf mtu {
          type string;
        }
        leaf state {
          tailf:cli-drop-node-name;
          type string;
        }
        container isis;
        container ospf;
      }
    }
    uses ncs_template_vlan-grouping;
    // NCS expand uses statement
    container ip {
      list access-list {
        // NCS patched for predictable order
        ordered-by user;
        key "name";
        leaf name {
          type string;
        }
        list access-list-rule {
          // NCS patched for predictable order
          ordered-by user;
          tailf:cli-suppress-mode;
          tailf:cli-drop-node-name;
          key "rule";
          leaf rule {
            type string;
          }
        }
      }
      list address {
        // NCS patched for predictable order
        ordered-by user;
        key "ip";
        tailf:cli-suppress-mode;
        leaf ip {
          tailf:cli-drop-node-name;
          type string;
        }
        leaf mask {
          tailf:cli-drop-node-name;
          type ncs_template_ipv4-mask;
        }
      }
      container anomaly-drop {
        leaf bad-content {
          type string;
        }
        leaf drop-all {
          type empty;
        }
        leaf frag {
          type empty;
        }
        leaf ip-option {
          type string;
        }
        leaf land-attack {
          type empty;
        }
        leaf out-of-sequence {
          type string;
        }
        leaf ping-of-death {
          type empty;
        }
        leaf tcp-no-flag {
          type empty;
        }
        leaf tcp-syn-fin {
          type empty;
        }
        leaf tcp-syn-frag {
          type empty;
        }
        leaf zero-window {
          type string;
        }
        container security-attack {
          leaf layer-3 {
            type empty;
          }
          leaf layer-4 {
            type empty;
          }
        }
        list packet-deformity {
          // NCS patched for predictable order
          ordered-by user;
          tailf:cli-suppress-mode;
          key "layer";
          leaf layer {
            type string;
          }
        }
      }
      container as-path {
        list access-list {
          // NCS patched for predictable order
          ordered-by user;
          tailf:cli-suppress-mode;
          key "name action path";
          leaf name {
            type string;
          }
          leaf action {
            type string;
          }
          leaf path {
            type string;
          }
        }
      }
      container community-list {
        list standard-number {
          // NCS patched for predictable order
          ordered-by user;
          tailf:cli-drop-node-name;
          tailf:cli-suppress-mode;
          key "nr";
          leaf nr {
            type string;
          }
          list rules {
            // NCS patched for predictable order
            ordered-by user;
            tailf:cli-drop-node-name;
            tailf:cli-suppress-mode;
            key "action expr";
            leaf action {
              type string;
            }
            leaf expr {
              type string;
            }
          }
        }
        list expanded-number {
          // NCS patched for predictable order
          ordered-by user;
          tailf:cli-drop-node-name;
          tailf:cli-suppress-mode;
          key "nr";
          leaf nr {
            type string;
          }
          list rules {
            // NCS patched for predictable order
            ordered-by user;
            tailf:cli-drop-node-name;
            tailf:cli-suppress-mode;
            key "action expr";
            leaf action {
              type string;
            }
            leaf expr {
              type string;
            }
          }
        }
        list word {
          // NCS patched for predictable order
          ordered-by user;
          tailf:cli-drop-node-name;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
        list expanded {
          // NCS patched for predictable order
          ordered-by user;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
        list standard {
          // NCS patched for predictable order
          ordered-by user;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
      }
      leaf default-gateway {
        type string;
      }
      container dns {
        leaf primary {
          type string;
        }
        leaf secondary {
          type string;
        }
        leaf suffix {
          type string;
        }
      }
      container extcommunity-list {
        list standard-number {
          // NCS patched for predictable order
          ordered-by user;
          tailf:cli-drop-node-name;
          tailf:cli-suppress-mode;
          key "nr";
          leaf nr {
            type string;
          }
          list rules {
            // NCS patched for predictable order
            ordered-by user;
            tailf:cli-drop-node-name;
            tailf:cli-suppress-mode;
            key "action expr";
            leaf action {
              type string;
            }
            leaf expr {
              type string;
            }
          }
        }
        list expanded-number {
          // NCS patched for predictable order
          ordered-by user;
          tailf:cli-drop-node-name;
          tailf:cli-suppress-mode;
          key "nr";
          leaf nr {
            type string;
          }
          list rules {
            // NCS patched for predictable order
            ordered-by user;
            tailf:cli-drop-node-name;
            tailf:cli-suppress-mode;
            key "action expr";
            leaf action {
              type string;
            }
            leaf expr {
              type string;
            }
          }
        }
        list expanded {
          // NCS patched for predictable order
          ordered-by user;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
        list standard {
          // NCS patched for predictable order
          ordered-by user;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
      }
      container frag {
        leaf buff {
          type string;
        }
        container cpu-threshold {
          leaf high {
            type string;
          }
          leaf low {
            type string;
          }
        }
        leaf max-reassembly-sessions {
          type string;
        }
        leaf timeout {
          type string;
        }
      }
      container icmp {
        container disable {
          leaf redirect {
            type empty;
          }
          leaf unreachable {
            type empty;
          }
        }
      }
      container mgmt-traffic {
        container snmp {
          // NCS expand uses statement
          container source-interface {
            leaf loopback {
              type string;
            }
          }
        }
        container ntp {
          // NCS expand uses statement
          container source-interface {
            leaf loopback {
              type string;
            }
          }
        }
        container syslog {
          // NCS expand uses statement
          container source-interface {
            leaf loopback {
              type string;
            }
          }
        }
        container ssh {
          // NCS expand uses statement
          container source-interface {
            leaf loopback {
              type string;
            }
          }
        }
        container telnet {
          // NCS expand uses statement
          container source-interface {
            leaf loopback {
              type string;
            }
          }
        }
        container ftp {
          // NCS expand uses statement
          container source-interface {
            leaf loopback {
              type string;
            }
          }
        }
        container tftp {
          // NCS expand uses statement
          container source-interface {
            leaf loopback {
              type string;
            }
          }
        }
        container rcp {
          // NCS expand uses statement
          container source-interface {
            leaf loopback {
              type string;
            }
          }
        }
        container web {
          // NCS expand uses statement
          container source-interface {
            leaf loopback {
              type string;
            }
          }
        }
        container all {
          // NCS expand uses statement
          container source-interface {
            leaf loopback {
              type string;
            }
          }
        }
      }
      container nat {
        // NCS expand uses statement
        container alg {
          // NCS expand uses statement
          leaf pptp {
            type string;
          }
          // NCS expand uses statement
          leaf tftp {
            type string;
          }
          // NCS expand uses statement
          leaf rtsp {
            type string;
          }
          // NCS expand uses statement
          leaf esp {
            type string;
          }
        }
        leaf allow-static-host {
          type empty;
        }
        container inside {
          container source {
            list list {
              // NCS patched for predictable order
              ordered-by user;
              tailf:cli-suppress-mode;
              key "id";
              leaf id {
                type string;
              }
              leaf pool {
                // NCS drop mandatory statement
                type string;
              }
            }
            leaf class-list {
              type string;
            }
            list static {
              // NCS patched for predictable order
              ordered-by user;
              tailf:cli-suppress-mode;
              key "source nat";
              leaf source {
                type string;
              }
              leaf nat {
                type string;
              }
              leaf vrid {
                type string;
              }
            }
          }
        }
        list pool {
          // NCS patched for predictable order
          ordered-by user;
          tailf:cli-suppress-mode;
          key "name";
          leaf name {
            type string;
          }
          leaf ipstart {
            // NCS drop mandatory statement
            tailf:cli-drop-node-name;
            type string;
          }
          leaf ipend {
            // NCS drop mandatory statement
            tailf:cli-drop-node-name;
            type string;
          }
          leaf netmask {
            // NCS drop mandatory statement
            type string;
          }
          leaf gateway {
            type string;
          }
          leaf ha-group-id {
            type string;
          }
          leaf ha-use-all-ports {
            type empty;
          }
          leaf vrid {
            type string;
          }
          leaf ip-rr {
            type empty;
          }
          leaf lsn {
            type empty;
          }
          leaf max-users-per-ip {
            type string;
          }
        }
        list pool-group {
          // NCS patched for predictable order
          ordered-by user;
          key "name";
          leaf name {
            type string;
          }
          leaf ha-group-id {
            type string;
          }
          list member {
            // NCS patched for predictable order
            ordered-by user;
            key "member-id";
            tailf:cli-suppress-mode;
            leaf member-id {
              type string;
            }
          }
        }
        container range-list;
        leaf reset-idle-tcp-conn {
          type empty;
        }
        container template {
          list logging {
            // NCS patched for predictable order
            ordered-by user;
            key "name";
            leaf name {
              type string;
            }
          }
        }
        container translation {
          leaf icmp-timeout {
            type string;
          }
          leaf tcp-timeout {
            type string;
          }
          leaf udp-timeout {
            type string;
          }
          leaf syn-timeout {
            type string;
          }
          list service-timeout {
            // NCS patched for predictable order
            ordered-by user;
            tailf:cli-suppress-mode;
            key "protocol from";
            leaf protocol {
              type string;
            }
            leaf from {
              type string;
            }
            leaf to {
              type string;
            }
            leaf timeout {
              tailf:cli-drop-node-name;
              type string;
            }
          }
        }
        container lsn {
          container endpoint-independent-mapping {
            container tcp {
              container enable {
                leaf ephemeral {
                  type empty;
                }
                leaf well-known {
                  type empty;
                }
              }
            }
            container udp {
              container enable {
                leaf ephemeral {
                  type empty;
                }
                leaf well-known {
                  type empty;
                }
              }
            }
          }
          container endpoint-independent-filtering {
            container tcp {
              container enable {
                leaf ephemeral {
                  type empty;
                  // NCS drop must statement
                }
                leaf well-known {
                  type empty;
                  // NCS drop must statement
                }
              }
            }
            container udp {
              container enable {
                leaf ephemeral {
                  type empty;
                  // NCS drop must statement
                }
                leaf well-known {
                  type empty;
                  // NCS drop must statement
                }
              }
            }
          }
          leaf ip-selection {
            type string;
          }
          leaf attempt-port-preservation {
            type string;
          }
          // NCS expand uses statement
          container alg {
            // NCS expand uses statement
            leaf pptp {
              type string;
            }
            // NCS expand uses statement
            leaf tftp {
              type string;
            }
            // NCS expand uses statement
            leaf rtsp {
              type string;
            }
            // NCS expand uses statement
            leaf esp {
              type string;
            }
          }
        }
      }
      // NCS expand uses statement
      list prefix-list {
        // NCS patched for predictable order
        ordered-by user;
        tailf:cli-suppress-mode;
        key "name seq";
        leaf name {
          type string;
        }
        leaf seq {
          type string;
        }
        choice permit-deny {
          leaf permit {
            type string;
          }
          leaf deny {
            type string;
          }
        }
        leaf ge {
          type string;
        }
        leaf le {
          type string;
        }
      }
      // NCS expand uses statement
      list route {
        // NCS patched for predictable order
        ordered-by user;
        tailf:cli-suppress-mode;
        key "ip mask forwarding-router";
        leaf ip {
          type string;
        }
        leaf mask {
          type string;
        }
        leaf forwarding-router {
          type string;
        }
        leaf distance {
          tailf:cli-drop-node-name;
          type string;
        }
        leaf cpu-process {
          tailf:cli-drop-node-name;
          type string;
        }
      }
      container tcp {
        container syn-cookie {
          leaf threshold {
            type string;
          }
        }
      }
    }
    uses ncs_template_ipv6-grouping;
    uses ncs_template_nat64-grouping;
    uses ncs_template_lsn-lid-grouping;
    uses ncs_template_ha-grouping;
    uses ncs_template_floating-ip-grouping;
    uses ncs_template_glid-grouping;
    uses ncs_template_slb-grouping;
    uses ncs_template_gslb-grouping;
    uses ncs_template_logging-grouping;
    uses ncs_template_snmp-server-grouping;
    uses ncs_template_audit-grouping;
    uses ncs_template_harmony-controller-grouping;
    uses ncs_template_terminal-grouping;
    uses ncs_template_web-service-grouping;
    uses ncs_template_multi-config-grouping;
    uses ncs_template_banner-grouping;
    uses ncs_template_vrrp-a-grouping;
    uses ncs_template_router-grouping;
    uses ncs_template_bfd-grouping;
    uses ncs_template_lldp-grouping;
    uses ncs_template_route-map-grouping;
    uses ncs_template_device-context-grouping;
    // NCS expand uses statement
    container vcs {
      leaf state {
        tailf:cli-drop-node-name;
        type string;
      }
      list device {
        // NCS patched for predictable order
        ordered-by user;
        key "id";
        leaf id {
          type string;
        }
        leaf priority {
          type string;
        }
        container interfaces {
          leaf management {
            type empty;
          }
          list ethernet {
            // NCS patched for predictable order
            ordered-by user;
            tailf:cli-suppress-mode;
            key "id";
            leaf id {
              type string;
            }
          }
          list trunk {
            // NCS patched for predictable order
            ordered-by user;
            tailf:cli-suppress-mode;
            key "id";
            leaf id {
              type string;
            }
          }
          list ve {
            // NCS patched for predictable order
            ordered-by user;
            tailf:cli-suppress-mode;
            key "id";
            leaf id {
              type string;
            }
          }
        }
        leaf enable {
          type empty;
        }
      }
      list floating-ip {
        // NCS patched for predictable order
        ordered-by user;
        tailf:cli-suppress-mode;
        key "floating-ip-address";
        leaf floating-ip-address {
          tailf:cli-drop-node-name;
          type string;
        }
        leaf mask {
          tailf:cli-drop-node-name;
          type ncs_template_ipv4-mask;
        }
      }
      leaf ssl-enable {
        type empty;
      }
      leaf failure-retry-count {
        type string;
      }
    }
    uses ncs_template_system-grouping;
    uses ncs_template_ve-stats-grouping;
    uses ncs_template_partition-grouping;
    uses ncs_template_partition-group-grouping;
    uses ncs_template_access-list-grouping;
    uses ncs_template_tftp-grouping;
    uses ncs_template_health-grouping;
    uses ncs_template_stats-data-disable-grouping;
    uses ncs_template_syn-cookie-grouping;
    uses ncs_template_enable-management-grouping;
    uses ncs_template_disable-management-grouping;
    uses ncs_template_monitor-grouping;
    uses ncs_template_extended-stats-grouping;
    uses ncs_template_admin-grouping;
    uses ncs_template_zone-grouping;
    uses ncs_template_object-grouping;
    uses ncs_template_object-group-grouping;
    uses ncs_template_rule-set-grouping;
    uses ncs_template_fw-grouping;
    uses ncs_template_enable-core-grouping;
    uses ncs_template_bw-list-grouping;
    list active-partition {
      // NCS patched for predictable order
      ordered-by user;
      key "name";
      leaf name {
        type string;
      }
      uses ncs_template_aflex-grouping;
      uses ncs_template_hostname-grouping;
      // NCS expand uses statement
      container interface {

        grouping lldp-interface-grouping {
          container lldp {
            container enable {
              leaf rx {
                type empty;
              }
              leaf tx {
                type empty;
              }
            }
            leaf notification {
              type string;
            }
            leaf tx-dot1-tlvs {
              type string;
            }
          }
        }
        container management {
          container bcast-rate-limit {
            presence "present";
            leaf rate {
              type string;
            }
          }
          container ip {
            // NCS expand uses statement
            list address {
              // NCS patched for predictable order
              ordered-by user;
              tailf:cli-suppress-mode;
              key "address mask";
              leaf address {
                type string;
              }
              leaf mask {
                type string;
              }
            }
            leaf control-apps-use-mgmt-port {
              type empty;
            }
            leaf default-gateway {
              type string;
            }
          }
          container ipv6 {
            list address {
              // NCS patched for predictable order
              ordered-by user;
              key "ip";
              tailf:cli-suppress-mode;
              leaf ip {
                tailf:cli-drop-node-name;
                type ncs_template_ipv6-prefix;
              }
              leaf link-local {
                type empty;
              }
            }
            leaf default-gateway {
              type string;
            }
          }
          // NCS expand uses statement
          container lldp {
            container enable {
              leaf rx {
                type empty;
              }
              leaf tx {
                type empty;
              }
            }
            leaf notification {
              type string;
            }
            leaf tx-dot1-tlvs {
              type string;
            }
          }
          leaf flow-control {
            type empty;
          }
          container access-list {
            leaf id {
              tailf:cli-drop-node-name;
              type string;
            }
            leaf in {
              // NCS drop must statement
              type empty;
            }
          }
          leaf enabled-disabled {
            tailf:cli-drop-node-name;
            type string;
          }
          leaf duplexity {
            type string;
          }
          leaf mtu {
            type string;
          }
          leaf speed {
            type string;
          }
        }
        list ethernet {
          // NCS patched for predictable order
          ordered-by user;
          key "nr";
          leaf nr {
            type ncs_template_ethernet-index;
          }
          leaf name {
            type string;
          }
          container ip {
            // NCS expand uses statement
            list address {
              // NCS patched for predictable order
              ordered-by user;
              tailf:cli-suppress-mode;
              key "address mask";
              leaf address {
                type string;
              }
              leaf mask {
                type string;
              }
            }
            leaf cache-spoofing-port {
              type empty;
            }
            leaf helper-address {
              type string;
            }
            container nat {
              leaf inside {
                type empty;
              }
              leaf outside {
                type empty;
              }
            }
            container ospf;
            container router {
              container isis {
                presence "true";
                leaf cmds {
                  tailf:cli-drop-node-name;
                  type string;
                }
              }
            }
            leaf allow-promiscuous-vip {
              type empty;
            }
            container tcp {
              leaf syn-cookie {
                type empty;
              }
            }
          }
          container ipv6 {
            container access-list {
              leaf id {
                tailf:cli-drop-node-name;
                type string;
              }
              leaf in {
                // NCS drop must statement
                type empty;
              }
            }
            list address {
              // NCS patched for predictable order
              ordered-by user;
              key "ip";
              tailf:cli-suppress-mode;
              leaf ip {
                tailf:cli-drop-node-name;
                type ncs_template_ipv6-prefix;
              }
              leaf link-local {
                type empty;
              }
              leaf anycast {
                type empty;
              }
            }
            container nat {
              leaf inside {
                type empty;
              }
              leaf outside {
                type empty;
              }
            }
            container ndisc {
              container router-advertisement;
            }
            container ospf;
            container router {
              container isis {
                presence "true";
                leaf cmds {
                  tailf:cli-drop-node-name;
                  type string;
                }
              }
            }
          }
          leaf load-interval {
            type string;
          }
          container access-list {
            leaf id {
              tailf:cli-drop-node-name;
              type string;
            }
            leaf in {
              // NCS drop must statement
              type empty;
            }
          }
          leaf state {
            tailf:cli-drop-node-name;
            type string;
          }
          leaf state-alt {
            tailf:cli-drop-node-name;
            type string;
          }
          leaf duplexity {
            type string;
          }
          leaf cpu-process {
            type empty;
          }
          leaf flow-control {
            type empty;
          }
          container icmp-rate-limit {
            leaf rate {
              tailf:cli-drop-node-name;
              type string;
            }
            leaf lockup {
              // NCS drop must statement
              type string;
            }
            leaf lockup-period {
              // NCS drop must statement
              tailf:cli-drop-node-name;
              type string;
            }
          }
          container ospf;
          container isis;
          leaf l3-vlan-fwd-disable {
            type empty;
          }
          container lacp {
            leaf port-priority {
              type string;
            }
            leaf timeout {
              type string;
            }
            container trunk {
              leaf number {
                tailf:cli-drop-node-name;
                type string;
              }
              leaf admin-key {
                // NCS drop must statement
                type string;
              }
              leaf mode {
                // NCS drop must statement
                type string;
              }
              leaf unidirectional-detection {
                // NCS drop must statement
                type empty;
              }
            }
            container udld-timeout {
              leaf timeout-type {
                tailf:cli-drop-node-name;
                type string;
              }
              leaf milli {
                tailf:cli-drop-node-name;
                type string;
              }
              leaf secs {
                tailf:cli-drop-node-name;
                type string;
              }
            }
          }
          // NCS expand uses statement
          container lldp {
            container enable {
              leaf rx {
                type empty;
              }
              leaf tx {
                type empty;
              }
            }
            leaf notification {
              type string;
            }
            leaf tx-dot1-tlvs {
              type string;
            }
          }
          leaf mtu {
            type string;
          }
          leaf speed {
            type string;
          }
          list trunk-group-list {
            // NCS patched for predictable order
            ordered-by user;
            key "trunk-group-key";
            tailf:cli-drop-node-name;
            leaf trunk-group-key {
              type string;
            }
            leaf trunk-group-id {
              tailf:cli-drop-node-name;
              // NCS drop mandatory statement
              type string;
            }
            leaf trunk-group-type {
              tailf:cli-drop-node-name;
              type string;
            }
          }
        }
        list trunk {
          // NCS patched for predictable order
          ordered-by user;
          key "nr";
          leaf nr {
            type ncs_template_ethernet-index;
          }
          leaf name {
            type string;
          }
          leaf state {
            tailf:cli-drop-node-name;
            type string;
          }
          container icmp-rate-limit {
            leaf rate {
              tailf:cli-drop-node-name;
              type string;
            }
            leaf lockup {
              // NCS drop must statement
              type string;
            }
            leaf lockup-period {
              // NCS drop must statement
              tailf:cli-drop-node-name;
              type string;
            }
          }
          list access-list {
            // NCS patched for predictable order
            ordered-by user;
            tailf:cli-suppress-mode;
            key "id in-type";
            leaf id {
              type string;
            }
            leaf in-type {
              type string;
            }
          }
          container ip {
            list address {
              // NCS patched for predictable order
              ordered-by user;
              key "ip mask";
              tailf:cli-suppress-mode;
              leaf ip {
                type string;
              }
              leaf mask {
                type ncs_template_ipv4-mask;
              }
            }
            leaf allow-promiscuous-vip {
              type empty;
            }
            leaf cache-spoofing-port {
              type empty;
            }
            container nat {
              leaf inside {
                type empty;
              }
              leaf outside {
                type empty;
              }
            }
          }
        }
        list loopback {
          // NCS patched for predictable order
          ordered-by user;
          key "nr";
          leaf nr {
            type ncs_template_ethernet-index;
          }
          container ip {
            // NCS expand uses statement
            list address {
              // NCS patched for predictable order
              ordered-by user;
              tailf:cli-suppress-mode;
              key "address mask";
              leaf address {
                type string;
              }
              leaf mask {
                type string;
              }
            }
            container router {
              choice isis-choice {
                container isis-alt {
                  tailf:cli-drop-node-name;
                  leaf isis {
                    type string;
                  }
                }
                leaf isis {
                  type empty;
                }
              }
            }
          }
          container icmp-rate-limit {
            leaf rate {
              tailf:cli-drop-node-name;
              type string;
            }
            leaf lockup {
              // NCS drop must statement
              type string;
            }
            leaf lockup-period {
              tailf:cli-drop-node-name;
              // NCS drop must statement
              type string;
            }
          }
          leaf state {
            tailf:cli-drop-node-name;
            type string;
          }
        }
        list ve {
          // NCS patched for predictable order
          ordered-by user;
          key "id";
          leaf id {
            type ncs_template_vlan-index;
          }
          leaf name {
            type string;
          }
          container bfd {
            container echo {
              presence "true";
            }
          }
          container icmp-rate-limit {
            leaf rate {
              tailf:cli-drop-node-name;
              type string;
            }
            leaf lockup {
              // NCS drop must statement
              type string;
            }
            leaf lockup-period {
              tailf:cli-drop-node-name;
              // NCS drop must statement
              type string;
            }
          }
          container access-list {
            leaf id {
              tailf:cli-drop-node-name;
              type string;
            }
            leaf in {
              // NCS drop must statement
              type empty;
            }
          }
          leaf l3-vlan-fwd-disable {
            type empty;
          }
          container ip {
            leaf allow-promiscuous-vip {
              type empty;
            }
            leaf cache-spoofing-port {
              type empty;
            }
            leaf helper-address {
              type string;
            }
            container nat {
              leaf inside {
                type empty;
              }
              leaf outside {
                type empty;
              }
            }
            container ospf;
            container router {
              container isis {
                presence "true";
                leaf cmds {
                  tailf:cli-drop-node-name;
                  type string;
                }
              }
            }
            container tcp {
              leaf syn-cookie {
                type empty;
              }
            }
            // NCS expand uses statement
            list address {
              // NCS patched for predictable order
              ordered-by user;
              tailf:cli-suppress-mode;
              key "address mask";
              leaf address {
                type string;
              }
              leaf mask {
                type string;
              }
            }
          }
          container ipv6 {
            container access-list {
              leaf id {
                tailf:cli-drop-node-name;
                type string;
              }
              leaf in {
                // NCS drop must statement
                type empty;
              }
            }
            container nat {
              leaf inside {
                type empty;
              }
              leaf outside {
                type empty;
              }
            }
            container ndisc {
              container router-advertisement;
            }
            container ospf;
            container router {
              container isis {
                presence "true";
                leaf cmds {
                  tailf:cli-drop-node-name;
                  type string;
                }
              }
            }
            list address {
              // NCS patched for predictable order
              ordered-by user;
              key "ip";
              tailf:cli-suppress-mode;
              leaf ip {
                tailf:cli-drop-node-name;
                type ncs_template_ipv6-prefix;
              }
              leaf link-local {
                type empty;
              }
              leaf anycast {
                type empty;
              }
            }
          }
          leaf mtu {
            type string;
          }
          leaf state {
            tailf:cli-drop-node-name;
            type string;
          }
          container isis;
          container ospf;
        }
      }
      // NCS expand uses statement
      container ip {
        list access-list {
          // NCS patched for predictable order
          ordered-by user;
          key "name";
          leaf name {
            type string;
          }
          list access-list-rule {
            // NCS patched for predictable order
            ordered-by user;
            tailf:cli-suppress-mode;
            tailf:cli-drop-node-name;
            key "rule";
            leaf rule {
              type string;
            }
          }
        }
        list address {
          // NCS patched for predictable order
          ordered-by user;
          key "ip";
          tailf:cli-suppress-mode;
          leaf ip {
            tailf:cli-drop-node-name;
            type string;
          }
          leaf mask {
            tailf:cli-drop-node-name;
            type ncs_template_ipv4-mask;
          }
        }
        container anomaly-drop {
          leaf bad-content {
            type string;
          }
          leaf drop-all {
            type empty;
          }
          leaf frag {
            type empty;
          }
          leaf ip-option {
            type string;
          }
          leaf land-attack {
            type empty;
          }
          leaf out-of-sequence {
            type string;
          }
          leaf ping-of-death {
            type empty;
          }
          leaf tcp-no-flag {
            type empty;
          }
          leaf tcp-syn-fin {
            type empty;
          }
          leaf tcp-syn-frag {
            type empty;
          }
          leaf zero-window {
            type string;
          }
          container security-attack {
            leaf layer-3 {
              type empty;
            }
            leaf layer-4 {
              type empty;
            }
          }
          list packet-deformity {
            // NCS patched for predictable order
            ordered-by user;
            tailf:cli-suppress-mode;
            key "layer";
            leaf layer {
              type string;
            }
          }
        }
        container as-path {
          list access-list {
            // NCS patched for predictable order
            ordered-by user;
            tailf:cli-suppress-mode;
            key "name action path";
            leaf name {
              type string;
            }
            leaf action {
              type string;
            }
            leaf path {
              type string;
            }
          }
        }
        container community-list {
          list standard-number {
            // NCS patched for predictable order
            ordered-by user;
            tailf:cli-drop-node-name;
            tailf:cli-suppress-mode;
            key "nr";
            leaf nr {
              type string;
            }
            list rules {
              // NCS patched for predictable order
              ordered-by user;
              tailf:cli-drop-node-name;
              tailf:cli-suppress-mode;
              key "action expr";
              leaf action {
                type string;
              }
              leaf expr {
                type string;
              }
            }
          }
          list expanded-number {
            // NCS patched for predictable order
            ordered-by user;
            tailf:cli-drop-node-name;
            tailf:cli-suppress-mode;
            key "nr";
            leaf nr {
              type string;
            }
            list rules {
              // NCS patched for predictable order
              ordered-by user;
              tailf:cli-drop-node-name;
              tailf:cli-suppress-mode;
              key "action expr";
              leaf action {
                type string;
              }
              leaf expr {
                type string;
              }
            }
          }
          list word {
            // NCS patched for predictable order
            ordered-by user;
            tailf:cli-drop-node-name;
            tailf:cli-suppress-mode;
            key "name";
            leaf name {
              type string;
            }
            list rules {
              // NCS patched for predictable order
              ordered-by user;
              tailf:cli-drop-node-name;
              tailf:cli-suppress-mode;
              key "action expr";
              leaf action {
                type string;
              }
              leaf expr {
                type string;
              }
            }
          }
          list expanded {
            // NCS patched for predictable order
            ordered-by user;
            tailf:cli-suppress-mode;
            key "name";
            leaf name {
              type string;
            }
            list rules {
              // NCS patched for predictable order
              ordered-by user;
              tailf:cli-drop-node-name;
              tailf:cli-suppress-mode;
              key "action expr";
              leaf action {
                type string;
              }
              leaf expr {
                type string;
              }
            }
          }
          list standard {
            // NCS patched for predictable order
            ordered-by user;
            tailf:cli-suppress-mode;
            key "name";
            leaf name {
              type string;
            }
            list rules {
              // NCS patched for predictable order
              ordered-by user;
              tailf:cli-drop-node-name;
              tailf:cli-suppress-mode;
              key "action expr";
              leaf action {
                type string;
              }
              leaf expr {
                type string;
              }
            }
          }
        }
        leaf default-gateway {
          type string;
        }
        container dns {
          leaf primary {
            type string;
          }
          leaf secondary {
            type string;
          }
          leaf suffix {
            type string;
          }
        }
        container extcommunity-list {
          list standard-number {
            // NCS patched for predictable order
            ordered-by user;
            tailf:cli-drop-node-name;
            tailf:cli-suppress-mode;
            key "nr";
            leaf nr {
              type string;
            }
            list rules {
              // NCS patched for predictable order
              ordered-by user;
              tailf:cli-drop-node-name;
              tailf:cli-suppress-mode;
              key "action expr";
              leaf action {
                type string;
              }
              leaf expr {
                type string;
              }
            }
          }
          list expanded-number {
            // NCS patched for predictable order
            ordered-by user;
            tailf:cli-drop-node-name;
            tailf:cli-suppress-mode;
            key "nr";
            leaf nr {
              type string;
            }
            list rules {
              // NCS patched for predictable order
              ordered-by user;
              tailf:cli-drop-node-name;
              tailf:cli-suppress-mode;
              key "action expr";
              leaf action {
                type string;
              }
              leaf expr {
                type string;
              }
            }
          }
          list expanded {
            // NCS patched for predictable order
            ordered-by user;
            tailf:cli-suppress-mode;
            key "name";
            leaf name {
              type string;
            }
            list rules {
              // NCS patched for predictable order
              ordered-by user;
              tailf:cli-drop-node-name;
              tailf:cli-suppress-mode;
              key "action expr";
              leaf action {
                type string;
              }
              leaf expr {
                type string;
              }
            }
          }
          list standard {
            // NCS patched for predictable order
            ordered-by user;
            tailf:cli-suppress-mode;
            key "name";
            leaf name {
              type string;
            }
            list rules {
              // NCS patched for predictable order
              ordered-by user;
              tailf:cli-drop-node-name;
              tailf:cli-suppress-mode;
              key "action expr";
              leaf action {
                type string;
              }
              leaf expr {
                type string;
              }
            }
          }
        }
        container frag {
          leaf buff {
            type string;
          }
          container cpu-threshold {
            leaf high {
              type string;
            }
            leaf low {
              type string;
            }
          }
          leaf max-reassembly-sessions {
            type string;
          }
          leaf timeout {
            type string;
          }
        }
        container icmp {
          container disable {
            leaf redirect {
              type empty;
            }
            leaf unreachable {
              type empty;
            }
          }
        }
        container mgmt-traffic {
          container snmp {
            // NCS expand uses statement
            container source-interface {
              leaf loopback {
                type string;
              }
            }
          }
          container ntp {
            // NCS expand uses statement
            container source-interface {
              leaf loopback {
                type string;
              }
            }
          }
          container syslog {
            // NCS expand uses statement
            container source-interface {
              leaf loopback {
                type string;
              }
            }
          }
          container ssh {
            // NCS expand uses statement
            container source-interface {
              leaf loopback {
                type string;
              }
            }
          }
          container telnet {
            // NCS expand uses statement
            container source-interface {
              leaf loopback {
                type string;
              }
            }
          }
          container ftp {
            // NCS expand uses statement
            container source-interface {
              leaf loopback {
                type string;
              }
            }
          }
          container tftp {
            // NCS expand uses statement
            container source-interface {
              leaf loopback {
                type string;
              }
            }
          }
          container rcp {
            // NCS expand uses statement
            container source-interface {
              leaf loopback {
                type string;
              }
            }
          }
          container web {
            // NCS expand uses statement
            container source-interface {
              leaf loopback {
                type string;
              }
            }
          }
          container all {
            // NCS expand uses statement
            container source-interface {
              leaf loopback {
                type string;
              }
            }
          }
        }
        container nat {
          // NCS expand uses statement
          container alg {
            // NCS expand uses statement
            leaf pptp {
              type string;
            }
            // NCS expand uses statement
            leaf tftp {
              type string;
            }
            // NCS expand uses statement
            leaf rtsp {
              type string;
            }
            // NCS expand uses statement
            leaf esp {
              type string;
            }
          }
          leaf allow-static-host {
            type empty;
          }
          container inside {
            container source {
              list list {
                // NCS patched for predictable order
                ordered-by user;
                tailf:cli-suppress-mode;
                key "id";
                leaf id {
                  type string;
                }
                leaf pool {
                  // NCS drop mandatory statement
                  type string;
                }
              }
              leaf class-list {
                type string;
              }
              list static {
                // NCS patched for predictable order
                ordered-by user;
                tailf:cli-suppress-mode;
                key "source nat";
                leaf source {
                  type string;
                }
                leaf nat {
                  type string;
                }
                leaf vrid {
                  type string;
                }
              }
            }
          }
          list pool {
            // NCS patched for predictable order
            ordered-by user;
            tailf:cli-suppress-mode;
            key "name";
            leaf name {
              type string;
            }
            leaf ipstart {
              // NCS drop mandatory statement
              tailf:cli-drop-node-name;
              type string;
            }
            leaf ipend {
              // NCS drop mandatory statement
              tailf:cli-drop-node-name;
              type string;
            }
            leaf netmask {
              // NCS drop mandatory statement
              type string;
            }
            leaf gateway {
              type string;
            }
            leaf ha-group-id {
              type string;
            }
            leaf ha-use-all-ports {
              type empty;
            }
            leaf vrid {
              type string;
            }
            leaf ip-rr {
              type empty;
            }
            leaf lsn {
              type empty;
            }
            leaf max-users-per-ip {
              type string;
            }
          }
          list pool-group {
            // NCS patched for predictable order
            ordered-by user;
            key "name";
            leaf name {
              type string;
            }
            leaf ha-group-id {
              type string;
            }
            list member {
              // NCS patched for predictable order
              ordered-by user;
              key "member-id";
              tailf:cli-suppress-mode;
              leaf member-id {
                type string;
              }
            }
          }
          container range-list;
          leaf reset-idle-tcp-conn {
            type empty;
          }
          container template {
            list logging {
              // NCS patched for predictable order
              ordered-by user;
              key "name";
              leaf name {
                type string;
              }
            }
          }
          container translation {
            leaf icmp-timeout {
              type string;
            }
            leaf tcp-timeout {
              type string;
            }
            leaf udp-timeout {
              type string;
            }
            leaf syn-timeout {
              type string;
            }
            list service-timeout {
              // NCS patched for predictable order
              ordered-by user;
              tailf:cli-suppress-mode;
              key "protocol from";
              leaf protocol {
                type string;
              }
              leaf from {
                type string;
              }
              leaf to {
                type string;
              }
              leaf timeout {
                tailf:cli-drop-node-name;
                type string;
              }
            }
          }
          container lsn {
            container endpoint-independent-mapping {
              container tcp {
                container enable {
                  leaf ephemeral {
                    type empty;
                  }
                  leaf well-known {
                    type empty;
                  }
                }
              }
              container udp {
                container enable {
                  leaf ephemeral {
                    type empty;
                  }
                  leaf well-known {
                    type empty;
                  }
                }
              }
            }
            container endpoint-independent-filtering {
              container tcp {
                container enable {
                  leaf ephemeral {
                    type empty;
                    // NCS drop must statement
                  }
                  leaf well-known {
                    type empty;
                    // NCS drop must statement
                  }
                }
              }
              container udp {
                container enable {
                  leaf ephemeral {
                    type empty;
                    // NCS drop must statement
                  }
                  leaf well-known {
                    type empty;
                    // NCS drop must statement
                  }
                }
              }
            }
            leaf ip-selection {
              type string;
            }
            leaf attempt-port-preservation {
              type string;
            }
            // NCS expand uses statement
            container alg {
              // NCS expand uses statement
              leaf pptp {
                type string;
              }
              // NCS expand uses statement
              leaf tftp {
                type string;
              }
              // NCS expand uses statement
              leaf rtsp {
                type string;
              }
              // NCS expand uses statement
              leaf esp {
                type string;
              }
            }
          }
        }
        // NCS expand uses statement
        list prefix-list {
          // NCS patched for predictable order
          ordered-by user;
          tailf:cli-suppress-mode;
          key "name seq";
          leaf name {
            type string;
          }
          leaf seq {
            type string;
          }
          choice permit-deny {
            leaf permit {
              type string;
            }
            leaf deny {
              type string;
            }
          }
          leaf ge {
            type string;
          }
          leaf le {
            type string;
          }
        }
        // NCS expand uses statement
        list route {
          // NCS patched for predictable order
          ordered-by user;
          tailf:cli-suppress-mode;
          key "ip mask forwarding-router";
          leaf ip {
            type string;
          }
          leaf mask {
            type string;
          }
          leaf forwarding-router {
            type string;
          }
          leaf distance {
            tailf:cli-drop-node-name;
            type string;
          }
          leaf cpu-process {
            tailf:cli-drop-node-name;
            type string;
          }
        }
        container tcp {
          container syn-cookie {
            leaf threshold {
              type string;
            }
          }
        }
      }
      uses ncs_template_bfd-grouping;
      uses ncs_template_health-grouping;
      uses ncs_template_glid-grouping;
      uses ncs_template_class-list-grouping;
      uses ncs_template_class-list-group-grouping;
      uses ncs_template_slb-grouping;
      uses ncs_template_gslb-grouping;
      uses ncs_template_vrrp-a-grouping;
      uses ncs_template_vlan-grouping;
      uses ncs_template_logging-grouping;
      uses ncs_template_bw-list-grouping;
      uses ncs_template_ip-list-grouping;
      uses ncs_template_cgnv6-grouping;
      uses ncs_template_router-grouping;
      uses ncs_template_system-jumbo-global-grouping;
      uses ncs_template_hd-monitor-grouping;
      uses ncs_template_clock-grouping;
      uses ncs_template_ntp-grouping;
      uses ncs_template_netflow-grouping;
      uses ncs_template_tacacs-server-grouping;
      uses ncs_template_radius-server-grouping;
      uses ncs_template_authentication-grouping;
      uses ncs_template_ipv6-grouping;
      uses ncs_template_nat64-grouping;
      uses ncs_template_lsn-lid-grouping;
      uses ncs_template_ha-grouping;
      uses ncs_template_floating-ip-grouping;
      uses ncs_template_snmp-server-grouping;
      uses ncs_template_audit-grouping;
      uses ncs_template_terminal-grouping;
      uses ncs_template_web-service-grouping;
      uses ncs_template_multi-config-grouping;
      uses ncs_template_lldp-grouping;
      uses ncs_template_banner-grouping;
      uses ncs_template_device-context-grouping;
      uses ncs_template_system-grouping;
      uses ncs_template_partition-grouping;
      uses ncs_template_partition-group-grouping;
      uses ncs_template_access-list-grouping;
      uses ncs_template_tftp-grouping;
      uses ncs_template_stats-data-disable-grouping;
      uses ncs_template_syn-cookie-grouping;
      uses ncs_template_enable-management-grouping;
      uses ncs_template_disable-management-grouping;
      uses ncs_template_monitor-grouping;
      uses ncs_template_extended-stats-grouping;
      uses ncs_template_admin-grouping;
      uses ncs_template_enable-core-grouping;
      uses ncs_template_trunk-grouping;
      uses ncs_template_lacp-grouping;
      uses ncs_template_sflow-grouping;
      uses ncs_template_zone-grouping;
      uses ncs_template_object-grouping;
      uses ncs_template_object-group-grouping;
      uses ncs_template_rule-set-grouping;
      uses ncs_template_fw-grouping;
      uses ncs_template_route-map-grouping;
      uses ncs_template_accounting-grouping;
      uses ncs_template_ve-stats-grouping;
      uses ncs_template_acos-events-grouping;
      uses ncs_template_bgp-grouping;
      uses ncs_template_harmony-controller-grouping;
      // NCS expand uses statement
      container vcs {
        leaf state {
          tailf:cli-drop-node-name;
          type string;
        }
        list device {
          // NCS patched for predictable order
          ordered-by user;
          key "id";
          leaf id {
            type string;
          }
          leaf priority {
            type string;
          }
          container interfaces {
            leaf management {
              type empty;
            }
            list ethernet {
              // NCS patched for predictable order
              ordered-by user;
              tailf:cli-suppress-mode;
              key "id";
              leaf id {
                type string;
              }
            }
            list trunk {
              // NCS patched for predictable order
              ordered-by user;
              tailf:cli-suppress-mode;
              key "id";
              leaf id {
                type string;
              }
            }
            list ve {
              // NCS patched for predictable order
              ordered-by user;
              tailf:cli-suppress-mode;
              key "id";
              leaf id {
                type string;
              }
            }
          }
          leaf enable {
            type empty;
          }
        }
        list floating-ip {
          // NCS patched for predictable order
          ordered-by user;
          tailf:cli-suppress-mode;
          key "floating-ip-address";
          leaf floating-ip-address {
            tailf:cli-drop-node-name;
            type string;
          }
          leaf mask {
            tailf:cli-drop-node-name;
            type ncs_template_ipv4-mask;
          }
        }
        leaf ssl-enable {
          type empty;
        }
        leaf failure-retry-count {
          type string;
        }
      }
    }
  }
  augment "/ncs:compliance/ncs:template/ncs:ned-id/ncs:config" {
    leaf os-major {
      type string;
    }
    leaf os-minor {
      type string;
    }
    uses ncs_compliance_template_ip-list-grouping;
    uses ncs_compliance_template_cgnv6-grouping;
    uses ncs_compliance_template_sflow-grouping;
    uses ncs_compliance_template_accounting-grouping;
    uses ncs_compliance_template_acos-events-grouping;
    uses ncs_compliance_template_authorization-grouping;
    uses ncs_compliance_template_bgp-grouping;
    uses ncs_compliance_template_lacp-grouping;
    uses ncs_compliance_template_aflex-grouping;
    container EXEC {
      tailf:cli-drop-node-name;
    }
    uses ncs_compliance_template_system-jumbo-global-grouping;
    uses ncs_compliance_template_hostname-grouping;
    uses ncs_compliance_template_hd-monitor-grouping;
    uses ncs_compliance_template_timezone-nodst-grouping;
    uses ncs_compliance_template_clock-grouping;
    uses ncs_compliance_template_ntp-grouping;
    uses ncs_compliance_template_netflow-grouping;
    uses ncs_compliance_template_trunk-grouping;
    uses ncs_compliance_template_class-list-grouping;
    uses ncs_compliance_template_class-list-group-grouping;
    uses ncs_compliance_template_tacacs-server-grouping;
    uses ncs_compliance_template_radius-server-grouping;
    uses ncs_compliance_template_authentication-grouping;
    // NCS expand uses statement
    container interface {

      grouping lldp-interface-grouping {
        container lldp {
          container enable {
            leaf rx {
              type empty;
            }
            leaf tx {
              type empty;
            }
          }
          leaf notification {
            type string;
          }
          leaf tx-dot1-tlvs {
            type string;
          }
        }
      }
      container management {
        container bcast-rate-limit {
          presence "present";
          leaf rate {
            type string;
          }
        }
        container ip {
          // NCS expand uses statement
          list address {
            // NCS patched for predictable order
            ordered-by user;
            tailf:cli-suppress-mode;
            key "address mask";
            leaf address {
              type string;
            }
            leaf mask {
              type string;
            }
          }
          leaf control-apps-use-mgmt-port {
            type empty;
          }
          leaf default-gateway {
            type string;
          }
        }
        container ipv6 {
          list address {
            // NCS patched for predictable order
            ordered-by user;
            key "ip";
            tailf:cli-suppress-mode;
            leaf ip {
              tailf:cli-drop-node-name;
              type ncs_compliance_template_ipv6-prefix;
            }
            leaf link-local {
              type empty;
            }
          }
          leaf default-gateway {
            type string;
          }
        }
        // NCS expand uses statement
        container lldp {
          container enable {
            leaf rx {
              type empty;
            }
            leaf tx {
              type empty;
            }
          }
          leaf notification {
            type string;
          }
          leaf tx-dot1-tlvs {
            type string;
          }
        }
        leaf flow-control {
          type empty;
        }
        container access-list {
          leaf id {
            tailf:cli-drop-node-name;
            type string;
          }
          leaf in {
            // NCS drop must statement
            type empty;
          }
        }
        leaf enabled-disabled {
          tailf:cli-drop-node-name;
          type string;
        }
        leaf duplexity {
          type string;
        }
        leaf mtu {
          type string;
        }
        leaf speed {
          type string;
        }
      }
      list ethernet {
        // NCS patched for predictable order
        ordered-by user;
        key "nr";
        leaf nr {
          type ncs_compliance_template_ethernet-index;
        }
        leaf name {
          type string;
        }
        container ip {
          // NCS expand uses statement
          list address {
            // NCS patched for predictable order
            ordered-by user;
            tailf:cli-suppress-mode;
            key "address mask";
            leaf address {
              type string;
            }
            leaf mask {
              type string;
            }
          }
          leaf cache-spoofing-port {
            type empty;
          }
          leaf helper-address {
            type string;
          }
          container nat {
            leaf inside {
              type empty;
            }
            leaf outside {
              type empty;
            }
          }
          container ospf;
          container router {
            container isis {
              presence "true";
              leaf cmds {
                tailf:cli-drop-node-name;
                type string;
              }
            }
          }
          leaf allow-promiscuous-vip {
            type empty;
          }
          container tcp {
            leaf syn-cookie {
              type empty;
            }
          }
        }
        container ipv6 {
          container access-list {
            leaf id {
              tailf:cli-drop-node-name;
              type string;
            }
            leaf in {
              // NCS drop must statement
              type empty;
            }
          }
          list address {
            // NCS patched for predictable order
            ordered-by user;
            key "ip";
            tailf:cli-suppress-mode;
            leaf ip {
              tailf:cli-drop-node-name;
              type ncs_compliance_template_ipv6-prefix;
            }
            leaf link-local {
              type empty;
            }
            leaf anycast {
              type empty;
            }
          }
          container nat {
            leaf inside {
              type empty;
            }
            leaf outside {
              type empty;
            }
          }
          container ndisc {
            container router-advertisement;
          }
          container ospf;
          container router {
            container isis {
              presence "true";
              leaf cmds {
                tailf:cli-drop-node-name;
                type string;
              }
            }
          }
        }
        leaf load-interval {
          type string;
        }
        container access-list {
          leaf id {
            tailf:cli-drop-node-name;
            type string;
          }
          leaf in {
            // NCS drop must statement
            type empty;
          }
        }
        leaf state {
          tailf:cli-drop-node-name;
          type string;
        }
        leaf state-alt {
          tailf:cli-drop-node-name;
          type string;
        }
        leaf duplexity {
          type string;
        }
        leaf cpu-process {
          type empty;
        }
        leaf flow-control {
          type empty;
        }
        container icmp-rate-limit {
          leaf rate {
            tailf:cli-drop-node-name;
            type string;
          }
          leaf lockup {
            // NCS drop must statement
            type string;
          }
          leaf lockup-period {
            // NCS drop must statement
            tailf:cli-drop-node-name;
            type string;
          }
        }
        container ospf;
        container isis;
        leaf l3-vlan-fwd-disable {
          type empty;
        }
        container lacp {
          leaf port-priority {
            type string;
          }
          leaf timeout {
            type string;
          }
          container trunk {
            leaf number {
              tailf:cli-drop-node-name;
              type string;
            }
            leaf admin-key {
              // NCS drop must statement
              type string;
            }
            leaf mode {
              // NCS drop must statement
              type string;
            }
            leaf unidirectional-detection {
              // NCS drop must statement
              type empty;
            }
          }
          container udld-timeout {
            leaf timeout-type {
              tailf:cli-drop-node-name;
              type string;
            }
            leaf milli {
              tailf:cli-drop-node-name;
              type string;
            }
            leaf secs {
              tailf:cli-drop-node-name;
              type string;
            }
          }
        }
        // NCS expand uses statement
        container lldp {
          container enable {
            leaf rx {
              type empty;
            }
            leaf tx {
              type empty;
            }
          }
          leaf notification {
            type string;
          }
          leaf tx-dot1-tlvs {
            type string;
          }
        }
        leaf mtu {
          type string;
        }
        leaf speed {
          type string;
        }
        list trunk-group-list {
          // NCS patched for predictable order
          ordered-by user;
          key "trunk-group-key";
          tailf:cli-drop-node-name;
          leaf trunk-group-key {
            type string;
          }
          leaf trunk-group-id {
            tailf:cli-drop-node-name;
            // NCS drop mandatory statement
            type string;
          }
          leaf trunk-group-type {
            tailf:cli-drop-node-name;
            type string;
          }
        }
      }
      list trunk {
        // NCS patched for predictable order
        ordered-by user;
        key "nr";
        leaf nr {
          type ncs_compliance_template_ethernet-index;
        }
        leaf name {
          type string;
        }
        leaf state {
          tailf:cli-drop-node-name;
          type string;
        }
        container icmp-rate-limit {
          leaf rate {
            tailf:cli-drop-node-name;
            type string;
          }
          leaf lockup {
            // NCS drop must statement
            type string;
          }
          leaf lockup-period {
            // NCS drop must statement
            tailf:cli-drop-node-name;
            type string;
          }
        }
        list access-list {
          // NCS patched for predictable order
          ordered-by user;
          tailf:cli-suppress-mode;
          key "id in-type";
          leaf id {
            type string;
          }
          leaf in-type {
            type string;
          }
        }
        container ip {
          list address {
            // NCS patched for predictable order
            ordered-by user;
            key "ip mask";
            tailf:cli-suppress-mode;
            leaf ip {
              type string;
            }
            leaf mask {
              type ncs_compliance_template_ipv4-mask;
            }
          }
          leaf allow-promiscuous-vip {
            type empty;
          }
          leaf cache-spoofing-port {
            type empty;
          }
          container nat {
            leaf inside {
              type empty;
            }
            leaf outside {
              type empty;
            }
          }
        }
      }
      list loopback {
        // NCS patched for predictable order
        ordered-by user;
        key "nr";
        leaf nr {
          type ncs_compliance_template_ethernet-index;
        }
        container ip {
          // NCS expand uses statement
          list address {
            // NCS patched for predictable order
            ordered-by user;
            tailf:cli-suppress-mode;
            key "address mask";
            leaf address {
              type string;
            }
            leaf mask {
              type string;
            }
          }
          container router {
            choice isis-choice {
              container isis-alt {
                tailf:cli-drop-node-name;
                leaf isis {
                  type string;
                }
              }
              leaf isis {
                type empty;
              }
            }
          }
        }
        container icmp-rate-limit {
          leaf rate {
            tailf:cli-drop-node-name;
            type string;
          }
          leaf lockup {
            // NCS drop must statement
            type string;
          }
          leaf lockup-period {
            tailf:cli-drop-node-name;
            // NCS drop must statement
            type string;
          }
        }
        leaf state {
          tailf:cli-drop-node-name;
          type string;
        }
      }
      list ve {
        // NCS patched for predictable order
        ordered-by user;
        key "id";
        leaf id {
          type ncs_compliance_template_vlan-index;
        }
        leaf name {
          type string;
        }
        container bfd {
          container echo {
            presence "true";
          }
        }
        container icmp-rate-limit {
          leaf rate {
            tailf:cli-drop-node-name;
            type string;
          }
          leaf lockup {
            // NCS drop must statement
            type string;
          }
          leaf lockup-period {
            tailf:cli-drop-node-name;
            // NCS drop must statement
            type string;
          }
        }
        container access-list {
          leaf id {
            tailf:cli-drop-node-name;
            type string;
          }
          leaf in {
            // NCS drop must statement
            type empty;
          }
        }
        leaf l3-vlan-fwd-disable {
          type empty;
        }
        container ip {
          leaf allow-promiscuous-vip {
            type empty;
          }
          leaf cache-spoofing-port {
            type empty;
          }
          leaf helper-address {
            type string;
          }
          container nat {
            leaf inside {
              type empty;
            }
            leaf outside {
              type empty;
            }
          }
          container ospf;
          container router {
            container isis {
              presence "true";
              leaf cmds {
                tailf:cli-drop-node-name;
                type string;
              }
            }
          }
          container tcp {
            leaf syn-cookie {
              type empty;
            }
          }
          // NCS expand uses statement
          list address {
            // NCS patched for predictable order
            ordered-by user;
            tailf:cli-suppress-mode;
            key "address mask";
            leaf address {
              type string;
            }
            leaf mask {
              type string;
            }
          }
        }
        container ipv6 {
          container access-list {
            leaf id {
              tailf:cli-drop-node-name;
              type string;
            }
            leaf in {
              // NCS drop must statement
              type empty;
            }
          }
          container nat {
            leaf inside {
              type empty;
            }
            leaf outside {
              type empty;
            }
          }
          container ndisc {
            container router-advertisement;
          }
          container ospf;
          container router {
            container isis {
              presence "true";
              leaf cmds {
                tailf:cli-drop-node-name;
                type string;
              }
            }
          }
          list address {
            // NCS patched for predictable order
            ordered-by user;
            key "ip";
            tailf:cli-suppress-mode;
            leaf ip {
              tailf:cli-drop-node-name;
              type ncs_compliance_template_ipv6-prefix;
            }
            leaf link-local {
              type empty;
            }
            leaf anycast {
              type empty;
            }
          }
        }
        leaf mtu {
          type string;
        }
        leaf state {
          tailf:cli-drop-node-name;
          type string;
        }
        container isis;
        container ospf;
      }
    }
    uses ncs_compliance_template_vlan-grouping;
    // NCS expand uses statement
    container ip {
      list access-list {
        // NCS patched for predictable order
        ordered-by user;
        key "name";
        leaf name {
          type string;
        }
        list access-list-rule {
          // NCS patched for predictable order
          ordered-by user;
          tailf:cli-suppress-mode;
          tailf:cli-drop-node-name;
          key "rule";
          leaf rule {
            type string;
          }
        }
      }
      list address {
        // NCS patched for predictable order
        ordered-by user;
        key "ip";
        tailf:cli-suppress-mode;
        leaf ip {
          tailf:cli-drop-node-name;
          type string;
        }
        leaf mask {
          tailf:cli-drop-node-name;
          type ncs_compliance_template_ipv4-mask;
        }
      }
      container anomaly-drop {
        leaf bad-content {
          type string;
        }
        leaf drop-all {
          type empty;
        }
        leaf frag {
          type empty;
        }
        leaf ip-option {
          type string;
        }
        leaf land-attack {
          type empty;
        }
        leaf out-of-sequence {
          type string;
        }
        leaf ping-of-death {
          type empty;
        }
        leaf tcp-no-flag {
          type empty;
        }
        leaf tcp-syn-fin {
          type empty;
        }
        leaf tcp-syn-frag {
          type empty;
        }
        leaf zero-window {
          type string;
        }
        container security-attack {
          leaf layer-3 {
            type empty;
          }
          leaf layer-4 {
            type empty;
          }
        }
        list packet-deformity {
          // NCS patched for predictable order
          ordered-by user;
          tailf:cli-suppress-mode;
          key "layer";
          leaf layer {
            type string;
          }
        }
      }
      container as-path {
        list access-list {
          // NCS patched for predictable order
          ordered-by user;
          tailf:cli-suppress-mode;
          key "name action path";
          leaf name {
            type string;
          }
          leaf action {
            type string;
          }
          leaf path {
            type string;
          }
        }
      }
      container community-list {
        list standard-number {
          // NCS patched for predictable order
          ordered-by user;
          tailf:cli-drop-node-name;
          tailf:cli-suppress-mode;
          key "nr";
          leaf nr {
            type string;
          }
          list rules {
            // NCS patched for predictable order
            ordered-by user;
            tailf:cli-drop-node-name;
            tailf:cli-suppress-mode;
            key "action expr";
            leaf action {
              type string;
            }
            leaf expr {
              type string;
            }
          }
        }
        list expanded-number {
          // NCS patched for predictable order
          ordered-by user;
          tailf:cli-drop-node-name;
          tailf:cli-suppress-mode;
          key "nr";
          leaf nr {
            type string;
          }
          list rules {
            // NCS patched for predictable order
            ordered-by user;
            tailf:cli-drop-node-name;
            tailf:cli-suppress-mode;
            key "action expr";
            leaf action {
              type string;
            }
            leaf expr {
              type string;
            }
          }
        }
        list word {
          // NCS patched for predictable order
          ordered-by user;
          tailf:cli-drop-node-name;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
        list expanded {
          // NCS patched for predictable order
          ordered-by user;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
        list standard {
          // NCS patched for predictable order
          ordered-by user;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
      }
      leaf default-gateway {
        type string;
      }
      container dns {
        leaf primary {
          type string;
        }
        leaf secondary {
          type string;
        }
        leaf suffix {
          type string;
        }
      }
      container extcommunity-list {
        list standard-number {
          // NCS patched for predictable order
          ordered-by user;
          tailf:cli-drop-node-name;
          tailf:cli-suppress-mode;
          key "nr";
          leaf nr {
            type string;
          }
          list rules {
            // NCS patched for predictable order
            ordered-by user;
            tailf:cli-drop-node-name;
            tailf:cli-suppress-mode;
            key "action expr";
            leaf action {
              type string;
            }
            leaf expr {
              type string;
            }
          }
        }
        list expanded-number {
          // NCS patched for predictable order
          ordered-by user;
          tailf:cli-drop-node-name;
          tailf:cli-suppress-mode;
          key "nr";
          leaf nr {
            type string;
          }
          list rules {
            // NCS patched for predictable order
            ordered-by user;
            tailf:cli-drop-node-name;
            tailf:cli-suppress-mode;
            key "action expr";
            leaf action {
              type string;
            }
            leaf expr {
              type string;
            }
          }
        }
        list expanded {
          // NCS patched for predictable order
          ordered-by user;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
        list standard {
          // NCS patched for predictable order
          ordered-by user;
          tailf:cli-suppress-mode;
          key "name";
          leaf name {
            type string;
          }
          list rules {
            // NCS patched for predictable order
            ordered-by user;
            tailf:cli-drop-node-name;
            tailf:cli-suppress-mode;
            key "action expr";
            leaf action {
              type string;
            }
            leaf expr {
              type string;
            }
          }
        }
      }
      container frag {
        leaf buff {
          type string;
        }
        container cpu-threshold {
          leaf high {
            type string;
          }
          leaf low {
            type string;
          }
        }
        leaf max-reassembly-sessions {
          type string;
        }
        leaf timeout {
          type string;
        }
      }
      container icmp {
        container disable {
          leaf redirect {
            type empty;
          }
          leaf unreachable {
            type empty;
          }
        }
      }
      container mgmt-traffic {
        container snmp {
          // NCS expand uses statement
          container source-interface {
            leaf loopback {
              type string;
            }
          }
        }
        container ntp {
          // NCS expand uses statement
          container source-interface {
            leaf loopback {
              type string;
            }
          }
        }
        container syslog {
          // NCS expand uses statement
          container source-interface {
            leaf loopback {
              type string;
            }
          }
        }
        container ssh {
          // NCS expand uses statement
          container source-interface {
            leaf loopback {
              type string;
            }
          }
        }
        container telnet {
          // NCS expand uses statement
          container source-interface {
            leaf loopback {
              type string;
            }
          }
        }
        container ftp {
          // NCS expand uses statement
          container source-interface {
            leaf loopback {
              type string;
            }
          }
        }
        container tftp {
          // NCS expand uses statement
          container source-interface {
            leaf loopback {
              type string;
            }
          }
        }
        container rcp {
          // NCS expand uses statement
          container source-interface {
            leaf loopback {
              type string;
            }
          }
        }
        container web {
          // NCS expand uses statement
          container source-interface {
            leaf loopback {
              type string;
            }
          }
        }
        container all {
          // NCS expand uses statement
          container source-interface {
            leaf loopback {
              type string;
            }
          }
        }
      }
      container nat {
        // NCS expand uses statement
        container alg {
          // NCS expand uses statement
          leaf pptp {
            type string;
          }
          // NCS expand uses statement
          leaf tftp {
            type string;
          }
          // NCS expand uses statement
          leaf rtsp {
            type string;
          }
          // NCS expand uses statement
          leaf esp {
            type string;
          }
        }
        leaf allow-static-host {
          type empty;
        }
        container inside {
          container source {
            list list {
              // NCS patched for predictable order
              ordered-by user;
              tailf:cli-suppress-mode;
              key "id";
              leaf id {
                type string;
              }
              leaf pool {
                // NCS drop mandatory statement
                type string;
              }
            }
            leaf class-list {
              type string;
            }
            list static {
              // NCS patched for predictable order
              ordered-by user;
              tailf:cli-suppress-mode;
              key "source nat";
              leaf source {
                type string;
              }
              leaf nat {
                type string;
              }
              leaf vrid {
                type string;
              }
            }
          }
        }
        list pool {
          // NCS patched for predictable order
          ordered-by user;
          tailf:cli-suppress-mode;
          key "name";
          leaf name {
            type string;
          }
          leaf ipstart {
            // NCS drop mandatory statement
            tailf:cli-drop-node-name;
            type string;
          }
          leaf ipend {
            // NCS drop mandatory statement
            tailf:cli-drop-node-name;
            type string;
          }
          leaf netmask {
            // NCS drop mandatory statement
            type string;
          }
          leaf gateway {
            type string;
          }
          leaf ha-group-id {
            type string;
          }
          leaf ha-use-all-ports {
            type empty;
          }
          leaf vrid {
            type string;
          }
          leaf ip-rr {
            type empty;
          }
          leaf lsn {
            type empty;
          }
          leaf max-users-per-ip {
            type string;
          }
        }
        list pool-group {
          // NCS patched for predictable order
          ordered-by user;
          key "name";
          leaf name {
            type string;
          }
          leaf ha-group-id {
            type string;
          }
          list member {
            // NCS patched for predictable order
            ordered-by user;
            key "member-id";
            tailf:cli-suppress-mode;
            leaf member-id {
              type string;
            }
          }
        }
        container range-list;
        leaf reset-idle-tcp-conn {
          type empty;
        }
        container template {
          list logging {
            // NCS patched for predictable order
            ordered-by user;
            key "name";
            leaf name {
              type string;
            }
          }
        }
        container translation {
          leaf icmp-timeout {
            type string;
          }
          leaf tcp-timeout {
            type string;
          }
          leaf udp-timeout {
            type string;
          }
          leaf syn-timeout {
            type string;
          }
          list service-timeout {
            // NCS patched for predictable order
            ordered-by user;
            tailf:cli-suppress-mode;
            key "protocol from";
            leaf protocol {
              type string;
            }
            leaf from {
              type string;
            }
            leaf to {
              type string;
            }
            leaf timeout {
              tailf:cli-drop-node-name;
              type string;
            }
          }
        }
        container lsn {
          container endpoint-independent-mapping {
            container tcp {
              container enable {
                leaf ephemeral {
                  type empty;
                }
                leaf well-known {
                  type empty;
                }
              }
            }
            container udp {
              container enable {
                leaf ephemeral {
                  type empty;
                }
                leaf well-known {
                  type empty;
                }
              }
            }
          }
          container endpoint-independent-filtering {
            container tcp {
              container enable {
                leaf ephemeral {
                  type empty;
                  // NCS drop must statement
                }
                leaf well-known {
                  type empty;
                  // NCS drop must statement
                }
              }
            }
            container udp {
              container enable {
                leaf ephemeral {
                  type empty;
                  // NCS drop must statement
                }
                leaf well-known {
                  type empty;
                  // NCS drop must statement
                }
              }
            }
          }
          leaf ip-selection {
            type string;
          }
          leaf attempt-port-preservation {
            type string;
          }
          // NCS expand uses statement
          container alg {
            // NCS expand uses statement
            leaf pptp {
              type string;
            }
            // NCS expand uses statement
            leaf tftp {
              type string;
            }
            // NCS expand uses statement
            leaf rtsp {
              type string;
            }
            // NCS expand uses statement
            leaf esp {
              type string;
            }
          }
        }
      }
      // NCS expand uses statement
      list prefix-list {
        // NCS patched for predictable order
        ordered-by user;
        tailf:cli-suppress-mode;
        key "name seq";
        leaf name {
          type string;
        }
        leaf seq {
          type string;
        }
        choice permit-deny {
          leaf permit {
            type string;
          }
          leaf deny {
            type string;
          }
        }
        leaf ge {
          type string;
        }
        leaf le {
          type string;
        }
      }
      // NCS expand uses statement
      list route {
        // NCS patched for predictable order
        ordered-by user;
        tailf:cli-suppress-mode;
        key "ip mask forwarding-router";
        leaf ip {
          type string;
        }
        leaf mask {
          type string;
        }
        leaf forwarding-router {
          type string;
        }
        leaf distance {
          tailf:cli-drop-node-name;
          type string;
        }
        leaf cpu-process {
          tailf:cli-drop-node-name;
          type string;
        }
      }
      container tcp {
        container syn-cookie {
          leaf threshold {
            type string;
          }
        }
      }
    }
    uses ncs_compliance_template_ipv6-grouping;
    uses ncs_compliance_template_nat64-grouping;
    uses ncs_compliance_template_lsn-lid-grouping;
    uses ncs_compliance_template_ha-grouping;
    uses ncs_compliance_template_floating-ip-grouping;
    uses ncs_compliance_template_glid-grouping;
    uses ncs_compliance_template_slb-grouping;
    uses ncs_compliance_template_gslb-grouping;
    uses ncs_compliance_template_logging-grouping;
    uses ncs_compliance_template_snmp-server-grouping;
    uses ncs_compliance_template_audit-grouping;
    uses ncs_compliance_template_harmony-controller-grouping;
    uses ncs_compliance_template_terminal-grouping;
    uses ncs_compliance_template_web-service-grouping;
    uses ncs_compliance_template_multi-config-grouping;
    uses ncs_compliance_template_banner-grouping;
    uses ncs_compliance_template_vrrp-a-grouping;
    uses ncs_compliance_template_router-grouping;
    uses ncs_compliance_template_bfd-grouping;
    uses ncs_compliance_template_lldp-grouping;
    uses ncs_compliance_template_route-map-grouping;
    uses ncs_compliance_template_device-context-grouping;
    // NCS expand uses statement
    container vcs {
      leaf state {
        tailf:cli-drop-node-name;
        type string;
      }
      list device {
        // NCS patched for predictable order
        ordered-by user;
        key "id";
        leaf id {
          type string;
        }
        leaf priority {
          type string;
        }
        container interfaces {
          leaf management {
            type empty;
          }
          list ethernet {
            // NCS patched for predictable order
            ordered-by user;
            tailf:cli-suppress-mode;
            key "id";
            leaf id {
              type string;
            }
          }
          list trunk {
            // NCS patched for predictable order
            ordered-by user;
            tailf:cli-suppress-mode;
            key "id";
            leaf id {
              type string;
            }
          }
          list ve {
            // NCS patched for predictable order
            ordered-by user;
            tailf:cli-suppress-mode;
            key "id";
            leaf id {
              type string;
            }
          }
        }
        leaf enable {
          type empty;
        }
      }
      list floating-ip {
        // NCS patched for predictable order
        ordered-by user;
        tailf:cli-suppress-mode;
        key "floating-ip-address";
        leaf floating-ip-address {
          tailf:cli-drop-node-name;
          type string;
        }
        leaf mask {
          tailf:cli-drop-node-name;
          type ncs_compliance_template_ipv4-mask;
        }
      }
      leaf ssl-enable {
        type empty;
      }
      leaf failure-retry-count {
        type string;
      }
    }
    uses ncs_compliance_template_system-grouping;
    uses ncs_compliance_template_ve-stats-grouping;
    uses ncs_compliance_template_partition-grouping;
    uses ncs_compliance_template_partition-group-grouping;
    uses ncs_compliance_template_access-list-grouping;
    uses ncs_compliance_template_tftp-grouping;
    uses ncs_compliance_template_health-grouping;
    uses ncs_compliance_template_stats-data-disable-grouping;
    uses ncs_compliance_template_syn-cookie-grouping;
    uses ncs_compliance_template_enable-management-grouping;
    uses ncs_compliance_template_disable-management-grouping;
    uses ncs_compliance_template_monitor-grouping;
    uses ncs_compliance_template_extended-stats-grouping;
    uses ncs_compliance_template_admin-grouping;
    uses ncs_compliance_template_zone-grouping;
    uses ncs_compliance_template_object-grouping;
    uses ncs_compliance_template_object-group-grouping;
    uses ncs_compliance_template_rule-set-grouping;
    uses ncs_compliance_template_fw-grouping;
    uses ncs_compliance_template_enable-core-grouping;
    uses ncs_compliance_template_bw-list-grouping;
    list active-partition {
      // NCS patched for predictable order
      ordered-by user;
      key "name";
      leaf name {
        type string;
      }
      uses ncs_compliance_template_aflex-grouping;
      uses ncs_compliance_template_hostname-grouping;
      // NCS expand uses statement
      container interface {

        grouping lldp-interface-grouping {
          container lldp {
            container enable {
              leaf rx {
                type empty;
              }
              leaf tx {
                type empty;
              }
            }
            leaf notification {
              type string;
            }
            leaf tx-dot1-tlvs {
              type string;
            }
          }
        }
        container management {
          container bcast-rate-limit {
            presence "present";
            leaf rate {
              type string;
            }
          }
          container ip {
            // NCS expand uses statement
            list address {
              // NCS patched for predictable order
              ordered-by user;
              tailf:cli-suppress-mode;
              key "address mask";
              leaf address {
                type string;
              }
              leaf mask {
                type string;
              }
            }
            leaf control-apps-use-mgmt-port {
              type empty;
            }
            leaf default-gateway {
              type string;
            }
          }
          container ipv6 {
            list address {
              // NCS patched for predictable order
              ordered-by user;
              key "ip";
              tailf:cli-suppress-mode;
              leaf ip {
                tailf:cli-drop-node-name;
                type ncs_compliance_template_ipv6-prefix;
              }
              leaf link-local {
                type empty;
              }
            }
            leaf default-gateway {
              type string;
            }
          }
          // NCS expand uses statement
          container lldp {
            container enable {
              leaf rx {
                type empty;
              }
              leaf tx {
                type empty;
              }
            }
            leaf notification {
              type string;
            }
            leaf tx-dot1-tlvs {
              type string;
            }
          }
          leaf flow-control {
            type empty;
          }
          container access-list {
            leaf id {
              tailf:cli-drop-node-name;
              type string;
            }
            leaf in {
              // NCS drop must statement
              type empty;
            }
          }
          leaf enabled-disabled {
            tailf:cli-drop-node-name;
            type string;
          }
          leaf duplexity {
            type string;
          }
          leaf mtu {
            type string;
          }
          leaf speed {
            type string;
          }
        }
        list ethernet {
          // NCS patched for predictable order
          ordered-by user;
          key "nr";
          leaf nr {
            type ncs_compliance_template_ethernet-index;
          }
          leaf name {
            type string;
          }
          container ip {
            // NCS expand uses statement
            list address {
              // NCS patched for predictable order
              ordered-by user;
              tailf:cli-suppress-mode;
              key "address mask";
              leaf address {
                type string;
              }
              leaf mask {
                type string;
              }
            }
            leaf cache-spoofing-port {
              type empty;
            }
            leaf helper-address {
              type string;
            }
            container nat {
              leaf inside {
                type empty;
              }
              leaf outside {
                type empty;
              }
            }
            container ospf;
            container router {
              container isis {
                presence "true";
                leaf cmds {
                  tailf:cli-drop-node-name;
                  type string;
                }
              }
            }
            leaf allow-promiscuous-vip {
              type empty;
            }
            container tcp {
              leaf syn-cookie {
                type empty;
              }
            }
          }
          container ipv6 {
            container access-list {
              leaf id {
                tailf:cli-drop-node-name;
                type string;
              }
              leaf in {
                // NCS drop must statement
                type empty;
              }
            }
            list address {
              // NCS patched for predictable order
              ordered-by user;
              key "ip";
              tailf:cli-suppress-mode;
              leaf ip {
                tailf:cli-drop-node-name;
                type ncs_compliance_template_ipv6-prefix;
              }
              leaf link-local {
                type empty;
              }
              leaf anycast {
                type empty;
              }
            }
            container nat {
              leaf inside {
                type empty;
              }
              leaf outside {
                type empty;
              }
            }
            container ndisc {
              container router-advertisement;
            }
            container ospf;
            container router {
              container isis {
                presence "true";
                leaf cmds {
                  tailf:cli-drop-node-name;
                  type string;
                }
              }
            }
          }
          leaf load-interval {
            type string;
          }
          container access-list {
            leaf id {
              tailf:cli-drop-node-name;
              type string;
            }
            leaf in {
              // NCS drop must statement
              type empty;
            }
          }
          leaf state {
            tailf:cli-drop-node-name;
            type string;
          }
          leaf state-alt {
            tailf:cli-drop-node-name;
            type string;
          }
          leaf duplexity {
            type string;
          }
          leaf cpu-process {
            type empty;
          }
          leaf flow-control {
            type empty;
          }
          container icmp-rate-limit {
            leaf rate {
              tailf:cli-drop-node-name;
              type string;
            }
            leaf lockup {
              // NCS drop must statement
              type string;
            }
            leaf lockup-period {
              // NCS drop must statement
              tailf:cli-drop-node-name;
              type string;
            }
          }
          container ospf;
          container isis;
          leaf l3-vlan-fwd-disable {
            type empty;
          }
          container lacp {
            leaf port-priority {
              type string;
            }
            leaf timeout {
              type string;
            }
            container trunk {
              leaf number {
                tailf:cli-drop-node-name;
                type string;
              }
              leaf admin-key {
                // NCS drop must statement
                type string;
              }
              leaf mode {
                // NCS drop must statement
                type string;
              }
              leaf unidirectional-detection {
                // NCS drop must statement
                type empty;
              }
            }
            container udld-timeout {
              leaf timeout-type {
                tailf:cli-drop-node-name;
                type string;
              }
              leaf milli {
                tailf:cli-drop-node-name;
                type string;
              }
              leaf secs {
                tailf:cli-drop-node-name;
                type string;
              }
            }
          }
          // NCS expand uses statement
          container lldp {
            container enable {
              leaf rx {
                type empty;
              }
              leaf tx {
                type empty;
              }
            }
            leaf notification {
              type string;
            }
            leaf tx-dot1-tlvs {
              type string;
            }
          }
          leaf mtu {
            type string;
          }
          leaf speed {
            type string;
          }
          list trunk-group-list {
            // NCS patched for predictable order
            ordered-by user;
            key "trunk-group-key";
            tailf:cli-drop-node-name;
            leaf trunk-group-key {
              type string;
            }
            leaf trunk-group-id {
              tailf:cli-drop-node-name;
              // NCS drop mandatory statement
              type string;
            }
            leaf trunk-group-type {
              tailf:cli-drop-node-name;
              type string;
            }
          }
        }
        list trunk {
          // NCS patched for predictable order
          ordered-by user;
          key "nr";
          leaf nr {
            type ncs_compliance_template_ethernet-index;
          }
          leaf name {
            type string;
          }
          leaf state {
            tailf:cli-drop-node-name;
            type string;
          }
          container icmp-rate-limit {
            leaf rate {
              tailf:cli-drop-node-name;
              type string;
            }
            leaf lockup {
              // NCS drop must statement
              type string;
            }
            leaf lockup-period {
              // NCS drop must statement
              tailf:cli-drop-node-name;
              type string;
            }
          }
          list access-list {
            // NCS patched for predictable order
            ordered-by user;
            tailf:cli-suppress-mode;
            key "id in-type";
            leaf id {
              type string;
            }
            leaf in-type {
              type string;
            }
          }
          container ip {
            list address {
              // NCS patched for predictable order
              ordered-by user;
              key "ip mask";
              tailf:cli-suppress-mode;
              leaf ip {
                type string;
              }
              leaf mask {
                type ncs_compliance_template_ipv4-mask;
              }
            }
            leaf allow-promiscuous-vip {
              type empty;
            }
            leaf cache-spoofing-port {
              type empty;
            }
            container nat {
              leaf inside {
                type empty;
              }
              leaf outside {
                type empty;
              }
            }
          }
        }
        list loopback {
          // NCS patched for predictable order
          ordered-by user;
          key "nr";
          leaf nr {
            type ncs_compliance_template_ethernet-index;
          }
          container ip {
            // NCS expand uses statement
            list address {
              // NCS patched for predictable order
              ordered-by user;
              tailf:cli-suppress-mode;
              key "address mask";
              leaf address {
                type string;
              }
              leaf mask {
                type string;
              }
            }
            container router {
              choice isis-choice {
                container isis-alt {
                  tailf:cli-drop-node-name;
                  leaf isis {
                    type string;
                  }
                }
                leaf isis {
                  type empty;
                }
              }
            }
          }
          container icmp-rate-limit {
            leaf rate {
              tailf:cli-drop-node-name;
              type string;
            }
            leaf lockup {
              // NCS drop must statement
              type string;
            }
            leaf lockup-period {
              tailf:cli-drop-node-name;
              // NCS drop must statement
              type string;
            }
          }
          leaf state {
            tailf:cli-drop-node-name;
            type string;
          }
        }
        list ve {
          // NCS patched for predictable order
          ordered-by user;
          key "id";
          leaf id {
            type ncs_compliance_template_vlan-index;
          }
          leaf name {
            type string;
          }
          container bfd {
            container echo {
              presence "true";
            }
          }
          container icmp-rate-limit {
            leaf rate {
              tailf:cli-drop-node-name;
              type string;
            }
            leaf lockup {
              // NCS drop must statement
              type string;
            }
            leaf lockup-period {
              tailf:cli-drop-node-name;
              // NCS drop must statement
              type string;
            }
          }
          container access-list {
            leaf id {
              tailf:cli-drop-node-name;
              type string;
            }
            leaf in {
              // NCS drop must statement
              type empty;
            }
          }
          leaf l3-vlan-fwd-disable {
            type empty;
          }
          container ip {
            leaf allow-promiscuous-vip {
              type empty;
            }
            leaf cache-spoofing-port {
              type empty;
            }
            leaf helper-address {
              type string;
            }
            container nat {
              leaf inside {
                type empty;
              }
              leaf outside {
                type empty;
              }
            }
            container ospf;
            container router {
              container isis {
                presence "true";
                leaf cmds {
                  tailf:cli-drop-node-name;
                  type string;
                }
              }
            }
            container tcp {
              leaf syn-cookie {
                type empty;
              }
            }
            // NCS expand uses statement
            list address {
              // NCS patched for predictable order
              ordered-by user;
              tailf:cli-suppress-mode;
              key "address mask";
              leaf address {
                type string;
              }
              leaf mask {
                type string;
              }
            }
          }
          container ipv6 {
            container access-list {
              leaf id {
                tailf:cli-drop-node-name;
                type string;
              }
              leaf in {
                // NCS drop must statement
                type empty;
              }
            }
            container nat {
              leaf inside {
                type empty;
              }
              leaf outside {
                type empty;
              }
            }
            container ndisc {
              container router-advertisement;
            }
            container ospf;
            container router {
              container isis {
                presence "true";
                leaf cmds {
                  tailf:cli-drop-node-name;
                  type string;
                }
              }
            }
            list address {
              // NCS patched for predictable order
              ordered-by user;
              key "ip";
              tailf:cli-suppress-mode;
              leaf ip {
                tailf:cli-drop-node-name;
                type ncs_compliance_template_ipv6-prefix;
              }
              leaf link-local {
                type empty;
              }
              leaf anycast {
                type empty;
              }
            }
          }
          leaf mtu {
            type string;
          }
          leaf state {
            tailf:cli-drop-node-name;
            type string;
          }
          container isis;
          container ospf;
        }
      }
      // NCS expand uses statement
      container ip {
        list access-list {
          // NCS patched for predictable order
          ordered-by user;
          key "name";
          leaf name {
            type string;
          }
          list access-list-rule {
            // NCS patched for predictable order
            ordered-by user;
            tailf:cli-suppress-mode;
            tailf:cli-drop-node-name;
            key "rule";
            leaf rule {
              type string;
            }
          }
        }
        list address {
          // NCS patched for predictable order
          ordered-by user;
          key "ip";
          tailf:cli-suppress-mode;
          leaf ip {
            tailf:cli-drop-node-name;
            type string;
          }
          leaf mask {
            tailf:cli-drop-node-name;
            type ncs_compliance_template_ipv4-mask;
          }
        }
        container anomaly-drop {
          leaf bad-content {
            type string;
          }
          leaf drop-all {
            type empty;
          }
          leaf frag {
            type empty;
          }
          leaf ip-option {
            type string;
          }
          leaf land-attack {
            type empty;
          }
          leaf out-of-sequence {
            type string;
          }
          leaf ping-of-death {
            type empty;
          }
          leaf tcp-no-flag {
            type empty;
          }
          leaf tcp-syn-fin {
            type empty;
          }
          leaf tcp-syn-frag {
            type empty;
          }
          leaf zero-window {
            type string;
          }
          container security-attack {
            leaf layer-3 {
              type empty;
            }
            leaf layer-4 {
              type empty;
            }
          }
          list packet-deformity {
            // NCS patched for predictable order
            ordered-by user;
            tailf:cli-suppress-mode;
            key "layer";
            leaf layer {
              type string;
            }
          }
        }
        container as-path {
          list access-list {
            // NCS patched for predictable order
            ordered-by user;
            tailf:cli-suppress-mode;
            key "name action path";
            leaf name {
              type string;
            }
            leaf action {
              type string;
            }
            leaf path {
              type string;
            }
          }
        }
        container community-list {
          list standard-number {
            // NCS patched for predictable order
            ordered-by user;
            tailf:cli-drop-node-name;
            tailf:cli-suppress-mode;
            key "nr";
            leaf nr {
              type string;
            }
            list rules {
              // NCS patched for predictable order
              ordered-by user;
              tailf:cli-drop-node-name;
              tailf:cli-suppress-mode;
              key "action expr";
              leaf action {
                type string;
              }
              leaf expr {
                type string;
              }
            }
          }
          list expanded-number {
            // NCS patched for predictable order
            ordered-by user;
            tailf:cli-drop-node-name;
            tailf:cli-suppress-mode;
            key "nr";
            leaf nr {
              type string;
            }
            list rules {
              // NCS patched for predictable order
              ordered-by user;
              tailf:cli-drop-node-name;
              tailf:cli-suppress-mode;
              key "action expr";
              leaf action {
                type string;
              }
              leaf expr {
                type string;
              }
            }
          }
          list word {
            // NCS patched for predictable order
            ordered-by user;
            tailf:cli-drop-node-name;
            tailf:cli-suppress-mode;
            key "name";
            leaf name {
              type string;
            }
            list rules {
              // NCS patched for predictable order
              ordered-by user;
              tailf:cli-drop-node-name;
              tailf:cli-suppress-mode;
              key "action expr";
              leaf action {
                type string;
              }
              leaf expr {
                type string;
              }
            }
          }
          list expanded {
            // NCS patched for predictable order
            ordered-by user;
            tailf:cli-suppress-mode;
            key "name";
            leaf name {
              type string;
            }
            list rules {
              // NCS patched for predictable order
              ordered-by user;
              tailf:cli-drop-node-name;
              tailf:cli-suppress-mode;
              key "action expr";
              leaf action {
                type string;
              }
              leaf expr {
                type string;
              }
            }
          }
          list standard {
            // NCS patched for predictable order
            ordered-by user;
            tailf:cli-suppress-mode;
            key "name";
            leaf name {
              type string;
            }
            list rules {
              // NCS patched for predictable order
              ordered-by user;
              tailf:cli-drop-node-name;
              tailf:cli-suppress-mode;
              key "action expr";
              leaf action {
                type string;
              }
              leaf expr {
                type string;
              }
            }
          }
        }
        leaf default-gateway {
          type string;
        }
        container dns {
          leaf primary {
            type string;
          }
          leaf secondary {
            type string;
          }
          leaf suffix {
            type string;
          }
        }
        container extcommunity-list {
          list standard-number {
            // NCS patched for predictable order
            ordered-by user;
            tailf:cli-drop-node-name;
            tailf:cli-suppress-mode;
            key "nr";
            leaf nr {
              type string;
            }
            list rules {
              // NCS patched for predictable order
              ordered-by user;
              tailf:cli-drop-node-name;
              tailf:cli-suppress-mode;
              key "action expr";
              leaf action {
                type string;
              }
              leaf expr {
                type string;
              }
            }
          }
          list expanded-number {
            // NCS patched for predictable order
            ordered-by user;
            tailf:cli-drop-node-name;
            tailf:cli-suppress-mode;
            key "nr";
            leaf nr {
              type string;
            }
            list rules {
              // NCS patched for predictable order
              ordered-by user;
              tailf:cli-drop-node-name;
              tailf:cli-suppress-mode;
              key "action expr";
              leaf action {
                type string;
              }
              leaf expr {
                type string;
              }
            }
          }
          list expanded {
            // NCS patched for predictable order
            ordered-by user;
            tailf:cli-suppress-mode;
            key "name";
            leaf name {
              type string;
            }
            list rules {
              // NCS patched for predictable order
              ordered-by user;
              tailf:cli-drop-node-name;
              tailf:cli-suppress-mode;
              key "action expr";
              leaf action {
                type string;
              }
              leaf expr {
                type string;
              }
            }
          }
          list standard {
            // NCS patched for predictable order
            ordered-by user;
            tailf:cli-suppress-mode;
            key "name";
            leaf name {
              type string;
            }
            list rules {
              // NCS patched for predictable order
              ordered-by user;
              tailf:cli-drop-node-name;
              tailf:cli-suppress-mode;
              key "action expr";
              leaf action {
                type string;
              }
              leaf expr {
                type string;
              }
            }
          }
        }
        container frag {
          leaf buff {
            type string;
          }
          container cpu-threshold {
            leaf high {
              type string;
            }
            leaf low {
              type string;
            }
          }
          leaf max-reassembly-sessions {
            type string;
          }
          leaf timeout {
            type string;
          }
        }
        container icmp {
          container disable {
            leaf redirect {
              type empty;
            }
            leaf unreachable {
              type empty;
            }
          }
        }
        container mgmt-traffic {
          container snmp {
            // NCS expand uses statement
            container source-interface {
              leaf loopback {
                type string;
              }
            }
          }
          container ntp {
            // NCS expand uses statement
            container source-interface {
              leaf loopback {
                type string;
              }
            }
          }
          container syslog {
            // NCS expand uses statement
            container source-interface {
              leaf loopback {
                type string;
              }
            }
          }
          container ssh {
            // NCS expand uses statement
            container source-interface {
              leaf loopback {
                type string;
              }
            }
          }
          container telnet {
            // NCS expand uses statement
            container source-interface {
              leaf loopback {
                type string;
              }
            }
          }
          container ftp {
            // NCS expand uses statement
            container source-interface {
              leaf loopback {
                type string;
              }
            }
          }
          container tftp {
            // NCS expand uses statement
            container source-interface {
              leaf loopback {
                type string;
              }
            }
          }
          container rcp {
            // NCS expand uses statement
            container source-interface {
              leaf loopback {
                type string;
              }
            }
          }
          container web {
            // NCS expand uses statement
            container source-interface {
              leaf loopback {
                type string;
              }
            }
          }
          container all {
            // NCS expand uses statement
            container source-interface {
              leaf loopback {
                type string;
              }
            }
          }
        }
        container nat {
          // NCS expand uses statement
          container alg {
            // NCS expand uses statement
            leaf pptp {
              type string;
            }
            // NCS expand uses statement
            leaf tftp {
              type string;
            }
            // NCS expand uses statement
            leaf rtsp {
              type string;
            }
            // NCS expand uses statement
            leaf esp {
              type string;
            }
          }
          leaf allow-static-host {
            type empty;
          }
          container inside {
            container source {
              list list {
                // NCS patched for predictable order
                ordered-by user;
                tailf:cli-suppress-mode;
                key "id";
                leaf id {
                  type string;
                }
                leaf pool {
                  // NCS drop mandatory statement
                  type string;
                }
              }
              leaf class-list {
                type string;
              }
              list static {
                // NCS patched for predictable order
                ordered-by user;
                tailf:cli-suppress-mode;
                key "source nat";
                leaf source {
                  type string;
                }
                leaf nat {
                  type string;
                }
                leaf vrid {
                  type string;
                }
              }
            }
          }
          list pool {
            // NCS patched for predictable order
            ordered-by user;
            tailf:cli-suppress-mode;
            key "name";
            leaf name {
              type string;
            }
            leaf ipstart {
              // NCS drop mandatory statement
              tailf:cli-drop-node-name;
              type string;
            }
            leaf ipend {
              // NCS drop mandatory statement
              tailf:cli-drop-node-name;
              type string;
            }
            leaf netmask {
              // NCS drop mandatory statement
              type string;
            }
            leaf gateway {
              type string;
            }
            leaf ha-group-id {
              type string;
            }
            leaf ha-use-all-ports {
              type empty;
            }
            leaf vrid {
              type string;
            }
            leaf ip-rr {
              type empty;
            }
            leaf lsn {
              type empty;
            }
            leaf max-users-per-ip {
              type string;
            }
          }
          list pool-group {
            // NCS patched for predictable order
            ordered-by user;
            key "name";
            leaf name {
              type string;
            }
            leaf ha-group-id {
              type string;
            }
            list member {
              // NCS patched for predictable order
              ordered-by user;
              key "member-id";
              tailf:cli-suppress-mode;
              leaf member-id {
                type string;
              }
            }
          }
          container range-list;
          leaf reset-idle-tcp-conn {
            type empty;
          }
          container template {
            list logging {
              // NCS patched for predictable order
              ordered-by user;
              key "name";
              leaf name {
                type string;
              }
            }
          }
          container translation {
            leaf icmp-timeout {
              type string;
            }
            leaf tcp-timeout {
              type string;
            }
            leaf udp-timeout {
              type string;
            }
            leaf syn-timeout {
              type string;
            }
            list service-timeout {
              // NCS patched for predictable order
              ordered-by user;
              tailf:cli-suppress-mode;
              key "protocol from";
              leaf protocol {
                type string;
              }
              leaf from {
                type string;
              }
              leaf to {
                type string;
              }
              leaf timeout {
                tailf:cli-drop-node-name;
                type string;
              }
            }
          }
          container lsn {
            container endpoint-independent-mapping {
              container tcp {
                container enable {
                  leaf ephemeral {
                    type empty;
                  }
                  leaf well-known {
                    type empty;
                  }
                }
              }
              container udp {
                container enable {
                  leaf ephemeral {
                    type empty;
                  }
                  leaf well-known {
                    type empty;
                  }
                }
              }
            }
            container endpoint-independent-filtering {
              container tcp {
                container enable {
                  leaf ephemeral {
                    type empty;
                    // NCS drop must statement
                  }
                  leaf well-known {
                    type empty;
                    // NCS drop must statement
                  }
                }
              }
              container udp {
                container enable {
                  leaf ephemeral {
                    type empty;
                    // NCS drop must statement
                  }
                  leaf well-known {
                    type empty;
                    // NCS drop must statement
                  }
                }
              }
            }
            leaf ip-selection {
              type string;
            }
            leaf attempt-port-preservation {
              type string;
            }
            // NCS expand uses statement
            container alg {
              // NCS expand uses statement
              leaf pptp {
                type string;
              }
              // NCS expand uses statement
              leaf tftp {
                type string;
              }
              // NCS expand uses statement
              leaf rtsp {
                type string;
              }
              // NCS expand uses statement
              leaf esp {
                type string;
              }
            }
          }
        }
        // NCS expand uses statement
        list prefix-list {
          // NCS patched for predictable order
          ordered-by user;
          tailf:cli-suppress-mode;
          key "name seq";
          leaf name {
            type string;
          }
          leaf seq {
            type string;
          }
          choice permit-deny {
            leaf permit {
              type string;
            }
            leaf deny {
              type string;
            }
          }
          leaf ge {
            type string;
          }
          leaf le {
            type string;
          }
        }
        // NCS expand uses statement
        list route {
          // NCS patched for predictable order
          ordered-by user;
          tailf:cli-suppress-mode;
          key "ip mask forwarding-router";
          leaf ip {
            type string;
          }
          leaf mask {
            type string;
          }
          leaf forwarding-router {
            type string;
          }
          leaf distance {
            tailf:cli-drop-node-name;
            type string;
          }
          leaf cpu-process {
            tailf:cli-drop-node-name;
            type string;
          }
        }
        container tcp {
          container syn-cookie {
            leaf threshold {
              type string;
            }
          }
        }
      }
      uses ncs_compliance_template_bfd-grouping;
      uses ncs_compliance_template_health-grouping;
      uses ncs_compliance_template_glid-grouping;
      uses ncs_compliance_template_class-list-grouping;
      uses ncs_compliance_template_class-list-group-grouping;
      uses ncs_compliance_template_slb-grouping;
      uses ncs_compliance_template_gslb-grouping;
      uses ncs_compliance_template_vrrp-a-grouping;
      uses ncs_compliance_template_vlan-grouping;
      uses ncs_compliance_template_logging-grouping;
      uses ncs_compliance_template_bw-list-grouping;
      uses ncs_compliance_template_ip-list-grouping;
      uses ncs_compliance_template_cgnv6-grouping;
      uses ncs_compliance_template_router-grouping;
      uses ncs_compliance_template_system-jumbo-global-grouping;
      uses ncs_compliance_template_hd-monitor-grouping;
      uses ncs_compliance_template_clock-grouping;
      uses ncs_compliance_template_ntp-grouping;
      uses ncs_compliance_template_netflow-grouping;
      uses ncs_compliance_template_tacacs-server-grouping;
      uses ncs_compliance_template_radius-server-grouping;
      uses ncs_compliance_template_authentication-grouping;
      uses ncs_compliance_template_ipv6-grouping;
      uses ncs_compliance_template_nat64-grouping;
      uses ncs_compliance_template_lsn-lid-grouping;
      uses ncs_compliance_template_ha-grouping;
      uses ncs_compliance_template_floating-ip-grouping;
      uses ncs_compliance_template_snmp-server-grouping;
      uses ncs_compliance_template_audit-grouping;
      uses ncs_compliance_template_terminal-grouping;
      uses ncs_compliance_template_web-service-grouping;
      uses ncs_compliance_template_multi-config-grouping;
      uses ncs_compliance_template_lldp-grouping;
      uses ncs_compliance_template_banner-grouping;
      uses ncs_compliance_template_device-context-grouping;
      uses ncs_compliance_template_system-grouping;
      uses ncs_compliance_template_partition-grouping;
      uses ncs_compliance_template_partition-group-grouping;
      uses ncs_compliance_template_access-list-grouping;
      uses ncs_compliance_template_tftp-grouping;
      uses ncs_compliance_template_stats-data-disable-grouping;
      uses ncs_compliance_template_syn-cookie-grouping;
      uses ncs_compliance_template_enable-management-grouping;
      uses ncs_compliance_template_disable-management-grouping;
      uses ncs_compliance_template_monitor-grouping;
      uses ncs_compliance_template_extended-stats-grouping;
      uses ncs_compliance_template_admin-grouping;
      uses ncs_compliance_template_enable-core-grouping;
      uses ncs_compliance_template_trunk-grouping;
      uses ncs_compliance_template_lacp-grouping;
      uses ncs_compliance_template_sflow-grouping;
      uses ncs_compliance_template_zone-grouping;
      uses ncs_compliance_template_object-grouping;
      uses ncs_compliance_template_object-group-grouping;
      uses ncs_compliance_template_rule-set-grouping;
      uses ncs_compliance_template_fw-grouping;
      uses ncs_compliance_template_route-map-grouping;
      uses ncs_compliance_template_accounting-grouping;
      uses ncs_compliance_template_ve-stats-grouping;
      uses ncs_compliance_template_acos-events-grouping;
      uses ncs_compliance_template_bgp-grouping;
      uses ncs_compliance_template_harmony-controller-grouping;
      // NCS expand uses statement
      container vcs {
        leaf state {
          tailf:cli-drop-node-name;
          type string;
        }
        list device {
          // NCS patched for predictable order
          ordered-by user;
          key "id";
          leaf id {
            type string;
          }
          leaf priority {
            type string;
          }
          container interfaces {
            leaf management {
              type empty;
            }
            list ethernet {
              // NCS patched for predictable order
              ordered-by user;
              tailf:cli-suppress-mode;
              key "id";
              leaf id {
                type string;
              }
            }
            list trunk {
              // NCS patched for predictable order
              ordered-by user;
              tailf:cli-suppress-mode;
              key "id";
              leaf id {
                type string;
              }
            }
            list ve {
              // NCS patched for predictable order
              ordered-by user;
              tailf:cli-suppress-mode;
              key "id";
              leaf id {
                type string;
              }
            }
          }
          leaf enable {
            type empty;
          }
        }
        list floating-ip {
          // NCS patched for predictable order
          ordered-by user;
          tailf:cli-suppress-mode;
          key "floating-ip-address";
          leaf floating-ip-address {
            tailf:cli-drop-node-name;
            type string;
          }
          leaf mask {
            tailf:cli-drop-node-name;
            type ncs_compliance_template_ipv4-mask;
          }
        }
        leaf ssl-enable {
          type empty;
        }
        leaf failure-retry-count {
          type string;
        }
      }
    }
  }
}
