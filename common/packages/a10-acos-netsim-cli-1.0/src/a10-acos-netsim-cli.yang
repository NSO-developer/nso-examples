module a10-acos-netsim-cli {
  yang-version 1.1;
  namespace "http://tail-f.com/ns/ned-id/a10-acos-netsim-cli";
  prefix a10-acos-netsim-cli;

  import tailf-common {
    prefix tailf;
  }

  import tailf-ncs-ned {
    prefix ned;
  }

  identity a10-acos-netsim-cli {
    tailf:abstract;
    base ned:cli-ned-id;
  }
}
