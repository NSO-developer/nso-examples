module router-gen-1.0 {
  yang-version 1.1;
  namespace "http://tail-f.com/ns/ned-id/router-gen-1.0";
  prefix router-gen-1.0;

  import router-gen {
    prefix family;
  }

  identity router-gen-1.0 {
    base family:router-gen;
  }
}
