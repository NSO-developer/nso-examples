module netsim-ned-cisco-asa-stats {
  // Generated by yanger -t ncs
  tailf:mount-id "cisco-asa-netsim-cli-1.0:cisco-asa-netsim-cli-1.0";
  tailf:ncs-device-type "cli-ned";

  namespace "http://cisco.com/ned/asa-stats";
  prefix asa-stats;

  import tailf-common {
    prefix tailf;
  }
  import tailf-ncs {
    prefix ncs;
  }

  augment "/ncs:devices/ncs:device/ncs:config" {
    // NCS drop config false container version
    // NCS drop config false container 'vpn-sessiondb'
    // NCS drop config false container ssl
    // NCS drop config false list inventory
    container exec {
      tailf:ncs-device-type "cli-ned";
      tailf:display-when "not(../../ncs:module) or ../../ncs:module[ncs:name='netsim-ned-cisco-asa-stats']";
      tailf:alt-name "exec-stats";
    }
  }
  augment "/ncs:devices/ncs:device/ncs:live-status" {
    container version {
      tailf:ncs-device-type "cli-ned";
      tailf:display-when "not(../../ncs:module) or ../../ncs:module[ncs:name='netsim-ned-cisco-asa-stats'] or (../../ncs:live-status-protocol[not(ncs:capability)]) or (../../ncs:live-status-protocol/ncs:capability/ncs:module[.='netsim-ned-cisco-asa-stats'])";
      presence "true";
      leaf name {
        type string;
      }
      leaf version {
        type string;
      }
      leaf model {
        type string;
      }
      leaf serial-number {
        type string;
      }
      tailf:alt-name "version-stats";
    }
    container vpn-sessiondb {
      tailf:ncs-device-type "cli-ned";
      tailf:display-when "not(../../ncs:module) or ../../ncs:module[ncs:name='netsim-ned-cisco-asa-stats'] or (../../ncs:live-status-protocol[not(ncs:capability)]) or (../../ncs:live-status-protocol/ncs:capability/ncs:module[.='netsim-ned-cisco-asa-stats'])";
      list anyconnect {
        key "username index";
        leaf username {
          type string;
        }
        leaf index {
          type uint32;
        }
        leaf login-time {
          type string;
        }
        leaf duration {
          type string;
        }
        leaf inactivity {
          type string;
        }
        leaf tx-bytes {
          type uint64;
        }
        leaf rx-bytes {
          type uint64;
        }
        leaf status {
          type enumeration {
            enum "active";
            enum "inactive";
          }
        }
      }
      tailf:alt-name "vpn-sessiondb-stats";
    }
    container ssl {
      tailf:ncs-device-type "cli-ned";
      tailf:display-when "not(../../ncs:module) or ../../ncs:module[ncs:name='netsim-ned-cisco-asa-stats'] or (../../ncs:live-status-protocol[not(ncs:capability)]) or (../../ncs:live-status-protocol/ncs:capability/ncs:module[.='netsim-ned-cisco-asa-stats'])";
      leaf post-decrypt-octets {
        type uint64;
      }
      leaf post-encrypt-octets {
        type uint64;
      }
      tailf:alt-name "ssl-stats";
    }
    list inventory {
      tailf:ncs-device-type "cli-ned";
      tailf:display-when "not(../ncs:module) or ../ncs:module[ncs:name='netsim-ned-cisco-asa-stats'] or (../ncs:live-status-protocol[not(ncs:capability)]) or (../ncs:live-status-protocol/ncs:capability/ncs:module[.='netsim-ned-cisco-asa-stats'])";
      key "name";
      leaf name {
        type string;
      }
      leaf descr {
        type string;
      }
      leaf sn {
        type string;
      }
      tailf:alt-name "inventory-stats";
    }
    container exec {
      tailf:ncs-device-type "cli-ned";
      tailf:display-when "not(../../ncs:module) or ../../ncs:module[ncs:name='netsim-ned-cisco-asa-stats'] or (../../ncs:live-status-protocol[not(ncs:capability)]) or (../../ncs:live-status-protocol/ncs:capability/ncs:module[.='netsim-ned-cisco-asa-stats'])";
      tailf:alt-name "exec-stats";
    }
  }
}
