module cisco-asa-netsim-cli {
  yang-version 1.1;
  namespace "http://tail-f.com/ns/ned-id/cisco-asa-netsim-cli";
  prefix cisco-asa-netsim-cli;

  import tailf-common {
    prefix tailf;
  }

  import tailf-ncs-ned {
    prefix ned;
  }

  identity cisco-asa-netsim-cli {
    tailf:abstract;
    base ned:cli-ned-id;
  }
}
