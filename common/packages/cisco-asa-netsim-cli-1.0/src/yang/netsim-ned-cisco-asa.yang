module netsim-ned-cisco-asa {
  namespace "http://cisco.com/ned/asa";
  prefix asa;

  import tailf-common {
    prefix tailf;
  }
  import ietf-inet-types {
    prefix inet;
  }

  revision 2025-06-26;

  typedef percentage-type {
    type uint8;
  }

  typedef ipv4-prefix {
    type string;
  }

  typedef ipv6-prefix {
    type string;
  }

  typedef host-type {
    type union {
      type inet:ip-address;
      type inet:domain-name;
    }
  }

  typedef asn-ip-type {
    type string;
  }

  typedef hhmm-type {
    type string;
  }

  typedef hhmmss-type {
    type string;
  }

  typedef weekday-type {
    type enumeration {
      enum "Mon";
      enum "Tue";
      enum "Wed";
      enum "Thu";
      enum "Fri";
      enum "Sat";
      enum "Sun";
    }
  }

  typedef month-type {
    type enumeration {
      enum "Jan";
      enum "Feb";
      enum "Mar";
      enum "Apr";
      enum "May";
      enum "Jun";
      enum "Jul";
      enum "Aug";
      enum "Sep";
      enum "Oct";
      enum "Nov";
      enum "Dec";
    }
  }

  typedef nameif-type {
    type string;
  }

  typedef secret128-type {
    type string;
  }

  typedef dscp-type {
    type union {
      type uint8;
      type enumeration {
        enum "af11" {
          value 10011;
        }
        enum "af12" {
          value 10012;
        }
        enum "af13" {
          value 10013;
        }
        enum "af21" {
          value 10021;
        }
        enum "af22" {
          value 10022;
        }
        enum "af23" {
          value 10023;
        }
        enum "af31" {
          value 10031;
        }
        enum "af32" {
          value 10032;
        }
        enum "af33" {
          value 10033;
        }
        enum "af41" {
          value 10041;
        }
        enum "af42" {
          value 10042;
        }
        enum "af43" {
          value 10043;
        }
        enum "cs1" {
          value 10001;
        }
        enum "cs2" {
          value 10002;
        }
        enum "cs3" {
          value 10003;
        }
        enum "cs4" {
          value 10004;
        }
        enum "cs5" {
          value 10005;
        }
        enum "cs6" {
          value 10006;
        }
        enum "cs7" {
          value 10007;
        }
        enum "default" {
          tailf:code-name "dscp_default";
          value 1000;
        }
        enum "dscp" {
          value 1001;
        }
        enum "ef" {
          value 1002;
        }
        enum "precedence" {
          value 1003;
        }
      }
    }
  }

  typedef precedence-type {
    type union {
      type uint8;
      type enumeration {
        enum "critical";
        enum "flash";
        enum "flash-override";
        enum "immediate";
        enum "internet" {
          tailf:code-name "prec_internet";
        }
        enum "network";
        enum "priority" {
          tailf:code-name "prec_priority";
        }
        enum "routine";
      }
    }
  }

  typedef access-list-in-out-type {
    type enumeration {
      enum "in";
      enum "out";
    }
  }

  typedef ospf-area-type {
    type union {
      type uint32;
      type inet:host;
    }
  }

  typedef ospf-metric-type {
    type uint8;
  }

  typedef logging-level-type {
    type enumeration {
      enum "alerts";
      enum "critical";
      enum "debugging";
      enum "emergencies";
      enum "errors";
      enum "informational";
      enum "notifications";
      enum "warnings";
    }
  }

  typedef logging-type {
    type union {
      type string;
      type logging-level-type;
    }
  }

  typedef bgp-as-no-type {
    type union {
      type uint32;
      type string;
    }
  }

  typedef eigrp-as-no-type {
    type uint16;
  }

  typedef attribute-type {
    type enumeration {
      enum "C";
      enum "CN";
      enum "DNQ";
      enum "EA";
      enum "GENQ";
      enum "GN";
      enum "I";
      enum "L";
      enum "N";
      enum "O";
      enum "OU";
      enum "SER";
      enum "SN";
      enum "SP";
      enum "T";
      enum "UID";
      enum "UPN";
    }
  }

  typedef tls-version-type {
    type enumeration {
      enum "tlsv1";
      enum "tlsv1.1";
      enum "tlsv1.2";
    }
  }

  grouping password-08-grouping {
    leaf type {
      tailf:cli-drop-node-name;
      tailf:cli-optional-in-sequence;
      type enumeration {
        enum "0";
        enum "8";
      }
    }
    leaf secret {
      tailf:cli-drop-node-name;
      type string;
    }
  }

  grouping interface-list-grouping {
    list name {
      tailf:cli-drop-node-name;
      tailf:cli-suppress-mode;
      tailf:cli-delete-when-empty;
      key "name";
      leaf name {
        type nameif-type;
      }
    }
  }

  grouping interface-name-grouping {
    leaf nameif {
      tailf:cli-drop-node-name;
      type nameif-type;
    }
  }

  grouping distribute-list-content-grouping {
    leaf access-list-name {
      tailf:cli-drop-node-name;
      tailf:cli-prefix-key;
      type string;
    }
    leaf connected {
      type empty;
    }
    leaf static {
      type empty;
    }
    leaf-list ospf {
      type uint16;
    }
    leaf rip {
      type empty;
    }
    leaf bgp {
      type bgp-as-no-type;
    }
    leaf eigrp {
      type eigrp-as-no-type;
    }
  }

  grouping router-distribute-list-grouping {
    container distribute-list-interface {
      tailf:cli-drop-node-name;
      list distribute-list {
        tailf:cli-suppress-mode;
        tailf:cli-delete-when-empty;
        key "direction interface";
        leaf direction {
          type enumeration {
            enum "in";
            enum "out";
          }
        }
        leaf interface {
          tailf:cli-expose-key-name;
          type nameif-type;
        }
        uses distribute-list-content-grouping;
      }
    }
    list distribute-list {
      tailf:cli-suppress-mode;
      tailf:cli-delete-when-empty;
      key "direction";
      leaf direction {
        type enumeration {
          enum "in";
          enum "out";
        }
      }
      uses distribute-list-content-grouping;
    }
  }

  grouping passive-interface-grouping {
    container passive-interface {
      tailf:cli-delete-when-empty;
      choice passive-interface-choice {
        leaf default {
          type empty;
        }
        list interface {
          tailf:cli-drop-node-name;
          tailf:cli-suppress-mode;
          tailf:cli-delete-when-empty;
          key "name";
          leaf name {
            type string;
          }
        }
      }
    }
    container disable {
      list passive-interface {
        tailf:cli-suppress-mode;
        tailf:cli-delete-when-empty;
        tailf:cli-compact-syntax;
        key "interface";
        leaf interface {
          tailf:cli-multi-word-key;
          type nameif-type;
        }
      }
    }
  }

  grouping ip-community-list-standard-grouping {
    container deny {
      presence "true";
      list deny-list {
        tailf:cli-drop-node-name;
        tailf:cli-suppress-mode;
        tailf:cli-delete-when-empty;
        key "expr";
        leaf expr {
          tailf:cli-multi-word-key;
          type string;
        }
      }
    }
    container permit {
      presence "Specify community to accept";
      list permit-list {
        tailf:cli-drop-node-name;
        tailf:cli-suppress-mode;
        tailf:cli-delete-when-empty;
        key "expr";
        leaf expr {
          tailf:cli-multi-word-key;
          type string;
        }
      }
    }
  }

  grouping interface-common-grouping0 {
    leaf description {
      tailf:cli-multi-value;
      type string;
    }
    leaf management-only {
      type empty;
    }
    container authentication {
      container mode {
        container eigrp {
          tailf:cli-compact-syntax;
          tailf:cli-sequence-commands {
            tailf:cli-reset-siblings;
          }
          leaf process-id {
            tailf:cli-drop-node-name;
            type uint16;
          }
          leaf md5 {
            type empty;
          }
        }
      }
    }
    container mac-address {
      tailf:cli-compact-syntax;
      tailf:cli-sequence-commands {
        tailf:cli-reset-siblings;
      }
      leaf active {
        tailf:cli-drop-node-name;
        type string;
      }
      leaf standby {
        type string;
      }
    }
    container ip {
      container address {
        choice address-choice {
          container ip {
            tailf:cli-drop-node-name;
            tailf:cli-compact-syntax;
            tailf:cli-sequence-commands {
              tailf:cli-reset-siblings;
            }
            leaf host-ip {
              tailf:cli-drop-node-name;
              type string;
            }
            leaf netmask {
              tailf:cli-drop-node-name;
              type inet:ipv4-address;
            }
            choice ip-choice {
              leaf cluster-pool {
                type string;
              }
              leaf standby {
                type inet:host;
              }
              container pppoe {
                presence "true";
                leaf setroute {
                  type empty;
                }
              }
            }
          }
          container dhcp {
            presence "true";
            leaf setroute {
              type empty;
            }
          }
          container pppoe {
            presence "true";
            leaf setroute {
              type empty;
            }
          }
        }
      }
    }
    container ipv6 {
      leaf enable {
        type empty;
      }
      container address {
        tailf:cli-compact-syntax;
        tailf:cli-sequence-commands {
          tailf:cli-reset-siblings;
        }
        leaf address {
          tailf:cli-drop-node-name;
          type union {
            type inet:ip-address;
            type string;
          }
        }
        leaf standby {
          tailf:cli-optional-in-sequence;
          type inet:host;
        }
        leaf autoconfig {
          type empty;
        }
      }
      container nd {
        leaf suppress-ra {
          type empty;
        }
        container dad {
          leaf attempts {
            type uint16;
          }
        }
      }
      container ospf {
        leaf priority {
          type uint8;
        }
        leaf hello-interval {
          type uint16;
        }
        container network {
          choice network-choice {
            leaf broadcast {
              type empty;
            }
            container point-to-point {
              leaf non-broadcast {
                type empty;
              }
            }
          }
        }
        leaf mtu-ignore {
          type empty;
        }
        container router {
          tailf:cli-drop-node-name;
          tailf:cli-compact-syntax;
          tailf:cli-sequence-commands {
            tailf:cli-reset-siblings;
          }
          leaf id {
            tailf:cli-drop-node-name;
            type uint16;
          }
          leaf area {
            type ospf-area-type;
          }
        }
      }
    }
    leaf vlan {
      type uint16;
    }
    leaf nameif {
      type string;
    }
    leaf shutdown {
      type empty;
    }
    leaf bridge-group {
      type uint8;
    }
    leaf security-level {
      type uint8;
    }
    container ospf {
      leaf priority {
        type uint8;
      }
      leaf hello-interval {
        type uint16;
      }
      container network {
        container point-to-point {
          leaf non-broadcast {
            type empty;
          }
        }
      }
      container authentication-key {
        tailf:cli-compact-syntax;
        tailf:cli-sequence-commands;
        uses password-08-grouping {
          refine "secret";
        }
      }
      list message-digest-key {
        tailf:cli-suppress-mode;
        tailf:cli-delete-when-empty;
        key "id";
        leaf id {
          type uint8;
        }
        container md5 {
          tailf:cli-flatten-container;
          tailf:cli-compact-syntax;
          tailf:cli-sequence-commands;
          uses password-08-grouping {
            refine "secret";
          }
        }
      }
      container authentication {
        tailf:cli-delete-when-empty;
        presence "true";
        leaf type {
          tailf:cli-drop-node-name;
          type enumeration {
            enum "message-digest";
            enum "null";
          }
        }
      }
      leaf cost {
        type uint16;
      }
      leaf mtu-ignore {
        type empty;
      }
    }
    container policy-route {
      leaf route-map {
        type string;
      }
    }
    container zone-member {
      leaf name {
        tailf:cli-drop-node-name;
        type string;
      }
    }
  }

  grouping interface-common-grouping {
    uses interface-common-grouping0 {
      refine "policy-route/route-map";
      refine "zone-member/name";
    }
  }

  grouping sub-interface-common-grouping {
    uses interface-common-grouping0 {
      refine "policy-route/route-map";
      refine "zone-member/name";
    }
  }

  grouping interface-ethernet-grouping {
    leaf speed {
      type enumeration {
        enum "10";
        enum "100";
        enum "1000";
        enum "auto";
        enum "nonegotiate";
      }
    }
    leaf duplex {
      type enumeration {
        enum "auto";
        enum "full";
        enum "half";
      }
    }
    container channel-group {
      tailf:cli-compact-syntax;
      tailf:cli-sequence-commands {
        tailf:cli-reset-siblings;
      }
      leaf number {
        tailf:cli-drop-node-name;
        type uint16;
      }
      leaf mode {
        type enumeration {
          enum "active";
          enum "on";
          enum "passive";
        }
      }
      leaf vss-id {
        type uint8;
      }
    }
    container pppoe {
      container client {
        container route {
          leaf distance {
            type uint8;
          }
          leaf track {
            type uint16;
          }
        }
        container secondary {
          leaf track {
            type uint16;
          }
        }
        container vpdn {
          leaf group {
            type string;
          }
        }
      }
    }
    container lacp {
      leaf system-priority {
        type uint16;
      }
      leaf max-bundle {
        type uint8;
      }
    }
  }

  grouping interface-switch-grouping {
    container switchport {
      presence "true";
      container access {
        leaf vlan {
          type uint16;
        }
      }
      container trunk {
        container native {
          leaf vlan {
            type uint16;
          }
        }
        container allowed {
          leaf-list vlans {
            tailf:cli-range-list-syntax;
            type uint16;
          }
        }
      }
      container mode {
        choice mode-choice {
          container access {
            presence "true";
          }
          container trunk {
            presence "true";
          }
        }
      }
      leaf protected {
        type empty;
      }
    }
  }

  grouping redistribute-ospf-match-grouping {
    leaf match {
      type empty;
    }
    leaf internal {
      type empty;
    }
    container external-1 {
      tailf:cli-drop-node-name;
      tailf:cli-flatten-container;
      leaf external {
        type enumeration {
          enum "1";
        }
      }
    }
    container external-2 {
      tailf:cli-drop-node-name;
      tailf:cli-flatten-container;
      leaf external {
        type enumeration {
          enum "2";
        }
      }
    }
    container nssa-external-1 {
      tailf:cli-drop-node-name;
      tailf:cli-flatten-container;
      leaf nssa-external {
        type enumeration {
          enum "1";
        }
      }
    }
    container nssa-external-2 {
      tailf:cli-drop-node-name;
      tailf:cli-flatten-container;
      leaf nssa-external {
        type enumeration {
          enum "2";
        }
      }
    }
  }

  grouping router-rip-redistribute-grouping {
    leaf metric {
      type union {
        type uint8;
        type enumeration {
          enum "transparent";
        }
      }
    }
    leaf route-map {
      type string;
    }
  }

  grouping router-route-map-grouping5 {
    leaf route-map {
      type string;
    }
  }

  grouping router-route-map-grouping6 {
    leaf route-map {
      type string;
    }
  }

  grouping router-ospf-redistribute-grouping {
    leaf metric {
      type uint32;
    }
    leaf metric-type {
      type enumeration {
        enum "1";
        enum "2";
      }
    }
    leaf nssa-only {
      type empty;
    }
    leaf tag {
      type uint32;
    }
    leaf subnets {
      type empty;
    }
  }

  grouping router-bgp-neighbor-grouping {
    leaf remote-as {
      type string;
    }
    container local-as {
      tailf:cli-compact-syntax;
      tailf:cli-sequence-commands {
        tailf:cli-reset-siblings;
      }
      tailf:cli-delete-when-empty;
      presence "true";
      leaf as-no {
        tailf:cli-drop-node-name;
        type bgp-as-no-type;
      }
      leaf no-prepend {
        type empty;
      }
      leaf replace-as {
        type empty;
      }
      leaf dual-as {
        type empty;
      }
    }
    container ha-mode {
      container graceful-restart {
        tailf:cli-delete-when-empty;
        presence "true";
        leaf disable {
          type empty;
        }
      }
    }
    leaf description {
      tailf:cli-multi-value;
      type string;
    }
    leaf shutdown {
      type empty;
    }
    leaf ebgp-multihop {
      type uint8;
    }
    container transport {
      leaf connection-mode {
        type enumeration {
          enum "active";
          enum "passive";
        }
      }
    }
    container password {
      tailf:cli-compact-syntax;
      tailf:cli-sequence-commands;
      leaf enctype {
        tailf:cli-drop-node-name;
        tailf:cli-optional-in-sequence;
        type uint8;
      }
      leaf text {
        tailf:cli-drop-node-name;
        tailf:cli-multi-value;
        type secret128-type;
      }
    }
    container ttl-security {
      leaf hops {
        type uint8;
      }
    }
    leaf version {
      type uint8;
    }
    container timers {
      tailf:cli-compact-syntax;
      tailf:cli-sequence-commands {
        tailf:cli-reset-siblings;
      }
      leaf keepalive-interval {
        tailf:cli-drop-node-name;
        type uint16;
      }
      leaf holdtime {
        tailf:cli-drop-node-name;
        type uint16;
      }
      leaf minimum-neighbor-hold {
        tailf:cli-drop-node-name;
        type uint16;
      }
    }
    leaf disable-connected-check {
      type empty;
    }
    leaf activate {
      type empty;
    }
    container send-community {
      presence "true";
    }
    container advertise-map {
      tailf:cli-compact-syntax;
      tailf:cli-sequence-commands;
      leaf name {
        tailf:cli-drop-node-name;
        type string;
      }
      leaf exist-map {
        type string;
      }
    }
    leaf next-hop-self {
      type empty;
    }
    container default-originate {
      tailf:cli-delete-when-empty;
      presence "true";
      leaf route-map {
        type string;
      }
    }
    leaf advertisement-interval {
      type uint16;
    }
    uses router-distribute-list-grouping {
      refine "distribute-list-interface/distribute-list/access-list-name";
      refine "distribute-list-interface";
      refine "distribute-list/access-list-name";
      refine "distribute-list";
    }
    list route-map {
      tailf:cli-suppress-mode;
      tailf:cli-delete-when-empty;
      key "direction";
      leaf direction {
        type enumeration {
          enum "in";
          enum "out";
        }
      }
      leaf route-map-name {
        tailf:cli-drop-node-name;
        tailf:cli-prefix-key;
        type string;
        mandatory true;
      }
    }
    container maximum-prefix {
      tailf:cli-compact-syntax;
      tailf:cli-sequence-commands {
        tailf:cli-reset-all-siblings;
      }
      leaf max-prefix-no {
        tailf:cli-drop-node-name;
        type uint32;
      }
      leaf threshold {
        tailf:cli-drop-node-name;
        tailf:cli-break-sequence-commands;
        type uint8;
      }
      leaf restart {
        type uint16;
      }
      leaf warning-only {
        type empty;
      }
    }
    list filter-list {
      tailf:cli-suppress-mode;
      tailf:cli-delete-when-empty;
      tailf:cli-compact-syntax;
      key "direction";
      leaf direction {
        type enumeration {
          enum "in";
          enum "out";
        }
      }
      leaf as-path-list {
        tailf:cli-drop-node-name;
        tailf:cli-prefix-key;
        type uint16;
      }
    }
    leaf weight {
      type uint16;
    }
    list prefix-list {
      tailf:cli-suppress-mode;
      tailf:cli-delete-when-empty;
      key "direction";
      leaf direction {
        type enumeration {
          enum "in";
          enum "out";
        }
      }
      leaf prefix-list-name {
        tailf:cli-drop-node-name;
        tailf:cli-prefix-key;
        type string;
      }
    }
    leaf remove-private-as {
      type empty;
    }
  }

  grouping router-bgp-max-path-grouping {
    container paths {
      tailf:cli-drop-node-name;
      tailf:cli-compact-syntax;
      tailf:cli-sequence-commands {
        tailf:cli-reset-siblings;
      }
      leaf number-of-paths {
        tailf:cli-drop-node-name;
        type uint16;
      }
      leaf import {
        type uint16;
      }
    }
  }

  grouping router-bgp-redistribute-grouping {
    leaf metric {
      type uint32;
    }
    leaf route-map {
      type string;
    }
  }

  grouping router-bgp-af-grouping {
    container bgp {
      leaf router-id {
        type inet:ipv4-address;
      }
      leaf scan-time {
        type uint8;
      }
      container nexthop {
        container trigger {
          leaf delay {
            type uint8;
          }
          leaf enable {
            type boolean;
          }
        }
      }
      list inject-map {
        tailf:cli-suppress-mode;
        tailf:cli-delete-when-empty;
        tailf:cli-compact-syntax;
        tailf:cli-sequence-commands;
        key "name";
        leaf name {
          type string;
        }
        leaf exist-map {
          type string;
        }
        leaf copy-attributes {
          type empty;
        }
      }
      leaf redistribute-internal {
        type empty;
      }
      leaf suppress-inactive {
        type empty;
      }
    }
    list neighbor {
      tailf:cli-suppress-mode;
      tailf:cli-delete-when-empty;
      key "id";
      leaf id {
        type union {
          type inet:host;
          type inet:ipv6-address;
        }
      }
      uses router-bgp-neighbor-grouping;
    }
    list network {
      tailf:cli-suppress-mode;
      tailf:cli-delete-when-empty;
      tailf:cli-compact-syntax;
      key "number";
      leaf number {
        type union {
          type inet:ipv4-address;
          type ipv6-prefix;
        }
      }
      leaf backdoor {
        type empty;
      }
      leaf mask {
        type inet:ipv4-address;
      }
      leaf route-map {
        type string;
      }
    }
    container redistribute {
      container bgp {
        tailf:cli-compact-syntax;
        tailf:cli-sequence-commands {
          tailf:cli-reset-all-siblings;
        }
        leaf as-no {
          tailf:cli-drop-node-name;
          type bgp-as-no-type;
        }
        uses router-bgp-redistribute-grouping {
          refine "metric" {
            tailf:cli-break-sequence-commands;
          }
        }
      }
      container connected {
        tailf:cli-compact-syntax;
        tailf:cli-delete-when-empty;
        presence "true";
        uses router-bgp-redistribute-grouping;
      }
      container static {
        tailf:cli-compact-syntax;
        tailf:cli-delete-when-empty;
        presence "true";
        uses router-bgp-redistribute-grouping;
      }
      list eigrp {
        tailf:cli-suppress-mode;
        tailf:cli-delete-when-empty;
        tailf:cli-compact-syntax;
        key "as-no";
        leaf as-no {
          type eigrp-as-no-type;
        }
        uses router-bgp-redistribute-grouping;
      }
      list ospf {
        tailf:cli-suppress-mode;
        tailf:cli-delete-when-empty;
        tailf:cli-compact-syntax;
        key "id";
        leaf id {
          type uint16;
        }
        uses router-bgp-redistribute-grouping;
        uses redistribute-ospf-match-grouping;
      }
      container rip {
        tailf:cli-compact-syntax;
        presence "true";
        uses router-bgp-redistribute-grouping;
      }
    }
    list aggregate-address {
      tailf:cli-suppress-mode;
      tailf:cli-delete-when-empty;
      tailf:cli-compact-syntax;
      tailf:cli-sequence-commands {
        tailf:cli-reset-all-siblings;
      }
      key "address mask";
      leaf address {
        type inet:ipv4-address;
      }
      leaf mask {
        type inet:ipv4-address;
      }
      leaf as-set {
        tailf:cli-break-sequence-commands;
        type empty;
      }
      leaf summary-only {
        type empty;
      }
      leaf attribute-map {
        type string;
      }
      leaf advertise-map {
        type string;
      }
      leaf suppress-map {
        type string;
      }
    }
    container distance {
      container bgp {
        tailf:cli-compact-syntax;
        tailf:cli-sequence-commands;
        leaf extern-as {
          tailf:cli-drop-node-name;
          type uint16;
        }
        leaf internal-as {
          tailf:cli-drop-node-name;
          type uint16;
        }
        leaf local {
          tailf:cli-drop-node-name;
          type uint16;
        }
      }
    }
    uses router-distribute-list-grouping {
      refine "distribute-list-interface/distribute-list/access-list-name";
      refine "distribute-list/access-list-name";
    }
    container maximum-paths {
      uses router-bgp-max-path-grouping;
      container ibgp {
        choice ibgp-choice {
          case a {
            container unequal-cost {
              uses router-bgp-max-path-grouping;
            }
          }
          case b {
            uses router-bgp-max-path-grouping;
          }
        }
      }
    }
    leaf table-map {
      type string;
    }
    container default-information {
      leaf originate {
        type empty;
      }
    }
    leaf auto-summary {
      type boolean;
    }
    leaf synchronization {
      type empty;
    }
  }

  grouping router-bgp-grouping {
    container bgp {
      leaf log-neighbor-changes {
        type boolean;
      }
      leaf always-compare-med {
        type empty;
      }
      container bestpath {
        leaf compare-routerid {
          type empty;
        }
        container med {
          choice med-choice {
            container confed {
              presence "Compare MED among confederation paths";
              leaf missing-at-worst {
                type empty;
              }
            }
            leaf missing-at-worst {
              type empty;
            }
          }
        }
      }
      container default {
        leaf ipv4-unicast {
          type boolean;
        }
        leaf ipv4-activate {
          type boolean;
        }
        leaf local-preference {
          type uint32;
        }
        container route-target {
          leaf filter {
            type boolean;
          }
        }
      }
      leaf deterministic-med {
        type empty;
      }
      container graceful-restart {
        tailf:cli-delete-when-empty;
        presence "true";
        leaf restart-time {
          type uint16;
        }
        leaf stalepath-time {
          type uint16;
        }
      }
      leaf enforce-first-as {
        type boolean;
      }
      leaf fast-external-fallover {
        type boolean;
      }
      leaf router-id {
        type inet:ipv4-address;
      }
      leaf maxas-limit {
        type uint16;
      }
    }
    container timers {
      container bgp {
        tailf:cli-compact-syntax;
        tailf:cli-sequence-commands {
          tailf:cli-reset-siblings;
        }
        leaf keepalive {
          tailf:cli-drop-node-name;
          type uint16;
        }
        leaf holdtime {
          tailf:cli-drop-node-name;
          type uint16;
        }
        leaf min-holdtime {
          tailf:cli-drop-node-name;
          type uint16;
        }
      }
    }
  }

  grouping router-ospf-common-grouping {
    container default-information {
      container originate {
        tailf:cli-compact-syntax;
        tailf:cli-delete-when-empty;
        presence "true";
        leaf always {
          type empty;
        }
        leaf metric {
          type uint32;
        }
        leaf metric-type {
          type ospf-metric-type;
        }
        leaf route-map {
          type string;
        }
      }
    }
  }

  grouping router-ospf-grouping {
    leaf router-id {
      type inet:ipv4-address;
    }
    list network {
      tailf:cli-suppress-mode;
      tailf:cli-delete-when-empty;
      key "ip mask";
      leaf ip {
        type inet:host;
      }
      leaf mask {
        type inet:ipv4-address;
      }
      leaf area {
        type ospf-area-type;
      }
    }
    list area {
      tailf:cli-suppress-mode;
      tailf:cli-delete-when-empty;
      key "id";
      leaf id {
        tailf:cli-suppress-range;
        type ospf-area-type;
      }
      container authentication {
        tailf:cli-delete-when-empty;
        presence "true";
        leaf message-digest {
          type empty;
        }
      }
      container nssa {
        tailf:cli-compact-syntax;
        presence "true";
        leaf no-redistribution {
          type empty;
        }
        leaf default-information-originate {
          type empty;
        }
        leaf metric-type {
          type ospf-metric-type;
        }
        leaf metric {
          type int32;
        }
        leaf no-summary {
          type empty;
        }
      }
      leaf default-cost {
        type uint32;
      }
      list filter-list {
        tailf:cli-suppress-mode;
        tailf:cli-delete-when-empty;
        tailf:cli-compact-syntax;
        key "direction";
        leaf direction {
          type enumeration {
            enum "in";
            enum "out";
          }
        }
        leaf prefix {
          tailf:cli-prefix-key;
          type string;
        }
      }
      list range {
        tailf:cli-suppress-mode;
        tailf:cli-delete-when-empty;
        tailf:cli-compact-syntax;
        key "ip mask";
        leaf ip {
          type inet:host;
        }
        leaf mask {
          type inet:ipv4-address;
        }
        leaf range-status {
          tailf:cli-drop-node-name;
          type enumeration {
            enum "advertise";
            enum "not-advertise";
          }
        }
      }
      container range-ipv6 {
        tailf:cli-drop-node-name;
        list range {
          tailf:cli-suppress-mode;
          tailf:cli-delete-when-empty;
          tailf:cli-compact-syntax;
          key "prefix";
          leaf prefix {
            type ipv6-prefix;
          }
          choice advertise-choice {
            leaf advertise {
              type empty;
            }
            leaf not-advertise {
              type empty;
            }
          }
          leaf cost {
            type uint32;
          }
        }
      }
      container stub {
        tailf:cli-delete-when-empty;
        presence "true";
        leaf no-summary {
          type empty;
        }
      }
      list virtual-link {
        tailf:cli-suppress-mode;
        tailf:cli-delete-when-empty;
        tailf:cli-compact-syntax;
        key "id";
        leaf id {
          type inet:host;
        }
        leaf retransmit-interval {
          type uint16;
        }
        leaf transmit-delay {
          type uint16;
        }
        leaf hello-interval {
          type int32;
        }
        leaf dead-interval {
          type uint16;
        }
        leaf authentication {
          type empty;
        }
        container authentication-key {
          tailf:cli-flatten-container;
          tailf:cli-compact-syntax;
          tailf:cli-sequence-commands;
          uses password-08-grouping {
            refine "secret";
          }
        }
        leaf message-digest {
          type empty;
        }
        list message-digest-key {
          tailf:cli-suppress-mode;
          tailf:cli-delete-when-empty;
          tailf:cli-compact-syntax;
          key "id";
          leaf id {
            tailf:cli-suppress-range;
            type uint8;
          }
          container md5 {
            tailf:cli-flatten-container;
            tailf:cli-compact-syntax;
            tailf:cli-sequence-commands;
            uses password-08-grouping {
              refine "secret";
            }
          }
        }
      }
    }
    list neighbor {
      tailf:cli-suppress-mode;
      tailf:cli-delete-when-empty;
      tailf:cli-compact-syntax;
      tailf:cli-sequence-commands {
        tailf:cli-reset-siblings;
      }
      key "ip";
      leaf ip {
        type inet:ipv4-address;
      }
      container interface {
        tailf:cli-flatten-container;
        tailf:cli-compact-syntax;
        uses interface-name-grouping;
      }
    }
    container nsf {
      container cisco {
        leaf helper {
          type boolean;
        }
      }
      container ietf {
        leaf helper {
          type boolean;
        }
      }
    }
    container capability {
      leaf opaque {
        type boolean;
      }
      leaf lls {
        type boolean;
      }
    }
    container timers {
      container lsa {
        leaf arrival {
          type uint32;
        }
      }
      container pacing {
        leaf flood {
          type uint16;
        }
        leaf lsa-group {
          type uint16;
        }
        leaf retransmission {
          type uint16;
        }
      }
      container throttle {
        container lsa {
          tailf:cli-compact-syntax;
          tailf:cli-sequence-commands;
          leaf start-interval {
            tailf:cli-drop-node-name;
            type uint32;
          }
          leaf hold-interval {
            tailf:cli-drop-node-name;
            type uint32;
          }
          leaf max-interval {
            tailf:cli-drop-node-name;
            type uint32;
          }
        }
        container spf {
          tailf:cli-compact-syntax;
          tailf:cli-sequence-commands;
          leaf spf-start {
            tailf:cli-drop-node-name;
            type uint32;
          }
          leaf spf-hold {
            tailf:cli-drop-node-name;
            type uint32;
          }
          leaf spf-max-wait {
            tailf:cli-drop-node-name;
            type uint32;
          }
        }
      }
    }
    container distance {
      container ospf {
        tailf:cli-compact-syntax;
        leaf intra-area {
          type uint32;
        }
        leaf inter-area {
          type uint32;
        }
        leaf external {
          type uint32;
        }
      }
    }
    container compatible {
      leaf rfc1583 {
        type boolean;
      }
    }
    container ignore {
      container lsa {
        leaf mospf {
          type empty;
        }
      }
    }
    container redistribute {
      container connected {
        tailf:cli-compact-syntax;
        tailf:cli-delete-when-empty;
        presence "true";
        uses router-ospf-redistribute-grouping;
        uses router-route-map-grouping5;
      }
      container static {
        tailf:cli-compact-syntax;
        tailf:cli-delete-when-empty;
        presence "true";
        uses router-ospf-redistribute-grouping;
        uses router-route-map-grouping5;
      }
      list bgp {
        tailf:cli-suppress-mode;
        tailf:cli-delete-when-empty;
        tailf:cli-compact-syntax;
        key "as-no";
        leaf as-no {
          type bgp-as-no-type;
        }
        uses router-ospf-redistribute-grouping;
        uses router-route-map-grouping5;
      }
      list ospf {
        tailf:cli-suppress-mode;
        tailf:cli-delete-when-empty;
        tailf:cli-compact-syntax;
        key "id";
        leaf id {
          tailf:cli-suppress-range;
          type uint16;
        }
        uses router-ospf-redistribute-grouping;
        uses redistribute-ospf-match-grouping;
        uses router-route-map-grouping5;
      }
      list eigrp {
        tailf:cli-suppress-mode;
        tailf:cli-delete-when-empty;
        tailf:cli-compact-syntax;
        key "as-no";
        leaf as-no {
          type eigrp-as-no-type;
        }
        uses router-ospf-redistribute-grouping;
        uses router-route-map-grouping5;
      }
      container rip {
        tailf:cli-compact-syntax;
        tailf:cli-delete-when-empty;
        presence "true";
        uses router-ospf-redistribute-grouping;
        uses router-route-map-grouping5;
        list redistribute-list-rip {
          tailf:cli-drop-node-name;
          tailf:cli-suppress-mode;
          tailf:cli-delete-when-empty;
          tailf:cli-compact-syntax;
          key "name";
          leaf name {
            type string;
          }
          uses router-ospf-redistribute-grouping;
          uses router-route-map-grouping6;
        }
      }
    }
    list summary-address {
      tailf:cli-suppress-mode;
      tailf:cli-compact-syntax;
      key "ip wildcard";
      leaf ip {
        type inet:host;
      }
      leaf wildcard {
        type inet:ipv4-address;
      }
      leaf not-advertise {
        type empty;
      }
      leaf tag {
        type uint32;
      }
    }
    uses router-distribute-list-grouping {
      refine "distribute-list-interface/distribute-list/access-list-name";
      refine "distribute-list/access-list-name";
    }
    container log-adj-changes {
      presence "true";
      leaf detail {
        type empty;
      }
    }
    uses router-ospf-common-grouping {
      refine "default-information/originate/route-map";
    }
  }

  grouping router-rip-grouping {
    list network {
      tailf:cli-suppress-mode;
      tailf:cli-delete-when-empty;
      key "ip";
      leaf ip {
        type inet:host;
      }
    }
    uses passive-interface-grouping;
    container redistribute {
      container connected {
        tailf:cli-compact-syntax;
        tailf:cli-delete-when-empty;
        presence "true";
        uses router-rip-redistribute-grouping;
      }
      container bgp {
        tailf:cli-compact-syntax;
        leaf as-no {
          tailf:cli-drop-node-name;
          type bgp-as-no-type;
        }
        uses router-rip-redistribute-grouping;
      }
      list eigrp {
        tailf:cli-suppress-mode;
        tailf:cli-delete-when-empty;
        tailf:cli-compact-syntax;
        key "as-no";
        leaf as-no {
          type eigrp-as-no-type;
        }
        uses router-rip-redistribute-grouping;
      }
      list ospf {
        tailf:cli-suppress-mode;
        tailf:cli-delete-when-empty;
        tailf:cli-compact-syntax;
        key "id";
        leaf id {
          tailf:cli-suppress-range;
          type uint16;
        }
        uses router-rip-redistribute-grouping;
        uses redistribute-ospf-match-grouping;
      }
      container static {
        tailf:cli-compact-syntax;
        tailf:cli-delete-when-empty;
        presence "true";
        uses router-rip-redistribute-grouping;
      }
      container rip {
        tailf:cli-compact-syntax;
        presence "true";
        uses router-rip-redistribute-grouping;
      }
    }
    container default-information {
      container originate {
        tailf:cli-delete-when-empty;
        presence "true";
        leaf route-map {
          type string;
        }
      }
    }
    leaf version {
      type uint8;
    }
    uses router-distribute-list-grouping {
      refine "distribute-list-interface/distribute-list/access-list-name";
      refine "distribute-list/access-list-name";
    }
    leaf auto-summary {
      type boolean;
    }
  }

  grouping ip-audit-action-grouping {
    container action {
      tailf:cli-compact-syntax;
      tailf:cli-delete-when-empty;
      presence "true";
      leaf alarm {
        type empty;
      }
      leaf drop {
        type empty;
      }
      leaf reset {
        type empty;
      }
    }
  }

  grouping policy-map-class-police-grouping {
    leaf conform-rate {
      tailf:cli-drop-node-name;
      type uint32;
    }
    leaf conform-burst {
      tailf:cli-drop-node-name;
      tailf:cli-optional-in-sequence;
      type uint32;
    }
    leaf conform-action {
      type enumeration {
        enum "drop";
        enum "transmit";
      }
    }
    leaf exceed-action {
      type enumeration {
        enum "drop";
        enum "transmit";
      }
    }
  }

  grouping aaa-authentication-dot1x-grouping {
    leaf group {
      type union {
        type string;
        type enumeration {
          enum "radius";
          enum "tacacs+";
        }
      }
    }
  }

  grouping aaa-authentication-console-grouping {
    container console {
      tailf:cli-compact-syntax;
      leaf server_group {
        tailf:cli-drop-node-name;
        tailf:code-name "aaa_server_group";
        type string;
      }
      leaf LOCAL {
        type empty;
      }
    }
  }

  grouping aaa-accounting-console-grouping {
    container console {
      tailf:cli-flatten-container;
      tailf:cli-compact-syntax;
      leaf server_group {
        tailf:cli-drop-node-name;
        tailf:code-name "aaa_server_group";
        type string;
      }
    }
  }

  grouping snmp-server-host-grouping {
    choice trap-or-poll {
      leaf poll {
        tailf:cli-optional-in-sequence;
        type empty;
      }
      leaf trap {
        tailf:cli-optional-in-sequence;
        type empty;
      }
    }
    container community {
      tailf:cli-optional-in-sequence;
      tailf:cli-flatten-container;
      tailf:cli-compact-syntax;
      tailf:cli-sequence-commands;
      uses password-08-grouping {
        refine "type";
        refine "secret";
      }
    }
    container version {
      tailf:cli-optional-in-sequence;
      tailf:cli-flatten-container;
      tailf:cli-compact-syntax;
      leaf version {
        tailf:cli-drop-node-name;
        type enumeration {
          enum "1";
          enum "2c";
          enum "3";
        }
      }
      leaf username {
        tailf:cli-drop-node-name;
        type string;
      }
    }
    leaf udp-port {
      type uint16;
    }
  }

  grouping cipher-grouping {
    choice level-choice {
      leaf level {
        tailf:cli-drop-node-name;
        type enumeration {
          enum "all";
          enum "low";
          enum "medium";
          enum "fips";
          enum "high";
        }
      }
      container level-custom {
        tailf:cli-drop-node-name;
        leaf custom {
          type string;
        }
      }
    }
  }

  grouping object-service-port-grouping {
    leaf operator {
      tailf:cli-drop-node-name;
      type enumeration {
        enum "eq";
        enum "gt";
        enum "lt";
        enum "neq";
        enum "range";
      }
    }
    leaf port {
      tailf:cli-drop-node-name;
      type string;
    }
    leaf max-port {
      tailf:cli-drop-node-name;
      type string;
    }
  }

  grouping threat-detection-rate-interval-list-grouping {
    list rate-interval {
      tailf:cli-suppress-mode;
      tailf:cli-delete-when-empty;
      tailf:cli-compact-syntax;
      tailf:cli-sequence-commands;
      key "seconds";
      leaf seconds {
        type uint32;
      }
      leaf average-rate {
        type uint32;
      }
      leaf burst-rate {
        type uint32;
      }
    }
  }

  uses config-grouping;

  grouping config-grouping {
    leaf xxyyzz-fail-first {
      type empty;
    }
    container tailfned-first {
      leaf acl-old {
        type string;
      }
      leaf acl-new {
        type string;
      }
      leaf acl-leafref {
        type string;
      }
    }
    leaf version {
      type string;
    }
    container firewall {
      leaf transparent {
        type empty;
      }
    }
    container terminal {
      leaf width {
        type uint16;
      }
    }
    container same-security-traffic {
      container permit {
        leaf inter-interface {
          type empty;
        }
        leaf intra-interface {
          type empty;
        }
      }
    }
    container object-group-search {
      leaf access-control {
        type empty;
      }
    }
    container service {
      leaf call-home {
        type empty;
      }
      leaf internal {
        type empty;
      }
      leaf password-recovery {
        type boolean;
      }
      container resetinbound {
        presence "true";
        container interface {
          uses interface-list-grouping;
        }
      }
      container resetoutbound {
        presence "true";
        container interface {
          list no-list {
            tailf:cli-suppress-mode;
            tailf:cli-delete-when-empty;
            key "name";
            leaf name {
              type nameif-type;
            }
          }
        }
      }
      leaf resetoutside {
        type empty;
      }
    }
    leaf hostname {
      type string;
    }
    list service-module {
      tailf:cli-suppress-mode;
      tailf:cli-delete-when-empty;
      key "id";
      leaf id {
        type uint8;
      }
      leaf keepalive-timeout {
        type uint8;
      }
      leaf keepalive-counter {
        type uint8;
      }
    }
    list service-policy {
      tailf:cli-suppress-mode;
      tailf:cli-delete-when-empty;
      tailf:cli-compact-syntax;
      tailf:cli-sequence-commands;
      key "policy-map";
      leaf policy-map {
        type string;
      }
      choice service-policy-type {
        leaf global {
          type empty;
        }
        container interface {
          tailf:cli-flatten-container;
          tailf:cli-compact-syntax;
          uses interface-name-grouping;
        }
      }
      leaf fail-close {
        type empty;
      }
    }
    container app-agent {
      container heartbeat {
        tailf:cli-compact-syntax;
        leaf interval {
          type uint16;
        }
        leaf retry-count {
          type uint8;
        }
      }
    }
    leaf domain-name {
      type string;
    }
    container http {
      container server {
        container enable {
          tailf:cli-delete-when-empty;
          presence "true";
          leaf listening-port {
            tailf:cli-drop-node-name;
            type uint16;
          }
        }
        leaf session-timeout {
          type uint16;
        }
        leaf idle-timeout {
          type uint16;
        }
      }
      list address {
        tailf:cli-drop-node-name;
        tailf:cli-suppress-mode;
        tailf:cli-delete-when-empty;
        tailf:cli-compact-syntax;
        tailf:cli-sequence-commands;
        key "ip";
        leaf ip {
          type string;
        }
        leaf mask {
          tailf:cli-drop-node-name;
          tailf:cli-optional-in-sequence;
          type inet:ip-address;
        }
        container interface {
          tailf:cli-drop-node-name;
          tailf:cli-flatten-container;
          tailf:cli-compact-syntax;
          uses interface-name-grouping;
        }
      }
    }
    container password {
      container encryption {
        leaf aes {
          type empty;
        }
      }
    }
    container passwd {
      tailf:cli-delete-when-empty;
      tailf:cli-compact-syntax;
      tailf:cli-sequence-commands;
      presence "true";
      leaf word {
        tailf:cli-drop-node-name;
        type secret128-type;
      }
      leaf level {
        tailf:cli-optional-in-sequence;
        type uint8;
      }
      choice encrypt-choice {
        leaf encrypted {
          tailf:cli-optional-in-sequence;
          type empty;
        }
        leaf pbkdf2 {
          type empty;
        }
      }
    }
    container enable {
      container password {
        tailf:cli-compact-syntax;
        tailf:cli-sequence-commands;
        leaf word {
          tailf:cli-drop-node-name;
          type secret128-type;
        }
        choice encrypt-choice {
          leaf encrypted {
            tailf:cli-optional-in-sequence;
            type empty;
          }
          leaf pbkdf2 {
            type empty;
          }
        }
      }
    }
    container fips {
      leaf enable {
        type empty;
      }
    }
    container asp {
      container load-balance {
        tailf:cli-compact-syntax;
        tailf:cli-sequence-commands {
          tailf:cli-reset-siblings;
        }
        leaf per-packet {
          type empty;
        }
        leaf auto {
          type empty;
        }
      }
      container rule-engine {
        container transactional-commit {
          leaf access-group {
            type empty;
          }
          leaf nat {
            type empty;
          }
        }
      }
    }
    container xlate {
      list per-session {
        tailf:cli-suppress-mode;
        tailf:cli-delete-when-empty;
        tailf:cli-compact-syntax;
        ordered-by user;
        key "rule";
        leaf rule {
          tailf:cli-multi-word-key;
          type string;
        }
      }
    }
    container mac-address {
      container auto {
        leaf prefix {
          type uint16;
        }
      }
    }
    container boot {
      leaf-list system {
        ordered-by user;
        type string;
      }
      leaf config {
        type string;
      }
    }
    leaf names {
      type empty;
    }
    list name {
      tailf:cli-suppress-mode;
      tailf:cli-delete-when-empty;
      tailf:cli-compact-syntax;
      key "address";
      leaf address {
        type union {
          type inet:ipv4-address;
          type inet:ipv6-address;
        }
      }
      leaf name {
        tailf:cli-drop-node-name;
        type string;
      }
      leaf description {
        tailf:cli-multi-value;
        type string;
      }
    }
    container dns-guard {
      presence "true";
    }
    list time-range {
      key "name";
      leaf name {
        type string;
      }
      container absolute {
        tailf:cli-compact-syntax;
        tailf:cli-sequence-commands {
          tailf:cli-reset-siblings;
        }
        choice when-choice {
          leaf start {
            type hhmm-type;
          }
          leaf end {
            type hhmm-type;
          }
        }
        leaf day-of-month {
          tailf:cli-drop-node-name;
          type uint8;
        }
        leaf month {
          tailf:cli-drop-node-name;
          type string;
        }
        leaf year {
          tailf:cli-drop-node-name;
          type uint16;
        }
      }
    }
    container ftp {
      leaf mode {
        type enumeration {
          enum "passive";
        }
      }
    }
    container pager {
      leaf lines {
        type uint32;
      }
    }
    container flow-export {
      list destination {
        tailf:cli-suppress-mode;
        tailf:cli-delete-when-empty;
        tailf:cli-compact-syntax;
        tailf:cli-sequence-commands;
        key "name host";
        leaf name {
          tailf:cli-suppress-range;
          type nameif-type;
        }
        leaf host {
          type inet:host;
        }
        leaf udp-port {
          tailf:cli-drop-node-name;
          type uint16;
        }
      }
      container delay {
        leaf flow-create {
          type uint8;
        }
      }
      container template {
        leaf timeout-rate {
          type uint16;
        }
      }
      container active {
        leaf refresh-interval {
          type uint16;
        }
      }
    }
    list mtu {
      tailf:cli-suppress-mode;
      tailf:cli-delete-when-empty;
      key "name";
      leaf name {
        type nameif-type;
      }
      leaf mtu-size {
        tailf:cli-drop-node-name;
        type uint16;
      }
    }
    list dynamic-access-policy-record {
      key "name";
      leaf name {
        type string;
      }
      leaf description {
        type string;
      }
      leaf user-message {
        type string;
      }
      leaf action {
        type enumeration {
          enum "continue";
          enum "quarantine";
          enum "terminate";
        }
      }
      leaf priority {
        type uint32;
      }
    }
    container user-identity {
      leaf default-domain {
        type string;
      }
    }
    container dhcprelay {
      list server {
        tailf:cli-suppress-mode;
        tailf:cli-delete-when-empty;
        key "address name";
        leaf address {
          type inet:host;
        }
        leaf name {
          type nameif-type;
        }
      }
      list enable {
        tailf:cli-suppress-mode;
        tailf:cli-delete-when-empty;
        key "name";
        leaf name {
          type nameif-type;
        }
      }
      list setroute {
        tailf:cli-suppress-mode;
        tailf:cli-delete-when-empty;
        key "name";
        leaf name {
          type nameif-type;
        }
      }
      leaf timeout {
        type uint16;
      }
    }
    list threat-detection {
      tailf:cli-suppress-mode;
      tailf:cli-delete-when-empty;
      tailf:cli-compact-syntax;
      key "id";
      leaf id {
        type enumeration {
          enum "basic-threat";
          enum "rate";
          enum "scanning-threat";
          enum "statistics";
        }
      }
      container host {
        presence "true";
      }
      container port {
        presence "true";
      }
      container protocol {
        presence "true";
      }
      container access-list {
        presence "true";
      }
      container shun {
        tailf:cli-compact-syntax;
        presence "true";
        container except {
          list ip-address {
            tailf:cli-suppress-mode;
            tailf:cli-delete-when-empty;
            key "address mask";
            leaf address {
              type inet:host;
            }
            leaf mask {
              type inet:ipv4-address;
            }
          }
        }
        leaf duration {
          type uint32;
        }
      }
      container scanning-threat {
        uses threat-detection-rate-interval-list-grouping;
      }
      container syn-attack {
        uses threat-detection-rate-interval-list-grouping;
      }
      container tcp-intercept {
        tailf:cli-compact-syntax;
        leaf rate-interval {
          type uint16;
        }
        leaf burst-rate {
          type uint32;
        }
        leaf average-rate {
          type uint32;
        }
      }
    }
    container telnet {
      list allowed-access {
        tailf:cli-drop-node-name;
        tailf:cli-suppress-mode;
        tailf:cli-delete-when-empty;
        tailf:cli-compact-syntax;
        key "address";
        leaf address {
          type union {
            type inet:host;
            type ipv6-prefix;
          }
        }
        leaf mask {
          tailf:cli-drop-node-name;
          type inet:ip-address;
        }
        container interface {
          tailf:cli-drop-node-name;
          tailf:cli-flatten-container;
          tailf:cli-compact-syntax;
          uses interface-name-grouping;
        }
      }
      leaf timeout {
        type uint16;
      }
    }
    container ssh {
      container stack {
        leaf ciscossh {
          type boolean;
        }
      }
      container key-exchange {
        leaf group {
          type enumeration {
            enum "dh-group1-sha1";
            enum "dh-group14-sha1";
            enum "dh-group14-sha256";
          }
        }
        leaf hostkey {
          type enumeration {
            enum "rsa";
            enum "ecdsa";
            enum "eddsa";
          }
        }
      }
      leaf timeout {
        type uint8;
      }
      container scopy {
        leaf enable {
          type empty;
        }
      }
      leaf stricthostkeycheck {
        type empty;
      }
      leaf-list version {
        tailf:cli-flat-list-syntax;
        type enumeration {
          enum "1";
          enum "2";
        }
      }
      container pubkey-chain {
        tailf:cli-add-mode;
        list server {
          key "address";
          leaf address {
            type inet:host;
          }
          container key-hash {
            tailf:cli-compact-syntax;
            tailf:cli-sequence-commands {
              tailf:cli-reset-siblings;
            }
            leaf alg {
              tailf:cli-drop-node-name;
              type enumeration {
                enum "md5";
                enum "sha256";
              }
            }
            leaf fingerprint {
              tailf:cli-drop-node-name;
              type string;
            }
          }
        }
      }
      container cipher {
        container integrity {
          uses cipher-grouping;
        }
        container encryption {
          choice encryption-choice {
            leaf level {
              tailf:cli-drop-node-name;
              type enumeration {
                enum "all";
                enum "low";
                enum "medium";
                enum "fips";
                enum "high";
              }
            }
            leaf custom {
              type string;
            }
          }
        }
      }
      list allowed-access {
        tailf:cli-drop-node-name;
        tailf:cli-suppress-mode;
        tailf:cli-delete-when-empty;
        tailf:cli-compact-syntax;
        key "address mask";
        leaf address {
          tailf:cli-suppress-range;
          type inet:host;
        }
        leaf mask {
          tailf:cli-suppress-range;
          type inet:ipv4-address;
        }
        container interface {
          tailf:cli-drop-node-name;
          uses interface-name-grouping;
        }
      }
      list ipv6-access {
        tailf:cli-drop-node-name;
        tailf:cli-suppress-mode;
        tailf:cli-delete-when-empty;
        tailf:cli-compact-syntax;
        key "address";
        leaf address {
          tailf:cli-suppress-range;
          type ipv6-prefix;
        }
        container interface {
          tailf:cli-drop-node-name;
          uses interface-name-grouping;
        }
      }
    }
    container dhcpd {
      list address {
        tailf:cli-suppress-mode;
        tailf:cli-delete-when-empty;
        tailf:cli-sequence-commands;
        key "interface";
        leaf interface {
          type nameif-type;
        }
        leaf ip-address {
          tailf:cli-drop-node-name;
          tailf:cli-prefix-key;
          type string;
        }
      }
      leaf lease {
        type uint32;
      }
      container dhcpd-interface {
        tailf:cli-drop-node-name;
        list lease {
          tailf:cli-suppress-mode;
          tailf:cli-delete-when-empty;
          tailf:cli-sequence-commands;
          key "interface";
          leaf interface {
            tailf:cli-expose-key-name;
            type nameif-type;
          }
          leaf seconds {
            tailf:cli-drop-node-name;
            tailf:cli-prefix-key;
            type uint32;
          }
        }
      }
      list enable {
        tailf:cli-suppress-mode;
        tailf:cli-delete-when-empty;
        key "name";
        leaf name {
          type nameif-type;
        }
      }
    }
    container password-policy {
      leaf minimum-length {
        type uint8;
      }
      leaf minimum-changes {
        type uint8;
      }
      leaf minimum-lowercase {
        type uint8;
      }
      leaf minimum-uppercase {
        type uint8;
      }
      leaf minimum-numeric {
        type uint8;
      }
      leaf minimum-special {
        type uint8;
      }
      leaf lifetime {
        type uint16;
      }
      leaf username-check {
        type empty;
      }
      leaf reuse-interval {
        type uint8;
      }
    }
    container quota {
      leaf management-session {
        type uint16;
      }
    }
    list username {
      tailf:cli-suppress-mode;
      tailf:cli-delete-when-empty;
      tailf:cli-compact-syntax;
      key "name";
      leaf name {
        type string;
      }
      choice password-choice {
        container password {
          tailf:cli-flatten-container;
          tailf:cli-compact-syntax;
          tailf:cli-sequence-commands {
            tailf:cli-reset-siblings;
          }
          leaf password {
            tailf:cli-drop-node-name;
            type secret128-type;
          }
          leaf mode {
            tailf:cli-drop-node-name;
            tailf:cli-optional-in-sequence;
            type enumeration {
              enum "encrypted";
              enum "mschap";
              enum "nt-encrypted";
              enum "pbkdf2";
            }
          }
          leaf privilege {
            type uint8;
          }
        }
        case nopassword {
          leaf nopassword {
            type empty;
          }
          leaf privilege {
            type uint8;
          }
        }
      }
      container attributes {
        tailf:cli-add-mode;
        leaf service-type {
          type enumeration {
            enum "admin";
            enum "nas-prompt";
            enum "remote-access";
          }
        }
        leaf vpn-group-policy {
          type string;
        }
        container vpn-filter {
          choice vpn-filter-choice {
            leaf none {
              type empty;
            }
            leaf value {
              type string;
            }
          }
        }
        leaf vpn-simultaneous-logins {
          type uint32;
        }
        container vpn-framed-ip-address {
          tailf:cli-compact-syntax;
          tailf:cli-sequence-commands {
            tailf:cli-reset-siblings;
          }
          leaf address {
            tailf:cli-drop-node-name;
            type inet:ipv4-address;
          }
          leaf mask {
            tailf:cli-drop-node-name;
            type inet:ipv4-address;
          }
        }
        container ssh {
          container authentication {
            tailf:cli-compact-syntax;
            tailf:cli-sequence-commands {
              tailf:cli-reset-siblings;
            }
            leaf publickey {
              type string;
            }
            leaf hashed {
              type empty;
            }
          }
        }
      }
    }
    container ip {
      container audit {
        container attack {
          presence "true";
          uses ip-audit-action-grouping;
        }
        container info {
          presence "true";
          uses ip-audit-action-grouping;
        }
        container interface {
          presence "true";
          uses ip-audit-action-grouping;
        }
        container name {
          presence "true";
          uses ip-audit-action-grouping;
        }
      }
      container local {
        list pool {
          tailf:cli-suppress-mode;
          tailf:cli-delete-when-empty;
          tailf:cli-compact-syntax;
          tailf:cli-sequence-commands {
            tailf:cli-reset-siblings;
          }
          key "id";
          leaf id {
            type string;
          }
          leaf address {
            tailf:cli-drop-node-name;
            type string;
          }
          leaf mask {
            type string;
          }
        }
      }
      container verify {
        container reverse-path {
          container interface {
            uses interface-list-grouping;
          }
        }
      }
    }
    container ipv6 {
      leaf enforce-eui64 {
        type nameif-type;
      }
      container local {
        list pool {
          tailf:cli-suppress-mode;
          tailf:cli-delete-when-empty;
          tailf:cli-compact-syntax;
          tailf:cli-sequence-commands {
            tailf:cli-reset-siblings;
          }
          key "id";
          leaf id {
            type string;
          }
          leaf prefix {
            tailf:cli-drop-node-name;
            type ipv6-prefix;
          }
          leaf number {
            tailf:cli-drop-node-name;
            type uint16;
          }
        }
      }
      list icmp {
        tailf:cli-suppress-mode;
        tailf:cli-delete-when-empty;
        key "nameif";
        leaf nameif {
          type string;
        }
        list rule {
          tailf:cli-drop-node-name;
          tailf:cli-suppress-mode;
          tailf:cli-delete-when-empty;
          ordered-by user;
          key "expr";
          leaf expr {
            tailf:cli-multi-word-key;
            type string;
          }
        }
      }
      list neighbor {
        tailf:cli-suppress-mode;
        tailf:cli-delete-when-empty;
        tailf:cli-compact-syntax;
        tailf:cli-sequence-commands {
          tailf:cli-reset-siblings;
        }
        key "address";
        leaf address {
          type inet:ipv6-address;
        }
        leaf interface-name {
          tailf:cli-drop-node-name;
          type nameif-type;
        }
        leaf hardware-address {
          tailf:cli-drop-node-name;
          type string;
        }
      }
      container prefix-list {
        leaf sequence-number {
          type boolean;
        }
        list prefixes {
          tailf:cli-drop-node-name;
          tailf:cli-suppress-mode;
          tailf:cli-delete-when-empty;
          key "name";
          leaf name {
            type string;
          }
          leaf description {
            tailf:cli-multi-value;
            type string;
          }
          leaf permit {
            type ipv6-prefix;
          }
          list seq {
            tailf:cli-suppress-mode;
            tailf:cli-delete-when-empty;
            tailf:cli-compact-syntax;
            key "no";
            leaf no {
              type uint32;
            }
            container deny {
              tailf:cli-compact-syntax;
              tailf:cli-sequence-commands {
                tailf:cli-reset-all-siblings;
              }
              leaf ip {
                tailf:cli-drop-node-name;
                type ipv6-prefix;
              }
              leaf ge {
                tailf:cli-break-sequence-commands;
                type uint8;
              }
              leaf le {
                type uint8;
              }
            }
            container permit {
              tailf:cli-compact-syntax;
              tailf:cli-sequence-commands {
                tailf:cli-reset-all-siblings;
              }
              leaf ip {
                tailf:cli-drop-node-name;
                type ipv6-prefix;
              }
              leaf ge {
                tailf:cli-break-sequence-commands;
                type uint8;
              }
              leaf le {
                type uint8;
              }
            }
          }
        }
      }
      list route {
        tailf:cli-suppress-mode;
        tailf:cli-delete-when-empty;
        tailf:cli-compact-syntax;
        key "id";
        leaf id {
          type nameif-type;
        }
        list prefix {
          tailf:cli-drop-node-name;
          tailf:cli-suppress-mode;
          tailf:cli-delete-when-empty;
          tailf:cli-compact-syntax;
          tailf:cli-sequence-commands {
            tailf:cli-reset-siblings;
          }
          key "id";
          leaf id {
            type ipv6-prefix;
          }
          leaf dest {
            tailf:cli-drop-node-name;
            type inet:ipv6-address;
          }
          leaf hop-count {
            tailf:cli-drop-node-name;
            tailf:cli-optional-in-sequence;
            type uint8;
          }
          leaf tunneled {
            type empty;
          }
        }
      }
      container access-list {
        list access-list-id {
          tailf:cli-drop-node-name;
          tailf:cli-suppress-mode;
          tailf:cli-delete-when-empty;
          key "id";
          leaf id {
            type string;
          }
          list rule {
            tailf:cli-drop-node-name;
            tailf:cli-suppress-mode;
            tailf:cli-delete-when-empty;
            tailf:cli-compact-syntax;
            tailf:cli-sequence-commands {
              tailf:cli-reset-siblings;
            }
            ordered-by user;
            key "id";
            leaf id {
              type string;
            }
            leaf log {
              tailf:cli-optional-in-sequence;
              type empty;
            }
            leaf level {
              tailf:cli-drop-node-name;
              tailf:cli-optional-in-sequence;
              type union {
                type logging-level-type;
                type enumeration {
                  enum "default" {
                    value 106023;
                  }
                }
              }
            }
            leaf interval {
              tailf:cli-optional-in-sequence;
              type uint16;
            }
            leaf time-range {
              tailf:cli-optional-in-sequence;
              type string;
            }
            leaf inactive {
              type empty;
            }
          }
        }
      }
      container router {
        list ospf {
          key "id";
          leaf id {
            type uint16;
          }
          leaf router-id {
            type inet:ipv4-address;
          }
          uses passive-interface-grouping;
          container log-adjacency-changes {
            presence "true";
          }
          uses router-ospf-common-grouping;
        }
      }
    }
    container nat-control {
      presence "true";
    }
    list global {
      tailf:cli-suppress-mode;
      tailf:cli-delete-when-empty;
      tailf:cli-compact-syntax;
      tailf:cli-sequence-commands;
      key "name address";
      leaf name {
        type string;
      }
      leaf id {
        tailf:cli-drop-node-name;
        tailf:cli-prefix-key {
          tailf:cli-before-key "2";
        }
        type uint32;
      }
      leaf address {
        type union {
          type string;
          type enumeration {
            enum "interface";
          }
        }
      }
      leaf netmask {
        type inet:ipv4-address;
      }
    }
    list static {
      tailf:cli-suppress-mode;
      tailf:cli-delete-when-empty;
      tailf:cli-compact-syntax;
      ordered-by user;
      key "rule";
      leaf rule {
        tailf:cli-multi-word-key;
        type string;
      }
    }
    list nat {
      tailf:cli-suppress-mode;
      tailf:cli-delete-when-empty;
      tailf:cli-compact-syntax;
      ordered-by user;
      key "rule";
      leaf rule {
        tailf:cli-multi-word-key;
        type string;
      }
    }
    container asdm {
      leaf image {
        type string;
      }
      container history {
        leaf enable {
          type boolean;
        }
      }
    }
    container failover-conf {
      tailf:cli-drop-node-name;
      leaf failover {
        type boolean;
      }
    }
    container failover {
      leaf wait-disable {
        type boolean;
      }
      list group {
        key "id";
        leaf id {
          type uint8;
        }
        leaf priority {
          tailf:cli-drop-node-name;
          type enumeration {
            enum "primary";
            enum "secondary";
          }
        }
        container preempt {
          tailf:cli-delete-when-empty;
          presence "true";
          leaf delay {
            tailf:cli-drop-node-name;
            type uint16;
          }
        }
        container replication {
          leaf http {
            type empty;
          }
        }
      }
      container key {
        tailf:cli-compact-syntax;
        tailf:cli-sequence-commands;
        uses password-08-grouping {
          refine "secret";
        }
      }
      container lan {
        leaf unit {
          type enumeration {
            enum "primary";
            enum "secondary";
          }
        }
        list interface {
          tailf:cli-suppress-mode;
          tailf:cli-delete-when-empty;
          key "name";
          leaf name {
            type nameif-type;
          }
          leaf phy_if {
            tailf:cli-drop-node-name;
            type string;
          }
        }
      }
      container polltime {
        container unit {
          tailf:cli-drop-node-name;
          tailf:cli-compact-syntax;
          tailf:cli-sequence-commands {
            tailf:cli-reset-siblings;
          }
          leaf unit {
            tailf:cli-optional-in-sequence;
            type empty;
          }
          choice poll-choice {
            leaf poll-time {
              tailf:cli-drop-node-name;
              type uint8;
            }
            leaf msec {
              type uint16;
            }
          }
          container holdtime {
            tailf:cli-flatten-container;
            tailf:cli-compact-syntax;
            choice hold-choice {
              leaf time {
                tailf:cli-drop-node-name;
                type uint8;
              }
              leaf msec {
                type uint16;
              }
            }
          }
        }
        container interface {
          tailf:cli-compact-syntax;
          tailf:cli-sequence-commands {
            tailf:cli-reset-siblings;
          }
          choice poll-choice {
            leaf poll-time {
              tailf:cli-drop-node-name;
              type uint8;
            }
            leaf msec {
              type uint16;
            }
          }
          leaf holdtime {
            type uint8;
          }
        }
      }
      leaf interface-policy {
        type uint16;
      }
      container replication {
        leaf http {
          type empty;
        }
        leaf rate {
          type uint32;
        }
      }
      list link {
        tailf:cli-suppress-mode;
        tailf:cli-delete-when-empty;
        key "name";
        leaf name {
          type nameif-type;
        }
        leaf phy_if {
          tailf:cli-drop-node-name;
          type string;
        }
      }
      container interface {
        list ip {
          tailf:cli-suppress-mode;
          tailf:cli-delete-when-empty;
          tailf:cli-compact-syntax;
          key "name";
          leaf name {
            type nameif-type;
          }
          choice address-choice {
            case ipv4 {
              leaf ip_address {
                tailf:cli-drop-node-name;
                tailf:code-name "ipv4_address";
                type inet:host;
              }
              leaf mask {
                tailf:cli-drop-node-name;
                type inet:ipv4-address;
              }
            }
            case ipv6 {
              leaf ipv6_address {
                tailf:cli-drop-node-name;
                type ipv6-prefix;
              }
            }
          }
          leaf standby {
            type string;
          }
        }
      }
    }
    container interface {
      list Management {
        tailf:cli-allow-join-with-key;
        key "name";
        leaf name {
          type string;
        }
        uses interface-ethernet-grouping;
        uses interface-common-grouping;
        uses interface-switch-grouping;
      }
      list Ethernet {
        tailf:cli-allow-join-with-key;
        key "name";
        leaf name {
          type string;
        }
        uses interface-ethernet-grouping;
        uses interface-common-grouping;
        uses interface-switch-grouping;
      }
      list FastEthernet {
        tailf:cli-allow-join-with-key;
        key "name";
        leaf name {
          type string;
        }
        uses interface-ethernet-grouping;
        uses interface-common-grouping;
        uses interface-switch-grouping;
      }
      list GigabitEthernet {
        tailf:cli-allow-join-with-key;
        key "name";
        leaf name {
          type string;
        }
        leaf media-type {
          type enumeration {
            enum "rj45";
            enum "sfp";
          }
        }
        leaf port-type {
          type enumeration {
            enum "nni";
          }
        }
        uses interface-ethernet-grouping;
        uses interface-common-grouping;
        uses interface-switch-grouping;
      }
      list TenGigabitEthernet {
        tailf:cli-allow-join-with-key;
        key "name";
        leaf name {
          type string;
        }
        leaf media-type {
          type enumeration {
            enum "rj45";
            enum "sfp";
          }
        }
        leaf port-type {
          type enumeration {
            enum "nni";
          }
        }
        uses interface-ethernet-grouping;
        uses interface-common-grouping;
        uses interface-switch-grouping;
      }
      list Tunnel {
        tailf:cli-allow-join-with-key;
        key "name";
        leaf name {
          type uint32;
        }
        leaf description {
          tailf:cli-multi-value;
          type string;
        }
        leaf shutdown {
          type empty;
        }
        leaf nameif {
          type string;
        }
        container ip {
          container address {
            container ip {
              tailf:cli-drop-node-name;
              tailf:cli-compact-syntax;
              tailf:cli-sequence-commands {
                tailf:cli-reset-siblings;
              }
              leaf host-ip {
                tailf:cli-drop-node-name;
                type string;
              }
              leaf netmask {
                tailf:cli-drop-node-name;
                type inet:ipv4-address;
              }
            }
          }
        }
        container tunnel {
          container source {
            container interface {
              uses interface-name-grouping;
            }
          }
          leaf destination {
            type inet:host;
          }
          container mode {
            container ipsec {
              leaf ipv4 {
                type empty;
              }
            }
          }
          container protection {
            container ipsec {
              leaf profile {
                type string;
              }
            }
          }
        }
      }
      list Vlan {
        tailf:cli-allow-join-with-key;
        key "name";
        leaf name {
          type uint16;
        }
        uses interface-ethernet-grouping;
        uses interface-common-grouping;
        uses interface-switch-grouping;
      }
      list Port-channel {
        tailf:cli-allow-join-with-key;
        key "name";
        leaf name {
          type string;
        }
        uses interface-ethernet-grouping;
        uses interface-common-grouping;
        uses interface-switch-grouping;
        container port-channel {
          leaf load-balance {
            type string;
          }
          container span-cluster {
            presence "true";
            leaf vss-load-balance {
              type empty;
            }
          }
        }
      }
      container Port-channel-subif {
        tailf:cli-drop-node-name;
        list Port-channel {
          tailf:cli-allow-join-with-key;
          key "name";
          leaf name {
            type string;
          }
          uses interface-ethernet-grouping;
          uses sub-interface-common-grouping;
          uses interface-switch-grouping;
        }
      }
      list BVI {
        tailf:cli-allow-join-with-key;
        key "name";
        leaf name {
          type string;
        }
        uses interface-common-grouping {
          refine "shutdown";
        }
      }
      list Redundant {
        tailf:cli-allow-join-with-key;
        key "name";
        leaf name {
          type uint32;
        }
        list member-interface {
          tailf:cli-suppress-mode;
          tailf:cli-delete-when-empty;
          key "name";
          leaf name {
            type string;
          }
        }
        uses interface-common-grouping {
          refine "nameif";
        }
        uses interface-switch-grouping;
      }
      list allocated {
        tailf:cli-drop-node-name;
        key "name";
        leaf name {
          type string;
        }
        uses interface-ethernet-grouping;
        uses interface-common-grouping;
        uses interface-switch-grouping;
      }
    }
    list regex {
      tailf:cli-suppress-mode;
      tailf:cli-delete-when-empty;
      key "name";
      leaf name {
        type string;
      }
      leaf regex {
        tailf:cli-drop-node-name;
        type string;
      }
    }
    list class {
      key "name";
      leaf name {
        type string;
      }
      list limit-resource {
        tailf:cli-suppress-mode;
        tailf:cli-delete-when-empty;
        key "name";
        leaf name {
          type enumeration {
            enum "ASDM";
            enum "All";
            enum "Conns";
            enum "Hosts";
            enum "Mac-addresses";
            enum "Routes";
            enum "SSH";
            enum "Telnet";
            enum "VPN";
            enum "Xlates";
            enum "Storage";
          }
        }
        leaf value {
          tailf:cli-drop-node-name;
          type string;
        }
      }
      container limit-resource-vpn {
        tailf:cli-drop-node-name;
        container limit-resource {
          container VPN {
            container Other {
              leaf value {
                tailf:cli-drop-node-name;
                type string;
              }
            }
          }
        }
      }
    }
    container forward-reference {
      leaf enable {
        type empty;
      }
    }
    container object {
      list network {
        key "name";
        leaf name {
          type string;
        }
        leaf description {
          tailf:cli-multi-value;
          type string;
        }
        choice object-network-choice {
          leaf host {
            type union {
              type inet:ipv4-address;
              type inet:ipv6-address;
            }
          }
          container range {
            tailf:cli-compact-syntax;
            tailf:cli-sequence-commands {
              tailf:cli-reset-siblings;
            }
            leaf start-ip {
              tailf:cli-drop-node-name;
              type union {
                type inet:ipv4-address;
                type inet:ipv6-address;
              }
            }
            leaf end-ip {
              tailf:cli-drop-node-name;
              type union {
                type inet:ipv4-address;
                type inet:ipv6-address;
              }
            }
          }
          container subnet {
            tailf:cli-compact-syntax;
            tailf:cli-sequence-commands {
              tailf:cli-reset-siblings;
            }
            leaf address {
              tailf:cli-drop-node-name;
              type union {
                type inet:host;
                type ipv6-prefix;
              }
            }
            leaf mask {
              tailf:cli-drop-node-name;
              type inet:ip-address;
            }
          }
          container fqdn {
            tailf:cli-compact-syntax;
            tailf:cli-sequence-commands;
            leaf af {
              tailf:cli-drop-node-name;
              tailf:cli-optional-in-sequence;
              type enumeration {
                enum "v4";
                enum "v6";
              }
            }
            leaf domain {
              tailf:cli-drop-node-name;
              type string;
            }
          }
        }
        container nat {
          tailf:cli-compact-syntax;
          tailf:cli-sequence-commands {
            tailf:cli-reset-siblings;
          }
          leaf ifc {
            tailf:cli-drop-node-name;
            type string;
          }
          leaf type {
            tailf:cli-drop-node-name;
            type enumeration {
              enum "dynamic";
              enum "static";
            }
          }
          choice mapped-choice {
            leaf mapped-inline-host-ip {
              tailf:cli-drop-node-name;
              tailf:cli-optional-in-sequence;
              type inet:ipv4-address;
            }
            leaf mapped-obj {
              tailf:cli-drop-node-name;
              tailf:cli-optional-in-sequence;
              type string;
            }
            leaf pat-pool {
              tailf:cli-optional-in-sequence;
              type string;
            }
          }
          leaf interface {
            tailf:cli-optional-in-sequence;
            type empty;
          }
          leaf ipv6 {
            tailf:cli-optional-in-sequence;
            type empty;
          }
          leaf net-to-net {
            tailf:cli-optional-in-sequence;
            type empty;
          }
          leaf dns {
            tailf:cli-optional-in-sequence;
            type empty;
          }
          leaf no-proxy-arp {
            tailf:cli-optional-in-sequence;
            type empty;
          }
          leaf route-lookup {
            tailf:cli-optional-in-sequence;
            type empty;
          }
          container service {
            tailf:cli-flatten-container;
            tailf:cli-compact-syntax;
            tailf:cli-sequence-commands {
              tailf:cli-reset-siblings;
            }
            leaf protocol {
              tailf:cli-drop-node-name;
              type enumeration {
                enum "tcp";
                enum "udp";
              }
            }
            leaf real-port {
              tailf:cli-drop-node-name;
              type union {
                type uint16;
                type string;
              }
            }
            leaf mapped-port {
              tailf:cli-drop-node-name;
              type union {
                type uint16;
                type string;
              }
            }
          }
        }
      }
      list service {
        key "name";
        leaf name {
          type string;
        }
        leaf description {
          tailf:cli-multi-value;
          type string;
        }
        container service {
          tailf:cli-compact-syntax;
          tailf:cli-sequence-commands {
            tailf:cli-reset-siblings;
          }
          leaf name {
            tailf:cli-drop-node-name;
            type string;
          }
          container source {
            tailf:cli-break-sequence-commands;
            tailf:cli-flatten-container;
            tailf:cli-compact-syntax;
            tailf:cli-sequence-commands {
              tailf:cli-reset-siblings;
            }
            uses object-service-port-grouping;
          }
          container destination {
            tailf:cli-flatten-container;
            tailf:cli-compact-syntax;
            tailf:cli-sequence-commands {
              tailf:cli-reset-siblings;
            }
            uses object-service-port-grouping;
          }
          container icmp {
            tailf:cli-drop-node-name;
            tailf:cli-flatten-container;
            tailf:cli-compact-syntax;
            tailf:cli-sequence-commands {
              tailf:cli-reset-siblings;
            }
            leaf type {
              tailf:cli-drop-node-name;
              type union {
                type uint8;
                type enumeration {
                  enum "echo-reply" {
                    value 0;
                  }
                  enum "unreachable" {
                    value 3;
                  }
                  enum "source-quench" {
                    value 4;
                  }
                  enum "redirect" {
                    value 5;
                  }
                  enum "alternate-address" {
                    value 6;
                  }
                  enum "echo" {
                    value 8;
                  }
                  enum "router-advertisement" {
                    value 9;
                  }
                  enum "router-solicitation" {
                    value 10;
                  }
                  enum "time-exceeded" {
                    value 11;
                  }
                  enum "parameter-problem" {
                    value 12;
                  }
                  enum "timestamp-request" {
                    value 13;
                  }
                  enum "timestamp-reply" {
                    value 14;
                  }
                  enum "information-request" {
                    value 15;
                  }
                  enum "information-reply" {
                    value 16;
                  }
                  enum "mask-request" {
                    value 17;
                  }
                  enum "mask-reply" {
                    value 18;
                  }
                  enum "traceroute" {
                    value 30;
                  }
                  enum "conversion-error" {
                    value 31;
                  }
                  enum "mobile-redirect" {
                    value 32;
                  }
                }
              }
            }
            leaf code {
              tailf:cli-drop-node-name;
              type uint8;
            }
          }
        }
      }
    }
    container object-group {
      list icmp-type {
        key "id";
        leaf id {
          type string;
        }
        leaf description {
          tailf:cli-multi-value;
          type string;
        }
        list icmp-object {
          tailf:cli-suppress-mode;
          tailf:cli-delete-when-empty;
          ordered-by user;
          key "id";
          leaf id {
            tailf:cli-multi-word-key;
            type string;
          }
        }
        leaf-list group-object {
          type string;
        }
      }
      list network {
        key "id";
        leaf id {
          type string;
        }
        leaf description {
          tailf:cli-multi-value;
          type string;
        }
        list network-object {
          tailf:cli-suppress-mode;
          tailf:cli-delete-when-empty;
          key "id";
          leaf id {
            tailf:cli-multi-word-key;
            type string;
          }
        }
        leaf-list group-object {
          type string;
        }
      }
      list service {
        key "id";
        leaf id {
          type string;
        }
        leaf proto {
          tailf:cli-drop-node-name;
          tailf:cli-hide-in-submode;
          type union {
            type uint8;
            type enumeration {
              enum "tcp";
              enum "tcp-udp";
              enum "udp";
            }
          }
        }
        leaf description {
          tailf:cli-multi-value;
          type string;
        }
        leaf-list group-object {
          type string;
        }
        list service-object {
          tailf:cli-suppress-mode;
          tailf:cli-delete-when-empty;
          key "arg";
          leaf arg {
            tailf:cli-suppress-range;
            tailf:cli-multi-word-key;
            type string;
          }
        }
        list port-object {
          tailf:cli-suppress-mode;
          tailf:cli-delete-when-empty;
          key "arg";
          leaf arg {
            tailf:cli-suppress-range;
            tailf:cli-multi-word-key;
            type string;
          }
        }
      }
      list user {
        key "id";
        leaf id {
          type string;
        }
        leaf description {
          tailf:cli-multi-value;
          type string;
        }
        leaf-list group-object {
          type string;
        }
        list user {
          tailf:cli-suppress-mode;
          tailf:cli-delete-when-empty;
          key "id";
          leaf id {
            type string;
          }
        }
        list user-group {
          tailf:cli-suppress-mode;
          tailf:cli-delete-when-empty;
          ordered-by user;
          key "id";
          leaf id {
            tailf:cli-multi-word-key;
            type string;
          }
        }
      }
      list security {
        key "id";
        leaf id {
          type string;
        }
        leaf description {
          tailf:cli-multi-value;
          type string;
        }
        container security-group {
          list name {
            tailf:cli-suppress-mode;
            tailf:cli-delete-when-empty;
            key "id";
            leaf id {
              type string;
            }
          }
          list tag {
            tailf:cli-suppress-mode;
            tailf:cli-delete-when-empty;
            key "id";
            leaf id {
              type uint16;
            }
          }
        }
      }
      list protocol {
        key "id";
        leaf id {
          type string;
        }
        leaf description {
          tailf:cli-multi-value;
          type string;
        }
        leaf-list group-object {
          type string;
        }
        list protocol-object {
          tailf:cli-suppress-mode;
          tailf:cli-delete-when-empty;
          key "id";
          leaf id {
            type string;
          }
        }
      }
    }
    container access-list {
      leaf deny-flow-max {
        type uint16;
      }
      leaf alert-interval {
        type uint16;
      }
      list access-list-id {
        tailf:cli-drop-node-name;
        tailf:cli-suppress-mode;
        tailf:cli-delete-when-empty;
        key "id";
        leaf id {
          type string;
        }
        list rule {
          tailf:cli-drop-node-name;
          tailf:cli-suppress-mode;
          tailf:cli-delete-when-empty;
          tailf:cli-compact-syntax;
          tailf:cli-sequence-commands {
            tailf:cli-reset-siblings;
          }
          ordered-by user;
          key "id";
          leaf id {
            type string;
          }
          leaf log {
            tailf:cli-optional-in-sequence;
            type empty;
          }
          leaf level {
            tailf:cli-drop-node-name;
            tailf:cli-optional-in-sequence;
            type union {
              type logging-level-type;
              type enumeration {
                enum "default" {
                  value 106023;
                }
              }
            }
          }
          leaf interval {
            tailf:cli-optional-in-sequence;
            type uint16;
          }
          leaf time-range {
            tailf:cli-optional-in-sequence;
            type string;
          }
          leaf inactive {
            type empty;
          }
        }
      }
    }
    container access-group {
      list interface-list {
        tailf:cli-drop-node-name;
        tailf:cli-suppress-mode;
        tailf:cli-delete-when-empty;
        tailf:cli-compact-syntax;
        tailf:cli-sequence-commands;
        key "direction interface";
        leaf direction {
          type enumeration {
            enum "in";
            enum "out";
          }
        }
        leaf interface {
          tailf:cli-expose-key-name;
          type nameif-type;
        }
        leaf access-list {
          tailf:cli-drop-node-name;
          tailf:cli-prefix-key;
          type string;
        }
      }
      list control-plane-list {
        tailf:cli-drop-node-name;
        tailf:cli-suppress-mode;
        tailf:cli-delete-when-empty;
        tailf:cli-compact-syntax;
        tailf:cli-sequence-commands;
        key "direction interface";
        leaf direction {
          type enumeration {
            enum "in";
          }
        }
        leaf interface {
          tailf:cli-expose-key-name;
          type nameif-type;
        }
        leaf access-list {
          tailf:cli-drop-node-name;
          tailf:cli-prefix-key;
          type string;
        }
        leaf control-plane {
          type empty;
        }
      }
      list global-list {
        tailf:cli-drop-node-name;
        tailf:cli-suppress-mode;
        tailf:cli-delete-when-empty;
        tailf:cli-compact-syntax;
        tailf:cli-sequence-commands;
        key "global";
        leaf global {
          type enumeration {
            enum "global";
          }
        }
        leaf access-list {
          tailf:cli-drop-node-name;
          tailf:cli-prefix-key;
          type string;
        }
      }
    }
    container prefix-list {
      leaf sequence-number {
        type boolean;
      }
      list prefixes {
        tailf:cli-drop-node-name;
        tailf:cli-suppress-mode;
        tailf:cli-delete-when-empty;
        key "name";
        leaf name {
          type string;
        }
        leaf description {
          tailf:cli-multi-value;
          type string;
        }
        leaf permit {
          type ipv4-prefix;
        }
        list seq {
          tailf:cli-suppress-mode;
          tailf:cli-delete-when-empty;
          tailf:cli-compact-syntax;
          key "no";
          leaf no {
            type uint32;
          }
          container deny {
            tailf:cli-compact-syntax;
            tailf:cli-sequence-commands {
              tailf:cli-reset-all-siblings;
            }
            leaf ip {
              tailf:cli-drop-node-name;
              type string;
            }
            leaf ge {
              tailf:cli-break-sequence-commands;
              type uint8;
            }
            leaf le {
              type uint8;
            }
          }
          container permit {
            tailf:cli-compact-syntax;
            tailf:cli-sequence-commands {
              tailf:cli-reset-all-siblings;
            }
            leaf ip {
              tailf:cli-drop-node-name;
              type string;
            }
            leaf ge {
              tailf:cli-break-sequence-commands;
              type uint8;
            }
            leaf le {
              type uint8;
            }
          }
        }
      }
    }
    list policy-list {
      key "name";
      leaf name {
        type string;
      }
      leaf operation {
        tailf:cli-drop-node-name;
        tailf:cli-hide-in-submode;
        type enumeration {
          enum "deny";
          enum "permit";
        }
      }
    }
    container cluster {
      list group {
        key "name";
        leaf name {
          type string;
        }
        leaf local-unit {
          type string;
        }
        container cluster-interface {
          tailf:cli-compact-syntax;
          tailf:cli-sequence-commands {
            tailf:cli-reset-siblings;
          }
          uses interface-name-grouping;
          leaf ip {
            type inet:host;
          }
          leaf mask {
            tailf:cli-drop-node-name;
            type inet:ipv4-address;
          }
        }
        leaf priority {
          type uint8;
        }
        leaf console-replicate {
          type empty;
        }
        container health-check {
          leaf holdtime {
            type string;
          }
        }
        container clacp {
          container system-mac {
            tailf:cli-compact-syntax;
            tailf:cli-sequence-commands {
              tailf:cli-reset-siblings;
            }
            leaf address {
              tailf:cli-drop-node-name;
              type union {
                type string;
                type enumeration {
                  enum "auto";
                }
              }
            }
            leaf system-priority {
              type uint16;
            }
          }
        }
        container enable {
          presence "true";
        }
      }
    }
    list tcp-map {
      key "name";
      leaf name {
        type string;
      }
      container tcp-options {
        list range {
          tailf:cli-suppress-mode;
          tailf:cli-delete-when-empty;
          key "option";
          leaf option {
            tailf:cli-suppress-range;
            type uint8;
          }
          leaf action {
            tailf:cli-drop-node-name;
            type enumeration {
              enum "allow";
              enum "drop";
            }
          }
        }
      }
      leaf urgent-flag {
        type enumeration {
          enum "clear";
          enum "allow";
        }
      }
    }
    list route-map {
      tailf:cli-compact-syntax;
      key "name sequence";
      leaf name {
        type string;
      }
      leaf sequence {
        type uint16;
      }
      leaf operation {
        tailf:cli-drop-node-name;
        tailf:cli-prefix-key {
          tailf:cli-before-key "2";
        }
        type enumeration {
          enum "deny";
          enum "permit";
        }
      }
      container match {
        container community {
          leaf-list name {
            tailf:cli-drop-node-name;
            tailf:cli-flat-list-syntax;
            ordered-by user;
            type union {
              type string;
              type enumeration {
                enum "exact-match";
              }
            }
          }
        }
        container ip {
          container address {
            choice address-choice {
              leaf access-list {
                tailf:cli-drop-node-name;
                type string;
              }
              leaf prefix-list {
                type string;
              }
            }
          }
        }
        container route-type {
          tailf:cli-compact-syntax;
          leaf internal {
            type empty;
          }
          leaf local {
            type empty;
          }
          container external-2 {
            tailf:cli-drop-node-name;
            tailf:cli-flatten-container;
            leaf external {
              type enumeration {
                enum "type-2";
              }
            }
          }
          container nssa-external-1 {
            tailf:cli-drop-node-name;
            tailf:cli-flatten-container;
            leaf nssa-external {
              type enumeration {
                enum "type-1";
              }
            }
          }
          leaf nssa-external {
            type empty;
          }
          container external-1 {
            tailf:cli-drop-node-name;
            tailf:cli-flatten-container;
            leaf external {
              type enumeration {
                enum "type-1";
              }
            }
          }
          leaf external {
            type empty;
          }
          container nssa-external-2 {
            tailf:cli-drop-node-name;
            tailf:cli-flatten-container;
            leaf nssa-external {
              type enumeration {
                enum "type-2";
              }
            }
          }
        }
      }
      container set {
        container ip {
          container next-hop {
            leaf-list address {
              tailf:cli-drop-node-name;
              tailf:cli-flat-list-syntax;
              type inet:host;
            }
            leaf peer-address {
              type empty;
            }
          }
          container address {
            leaf prefix-list {
              type string;
            }
          }
        }
        leaf weight {
          type uint32;
        }
        leaf origin {
          type enumeration {
            enum "igp";
            enum "incomplete";
          }
        }
        container as-path {
          container prepend {
            container as-container {
              tailf:cli-drop-node-name;
              leaf as-no {
                tailf:cli-drop-node-name;
                tailf:cli-multi-value;
                type string;
              }
            }
            container last-as-cont {
              tailf:cli-drop-node-name;
              tailf:cli-flatten-container;
              tailf:cli-compact-syntax;
              leaf last-as {
                type uint16;
              }
            }
          }
          container tag {
            presence "true";
          }
        }
        container community {
          leaf-list community-number {
            tailf:cli-drop-node-name;
            tailf:cli-flat-list-syntax;
            ordered-by user;
            type union {
              type uint32;
              type string;
              type enumeration {
                enum "additive";
                enum "internet";
                enum "local-AS";
                enum "no-advertise";
                enum "no-export";
                enum "none";
              }
            }
          }
        }
        container local-preference {
          tailf:cli-delete-when-empty;
          presence "true";
          leaf value {
            tailf:cli-drop-node-name;
            type uint32;
          }
        }
        leaf metric {
          type uint32;
        }
        leaf metric-type {
          type enumeration {
            enum "internal";
            enum "type-1";
            enum "type-2";
          }
        }
      }
    }
    container banner {
      leaf exec {
        type string;
      }
      leaf login {
        type string;
      }
      leaf motd {
        type string;
      }
      leaf asdm {
        type string;
      }
    }
    list class-map {
      tailf:cli-sequence-commands;
      key "name";
      leaf name {
        type string;
      }
      leaf type {
        tailf:cli-optional-in-sequence;
        tailf:cli-prefix-key;
        type enumeration {
          enum "inspect";
          enum "management";
          enum "regex";
        }
      }
      leaf protocol {
        tailf:cli-drop-node-name;
        tailf:cli-prefix-key;
        tailf:cli-optional-in-sequence;
        type enumeration {
          enum "dns";
          enum "ftp";
          enum "h323";
          enum "http";
          enum "im";
          enum "rtsp";
          enum "scansafe";
          enum "sip";
        }
      }
      leaf prematch {
        tailf:cli-drop-node-name;
        tailf:cli-prefix-key;
        tailf:cli-optional-in-sequence;
        type enumeration {
          enum "match-all";
          enum "match-any";
        }
      }
      leaf description {
        tailf:cli-break-sequence-commands;
        tailf:cli-multi-value;
        type string;
      }
      container match {
        leaf any {
          type empty;
        }
        leaf access-list {
          type string;
        }
        leaf-list dscp {
          tailf:cli-flat-list-syntax;
          type dscp-type;
        }
        container port {
          tailf:cli-compact-syntax;
          tailf:cli-sequence-commands {
            tailf:cli-reset-siblings;
          }
          leaf protocol {
            tailf:cli-drop-node-name;
            type enumeration {
              enum "tcp";
              enum "udp";
            }
          }
          choice port-choice {
            leaf eq {
              type union {
                type string;
                type uint16;
              }
            }
            container range {
              tailf:cli-flatten-container;
              tailf:cli-compact-syntax;
              tailf:cli-sequence-commands;
              leaf min {
                tailf:cli-drop-node-name;
                type uint16;
              }
              leaf max {
                tailf:cli-drop-node-name;
                type uint16;
              }
            }
          }
        }
        leaf-list precedence {
          tailf:cli-flat-list-syntax;
          type precedence-type;
        }
        leaf default-inspection-traffic {
          type empty;
        }
      }
    }
    container umbrella-global {
      tailf:cli-add-mode;
      presence "true";
      leaf token {
        type string;
      }
      container timeout {
        leaf edns {
          type hhmmss-type;
        }
      }
    }
    list policy-map {
      tailf:cli-sequence-commands;
      key "name";
      leaf name {
        type string;
      }
      leaf type {
        tailf:cli-prefix-key;
        tailf:cli-optional-in-sequence;
        type enumeration {
          enum "inspect";
        }
      }
      leaf protocol {
        tailf:cli-drop-node-name;
        tailf:cli-prefix-key;
        tailf:cli-optional-in-sequence;
        type enumeration {
          enum "dcerpc";
          enum "dns";
          enum "esmtp";
          enum "ftp";
          enum "gtp";
          enum "h323";
          enum "http";
          enum "im";
          enum "ip-options";
          enum "ipsec-pass-thru";
          enum "ipv6";
          enum "mgcp";
          enum "netbios";
          enum "radius-accounting";
          enum "rtsp";
          enum "scansafe";
          enum "sip";
          enum "skinny";
        }
      }
      leaf description {
        tailf:cli-break-sequence-commands;
        tailf:cli-multi-value;
        type string;
      }
      container parameters {
        tailf:cli-add-mode;
        container message-length {
          container maximum {
            leaf client {
              type union {
                type uint16;
                type enumeration {
                  enum "auto";
                }
              }
            }
            leaf length {
              tailf:cli-drop-node-name;
              type uint16;
            }
            leaf server {
              type union {
                type uint16;
                type enumeration {
                  enum "auto";
                }
              }
            }
          }
        }
        container umbrella {
          container tag {
            tailf:cli-compact-syntax;
            tailf:cli-sequence-commands {
              tailf:cli-reset-siblings;
            }
            leaf name {
              tailf:cli-drop-node-name;
              type string;
            }
            leaf fail-open {
              tailf:cli-optional-in-sequence;
              type empty;
            }
            leaf device-id {
              type string;
            }
          }
        }
        leaf tcp-inspection {
          type boolean;
        }
      }
      container match {
        container message-path {
          list regex {
            key "name";
            leaf name {
              type string;
            }
            container drop {
              presence "true";
            }
          }
        }
      }
      list class {
        ordered-by user;
        key "name";
        leaf name {
          type union {
            type string;
            type enumeration {
              enum "class-default";
            }
          }
        }
        leaf type {
          tailf:cli-prefix-key;
          type enumeration {
            enum "inspect";
            enum "management";
            enum "regex";
          }
        }
        container drop-connection {
          presence "true";
          leaf log {
            type empty;
          }
        }
        leaf priority {
          type empty;
        }
        container set {
          container connection {
            tailf:cli-compact-syntax;
            leaf conn-max {
              type uint32;
            }
            leaf embryonic-conn-max {
              type uint32;
            }
            leaf per-client-embryonic-max {
              type uint32;
            }
            leaf random-sequence-number {
              type enumeration {
                enum "disable";
                enum "enable";
              }
            }
            container timeout {
              container idle {
                tailf:cli-compact-syntax;
                tailf:cli-sequence-commands {
                  tailf:cli-reset-siblings;
                }
                leaf time {
                  tailf:cli-drop-node-name;
                  type string;
                }
                leaf reset {
                  type empty;
                }
              }
            }
            container advanced-options {
              leaf tcp-state-bypass {
                type empty;
              }
              leaf tcp-map {
                tailf:cli-drop-node-name;
                type string;
              }
            }
            leaf decrement-ttl {
              type empty;
            }
          }
        }
        container police {
          container output {
            tailf:cli-compact-syntax;
            tailf:cli-sequence-commands;
            uses policy-map-class-police-grouping;
          }
          container input {
            tailf:cli-compact-syntax;
            tailf:cli-sequence-commands;
            uses policy-map-class-police-grouping;
          }
        }
        container shape {
          presence "true";
          container average {
            tailf:cli-compact-syntax;
            tailf:cli-sequence-commands;
            choice average-choice {
              case a {
                leaf bit-rate {
                  tailf:cli-drop-node-name;
                  type uint32;
                }
                leaf bits-per-interval-sustained {
                  tailf:cli-drop-node-name;
                  type uint32;
                }
                leaf bits-per-interval-excess {
                  tailf:cli-drop-node-name;
                  type uint32;
                }
              }
              case b {
                leaf percent {
                  type percentage-type;
                }
                leaf burst-size-sustained {
                  tailf:cli-drop-node-name;
                  type uint16;
                }
                leaf ms {
                  type empty;
                }
                container bse {
                  tailf:cli-drop-node-name;
                  tailf:cli-flatten-container;
                  tailf:cli-compact-syntax;
                  tailf:cli-sequence-commands;
                  leaf burst-size-excess {
                    type uint16;
                  }
                  leaf ms {
                    type empty;
                  }
                }
              }
            }
          }
        }
        container flow-export {
          list event-type {
            tailf:cli-suppress-mode;
            tailf:cli-delete-when-empty;
            tailf:cli-compact-syntax;
            key "name";
            leaf name {
              type enumeration {
                enum "all";
                enum "flow-create";
                enum "flow-denied";
                enum "flow-teardown";
                enum "flow-update";
              }
            }
            leaf-list destination {
              tailf:cli-flat-list-syntax;
              type inet:host;
            }
          }
        }
        leaf service-policy {
          type string;
        }
        container inspect {
          container dns {
            tailf:cli-delete-when-empty;
            presence "true";
            leaf policy-map-name {
              tailf:cli-drop-node-name;
              type string;
            }
          }
          container ftp {
            tailf:cli-delete-when-empty;
            presence "true";
            leaf strict {
              type empty;
            }
          }
          container h323 {
            leaf h225 {
              type empty;
            }
            leaf ras {
              type empty;
            }
          }
          container netbios {
            presence "true";
          }
          leaf rsh {
            type empty;
          }
          leaf rtsp {
            type empty;
          }
          container skinny {
            presence "true";
          }
          container esmtp {
            presence "true";
          }
          leaf sqlnet {
            type empty;
          }
          leaf sunrpc {
            type empty;
          }
          leaf tftp {
            type empty;
          }
          container sip {
            tailf:cli-delete-when-empty;
            presence "true";
            leaf policy-map-name {
              tailf:cli-drop-node-name;
              type string;
            }
          }
          leaf xdmcp {
            type empty;
          }
          container icmp {
            presence "true";
            leaf error {
              type empty;
            }
          }
          container ipsec-pass-thru {
            presence "true";
          }
          container snmp {
            presence "true";
          }
          container ils {
            presence "true";
          }
          container ctiqbe {
            presence "true";
          }
          container http {
            presence "true";
          }
          container ip-options {
            presence "true";
          }
          container pptp {
            presence "true";
          }
          container ipv6 {
            tailf:cli-delete-when-empty;
            presence "true";
            leaf policy-map-name {
              tailf:cli-drop-node-name;
              type string;
            }
          }
        }
        container ips {
          tailf:cli-compact-syntax;
          tailf:cli-sequence-commands {
            tailf:cli-reset-siblings;
          }
          leaf mode {
            tailf:cli-drop-node-name;
            type enumeration {
              enum "inline";
              enum "promiscuous";
            }
          }
          leaf action {
            tailf:cli-drop-node-name;
            type enumeration {
              enum "fail-close";
              enum "fail-open";
            }
          }
          leaf sensor {
            type string;
          }
        }
      }
    }
    leaf config-register {
      type string;
    }
    container clock {
      container summer-time {
        tailf:cli-compact-syntax;
        tailf:cli-sequence-commands {
          tailf:cli-reset-siblings;
        }
        leaf zone {
          tailf:cli-drop-node-name;
          type string;
        }
        choice summer-choice {
          container date {
            tailf:cli-flatten-container;
            tailf:cli-compact-syntax;
            tailf:cli-sequence-commands {
              tailf:cli-reset-siblings;
            }
            leaf start-month {
              tailf:cli-drop-node-name;
              type month-type;
            }
            leaf start-date {
              tailf:cli-drop-node-name;
              type uint8;
            }
            leaf start-year {
              tailf:cli-drop-node-name;
              type uint16;
            }
            leaf start-time {
              tailf:cli-drop-node-name;
              type hhmm-type;
            }
            leaf end-month {
              tailf:cli-drop-node-name;
              type month-type;
            }
            leaf end-date {
              tailf:cli-drop-node-name;
              type uint8;
            }
            leaf end-year {
              tailf:cli-drop-node-name;
              type uint16;
            }
            leaf end-time {
              tailf:cli-drop-node-name;
              type hhmm-type;
            }
          }
          case recurring-case {
            leaf recurring {
              type empty;
            }
            leaf start {
              tailf:cli-drop-node-name;
              type union {
                type uint8;
                type enumeration {
                  enum "first";
                  enum "last";
                }
              }
            }
            leaf start-day {
              tailf:cli-drop-node-name;
              type weekday-type;
            }
            leaf start-month {
              tailf:cli-drop-node-name;
              type month-type;
            }
            leaf start-time {
              tailf:cli-drop-node-name;
              type hhmm-type;
            }
            leaf end {
              tailf:cli-drop-node-name;
              type union {
                type uint8;
                type enumeration {
                  enum "first";
                  enum "last";
                }
              }
            }
            leaf end-day {
              tailf:cli-drop-node-name;
              type weekday-type;
            }
            leaf end-month {
              tailf:cli-drop-node-name;
              type month-type;
            }
            leaf end-time {
              tailf:cli-drop-node-name;
              type hhmm-type;
            }
          }
        }
      }
      container timezone {
        tailf:cli-compact-syntax;
        tailf:cli-sequence-commands {
          tailf:cli-reset-siblings;
        }
        leaf zone {
          tailf:cli-drop-node-name;
          type string;
        }
        leaf hours {
          tailf:cli-drop-node-name;
          type int8;
        }
        leaf minutes {
          tailf:cli-drop-node-name;
          type int8;
        }
      }
    }
    container logging {
      leaf enable {
        type empty;
      }
      leaf timestamp {
        type empty;
      }
      leaf permit-hostdown {
        type empty;
      }
      list list {
        tailf:cli-suppress-mode;
        tailf:cli-delete-when-empty;
        tailf:cli-compact-syntax;
        key "name";
        leaf name {
          type string;
        }
        list message {
          tailf:cli-suppress-mode;
          tailf:cli-delete-when-empty;
          key "id";
          leaf id {
            type string;
          }
        }
        leaf level {
          type logging-level-type;
        }
        leaf class {
          type string;
        }
      }
      list class {
        tailf:cli-suppress-mode;
        tailf:cli-delete-when-empty;
        tailf:cli-compact-syntax;
        tailf:cli-sequence-commands {
          tailf:cli-reset-siblings;
        }
        key "name";
        leaf name {
          type string;
        }
        leaf destination {
          tailf:cli-drop-node-name;
          type enumeration {
            enum "asdm";
            enum "buffered";
            enum "console";
            enum "history";
            enum "mail";
            enum "monitor";
            enum "trap";
          }
        }
        leaf level {
          tailf:cli-drop-node-name;
          type logging-level-type;
        }
      }
      leaf buffer-size {
        type uint32;
      }
      leaf console {
        type logging-type;
      }
      leaf monitor {
        type logging-type;
      }
      leaf mail {
        type logging-type;
      }
      leaf from-address {
        type string;
      }
      list recipient-address {
        tailf:cli-suppress-mode;
        tailf:cli-delete-when-empty;
        key "address";
        leaf address {
          type string;
        }
        leaf level {
          type logging-level-type;
        }
      }
      leaf buffered {
        type logging-type;
      }
      leaf trap {
        type logging-type;
      }
      leaf history {
        type logging-type;
      }
      leaf asdm {
        type logging-type;
      }
      leaf facility {
        type uint8;
      }
      container device-id {
        choice device-id-choice {
          leaf hostname {
            type empty;
          }
          leaf cluster-id {
            type empty;
          }
          leaf context-name {
            type empty;
          }
          leaf string {
            type string;
          }
        }
      }
      leaf queue {
        type uint16;
      }
      list host {
        tailf:cli-suppress-mode;
        tailf:cli-delete-when-empty;
        tailf:cli-compact-syntax;
        key "interface host";
        leaf interface {
          type nameif-type;
        }
        leaf host {
          type inet:host;
        }
        leaf protocol-port {
          tailf:cli-drop-node-name;
          type string;
        }
        leaf secure {
          type empty;
        }
        container format {
          leaf emblem {
            type empty;
          }
        }
      }
      list rate-limit {
        tailf:cli-suppress-mode;
        tailf:cli-delete-when-empty;
        tailf:cli-compact-syntax;
        tailf:cli-sequence-commands {
          tailf:cli-reset-siblings;
        }
        key "level";
        leaf level {
          tailf:cli-expose-key-name;
          type union {
            type uint8;
            type logging-level-type;
          }
        }
        choice rate-limit-choice {
          leaf unlimited {
            tailf:cli-prefix-key;
            type empty;
          }
          case num-limited {
            leaf num {
              tailf:cli-drop-node-name;
              tailf:cli-prefix-key;
              type uint32;
            }
            leaf interval {
              tailf:cli-drop-node-name;
              tailf:cli-prefix-key;
              tailf:cli-optional-in-sequence;
              type uint32;
            }
          }
        }
      }
      container message {
        list no-list {
          tailf:cli-suppress-mode;
          tailf:cli-delete-when-empty;
          key "id";
          leaf id {
            type uint32;
          }
        }
        list yes-list {
          tailf:cli-drop-node-name;
          tailf:cli-suppress-mode;
          tailf:cli-delete-when-empty;
          key "id";
          leaf id {
            type uint32;
          }
          leaf level {
            type logging-level-type;
          }
        }
      }
      leaf flash-bufferwrap {
        type empty;
      }
      leaf flash-minimum-free {
        type uint32;
      }
      leaf flash-maximum-allocation {
        type uint32;
      }
      leaf standby {
        type empty;
      }
    }
    container ntp {
      list server {
        tailf:cli-suppress-mode;
        tailf:cli-delete-when-empty;
        tailf:cli-compact-syntax;
        tailf:cli-sequence-commands {
          tailf:cli-reset-all-siblings;
        }
        key "ip-address";
        leaf ip-address {
          type host-type;
        }
        leaf key {
          tailf:cli-break-sequence-commands;
          type uint32;
        }
        container source {
          tailf:cli-flatten-container;
          tailf:cli-compact-syntax;
          uses interface-name-grouping;
        }
        leaf prefer {
          type empty;
        }
      }
      list authentication-key {
        tailf:cli-suppress-mode;
        tailf:cli-delete-when-empty;
        key "id";
        leaf id {
          type uint32;
        }
        container md5 {
          tailf:cli-flatten-container;
          tailf:cli-compact-syntax;
          tailf:cli-sequence-commands;
          uses password-08-grouping {
            refine "secret";
          }
        }
      }
      leaf authenticate {
        type empty;
      }
      list trusted-key {
        tailf:cli-suppress-mode;
        tailf:cli-delete-when-empty;
        key "id";
        leaf id {
          type uint32;
        }
      }
    }
    container privilege {
      list command-list {
        tailf:cli-drop-node-name;
        tailf:cli-suppress-mode;
        tailf:cli-delete-when-empty;
        tailf:cli-compact-syntax;
        tailf:cli-suppress-key-abbreviation;
        ordered-by user;
        key "command";
        leaf command {
          tailf:cli-multi-word-key;
          type string;
        }
      }
    }
    container vpdn;
    list tftp-server {
      tailf:cli-suppress-mode;
      tailf:cli-delete-when-empty;
      tailf:cli-compact-syntax;
      tailf:cli-sequence-commands;
      key "name";
      leaf name {
        type nameif-type;
      }
      leaf server {
        tailf:cli-drop-node-name;
        type union {
          type inet:host;
          type inet:ipv6-address;
        }
      }
      leaf filename {
        tailf:cli-drop-node-name;
        type string;
      }
    }
    container zone {
      list zone-list {
        tailf:cli-drop-node-name;
        tailf:cli-suppress-mode;
        tailf:cli-delete-when-empty;
        key "name";
        leaf name {
          type string;
        }
      }
    }
    list aaa-server {
      key "name";
      leaf name {
        type string;
      }
      leaf protocol {
        tailf:cli-hide-in-submode;
        type enumeration {
          enum "http-form";
          enum "kerberos";
          enum "ldap";
          enum "radius";
          enum "sdi";
          enum "tacacs+";
        }
      }
      container interim-accounting-update {
        tailf:cli-delete-when-empty;
        presence "true";
        leaf periodic {
          type uint8;
        }
      }
      leaf accounting-mode {
        type enumeration {
          enum "single";
          enum "simultaneous";
        }
      }
      container reactivation-mode {
        tailf:cli-compact-syntax;
        tailf:cli-sequence-commands {
          tailf:cli-reset-siblings;
        }
        leaf mode {
          tailf:cli-drop-node-name;
          type enumeration {
            enum "timed";
            enum "depletion";
          }
        }
        leaf deadtime {
          type uint16;
        }
      }
      leaf max-failed-attempts {
        type uint8;
      }
      container dynamic-authorization {
        tailf:cli-delete-when-empty;
        presence "true";
        leaf port {
          type uint16;
        }
      }
    }
    container aaa-server-host-conf {
      tailf:cli-drop-node-name;
      list aaa-server {
        key "name interface host";
        leaf name {
          type string;
        }
        leaf interface {
          type string;
        }
        leaf host {
          tailf:cli-expose-key-name;
          type inet:host;
        }
        leaf retry-interval {
          type uint8;
        }
        leaf timeout {
          type uint16;
        }
        leaf ldap-base-dn {
          type string;
        }
        leaf ldap-group-base-dn {
          type string;
        }
        leaf ldap-scope {
          type enumeration {
            enum "onelevel";
            enum "subtree";
          }
        }
        leaf ldap-naming-attribute {
          type string;
        }
        container ldap-login-password {
          tailf:cli-flatten-container;
          tailf:cli-compact-syntax;
          tailf:cli-sequence-commands;
          uses password-08-grouping {
            refine "secret";
          }
        }
        container ldap-over-ssl {
          leaf enable {
            type empty;
          }
        }
        leaf ldap-login-dn {
          type string;
        }
        container sasl-mechanism {
          leaf digest-md5 {
            type empty;
          }
        }
        leaf ldap-attribute-map {
          type string;
        }
        container key {
          tailf:cli-compact-syntax;
          tailf:cli-sequence-commands;
          uses password-08-grouping {
            refine "secret";
          }
        }
        leaf radius-common-pw {
          type string;
        }
        leaf server-port {
          type uint16;
        }
        leaf server-type {
          type enumeration {
            enum "auto-detect";
            enum "microsoft";
            enum "novell";
            enum "openldap";
            enum "sun";
          }
        }
        leaf group-search-timeout {
          type uint16;
        }
        leaf authentication-port {
          type uint16;
        }
        leaf accounting-port {
          type uint16;
        }
      }
    }
    container aaa {
      container authentication {
        container ssh {
          uses aaa-authentication-console-grouping;
        }
        container telnet {
          uses aaa-authentication-console-grouping;
        }
        container http {
          uses aaa-authentication-console-grouping;
        }
        container enable {
          uses aaa-authentication-console-grouping;
        }
        container serial {
          uses aaa-authentication-console-grouping;
        }
        choice login-history-choice {
          leaf login-history {
            type boolean;
          }
          container login-history-duration {
            tailf:cli-drop-node-name;
            container login-history {
              presence "true";
              leaf duration {
                type uint16;
              }
            }
          }
        }
      }
      container authorization {
        container command {
          tailf:cli-compact-syntax;
          tailf:cli-sequence-commands {
            tailf:cli-reset-siblings;
          }
          leaf server_group {
            tailf:cli-drop-node-name;
            tailf:cli-optional-in-sequence;
            tailf:code-name "aaa_server_group";
            type string;
          }
          leaf LOCAL {
            type empty;
          }
        }
        container exec {
          choice exec-choice {
            container LOCAL {
              tailf:cli-delete-when-empty;
              presence "true";
              leaf auto-enable {
                type empty;
              }
            }
            container authentication-server {
              tailf:cli-delete-when-empty;
              presence "true";
              leaf auto-enable {
                type empty;
              }
            }
          }
        }
        container http {
          leaf console {
            type union {
              type enumeration {
                enum "LOCAL";
              }
              type string;
            }
          }
        }
      }
      container accounting {
        container enable {
          uses aaa-accounting-console-grouping;
        }
        container ssh {
          uses aaa-accounting-console-grouping;
        }
        container telnet {
          uses aaa-accounting-console-grouping;
        }
        container serial {
          uses aaa-accounting-console-grouping;
        }
        container command {
          tailf:cli-compact-syntax;
          leaf privilege {
            type uint8;
          }
          leaf server_group {
            tailf:cli-drop-node-name;
            tailf:code-name "aaa_server_group";
            type string;
          }
        }
      }
    }
    list route {
      tailf:cli-suppress-mode;
      tailf:cli-delete-when-empty;
      tailf:cli-compact-syntax;
      key "id net net-mask gw";
      leaf id {
        type nameif-type;
      }
      leaf net {
        type inet:host;
      }
      leaf net-mask {
        type inet:ipv4-address;
      }
      leaf gw {
        type inet:host;
      }
      choice route-choice {
        case a {
          leaf metric {
            tailf:cli-drop-node-name;
            type uint8;
          }
          leaf track {
            type uint16;
          }
        }
        case b {
          leaf tunneled {
            type empty;
          }
        }
      }
    }
    container monitor-interface {
      list if-list {
        tailf:cli-drop-node-name;
        tailf:cli-suppress-mode;
        tailf:cli-delete-when-empty;
        key "name";
        leaf name {
          type nameif-type;
        }
        leaf status {
          tailf:cli-drop-node-name;
          type enumeration {
            enum "disable";
            enum "enable";
          }
        }
      }
      leaf service-module {
        type boolean;
      }
    }
    container icmp {
      container unreachable {
        tailf:cli-compact-syntax;
        tailf:cli-sequence-commands;
        leaf rate-limit {
          type uint8;
        }
        leaf burst-size {
          type uint8;
        }
      }
      list icmp-list {
        tailf:cli-drop-node-name;
        tailf:cli-suppress-mode;
        tailf:cli-delete-when-empty;
        key "nameif";
        leaf nameif {
          type string;
        }
        list rule {
          tailf:cli-drop-node-name;
          tailf:cli-suppress-mode;
          tailf:cli-delete-when-empty;
          ordered-by user;
          key "expr";
          leaf expr {
            tailf:cli-multi-word-key;
            type string;
          }
        }
      }
    }
    container EXEC {
      tailf:cli-drop-node-name;
    }
    list fragment {
      tailf:cli-suppress-mode;
      tailf:cli-delete-when-empty;
      key "interface";
      leaf interface {
        type nameif-type;
      }
      leaf chain {
        type uint16;
      }
      container reassembly {
        leaf full {
          type empty;
        }
      }
      leaf size {
        type uint16;
      }
      leaf timeout {
        type uint8;
      }
    }
    container crypto {
      container ca {
        container certificate {
          list chain {
            key "name";
            leaf name {
              type string;
            }
            list certificate {
              tailf:cli-delete-when-empty;
              tailf:cli-compact-syntax;
              tailf:cli-sequence-commands;
              key "serial";
              leaf serial {
                type string;
              }
              leaf cert-type {
                tailf:cli-optional-in-sequence;
                tailf:cli-drop-node-name;
                tailf:cli-prefix-key;
                type enumeration {
                  enum "ca";
                  enum "ra-encrypt";
                  enum "ra-general";
                  enum "ra-sign";
                  enum "rollover";
                  enum "self-signed";
                }
              }
              leaf rollover {
                tailf:cli-optional-in-sequence;
                tailf:cli-prefix-key;
                type empty;
              }
              leaf cert {
                tailf:cli-drop-node-name;
                type string;
              }
            }
          }
          list map {
            tailf:cli-delete-when-empty;
            tailf:cli-compact-syntax;
            tailf:cli-sequence-commands;
            key "label sequence";
            leaf label {
              type string;
            }
            leaf sequence {
              type uint16;
            }
            container subject-name {
              list attr {
                tailf:cli-suppress-mode;
                tailf:cli-delete-when-empty;
                key "name sign compare";
                leaf name {
                  type enumeration {
                    enum "c";
                    enum "cn";
                    enum "dc";
                    enum "dnq";
                    enum "ea";
                    enum "genq";
                    enum "gn";
                    enum "i";
                    enum "ip";
                    enum "l";
                    enum "n";
                    enum "o";
                    enum "ou";
                    enum "ser";
                    enum "sn";
                    enum "sp";
                    enum "t";
                    enum "uid";
                    enum "uname";
                  }
                }
                leaf sign {
                  type enumeration {
                    enum "co";
                    enum "eq";
                    enum "nc";
                    enum "ne";
                  }
                }
                leaf compare {
                  tailf:cli-multi-value;
                  type string;
                }
              }
            }
          }
        }
        container trustpool {
          container policy {
            tailf:cli-add-mode;
            presence "true";
            leaf revocation-check {
              type enumeration {
                enum "crl";
                enum "none";
                enum "ocsp";
              }
            }
            container auto-import {
              presence "true";
            }
          }
        }
        list trustpoint {
          key "id";
          leaf id {
            type string;
          }
          container revocation-check {
            tailf:cli-compact-syntax;
            leaf crl {
              type empty;
            }
            leaf ocsp {
              type empty;
            }
            leaf none {
              type empty;
            }
          }
          container enrollment {
            choice enrollment-choice {
              leaf self {
                type empty;
              }
              leaf terminal {
                type empty;
              }
              leaf url {
                type string;
              }
              container protocol {
                container scep {
                  leaf url {
                    type string;
                  }
                }
              }
            }
          }
          container match {
            list certificate {
              tailf:cli-suppress-mode;
              tailf:cli-delete-when-empty;
              tailf:cli-compact-syntax;
              tailf:cli-sequence-commands {
                tailf:cli-reset-siblings;
              }
              key "name override";
              leaf name {
                type string;
              }
              leaf override {
                tailf:cli-expose-key-name;
                type enumeration {
                  enum "cdp";
                  enum "ocsp";
                }
              }
              leaf sequence {
                tailf:cli-drop-node-name;
                type uint16;
              }
              leaf url {
                type string;
              }
            }
          }
          choice validation-usage-choice {
            leaf validation-usage {
              type boolean;
            }
            container validation-usage-conf {
              tailf:cli-drop-node-name;
              leaf-list validation-usage {
                tailf:cli-flat-list-syntax;
                type enumeration {
                  enum "ipsec-client";
                  enum "ssl-client";
                  enum "ssl-server";
                }
              }
            }
          }
          container crl {
            container configure {
              tailf:cli-add-mode;
              presence "true";
              leaf policy {
                type string;
              }
              list url {
                tailf:cli-suppress-mode;
                tailf:cli-delete-when-empty;
                key "index";
                leaf index {
                  type uint8;
                }
                leaf path {
                  tailf:cli-drop-node-name;
                  type string;
                }
              }
              leaf cache-time {
                type uint16;
              }
              container protocol {
                leaf http {
                  type boolean;
                }
                leaf ldap {
                  type boolean;
                }
                leaf scep {
                  type boolean;
                }
              }
            }
          }
          leaf fqdn {
            type union {
              type string;
              type enumeration {
                enum "none";
              }
            }
          }
          leaf email {
            type string;
          }
          leaf subject-name {
            tailf:cli-multi-value;
            type string;
          }
          leaf serial-number {
            type empty;
          }
          leaf ip-address {
            type inet:ip-address;
          }
          leaf keypair {
            type string;
          }
        }
      }
      container ipsec {
        list transform-set {
          tailf:cli-suppress-mode;
          tailf:cli-delete-when-empty;
          tailf:cli-compact-syntax;
          key "name";
          leaf name {
            type string;
          }
          leaf encryption {
            tailf:cli-drop-node-name;
            type enumeration {
              enum "esp-3des";
              enum "esp-aes";
              enum "esp-aes-192";
              enum "esp-aes-256";
              enum "esp-des";
              enum "esp-null";
            }
          }
          leaf authentication {
            tailf:cli-drop-node-name;
            type enumeration {
              enum "esp-md5-hmac";
              enum "esp-none";
              enum "esp-sha-hmac";
            }
          }
          container mode {
            leaf transport {
              type empty;
            }
          }
        }
        container ikev1 {
          list transform-set {
            tailf:cli-suppress-mode;
            tailf:cli-delete-when-empty;
            key "name";
            leaf name {
              type string;
            }
            container transform {
              tailf:cli-drop-node-name;
              tailf:cli-compact-syntax;
              leaf encryption {
                tailf:cli-drop-node-name;
                type enumeration {
                  enum "esp-3des";
                  enum "esp-aes";
                  enum "esp-aes-192";
                  enum "esp-aes-256";
                  enum "esp-des";
                  enum "esp-null";
                }
              }
              leaf authentication {
                tailf:cli-drop-node-name;
                type enumeration {
                  enum "esp-md5-hmac";
                  enum "esp-none";
                  enum "esp-sha-hmac";
                }
              }
            }
            container mode {
              leaf transport {
                type empty;
              }
            }
          }
        }
        container ikev2 {
          list ipsec-proposal {
            key "name";
            leaf name {
              type string;
            }
            container protocol {
              container esp {
                leaf-list encryption {
                  tailf:cli-flat-list-syntax;
                  type enumeration {
                    enum "3des";
                    enum "aes";
                    enum "aes-192";
                    enum "aes-256";
                    enum "aes-gcm";
                    enum "aes-gcm-192";
                    enum "aes-gcm-256";
                    enum "aes-gmac";
                    enum "aes-gmac-192";
                    enum "aes-gmac-256";
                    enum "des";
                    enum "null";
                  }
                }
                leaf-list integrity {
                  tailf:cli-flat-list-syntax;
                  type enumeration {
                    enum "md5";
                    enum "null";
                    enum "sha-1";
                    enum "sha-256";
                    enum "sha-384";
                    enum "sha-512";
                  }
                }
              }
            }
          }
        }
        list profile {
          key "name";
          leaf name {
            type string;
          }
          container set {
            container ikev1 {
              leaf transform-set {
                type string;
              }
            }
            container ikev2 {
              leaf-list ipsec-proposal {
                tailf:cli-flat-list-syntax;
                ordered-by user;
                type string;
              }
            }
            leaf pfs {
              type enumeration {
                enum "group2";
                enum "group5";
                enum "group14";
              }
            }
            container security-association {
              container lifetime {
                leaf seconds {
                  type uint32;
                }
                leaf kilobytes {
                  type union {
                    type uint32;
                    type enumeration {
                      enum "unlimited";
                    }
                  }
                }
              }
            }
          }
        }
        container security-association {
          container lifetime {
            leaf seconds {
              type uint32;
            }
            leaf kilobytes {
              type union {
                type uint32;
                type enumeration {
                  enum "unlimited";
                }
              }
            }
          }
          container replay {
            leaf disable {
              type empty;
            }
            leaf window-size {
              type enumeration {
                enum "64";
                enum "128";
                enum "256";
                enum "512";
                enum "1024";
              }
            }
          }
          leaf pmtu-aging {
            type union {
              type uint8;
              type enumeration {
                enum "infinite";
              }
            }
          }
        }
        list df-bit {
          tailf:cli-suppress-mode;
          tailf:cli-delete-when-empty;
          tailf:cli-compact-syntax;
          tailf:cli-sequence-commands {
            tailf:cli-reset-siblings;
          }
          key "name";
          leaf name {
            type nameif-type;
          }
          leaf value {
            tailf:cli-drop-node-name;
            tailf:cli-prefix-key;
            type enumeration {
              enum "clear-df";
              enum "copy-df";
              enum "set-df";
            }
          }
        }
      }
      list dynamic-map {
        tailf:cli-suppress-mode;
        tailf:cli-delete-when-empty;
        key "name seq-num";
        leaf name {
          type string;
        }
        leaf seq-num {
          type uint16;
        }
        container set {
          container pfs {
            tailf:cli-delete-when-empty;
            presence "true";
            leaf group {
              tailf:cli-drop-node-name;
              type enumeration {
                enum "group1";
                enum "group14";
                enum "group19";
                enum "group2";
                enum "group20";
                enum "group21";
                enum "group24";
                enum "group5";
              }
            }
          }
          leaf-list transform-set {
            tailf:cli-flat-list-syntax;
            ordered-by user;
            type string;
          }
          container ikev1 {
            leaf-list transform-set {
              tailf:cli-flat-list-syntax;
              ordered-by user;
              type string;
            }
          }
          container ikev2 {
            leaf-list ipsec-proposal {
              tailf:cli-flat-list-syntax;
              ordered-by user;
              type string;
            }
          }
          container security-association {
            container lifetime {
              leaf seconds {
                type uint32;
              }
              leaf kilobytes {
                type union {
                  type uint32;
                  type enumeration {
                    enum "unlimited";
                  }
                }
              }
            }
          }
          leaf reverse-route {
            type empty;
          }
        }
        container match {
          leaf address {
            type string;
          }
        }
      }
      list map {
        tailf:cli-suppress-mode;
        tailf:cli-delete-when-empty;
        key "name";
        leaf name {
          type string;
        }
        list seq-num {
          tailf:cli-drop-node-name;
          tailf:cli-suppress-mode;
          tailf:cli-delete-when-empty;
          key "seq-num";
          leaf seq-num {
            type uint16;
          }
          container match {
            leaf address {
              type string;
            }
          }
          container set {
            container pfs {
              tailf:cli-delete-when-empty;
              presence "true";
              leaf group {
                tailf:cli-drop-node-name;
                type enumeration {
                  enum "group1";
                  enum "group14";
                  enum "group19";
                  enum "group2";
                  enum "group20";
                  enum "group21";
                  enum "group24";
                  enum "group5";
                }
              }
            }
            container security-association {
              container lifetime {
                leaf seconds {
                  type uint32;
                }
                leaf kilobytes {
                  type union {
                    type uint32;
                    type enumeration {
                      enum "unlimited";
                    }
                  }
                }
              }
            }
            leaf-list peer {
              tailf:cli-flat-list-syntax;
              ordered-by user;
              type inet:host;
            }
            container ikev1 {
              leaf-list transform-set {
                tailf:cli-flat-list-syntax;
                ordered-by user;
                type string;
              }
            }
            container ikev2 {
              leaf-list ipsec-proposal {
                tailf:cli-flat-list-syntax;
                ordered-by user;
                type string;
              }
            }
            leaf-list transform-set {
              tailf:cli-flat-list-syntax;
              type string;
            }
            leaf reverse-route {
              type empty;
            }
          }
          container ipsec-isakmp {
            leaf dynamic {
              type string;
            }
          }
        }
        container interface {
          tailf:cli-flatten-container;
          tailf:cli-compact-syntax;
          uses interface-name-grouping;
        }
      }
      container ikev2 {
        list policy {
          key "priority";
          leaf priority {
            type uint16;
          }
          leaf-list encryption {
            tailf:cli-flat-list-syntax;
            type enumeration {
              enum "3des";
              enum "aes";
              enum "aes-192";
              enum "aes-256";
              enum "aes-gcm";
              enum "aes-gcm-192";
              enum "aes-gcm-256";
              enum "des";
              enum "null";
            }
          }
          leaf-list integrity {
            tailf:cli-flat-list-syntax;
            type enumeration {
              enum "md5";
              enum "sha";
              enum "sha256";
              enum "sha384";
              enum "sha512";
            }
          }
          leaf-list group {
            tailf:cli-flat-list-syntax;
            type enumeration {
              enum "1";
              enum "14";
              enum "19";
              enum "2";
              enum "20";
              enum "21";
              enum "24";
              enum "5";
            }
          }
          leaf-list prf {
            tailf:cli-flat-list-syntax;
            type enumeration {
              enum "md5";
              enum "sha";
              enum "sha256";
              enum "sha384";
              enum "sha512";
            }
          }
          container lifetime {
            leaf seconds {
              type union {
                type uint32;
                type enumeration {
                  enum "none";
                }
              }
            }
          }
        }
        list enable {
          tailf:cli-suppress-mode;
          tailf:cli-delete-when-empty;
          tailf:cli-compact-syntax;
          tailf:cli-sequence-commands {
            tailf:cli-reset-siblings;
          }
          key "name";
          leaf name {
            type nameif-type;
          }
          leaf client-services {
            type empty;
          }
          leaf port {
            type uint16;
          }
        }
        leaf redirect {
          type enumeration {
            enum "during-auth";
            enum "during-init";
          }
        }
        container remote-access {
          list trustpoint {
            tailf:cli-suppress-mode;
            tailf:cli-delete-when-empty;
            key "name";
            leaf name {
              type string;
            }
          }
        }
      }
      container ikev1 {
        list policy {
          key "priority";
          leaf priority {
            type uint16;
          }
          leaf authentication {
            type enumeration {
              enum "crack";
              enum "pre-share";
              enum "rsa-sig";
            }
          }
          leaf encryption {
            type enumeration {
              enum "3des";
              enum "aes";
              enum "aes-192";
              enum "aes-256";
              enum "des";
            }
          }
          leaf hash {
            type enumeration {
              enum "md5";
              enum "sha";
            }
          }
          leaf group {
            type enumeration {
              enum "1";
              enum "2";
              enum "5";
              enum "7";
              enum "14";
            }
          }
          leaf lifetime {
            type union {
              type uint32;
              type enumeration {
                enum "none";
              }
            }
          }
        }
        list enable {
          tailf:cli-suppress-mode;
          tailf:cli-delete-when-empty;
          tailf:cli-compact-syntax;
          tailf:cli-sequence-commands {
            tailf:cli-reset-siblings;
          }
          key "name";
          leaf name {
            type nameif-type;
          }
        }
      }
      container isakmp {
        list enable {
          tailf:cli-suppress-mode;
          tailf:cli-delete-when-empty;
          key "interface";
          leaf interface {
            type nameif-type;
          }
        }
        list policy {
          key "id";
          leaf id {
            type uint16;
          }
          leaf authentication {
            type enumeration {
              enum "crack";
              enum "pre-share";
              enum "rsa-sig";
            }
          }
          leaf encryption {
            type enumeration {
              enum "3des";
              enum "aes";
              enum "aes-192";
              enum "aes-256";
              enum "des";
            }
          }
          leaf hash {
            type enumeration {
              enum "md5";
              enum "sha";
            }
          }
          leaf group {
            type enumeration {
              enum "1";
              enum "2";
              enum "5";
              enum "7";
            }
          }
          leaf lifetime {
            type union {
              type uint32;
              type enumeration {
                enum "none";
              }
            }
          }
        }
        container identity {
          choice identity-choice {
            leaf address {
              type empty;
            }
            leaf auto {
              type empty;
            }
            leaf hostname {
              type empty;
            }
            leaf key-id {
              type string;
            }
          }
        }
        choice nat-traversal-choice {
          container nat-traversal-enable {
            tailf:cli-drop-node-name;
            leaf nat-traversal {
              type boolean;
            }
          }
          leaf nat-traversal {
            type uint16;
          }
        }
        container ipsec-over-tcp {
          leaf port {
            type uint16;
          }
        }
      }
    }
    list track {
      tailf:cli-suppress-mode;
      tailf:cli-delete-when-empty;
      tailf:cli-compact-syntax;
      tailf:cli-sequence-commands;
      key "id";
      leaf id {
        tailf:cli-suppress-range;
        type uint16;
      }
      leaf rtr {
        type uint32;
      }
      leaf reachability {
        type empty;
      }
    }
    container bgp-community {
      leaf new-format {
        type empty;
      }
    }
    container as-path {
      list access-list {
        tailf:cli-suppress-mode;
        tailf:cli-delete-when-empty;
        key "id";
        leaf id {
          tailf:cli-suppress-range;
          type uint16;
        }
        list rule {
          tailf:cli-drop-node-name;
          tailf:cli-suppress-mode;
          tailf:cli-delete-when-empty;
          tailf:cli-compact-syntax;
          tailf:cli-sequence-commands {
            tailf:cli-reset-siblings;
          }
          ordered-by user;
          key "id";
          leaf id {
            type string;
          }
        }
      }
    }
    leaf multicast-routing {
      type empty;
    }
    container router {
      container rip {
        tailf:cli-add-mode;
        tailf:cli-delete-when-empty;
        presence "true";
        uses router-rip-grouping;
      }
      list ospf {
        key "id";
        leaf id {
          tailf:cli-suppress-range;
          type uint16;
        }
        uses router-ospf-grouping;
      }
      list bgp {
        key "as-no";
        leaf as-no {
          tailf:cli-suppress-range;
          type bgp-as-no-type;
        }
        uses router-bgp-grouping;
        container address-family {
          container ipv4 {
            container unicast {
              tailf:cli-add-mode;
              tailf:cli-delete-when-empty;
              presence "true";
              uses router-bgp-af-grouping;
            }
          }
          container ipv6 {
            container unicast {
              tailf:cli-add-mode;
              tailf:cli-delete-when-empty;
              presence "true";
              uses router-bgp-af-grouping;
            }
          }
        }
      }
      list eigrp {
        key "as-no";
        leaf as-no {
          tailf:cli-suppress-range;
          type eigrp-as-no-type;
        }
      }
    }
    container snmp {
      container cpu {
        container threshold {
          container rising {
            tailf:cli-compact-syntax;
            tailf:cli-sequence-commands;
            leaf threshold-value {
              tailf:cli-drop-node-name;
              type string;
            }
            leaf monitoring-period {
              tailf:cli-drop-node-name;
              type uint8;
            }
          }
        }
      }
    }
    container smtp-server {
      leaf address {
        tailf:cli-drop-node-name;
        type inet:host;
      }
    }
    container snmp-server {
      container community {
        tailf:cli-compact-syntax;
        tailf:cli-sequence-commands;
        uses password-08-grouping {
          refine "secret";
        }
      }
      leaf contact {
        tailf:cli-multi-value;
        type string;
      }
      container enable-conf {
        tailf:cli-drop-node-name;
        leaf enable {
          type boolean;
        }
      }
      container enable {
        list traps {
          tailf:cli-suppress-mode;
          tailf:cli-delete-when-empty;
          ordered-by user;
          key "name";
          leaf name {
            tailf:cli-multi-word-key;
            type string;
          }
        }
      }
      list group {
        tailf:cli-suppress-mode;
        tailf:cli-delete-when-empty;
        tailf:cli-compact-syntax;
        tailf:cli-sequence-commands;
        key "id";
        leaf id {
          type string;
        }
        leaf v3 {
          type empty;
        }
        leaf security-level {
          tailf:cli-drop-node-name;
          type enumeration {
            enum "auth";
            enum "noauth";
            enum "priv";
          }
        }
      }
      list user {
        tailf:cli-suppress-mode;
        tailf:cli-delete-when-empty;
        tailf:cli-compact-syntax;
        tailf:cli-sequence-commands {
          tailf:cli-reset-siblings;
        }
        key "name";
        leaf name {
          type string;
        }
        leaf groupname {
          tailf:cli-drop-node-name;
          type string;
        }
        leaf v3 {
          type empty;
        }
        leaf engineID {
          tailf:cli-optional-in-sequence;
          type string;
        }
        leaf encrypted {
          tailf:cli-optional-in-sequence;
          type empty;
        }
        leaf auth {
          type enumeration {
            enum "md5";
            enum "sha";
          }
        }
        leaf auth-password {
          tailf:cli-drop-node-name;
          type string;
        }
        leaf priv {
          type enumeration {
            enum "3des";
            enum "aes";
            enum "des";
          }
        }
        leaf bits {
          tailf:cli-drop-node-name;
          type enumeration {
            enum "128";
            enum "192";
            enum "256";
          }
        }
        leaf password {
          tailf:cli-drop-node-name;
          type string;
        }
      }
      list host-group {
        tailf:cli-suppress-mode;
        tailf:cli-delete-when-empty;
        tailf:cli-compact-syntax;
        tailf:cli-sequence-commands;
        key "interface object";
        leaf interface {
          type nameif-type;
        }
        leaf object {
          type string;
        }
        uses snmp-server-host-grouping;
      }
      list host {
        tailf:cli-suppress-mode;
        tailf:cli-delete-when-empty;
        tailf:cli-compact-syntax;
        tailf:cli-sequence-commands;
        key "interface ip-address";
        leaf interface {
          type nameif-type;
        }
        leaf ip-address {
          type host-type;
        }
        uses snmp-server-host-grouping;
      }
      leaf location {
        tailf:cli-multi-value;
        type string;
      }
    }
    container sla {
      container monitor {
        list entry {
          tailf:cli-drop-node-name;
          tailf:cli-delete-when-empty;
          key "number";
          leaf number {
            tailf:cli-suppress-range;
            type uint32;
          }
          container type {
            container echo {
              container protocol {
                tailf:cli-compact-syntax;
                tailf:cli-sequence-commands;
                leaf ipIcmpEcho {
                  type empty;
                }
                leaf hostname {
                  tailf:cli-drop-node-name;
                  type inet:host;
                }
                leaf interface {
                  type nameif-type;
                }
              }
            }
          }
          leaf num-packets {
            type uint8;
          }
          leaf request-data-size {
            type uint16;
          }
          leaf tos {
            type uint8;
          }
          leaf timeout {
            type uint32;
          }
          leaf threshold {
            type uint32;
          }
          leaf frequency {
            type uint32;
          }
        }
        list schedule {
          tailf:cli-suppress-mode;
          tailf:cli-compact-syntax;
          tailf:cli-delete-when-empty;
          key "number";
          leaf number {
            tailf:cli-suppress-range;
            type uint32;
          }
          leaf life {
            type union {
              type enumeration {
                enum "forever";
              }
              type uint32;
            }
          }
          container start-time {
            tailf:cli-flatten-container;
            tailf:cli-compact-syntax;
            choice start-time-choice {
              leaf after {
                type string;
              }
              leaf now {
                type empty;
              }
              leaf pending {
                type empty;
              }
              container hhmmss {
                tailf:cli-drop-node-name;
                tailf:cli-flatten-container;
                tailf:cli-compact-syntax;
                tailf:cli-sequence-commands;
                leaf hhmmss {
                  tailf:cli-drop-node-name;
                  type hhmmss-type;
                }
                leaf day-of-month {
                  tailf:cli-drop-node-name;
                  tailf:cli-break-sequence-commands;
                  type uint8;
                }
                leaf month {
                  tailf:cli-drop-node-name;
                  type string;
                }
              }
            }
          }
          leaf ageout {
            type uint32;
          }
          leaf recurring {
            type empty;
          }
        }
      }
    }
    container sysopt {
      list noproxyarp {
        tailf:cli-suppress-mode;
        tailf:cli-delete-when-empty;
        key "name";
        leaf name {
          type nameif-type;
        }
      }
      container traffic {
        leaf detailed-statistics {
          type empty;
        }
      }
      container connection {
        leaf preserve-vpn-flows {
          type empty;
        }
        leaf tcpmss {
          type uint16;
        }
        container tcpmss-minimum {
          tailf:cli-drop-node-name;
          container tcpmss {
            leaf minimum {
              type uint16;
            }
          }
        }
        leaf timewait {
          type empty;
        }
        leaf permit-vpn {
          type boolean;
        }
        leaf reclassify-vpn {
          type boolean;
        }
      }
      container radius {
        leaf ignore-secret {
          type empty;
        }
      }
    }
    container auth-prompt {
      leaf prompt {
        tailf:cli-multi-value;
        type string;
      }
      leaf accept {
        tailf:cli-multi-value;
        type string;
      }
      leaf reject {
        tailf:cli-multi-value;
        type string;
      }
    }
    container arp {
      list entry {
        tailf:cli-drop-node-name;
        tailf:cli-suppress-mode;
        tailf:cli-delete-when-empty;
        tailf:cli-compact-syntax;
        tailf:cli-sequence-commands {
          tailf:cli-reset-siblings;
        }
        key "name";
        leaf name {
          type nameif-type;
        }
        leaf ip_address {
          tailf:cli-drop-node-name;
          tailf:code-name "ipv4_address";
          type inet:host;
        }
        leaf mac_address {
          tailf:cli-drop-node-name;
          tailf:code-name "arp_mac_address";
          type string;
        }
        leaf alias {
          type empty;
        }
      }
      leaf timeout {
        type uint32;
      }
      leaf rate-limit {
        type uint16;
      }
      leaf permit-nonconnected {
        type boolean;
      }
    }
    container dns {
      tailf:cli-case-insensitive;
      list domain-lookup {
        tailf:cli-suppress-mode;
        tailf:cli-delete-when-empty;
        key "name";
        leaf name {
          type nameif-type;
        }
      }
      list server-group {
        key "name";
        leaf name {
          type string;
        }
        leaf-list name-server {
          type inet:host;
        }
        leaf domain-name {
          type string;
        }
      }
    }
    leaf-list prompt {
      tailf:cli-flat-list-syntax;
      ordered-by user;
      type enumeration {
        enum "hostname";
        enum "domain";
        enum "context";
        enum "cluster-unit";
        enum "management-mode";
        enum "priority";
        enum "state";
      }
    }
    container jumbo-frame {
      leaf reservation {
        type empty;
      }
    }
    container console {
      leaf serial {
        type empty;
      }
      leaf timeout {
        type uint8;
      }
    }
    container ssl {
      container cipher {
        container default {
          uses cipher-grouping;
        }
        container dtlsv1 {
          uses cipher-grouping;
        }
        container sslv3 {
          uses cipher-grouping;
        }
        container tlsv1 {
          uses cipher-grouping;
        }
        container tlsv1.1 {
          uses cipher-grouping;
        }
        container tlsv1.2 {
          uses cipher-grouping;
        }
      }
      container server-version {
        tailf:cli-compact-syntax;
        tailf:cli-sequence-commands {
          tailf:cli-reset-siblings;
        }
        leaf tls-version {
          tailf:cli-drop-node-name;
          type tls-version-type;
        }
        leaf dtls-version {
          tailf:cli-drop-node-name;
          type enumeration {
            enum "dtlsv1";
            enum "dtlsv1.2";
          }
        }
      }
      leaf client-version {
        type tls-version-type;
      }
      leaf trust-point {
        type string;
      }
      container trust-point-list {
        tailf:cli-drop-node-name;
        list trust-point {
          tailf:cli-suppress-mode;
          tailf:cli-delete-when-empty;
          tailf:cli-compact-syntax;
          tailf:cli-sequence-commands;
          key "interface";
          leaf interface {
            type nameif-type;
          }
          leaf name {
            tailf:cli-drop-node-name;
            tailf:cli-prefix-key;
            type string;
          }
        }
      }
      leaf-list encryption {
        tailf:cli-flat-list-syntax;
        ordered-by user;
        type enumeration {
          enum "3des-sha1";
          enum "aes128-sha1";
          enum "aes256-sha1";
          enum "des-sha1";
          enum "dhe-aes128-sha1";
          enum "dhe-aes256-sha1";
          enum "null-sha1";
          enum "rc4-md5";
          enum "rc4-sha1";
        }
      }
    }
    container webvpn {
      tailf:cli-add-mode;
      list enable {
        tailf:cli-suppress-mode;
        tailf:cli-delete-when-empty;
        key "name";
        leaf name {
          type nameif-type;
        }
      }
      container svc {
        list image {
          tailf:cli-suppress-mode;
          tailf:cli-delete-when-empty;
          key "name";
          leaf name {
            type string;
          }
          leaf order {
            tailf:cli-drop-node-name;
            type uint16;
          }
        }
        leaf enable {
          type empty;
        }
      }
      container hostscan {
        leaf image {
          type string;
        }
        leaf enable {
          type empty;
        }
      }
      container anyconnect-essentials {
        presence "true";
      }
      list anyconnect-custom-attr {
        tailf:cli-suppress-mode;
        tailf:cli-delete-when-empty;
        key "name";
        leaf name {
          type string;
        }
        leaf description {
          type string;
        }
      }
      container hsts {
        tailf:cli-add-mode;
        presence "true";
        leaf enable {
          type empty;
        }
        leaf max-age {
          type uint32;
        }
        leaf include-sub-domains {
          type empty;
        }
        leaf preload {
          type boolean;
        }
      }
      container http-headers {
        tailf:cli-add-mode;
        presence "true";
        leaf x-content-type-options {
          type empty;
        }
      }
      container anyconnect {
        leaf enable {
          type empty;
        }
        list image {
          tailf:cli-suppress-mode;
          tailf:cli-delete-when-empty;
          key "name";
          leaf name {
            tailf:cli-multi-word-key;
            type string;
          }
        }
        list profiles {
          tailf:cli-suppress-mode;
          tailf:cli-delete-when-empty;
          key "name option";
          leaf name {
            type string;
          }
          leaf option {
            type string;
          }
        }
      }
      container saml {
        list idp {
          key "name";
          leaf name {
            type string;
          }
          container url {
            leaf sign-in {
              type string;
            }
            leaf sign-out {
              type string;
            }
          }
          leaf base-url {
            type string;
          }
          container trustpoint {
            leaf idp {
              type string;
            }
            leaf sp {
              type string;
            }
          }
          leaf signature {
            type enumeration {
              enum "rsa-sha1";
              enum "rsa-sha256";
              enum "rsa-sha384";
              enum "rsa-sha512";
            }
          }
          container force {
            leaf re-authentication {
              type boolean;
            }
          }
        }
      }
      leaf tunnel-group-list {
        type string;
      }
      leaf tunnel-group-preference {
        type enumeration {
          enum "group-url";
        }
      }
      container cache {
        tailf:cli-add-mode;
        leaf disable {
          type boolean;
        }
      }
      list certificate-group-map {
        tailf:cli-suppress-mode;
        tailf:cli-delete-when-empty;
        key "ca sequence tunnel";
        leaf ca {
          type string;
        }
        leaf sequence {
          type uint16;
        }
        leaf tunnel {
          type string;
        }
      }
      container error-recovery {
        leaf disable {
          type boolean;
        }
      }
    }
    list anyconnect-custom-data {
      tailf:cli-suppress-mode;
      tailf:cli-delete-when-empty;
      tailf:cli-compact-syntax;
      key "name";
      leaf name {
        type string;
      }
      list attr-name {
        tailf:cli-drop-node-name;
        tailf:cli-suppress-mode;
        tailf:cli-delete-when-empty;
        key "name";
        leaf name {
          type string;
        }
        leaf-list attr-value {
          tailf:cli-drop-node-name;
          type string;
        }
      }
    }
    container group-policy {
      list group-policy-internal {
        tailf:cli-drop-node-name;
        tailf:cli-suppress-mode;
        tailf:cli-delete-when-empty;
        key "name";
        leaf name {
          type string;
        }
        leaf internal {
          type empty;
        }
      }
      list group-policy-attributes {
        tailf:cli-drop-node-name;
        tailf:cli-sequence-commands;
        key "name";
        leaf name {
          type string;
        }
        leaf attributes {
          tailf:cli-hide-in-submode;
          type empty;
        }
        container banner {
          tailf:cli-break-sequence-commands;
          choice banner-choice {
            leaf none {
              type empty;
            }
            leaf value {
              type string;
            }
          }
        }
        container group-lock {
          choice group-lock-choice {
            leaf none {
              type empty;
            }
            leaf value {
              type string;
            }
          }
        }
        leaf user-authentication {
          type enumeration {
            enum "disable";
            enum "enable";
          }
        }
        container address-pools {
          choice address-pools-choice {
            leaf none {
              type empty;
            }
            leaf-list value {
              tailf:cli-flat-list-syntax;
              type string;
            }
          }
        }
        leaf split-tunnel-policy {
          type enumeration {
            enum "excludespecified";
            enum "tunnelall";
            enum "tunnelspecified";
          }
        }
        container split-tunnel-network-list {
          choice split-tunnel-network-list-choice {
            leaf none {
              type empty;
            }
            leaf value {
              type string;
            }
          }
        }
        container default-domain {
          choice default-domain-choice {
            leaf none {
              type empty;
            }
            leaf value {
              type string;
            }
          }
        }
        container vpn-filter {
          choice vpn-filter-choice {
            leaf none {
              type empty;
            }
            leaf value {
              type string;
            }
          }
        }
        container wins-server {
          choice wins-server-choice {
            leaf none {
              type empty;
            }
            leaf-list value {
              tailf:cli-flat-list-syntax;
              ordered-by user;
              type inet:ip-address;
            }
          }
        }
        container dns-server {
          choice dns-server-choice {
            leaf none {
              type empty;
            }
            leaf-list value {
              tailf:cli-flat-list-syntax;
              ordered-by user;
              type union {
                type inet:ip-address;
                type inet:ipv6-address;
              }
            }
          }
        }
        leaf pfs {
          type enumeration {
            enum "disable";
            enum "enable";
          }
        }
        leaf-list vpn-tunnel-protocol {
          tailf:cli-flat-list-syntax;
          type enumeration {
            enum "IPSec";
            enum "ikev1";
            enum "ikev2";
            enum "l2tp-ipsec";
            enum "ssl-client";
            enum "ssl-clientless";
            enum "svc";
            enum "webvpn";
          }
        }
        container split-dns {
          leaf-list value {
            tailf:cli-flat-list-syntax;
            type string;
          }
        }
        leaf vpn-simultaneous-logins {
          type uint32;
        }
        container vpn-idle-timeout {
          leaf minutes {
            tailf:cli-drop-node-name;
            type uint32;
          }
        }
        container vpn-session-timeout {
          leaf minutes {
            tailf:cli-drop-node-name;
            type uint32;
          }
          leaf alert-interval {
            type union {
              type enumeration {
                enum "none";
              }
              type uint8;
            }
          }
        }
        container msie-proxy {
          container server {
            choice service-choice {
              leaf none {
                type empty;
              }
              leaf value {
                type string;
              }
            }
          }
          container pac-url {
            choice pac-url-choice {
              leaf none {
                type empty;
              }
              leaf value {
                type string;
              }
            }
          }
          leaf lockdown {
            type enumeration {
              enum "disable";
              enum "enable";
            }
          }
          leaf method {
            type enumeration {
              enum "auto-detect";
              enum "no-modify";
              enum "no-proxy";
              enum "none";
              enum "use-pac";
              enum "use-server";
            }
          }
          container except-list {
            choice except-list-choice {
              leaf none {
                type empty;
              }
              leaf value {
                type string;
              }
            }
          }
        }
        leaf split-tunnel-all-dns {
          type enumeration {
            enum "disable";
            enum "enable";
          }
        }
        leaf smartcard-removal-disconnect {
          type enumeration {
            enum "enable";
            enum "disable";
          }
        }
        list anyconnect-custom {
          tailf:cli-suppress-mode;
          tailf:cli-delete-when-empty;
          key "name";
          leaf name {
            type string;
          }
          choice none-or-value {
            leaf none {
              type empty;
            }
            leaf value {
              type string;
            }
          }
        }
        container webvpn {
          tailf:cli-add-mode;
          container url-list {
            choice none-or-value {
              leaf none {
                type empty;
              }
              leaf value {
                type string;
              }
            }
          }
          container customization {
            choice customization-choice {
              leaf none {
                type empty;
              }
              leaf value {
                type enumeration {
                  enum "DfltCustomization";
                }
              }
            }
          }
          container anyconnect {
            container ssl {
              leaf dtls {
                type enumeration {
                  enum "none";
                  enum "enable";
                }
              }
              leaf keepalive {
                type union {
                  type uint16;
                  type enumeration {
                    enum "none";
                  }
                }
              }
              container rekey {
                leaf time {
                  type union {
                    type uint16;
                    type enumeration {
                      enum "none";
                    }
                  }
                }
                leaf method {
                  type enumeration {
                    enum "none";
                    enum "new-tunnel";
                    enum "ssl";
                  }
                }
              }
              leaf df-bit-ignore {
                type enumeration {
                  enum "disable";
                  enum "enable";
                }
              }
            }
            container dtls {
              leaf compression {
                type enumeration {
                  enum "none";
                  enum "lzs";
                }
              }
            }
            container dpd-interval {
              leaf client {
                type union {
                  type uint16;
                  type enumeration {
                    enum "none";
                  }
                }
              }
              leaf gateway {
                type union {
                  type uint16;
                  type enumeration {
                    enum "none";
                  }
                }
              }
            }
            container ask {
              tailf:cli-compact-syntax;
              tailf:cli-sequence-commands {
                tailf:cli-reset-all-siblings;
              }
              leaf enable-none {
                tailf:cli-drop-node-name;
                type enumeration {
                  enum "enable";
                  enum "none";
                }
              }
              leaf default {
                type enumeration {
                  enum "anyconnect";
                  enum "webvpn";
                  enum "svc";
                }
              }
              leaf timeout {
                type uint8;
              }
            }
            container modules {
              choice modules-choice {
                leaf none {
                  type empty;
                }
                leaf value {
                  type string;
                }
              }
            }
            container profiles {
              choice profiles-choice {
                leaf none {
                  type empty;
                }
                container value {
                  tailf:cli-compact-syntax;
                  tailf:cli-sequence-commands {
                    tailf:cli-reset-siblings;
                  }
                  leaf name {
                    tailf:cli-drop-node-name;
                    type string;
                  }
                  leaf type {
                    type string;
                  }
                }
              }
            }
            leaf mtu {
              type uint16;
            }
          }
          container svc {
            leaf dtls {
              type enumeration {
                enum "enable";
                enum "none";
              }
            }
          }
        }
      }
    }
    container wccp {
      leaf web-cache {
        type empty;
      }
      list wccp-list {
        tailf:cli-drop-node-name;
        tailf:cli-suppress-mode;
        tailf:cli-delete-when-empty;
        tailf:cli-compact-syntax;
        key "id";
        leaf id {
          type uint8;
        }
        leaf redirect-list {
          type string;
        }
        container password {
          tailf:cli-compact-syntax;
          tailf:cli-sequence-commands;
          uses password-08-grouping {
            refine "secret";
          }
        }
        leaf group-list {
          type string;
        }
      }
      list interface {
        tailf:cli-suppress-mode;
        tailf:cli-delete-when-empty;
        tailf:cli-compact-syntax;
        tailf:cli-sequence-commands;
        key "interface name";
        leaf interface {
          type nameif-type;
        }
        leaf name {
          type union {
            type enumeration {
              enum "web-cache";
            }
            type uint8;
          }
        }
        leaf redirect {
          type enumeration {
            enum "in";
          }
        }
      }
    }
    container tunnel-group {
      list tunnel-group-list {
        tailf:cli-drop-node-name;
        tailf:cli-suppress-mode;
        tailf:cli-delete-when-empty;
        key "name";
        leaf name {
          type string;
        }
        leaf type {
          type enumeration {
            enum "ipsec-l2l";
            enum "ipsec-ra";
            enum "remote-access";
            enum "webvpn";
          }
        }
      }
      list tunnel-group-general-attributes {
        tailf:cli-drop-node-name;
        tailf:cli-sequence-commands;
        key "name";
        leaf name {
          type string;
        }
        leaf general-attributes {
          tailf:cli-hide-in-submode;
          type empty;
        }
        container address-pool-interface {
          tailf:cli-break-sequence-commands;
          tailf:cli-drop-node-name;
          list address-pool {
            tailf:cli-suppress-mode;
            tailf:cli-delete-when-empty;
            key "name";
            leaf name {
              type nameif-type;
            }
            leaf address-pool {
              tailf:cli-drop-node-name;
              type string;
            }
          }
        }
        leaf address-pool {
          type string;
        }
        leaf authorization-server-group {
          type string;
        }
        leaf accounting-server-group {
          type string;
        }
        leaf authentication-server-group {
          type string;
        }
        container secondary-authentication-server-group {
          tailf:cli-compact-syntax;
          tailf:cli-sequence-commands {
            tailf:cli-reset-siblings;
          }
          leaf name {
            tailf:cli-drop-node-name;
            type string;
          }
          leaf LOCAL {
            tailf:cli-optional-in-sequence;
            type empty;
          }
          leaf use-primary-username {
            type empty;
          }
        }
        leaf authentication-attr-from-server {
          type enumeration {
            enum "primary";
            enum "secondary";
          }
        }
        leaf authenticated-session-username {
          type enumeration {
            enum "primary";
            enum "secondary";
          }
        }
        list dhcp-server {
          tailf:cli-suppress-mode;
          tailf:cli-delete-when-empty;
          ordered-by user;
          key "address";
          leaf selection {
            tailf:cli-drop-node-name;
            tailf:cli-prefix-key;
            type enumeration {
              enum "link-selection";
              enum "subnet-selection";
            }
          }
          leaf address {
            type inet:host;
          }
        }
        leaf strip-realm {
          type empty;
        }
        leaf authorization-required {
          type empty;
        }
        leaf default-group-policy {
          type string;
        }
        container username-from-certificate {
          tailf:cli-compact-syntax;
          tailf:cli-sequence-commands {
            tailf:cli-reset-siblings;
          }
          choice username-choice {
            leaf use-entire-name {
              type empty;
            }
            leaf use-script {
              type empty;
            }
            case attr {
              leaf primary-attr {
                tailf:cli-drop-node-name;
                type attribute-type;
              }
              leaf second-attr {
                tailf:cli-drop-node-name;
                type attribute-type;
              }
            }
          }
        }
      }
      list tunnel-group-webvpn-attributes {
        tailf:cli-drop-node-name;
        key "name";
        leaf name {
          type string;
        }
        leaf webvpn-attributes {
          tailf:cli-hide-in-submode;
          type empty;
        }
        leaf-list authentication {
          tailf:cli-flat-list-syntax;
          type enumeration {
            enum "aaa";
            enum "certificate";
            enum "multiple-certificate";
            enum "saml";
          }
        }
        leaf radius-reject-message {
          type empty;
        }
        list group-alias {
          tailf:cli-suppress-mode;
          tailf:cli-delete-when-empty;
          tailf:cli-compact-syntax;
          key "name";
          leaf name {
            type string;
          }
          leaf status {
            tailf:cli-drop-node-name;
            type enumeration {
              enum "disable";
              enum "enable";
            }
          }
        }
        list group-url {
          tailf:cli-suppress-mode;
          tailf:cli-delete-when-empty;
          key "name";
          leaf name {
            type string;
          }
          leaf status {
            tailf:cli-drop-node-name;
            type enumeration {
              enum "disable";
              enum "enable";
            }
          }
        }
        container without-csd {
          tailf:cli-delete-when-empty;
          presence "true";
          leaf anyconnect {
            type empty;
          }
        }
        container saml {
          leaf identity-provider {
            type string;
          }
        }
      }
      list tunnel-group-ipsec-attributes-list {
        tailf:cli-drop-node-name;
        key "name";
        leaf name {
          type string;
        }
        leaf ipsec-attributes {
          tailf:cli-hide-in-submode;
          type empty;
        }
        container ikev1 {
          container pre-shared-key {
            tailf:cli-compact-syntax;
            tailf:cli-sequence-commands;
            uses password-08-grouping {
              refine "secret";
            }
          }
          container user-authentication {
            tailf:cli-compact-syntax;
            leaf type {
              tailf:cli-drop-node-name;
              type enumeration {
                enum "hybrid";
                enum "none";
                enum "xauth";
              }
            }
          }
          leaf trust-point {
            type string;
          }
        }
        container ikev2 {
          container local-authentication {
            container pre-shared-key {
              tailf:cli-compact-syntax;
              tailf:cli-sequence-commands;
              uses password-08-grouping {
                refine "secret";
              }
            }
          }
          container remote-authentication {
            container pre-shared-key {
              tailf:cli-compact-syntax;
              tailf:cli-sequence-commands;
              uses password-08-grouping {
                refine "secret";
              }
            }
          }
        }
        container isakmp {
          container keepalive {
            presence "true";
            leaf disable {
              type empty;
            }
          }
        }
        leaf peer-id-validate {
          type enumeration {
            enum "cert";
            enum "nocheck";
            enum "req";
          }
        }
        leaf pre-shared-key {
          type string;
        }
        leaf chain {
          type empty;
        }
      }
      list tunnel-group-ppp-attributes {
        tailf:cli-drop-node-name;
        tailf:cli-delete-when-empty;
        key "name";
        leaf name {
          type string;
        }
        leaf ppp-attributes {
          tailf:cli-hide-in-submode;
          type empty;
        }
        container authentication {
          leaf chap {
            type boolean;
          }
          leaf pap {
            type empty;
          }
          leaf ms-chap-v1 {
            type boolean;
          }
          leaf ms-chap-v2 {
            type empty;
          }
          leaf eap-proxy {
            type empty;
          }
        }
      }
    }
    container tunnel-group-map {
      container enable {
        leaf ou {
          type boolean;
        }
        leaf ike-id {
          type boolean;
        }
        leaf peer-ip {
          type boolean;
        }
        leaf rules {
          type empty;
        }
      }
      list tunnel-group-map-list {
        tailf:cli-drop-node-name;
        tailf:cli-suppress-mode;
        tailf:cli-delete-when-empty;
        key "ca sequence";
        leaf ca {
          type string;
        }
        leaf sequence {
          type uint16;
        }
        leaf tunnel {
          tailf:cli-drop-node-name;
          type string;
        }
      }
    }
    container vpn {
      container load-balancing {
        tailf:cli-add-mode;
        tailf:cli-delete-when-empty;
        presence "true";
        leaf nat {
          type string;
        }
        leaf redirect-fqdn {
          type enumeration {
            enum "disable";
            enum "enable";
          }
        }
        leaf priority {
          type uint8;
        }
        container interface {
          leaf lbprivate {
            type nameif-type;
          }
          leaf lbpublic {
            type nameif-type;
          }
        }
        container cluster {
          container key {
            tailf:cli-compact-syntax;
            tailf:cli-sequence-commands;
            uses password-08-grouping {
              refine "type";
              refine "secret";
            }
          }
          container ip {
            leaf address {
              type string;
            }
          }
          leaf encryption {
            type empty;
          }
          leaf port {
            type uint16;
          }
        }
        leaf participate {
          type empty;
        }
      }
    }
    container management-access {
      uses interface-name-grouping;
    }
    container vpn-sessiondb {
      leaf max-anyconnect-premium-or-essentials-limit {
        type uint16;
      }
    }
    container license {
      container smart {
        tailf:cli-add-mode;
        container feature {
          container tier {
            leaf standard {
              type empty;
            }
          }
          leaf context {
            type uint8;
          }
          leaf strong-encryption {
            type empty;
          }
        }
        container throughput {
          leaf level {
            type enumeration {
              enum "100m";
              enum "1G";
              enum "2G";
              enum "10G";
            }
          }
        }
      }
    }
    container timeout {
      leaf conn {
        type hhmmss-type;
      }
      leaf conn-holddown {
        type hhmmss-type;
      }
      leaf floating-conn {
        type hhmmss-type;
      }
      leaf h225 {
        type hhmmss-type;
      }
      leaf h323 {
        type hhmmss-type;
      }
      leaf half-closed {
        type hhmmss-type;
      }
      leaf sctp {
        type hhmmss-type;
      }
      leaf icmp {
        type hhmmss-type;
      }
      leaf mgcp {
        type hhmmss-type;
      }
      leaf mgcp-pat {
        type hhmmss-type;
      }
      leaf pat-xlate {
        type hhmmss-type;
      }
      leaf sip {
        type hhmmss-type;
      }
      leaf sip-disconnect {
        type hhmmss-type;
      }
      leaf sip-invite {
        type hhmmss-type;
      }
      leaf sip-provisional-media {
        type hhmmss-type;
      }
      leaf sip_media {
        type hhmmss-type;
      }
      leaf sunrpc {
        type hhmmss-type;
      }
      leaf tcp-proxy-reassembly {
        type hhmmss-type;
      }
      container uauth {
        tailf:cli-compact-syntax;
        tailf:cli-sequence-commands {
          tailf:cli-reset-all-siblings;
        }
        leaf value {
          tailf:cli-drop-node-name;
          type hhmmss-type;
        }
        leaf absolute {
          type empty;
        }
      }
      container igp {
        leaf stale-route {
          type hhmmss-type;
        }
      }
      leaf udp {
        type hhmmss-type;
      }
      leaf xlate {
        type hhmmss-type;
      }
    }
    container ldap {
      list attribute-map {
        key "name";
        leaf name {
          type string;
        }
        list map-name {
          tailf:cli-suppress-mode;
          tailf:cli-delete-when-empty;
          tailf:code-name "ldap_map_name";
          key "name";
          leaf name {
            type string;
          }
          leaf cisco-name {
            tailf:cli-drop-node-name;
            type string;
          }
        }
        list map-value {
          tailf:cli-suppress-mode;
          tailf:cli-delete-when-empty;
          tailf:cli-compact-syntax;
          tailf:cli-sequence-commands;
          key "name value";
          leaf name {
            type string;
          }
          leaf value {
            type string;
          }
          leaf cisco-value {
            tailf:cli-drop-node-name;
            type string;
          }
        }
      }
    }
    container loopback-proxy {
      leaf server {
        type boolean;
      }
      container client {
        leaf syslog {
          type boolean;
        }
      }
    }
    container tls-proxy {
      leaf maximum-session {
        type uint32;
      }
    }
    leaf xxyyzz-fail-last {
      type empty;
    }
  }

  leaf admin-context {
    type string;
  }
  list context {
    key "name";
    leaf name {
      type string;
    }
    leaf description {
      tailf:cli-multi-value;
      type string;
    }
    list allocate-interface {
      tailf:cli-suppress-mode;
      tailf:cli-delete-when-empty;
      tailf:cli-compact-syntax;
      key "name";
      leaf name {
        type string;
      }
      leaf map_name {
        tailf:cli-drop-node-name;
        type string;
      }
      leaf flag {
        tailf:cli-drop-node-name;
        type enumeration {
          enum "invisible";
          enum "visible";
        }
      }
    }
    container storage-url {
      container private {
        tailf:cli-compact-syntax;
        tailf:cli-sequence-commands {
          tailf:cli-reset-siblings;
        }
        leaf path {
          tailf:cli-drop-node-name;
          type string;
        }
        leaf context_label {
          tailf:cli-drop-node-name;
          type string;
        }
      }
      container shared {
        tailf:cli-compact-syntax;
        tailf:cli-sequence-commands {
          tailf:cli-reset-siblings;
        }
        leaf path {
          tailf:cli-drop-node-name;
          type string;
        }
        leaf context_label {
          tailf:cli-drop-node-name;
          type string;
        }
      }
    }
    leaf config-url {
      type string;
    }
    leaf join-failover-group {
      type uint8;
    }
  }
  container call-home-reporting {
    tailf:cli-drop-node-name;
    container call-home {
      container reporting {
        leaf anonymous {
          type empty;
        }
      }
    }
  }
  container call-home {
    tailf:cli-add-mode;
    container http-proxy {
      tailf:cli-compact-syntax;
      tailf:cli-sequence-commands;
      leaf name {
        tailf:cli-drop-node-name;
        type string;
      }
      leaf port {
        type uint16;
      }
    }
    list profile {
      key "id";
      leaf id {
        type string;
      }
      leaf active {
        type boolean;
      }
      container destination {
        container address {
          leaf-list http {
            type string;
          }
          leaf-list email {
            type string;
          }
        }
        leaf transport-method {
          type enumeration {
            enum "email";
            enum "http";
          }
        }
      }
      list subscribe-to-alert-group {
        tailf:cli-suppress-mode;
        tailf:cli-delete-when-empty;
        tailf:cli-compact-syntax;
        key "id";
        leaf id {
          type enumeration {
            enum "configuration";
            enum "diagnostic";
            enum "environment";
            enum "inventory";
            enum "snapshot";
            enum "syslog";
            enum "telemetry";
            enum "threat";
          }
        }
        container periodic {
          choice periodic-choice {
            container daily {
              presence "true";
              leaf time {
                tailf:cli-drop-node-name;
                type hhmm-type;
              }
            }
            container hourly {
              presence "true";
              leaf minute {
                tailf:cli-drop-node-name;
                type uint8;
              }
            }
            container monthly {
              tailf:cli-compact-syntax;
              tailf:cli-sequence-commands {
                tailf:cli-reset-siblings;
              }
              presence "true";
              leaf day {
                tailf:cli-drop-node-name;
                tailf:cli-optional-in-sequence;
                type uint8;
              }
              leaf time {
                tailf:cli-drop-node-name;
                type hhmm-type;
              }
            }
            container weekly {
              tailf:cli-compact-syntax;
              tailf:cli-sequence-commands {
                tailf:cli-reset-siblings;
              }
              leaf day {
                tailf:cli-drop-node-name;
                tailf:cli-optional-in-sequence;
                type weekday-type;
              }
              leaf time {
                tailf:cli-drop-node-name;
                type hhmm-type;
              }
              presence "true";
            }
          }
        }
      }
    }
    container source-interface {
      tailf:cli-compact-syntax;
      tailf:cli-sequence-commands;
      leaf name {
        tailf:cli-drop-node-name;
        type nameif-type;
      }
    }
  }
  container event {
    container manager {
      list applet {
        key "name";
        leaf name {
          type string;
        }
        container event {
          list syslog {
            tailf:cli-suppress-mode;
            tailf:cli-delete-when-empty;
            key "id";
            leaf id {
              tailf:cli-expose-key-name;
              type string;
            }
          }
        }
        list action {
          tailf:cli-suppress-mode;
          tailf:cli-delete-when-empty;
          tailf:cli-compact-syntax;
          ordered-by user;
          key "id";
          leaf id {
            type uint32;
          }
          container cli {
            leaf command {
              type string;
            }
          }
        }
        container output {
          leaf none {
            type empty;
          }
        }
      }
    }
  }
  container rest-api {
    leaf image {
      type string;
    }
    leaf agent {
      type empty;
    }
  }
  container changeto {
    list context {
      key "context-name";
      leaf context-name {
        tailf:cli-suppress-range;
        type string;
      }
      uses config-grouping;
    }
  }
}
