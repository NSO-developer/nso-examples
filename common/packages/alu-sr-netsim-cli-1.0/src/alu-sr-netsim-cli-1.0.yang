module alu-sr-netsim-cli-1.0 {
  yang-version 1.1;
  namespace "http://tail-f.com/ns/ned-id/alu-sr-netsim-cli-1.0";
  prefix alu-sr-netsim-cli-1.0;

  import alu-sr-netsim-cli {
    prefix family;
  }

  identity alu-sr-netsim-cli-1.0 {
    base family:alu-sr-netsim-cli;
  }
}
