module alu-sr-netsim-cli {
  yang-version 1.1;
  namespace "http://tail-f.com/ns/ned-id/alu-sr-netsim-cli";
  prefix alu-sr-netsim-cli;

  import tailf-common {
    prefix tailf;
  }

  import tailf-ncs-ned {
    prefix ned;
  }

  identity alu-sr-netsim-cli {
    tailf:abstract;
    base ned:cli-ned-id;
  }
}
