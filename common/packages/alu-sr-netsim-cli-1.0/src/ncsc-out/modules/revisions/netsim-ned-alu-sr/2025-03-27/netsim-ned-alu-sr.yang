module netsim-ned-alu-sr {
  // Generated by yanger -t ncs
  tailf:mount-id "alu-sr-netsim-cli-1.0:alu-sr-netsim-cli-1.0";
  tailf:ncs-device-type "cli-ned";

  namespace "http://tail-f.com/ned/alu-sr";
  prefix alu;

  import tailf-common {
    prefix tailf;
  }
  import ietf-inet-types {
    prefix inet;
  }
  import ietf-yang-types {
    prefix yang;
  }
  import tailf-ncs {
    prefix ncs;
  }

  revision 2025-03-27;

  typedef ncs_compliance_template_dscp-type {
    type string;
  }

  typedef ncs_compliance_template_service-id {
    type string;
  }

  typedef ncs_compliance_template_ieee-mac {
    type string;
  }

  typedef ncs_compliance_template_direction {
    type string;
  }

  typedef ncs_compliance_template_test-pattern {
    type string;
  }

  typedef ncs_compliance_template_limit-mac-move {
    type string;
  }

  typedef ncs_compliance_template_filter-action {
    type string;
  }

  typedef ncs_compliance_template_adaption-rule {
    type string;
  }

  typedef ncs_compliance_template_protocol {
    type string;
  }

  typedef ncs_compliance_template_icmp-type {
    type string;
  }

  typedef ncs_compliance_template_icmpv6-type {
    type string;
  }

  typedef ncs_compliance_template_family-names-type {
    type string;
  }

  typedef ncs_compliance_template_policy-options-tag {
    type string;
  }

  typedef ncs_compliance_template_filter-id {
    type string;
  }

  typedef ncs_compliance_template_weekday {
    type string;
  }

  typedef ncs_compliance_template_month {
    type string;
  }

  typedef ncs_compliance_template_date {
    type string;
  }

  typedef ncs_compliance_template_enable-disable {
    type string;
  }

  typedef ncs_compliance_template_net-application {
    type string;
  }

  typedef ncs_compliance_template_string32 {
    type string;
  }

  typedef ncs_compliance_template_fc-name {
    type string;
  }

  typedef ncs_compliance_template_in-out {
    type string;
  }

  typedef ncs_compliance_template_scheduler-mode {
    type string;
  }

  typedef ncs_compliance_template_expire-time {
    type string;
  }

  typedef ncs_compliance_template_hash-method {
    type string;
  }

  typedef ncs_compliance_template_router-type {
    type string;
  }

  typedef ncs_compliance_template_rate-type {
    type string;
  }

  typedef ncs_compliance_template_rate-type-with-sum {
    type string;
  }

  typedef ncs_compliance_template_port-speed {
    type string;
  }

  typedef ncs_compliance_template_hash-hash2-all-hash {
    type string;
  }

  typedef ncs_compliance_template_hash-hash2-cleartext {
    type string;
  }

  typedef ncs_compliance_template_queue-type {
    type string;
  }

  typedef ncs_compliance_template_policy-protocol {
    type string;
  }

  typedef ncs_compliance_template_policer-stat-mode {
    type string;
  }

  typedef ncs_template_dscp-type {
    type string;
  }

  typedef ncs_template_service-id {
    type string;
  }

  typedef ncs_template_ieee-mac {
    type string;
  }

  typedef ncs_template_direction {
    type string;
  }

  typedef ncs_template_test-pattern {
    type string;
  }

  typedef ncs_template_limit-mac-move {
    type string;
  }

  typedef ncs_template_filter-action {
    type string;
  }

  typedef ncs_template_adaption-rule {
    type string;
  }

  typedef ncs_template_protocol {
    type string;
  }

  typedef ncs_template_icmp-type {
    type string;
  }

  typedef ncs_template_icmpv6-type {
    type string;
  }

  typedef ncs_template_family-names-type {
    type string;
  }

  typedef ncs_template_policy-options-tag {
    type string;
  }

  typedef ncs_template_filter-id {
    type string;
  }

  typedef ncs_template_weekday {
    type string;
  }

  typedef ncs_template_month {
    type string;
  }

  typedef ncs_template_date {
    type string;
  }

  typedef ncs_template_enable-disable {
    type string;
  }

  typedef ncs_template_net-application {
    type string;
  }

  typedef ncs_template_string32 {
    type string;
  }

  typedef ncs_template_fc-name {
    type string;
  }

  typedef ncs_template_in-out {
    type string;
  }

  typedef ncs_template_scheduler-mode {
    type string;
  }

  typedef ncs_template_expire-time {
    type string;
  }

  typedef ncs_template_hash-method {
    type string;
  }

  typedef ncs_template_router-type {
    type string;
  }

  typedef ncs_template_rate-type {
    type string;
  }

  typedef ncs_template_rate-type-with-sum {
    type string;
  }

  typedef ncs_template_port-speed {
    type string;
  }

  typedef ncs_template_hash-hash2-all-hash {
    type string;
  }

  typedef ncs_template_hash-hash2-cleartext {
    type string;
  }

  typedef ncs_template_queue-type {
    type string;
  }

  typedef ncs_template_policy-protocol {
    type string;
  }

  typedef ncs_template_policer-stat-mode {
    type string;
  }

  typedef ncs_rpc_notif_dscp-type {
    type enumeration {
      enum "no";
      enum "be";
      enum "ef";
      enum "cp1";
      enum "cp2";
      enum "cp3";
      enum "cp4";
      enum "cp5";
      enum "cp6";
      enum "cp7";
      enum "cp9";
      enum "cs1";
      enum "cs2";
      enum "cs3";
      enum "cs4";
      enum "cs5";
      enum "nc1";
      enum "nc2";
      enum "l1";
      enum "l2";
      enum "af";
      enum "af11";
      enum "af12";
      enum "af13";
      enum "af21";
      enum "af22";
      enum "af23";
      enum "af31";
      enum "af32";
      enum "af33";
      enum "af41";
      enum "af42";
      enum "af43";
      enum "cp11";
      enum "cp13";
      enum "cp15";
      enum "cp17";
      enum "cp19";
      enum "cp21";
      enum "cp23";
      enum "cp25";
      enum "cp27";
      enum "cp29";
      enum "cp31";
      enum "cp33";
      enum "cp35";
      enum "cp37";
      enum "cp39";
      enum "cp41";
      enum "cp42";
      enum "cp43";
      enum "cp44";
      enum "cp45";
      enum "cp47";
      enum "cp49";
      enum "cp50";
      enum "cp51";
      enum "cp52";
      enum "cp53";
      enum "cp54";
      enum "cp55";
      enum "cp57";
      enum "cp58";
      enum "cp59";
      enum "cp60";
      enum "cp61";
      enum "cp62";
      enum "cp63";
    }
  }

  typedef ncs_rpc_notif_service-id {
    type union {
      type uint32;
      type string;
    }
  }

  typedef ncs_rpc_notif_ieee-mac {
    type string;
  }

  typedef ncs_rpc_notif_direction {
    type enumeration {
      enum "up";
      enum "down";
    }
  }

  typedef ncs_rpc_notif_test-pattern {
    type enumeration {
      enum "all-zeros";
      enum "all-ones";
    }
  }

  typedef ncs_rpc_notif_limit-mac-move {
    type enumeration {
      enum "blockable";
      enum "non-blockable";
    }
  }

  typedef ncs_rpc_notif_filter-action {
    type enumeration {
      enum "permit";
      enum "deny";
      enum "deny-host-unreachable";
    }
  }

  typedef ncs_rpc_notif_adaption-rule {
    type enumeration {
      enum "max";
      enum "min";
      enum "closest";
    }
  }

  typedef ncs_rpc_notif_protocol {
    type union {
      type enumeration {
        enum "none";
        enum "crtp";
        enum "crudp";
        enum "egp";
        enum "eigrp";
        enum "encap";
        enum "ether-ip";
        enum "gre";
        enum "icmp";
        enum "idrp";
        enum "igmp";
        enum "igp";
        enum "ip";
        enum "ipv6";
        enum "ipv6-frag";
        enum "ipv6-icmp";
        enum "ipv6-no-nxt";
        enum "ipv6-opts";
        enum "ipv6-route";
        enum "isis";
        enum "iso-ip";
        enum "l2tp";
        enum "ospf-igp";
        enum "pim";
        enum "pnni";
        enum "ptp";
        enum "rdp";
        enum "rsvp";
        enum "stp";
        enum "tcp";
        enum "udp";
        enum "vrrp";
        enum "*";
      }
      type uint8;
      type string;
    }
  }

  typedef ncs_rpc_notif_icmp-type {
    type union {
      type uint8;
      type enumeration {
        enum "none";
        enum "echo-reply";
        enum "dest-unreachable";
        enum "source-quench";
        enum "redirect";
        enum "echo-request";
        enum "router-advt";
        enum "router-selection";
        enum "time-exceeded";
        enum "parameter-problem";
        enum "timestamp-request";
        enum "timestamp-reply";
        enum "addr-mask-request";
        enum "addr-mask-reply";
        enum "photuris";
      }
    }
  }

  typedef ncs_rpc_notif_icmpv6-type {
    type union {
      type uint8;
      type enumeration {
        enum "none";
        enum "dest-unreachable";
        enum "packet-too-big";
        enum "time-exceeded";
        enum "parameter-problem";
        enum "echo-request";
        enum "echo-reply";
        enum "multicast-listen-query";
        enum "multicast-listen-report";
        enum "multicast-listen-done";
        enum "router-solicitation";
        enum "router-advt";
        enum "neighbor-solicitation";
        enum "neighbor-advertisement";
        enum "redirect-message";
        enum "router-renumbering";
        enum "icmp-node-info-query";
        enum "icmp-node-info-resp";
        enum "inv-nd-solicitation";
        enum "inv-nd-adv-message";
        enum "multicast-listener-report-v2";
        enum "home-agent-ad-request";
        enum "home-agent-ad-reply";
        enum "mobile-prefix-solicitation";
        enum "mobile-prefix-advt";
        enum "cert-path-solicitation";
        enum "cert-path-advt";
        enum "multicast-router-advt";
        enum "multicast-router-solicitation";
        enum "multicast-router-termination";
        enum "fmipv6";
        enum "rpl-control";
        enum "ilnpv6-locator-update";
        enum "duplicate-addr-request";
        enum "duplicate-addr-confirmation";
      }
    }
  }

  typedef ncs_rpc_notif_family-names-type {
    type enumeration {
      enum "ipv4";
      enum "vpn-ipv4";
      enum "ipv6";
      enum "vpn-ipv6";
      enum "mcast-ipv4";
      enum "l2-vpn";
      enum "mvpn-ipv4";
      enum "mdt-safi";
      enum "ms-pw";
      enum "flow-ipv4";
      enum "route-target";
      enum "mcast-vpn-ipv4";
      enum "mvpn-ipv6";
      enum "flow-ipv6";
      enum "evpn";
      enum "mcast-ipv6";
      enum "label-ipv4";
      enum "label-ipv6";
      enum "bgp-ls";
      enum "sr-policy-ipv4";
    }
  }

  typedef ncs_rpc_notif_policy-options-tag {
    type union {
      type enumeration {
        enum "no-tag";
      }
      type string;
    }
  }

  typedef ncs_rpc_notif_filter-id {
    type union {
      type uint16;
      type string;
    }
  }

  typedef ncs_rpc_notif_weekday {
    type enumeration {
      enum "sunday";
      enum "monday";
      enum "tuesday";
      enum "wednesday";
      enum "thursday";
      enum "friday";
      enum "saturday";
    }
  }

  typedef ncs_rpc_notif_month {
    type enumeration {
      enum "january";
      enum "february";
      enum "march";
      enum "april";
      enum "may";
      enum "june";
      enum "july";
      enum "august";
      enum "september";
      enum "october";
      enum "november";
      enum "december";
    }
  }

  typedef ncs_rpc_notif_date {
    type string;
  }

  typedef ncs_rpc_notif_enable-disable {
    type enumeration {
      enum "enable";
      enum "disable";
    }
  }

  typedef ncs_rpc_notif_net-application {
    type enumeration {
      enum "cflowd";
      enum "dns";
      enum "ftp";
      enum "ntp";
      enum "ping";
      enum "radius";
      enum "snmptrap";
      enum "sntp";
      enum "ssh";
      enum "syslog";
      enum "tacplus";
      enum "telnet";
      enum "traceroute";
      enum "mcreporter";
      enum "ldap";
      enum "ptp";
      enum "sflow";
      enum "snmperror";
      enum "icmp-error";
    }
  }

  typedef ncs_rpc_notif_string32 {
    type string;
  }

  typedef ncs_rpc_notif_fc-name {
    type union {
      type enumeration {
        enum "be";
        enum "l2";
        enum "af";
        enum "l1";
        enum "h2";
        enum "ef";
        enum "h1";
        enum "nc";
      }
      type string;
    }
  }

  typedef ncs_rpc_notif_in-out {
    type enumeration {
      enum "in";
      enum "out";
    }
  }

  typedef ncs_rpc_notif_scheduler-mode {
    type enumeration {
      enum "profile";
      enum "4-priority";
      enum "16-priority";
    }
  }

  typedef ncs_rpc_notif_expire-time {
    type union {
      type uint32;
      type enumeration {
        enum "forever";
      }
    }
  }

  typedef ncs_rpc_notif_hash-method {
    type enumeration {
      enum "hash";
      enum "hash2";
    }
  }

  typedef ncs_rpc_notif_router-type {
    type string;
  }

  typedef ncs_rpc_notif_rate-type {
    type union {
      type enumeration {
        enum "max";
      }
      type uint32;
    }
  }

  typedef ncs_rpc_notif_rate-type-with-sum {
    type union {
      type enumeration {
        enum "max";
        enum "sum";
      }
      type uint32;
    }
  }

  typedef ncs_rpc_notif_port-speed {
    type enumeration {
      enum "10";
      enum "100";
      enum "1000";
      enum "10000";
      enum "25000";
      enum "40000";
      enum "50000";
      enum "100000";
    }
  }

  typedef ncs_rpc_notif_hash-hash2-all-hash {
    type enumeration {
      enum "hash";
      enum "hash2";
      enum "all-hash";
    }
  }

  typedef ncs_rpc_notif_hash-hash2-cleartext {
    type enumeration {
      enum "hash";
      enum "hash2";
      enum "cleartext";
    }
  }

  typedef ncs_rpc_notif_queue-type {
    type enumeration {
      enum "expedite";
      enum "best-effort";
      enum "auto-expedite";
      enum "expedite-lo";
      enum "expedite-hi";
    }
  }

  typedef ncs_rpc_notif_policy-protocol {
    type enumeration {
      enum "arp-nd";
      enum "direct";
      enum "static";
      enum "bgp";
      enum "bgp-label";
      enum "isis";
      enum "ospf";
      enum "rip";
      enum "aggregate";
      enum "bgp-vpn";
      enum "igmp";
      enum "pim";
      enum "ospf3";
      enum "ldp";
      enum "sub-mgmt";
      enum "mld";
      enum "managed";
      enum "vpn-leak";
      enum "tms";
      enum "nat";
      enum "periodic";
      enum "ipsec";
      enum "mpls";
      enum "dhcpv6-pd";
      enum "dhcpv6-na";
      enum "dhcpv6-ta";
      enum "dhcpv6-pd-excl";
      enum "direct-interface";
    }
  }

  typedef ncs_rpc_notif_policer-stat-mode {
    type enumeration {
      enum "no-stats";
      enum "minimal";
      enum "offered-profile-no-cir";
      enum "offered-profile-cir";
      enum "offered-total-cir";
      enum "offered-limited-capped-cir";
      enum "offered-profile-capped-cir";
      enum "offered-total-cir-exceed";
      enum "offered-four-profile-no-cir";
      enum "offered-total-cir-four-profile";
      enum "offered-profile-with-discards";
      enum "v4-v6";
    }
  }

  typedef dscp-type {
    type enumeration {
      enum "no";
      enum "be";
      enum "ef";
      enum "cp1";
      enum "cp2";
      enum "cp3";
      enum "cp4";
      enum "cp5";
      enum "cp6";
      enum "cp7";
      enum "cp9";
      enum "cs1";
      enum "cs2";
      enum "cs3";
      enum "cs4";
      enum "cs5";
      enum "nc1";
      enum "nc2";
      enum "l1";
      enum "l2";
      enum "af";
      enum "af11";
      enum "af12";
      enum "af13";
      enum "af21";
      enum "af22";
      enum "af23";
      enum "af31";
      enum "af32";
      enum "af33";
      enum "af41";
      enum "af42";
      enum "af43";
      enum "cp11";
      enum "cp13";
      enum "cp15";
      enum "cp17";
      enum "cp19";
      enum "cp21";
      enum "cp23";
      enum "cp25";
      enum "cp27";
      enum "cp29";
      enum "cp31";
      enum "cp33";
      enum "cp35";
      enum "cp37";
      enum "cp39";
      enum "cp41";
      enum "cp42";
      enum "cp43";
      enum "cp44";
      enum "cp45";
      enum "cp47";
      enum "cp49";
      enum "cp50";
      enum "cp51";
      enum "cp52";
      enum "cp53";
      enum "cp54";
      enum "cp55";
      enum "cp57";
      enum "cp58";
      enum "cp59";
      enum "cp60";
      enum "cp61";
      enum "cp62";
      enum "cp63";
    }
  }

  typedef service-id {
    type union {
      type uint32;
      type string;
    }
  }

  typedef ieee-mac {
    type string;
  }

  typedef direction {
    type enumeration {
      enum "up";
      enum "down";
    }
  }

  typedef test-pattern {
    type enumeration {
      enum "all-zeros";
      enum "all-ones";
    }
  }

  typedef limit-mac-move {
    type enumeration {
      enum "blockable";
      enum "non-blockable";
    }
  }

  typedef filter-action {
    type enumeration {
      enum "permit";
      enum "deny";
      enum "deny-host-unreachable";
    }
  }

  typedef adaption-rule {
    type enumeration {
      enum "max";
      enum "min";
      enum "closest";
    }
  }

  typedef protocol {
    type union {
      type enumeration {
        enum "none";
        enum "crtp";
        enum "crudp";
        enum "egp";
        enum "eigrp";
        enum "encap";
        enum "ether-ip";
        enum "gre";
        enum "icmp";
        enum "idrp";
        enum "igmp";
        enum "igp";
        enum "ip";
        enum "ipv6";
        enum "ipv6-frag";
        enum "ipv6-icmp";
        enum "ipv6-no-nxt";
        enum "ipv6-opts";
        enum "ipv6-route";
        enum "isis";
        enum "iso-ip";
        enum "l2tp";
        enum "ospf-igp";
        enum "pim";
        enum "pnni";
        enum "ptp";
        enum "rdp";
        enum "rsvp";
        enum "stp";
        enum "tcp";
        enum "udp";
        enum "vrrp";
        enum "*";
      }
      type uint8;
      type string;
    }
  }

  typedef icmp-type {
    type union {
      type uint8;
      type enumeration {
        enum "none";
        enum "echo-reply";
        enum "dest-unreachable";
        enum "source-quench";
        enum "redirect";
        enum "echo-request";
        enum "router-advt";
        enum "router-selection";
        enum "time-exceeded";
        enum "parameter-problem";
        enum "timestamp-request";
        enum "timestamp-reply";
        enum "addr-mask-request";
        enum "addr-mask-reply";
        enum "photuris";
      }
    }
  }

  typedef icmpv6-type {
    type union {
      type uint8;
      type enumeration {
        enum "none";
        enum "dest-unreachable";
        enum "packet-too-big";
        enum "time-exceeded";
        enum "parameter-problem";
        enum "echo-request";
        enum "echo-reply";
        enum "multicast-listen-query";
        enum "multicast-listen-report";
        enum "multicast-listen-done";
        enum "router-solicitation";
        enum "router-advt";
        enum "neighbor-solicitation";
        enum "neighbor-advertisement";
        enum "redirect-message";
        enum "router-renumbering";
        enum "icmp-node-info-query";
        enum "icmp-node-info-resp";
        enum "inv-nd-solicitation";
        enum "inv-nd-adv-message";
        enum "multicast-listener-report-v2";
        enum "home-agent-ad-request";
        enum "home-agent-ad-reply";
        enum "mobile-prefix-solicitation";
        enum "mobile-prefix-advt";
        enum "cert-path-solicitation";
        enum "cert-path-advt";
        enum "multicast-router-advt";
        enum "multicast-router-solicitation";
        enum "multicast-router-termination";
        enum "fmipv6";
        enum "rpl-control";
        enum "ilnpv6-locator-update";
        enum "duplicate-addr-request";
        enum "duplicate-addr-confirmation";
      }
    }
  }

  typedef family-names-type {
    type enumeration {
      enum "ipv4";
      enum "vpn-ipv4";
      enum "ipv6";
      enum "vpn-ipv6";
      enum "mcast-ipv4";
      enum "l2-vpn";
      enum "mvpn-ipv4";
      enum "mdt-safi";
      enum "ms-pw";
      enum "flow-ipv4";
      enum "route-target";
      enum "mcast-vpn-ipv4";
      enum "mvpn-ipv6";
      enum "flow-ipv6";
      enum "evpn";
      enum "mcast-ipv6";
      enum "label-ipv4";
      enum "label-ipv6";
      enum "bgp-ls";
      enum "sr-policy-ipv4";
    }
  }

  typedef policy-options-tag {
    type union {
      type enumeration {
        enum "no-tag";
      }
      type string;
    }
  }

  typedef filter-id {
    type union {
      type uint16;
      type string;
    }
  }

  typedef weekday {
    type enumeration {
      enum "sunday";
      enum "monday";
      enum "tuesday";
      enum "wednesday";
      enum "thursday";
      enum "friday";
      enum "saturday";
    }
  }

  typedef month {
    type enumeration {
      enum "january";
      enum "february";
      enum "march";
      enum "april";
      enum "may";
      enum "june";
      enum "july";
      enum "august";
      enum "september";
      enum "october";
      enum "november";
      enum "december";
    }
  }

  typedef date {
    type string;
  }

  typedef enable-disable {
    type enumeration {
      enum "enable";
      enum "disable";
    }
  }

  typedef net-application {
    type enumeration {
      enum "cflowd";
      enum "dns";
      enum "ftp";
      enum "ntp";
      enum "ping";
      enum "radius";
      enum "snmptrap";
      enum "sntp";
      enum "ssh";
      enum "syslog";
      enum "tacplus";
      enum "telnet";
      enum "traceroute";
      enum "mcreporter";
      enum "ldap";
      enum "ptp";
      enum "sflow";
      enum "snmperror";
      enum "icmp-error";
    }
  }

  typedef string32 {
    type string;
  }

  typedef fc-name {
    type union {
      type enumeration {
        enum "be";
        enum "l2";
        enum "af";
        enum "l1";
        enum "h2";
        enum "ef";
        enum "h1";
        enum "nc";
      }
      type string;
    }
  }

  typedef in-out {
    type enumeration {
      enum "in";
      enum "out";
    }
  }

  typedef scheduler-mode {
    type enumeration {
      enum "profile";
      enum "4-priority";
      enum "16-priority";
    }
  }

  typedef expire-time {
    type union {
      type uint32;
      type enumeration {
        enum "forever";
      }
    }
  }

  typedef hash-method {
    type enumeration {
      enum "hash";
      enum "hash2";
    }
  }

  typedef router-type {
    type string;
  }

  typedef rate-type {
    type union {
      type enumeration {
        enum "max";
      }
      type uint32;
    }
  }

  typedef rate-type-with-sum {
    type union {
      type enumeration {
        enum "max";
        enum "sum";
      }
      type uint32;
    }
  }

  typedef port-speed {
    type enumeration {
      enum "10";
      enum "100";
      enum "1000";
      enum "10000";
      enum "25000";
      enum "40000";
      enum "50000";
      enum "100000";
    }
  }

  typedef hash-hash2-all-hash {
    type enumeration {
      enum "hash";
      enum "hash2";
      enum "all-hash";
    }
  }

  typedef hash-hash2-cleartext {
    type enumeration {
      enum "hash";
      enum "hash2";
      enum "cleartext";
    }
  }

  typedef queue-type {
    type enumeration {
      enum "expedite";
      enum "best-effort";
      enum "auto-expedite";
      enum "expedite-lo";
      enum "expedite-hi";
    }
  }

  typedef policy-protocol {
    type enumeration {
      enum "arp-nd";
      enum "direct";
      enum "static";
      enum "bgp";
      enum "bgp-label";
      enum "isis";
      enum "ospf";
      enum "rip";
      enum "aggregate";
      enum "bgp-vpn";
      enum "igmp";
      enum "pim";
      enum "ospf3";
      enum "ldp";
      enum "sub-mgmt";
      enum "mld";
      enum "managed";
      enum "vpn-leak";
      enum "tms";
      enum "nat";
      enum "periodic";
      enum "ipsec";
      enum "mpls";
      enum "dhcpv6-pd";
      enum "dhcpv6-na";
      enum "dhcpv6-ta";
      enum "dhcpv6-pd-excl";
      enum "direct-interface";
    }
  }

  typedef policer-stat-mode {
    type enumeration {
      enum "no-stats";
      enum "minimal";
      enum "offered-profile-no-cir";
      enum "offered-profile-cir";
      enum "offered-total-cir";
      enum "offered-limited-capped-cir";
      enum "offered-profile-capped-cir";
      enum "offered-total-cir-exceed";
      enum "offered-four-profile-no-cir";
      enum "offered-total-cir-four-profile";
      enum "offered-profile-with-discards";
      enum "v4-v6";
    }
  }

  grouping ncs_compliance_template_src-dst-ip {
    leaf src-ip {
      type string;
    }
    leaf dst-ip {
      type string;
    }
  }

  grouping ncs_compliance_template_ip-address-range {
    list low-high-list {
      // NCS patched for predictable order
      ordered-by user;
      tailf:cli-drop-node-name;
      tailf:cli-suppress-mode;
      key "low high";
      leaf low {
        type string;
      }
      leaf high {
        type string;
      }
    }
  }

  grouping ncs_compliance_template_eth-cfm {
    leaf collect-lmm-stats {
      type empty;
    }
    list mep {
      // NCS patched for predictable order
      ordered-by user;
      key "mep-id domain association";
      leaf mep-id {
        type string;
      }
      leaf domain {
        type string;
      }
      leaf association {
        type string;
      }
      leaf direction {
        type ncs_compliance_template_direction;
      }
      container ais-enable {
        leaf-list client-meg-level {
          // NCS patched for predictable order
          ordered-by user;
          type string;
        }
        leaf description {
          type string;
        }
        leaf interval {
          type string;
        }
        leaf priority {
          type string;
        }
      }
      leaf ccm-enable {
        type empty;
      }
      leaf ccm-ltm-priority {
        type string;
      }
      leaf ccm-padding-size {
        type string;
      }
      leaf description {
        type string;
      }
      container eth-test-enable {
        uses ncs_compliance_template_eth-test;
      }
      leaf fault-propagation-enable {
        type string;
      }
      leaf install-mep {
        type empty;
      }
      leaf low-priority-defect {
        type string;
      }
      leaf mac-address {
        type ncs_compliance_template_ieee-mac;
      }
      leaf one-way-delay-threshold {
        type string;
      }
      leaf shutdown {
        type string;
      }
    }
  }

  grouping ncs_compliance_template_enable-origin-validation-grouping {
    leaf-list enable-origin-validation {
      // NCS patched for predictable order
      ordered-by user;
      type string;
    }
  }

  grouping ncs_compliance_template_igmp-static-grouping {
    container static {
      list group {
        // NCS patched for predictable order
        ordered-by user;
        key "grp-ip-addr";
        leaf grp-ip-addr {
          type string;
        }
        list source {
          // NCS patched for predictable order
          ordered-by user;
          tailf:cli-suppress-mode;
          key "ip-address";
          leaf ip-address {
            type string;
          }
        }
        leaf starg {
          type empty;
        }
      }
    }
  }

  grouping ncs_compliance_template_igmp-snooping-grouping {
    leaf disable-router-alert {
      type empty;
    }
    leaf fast-leave {
      type empty;
    }
    leaf import {
      type string;
    }
    leaf last-member-query-interval {
      type string;
    }
    leaf max-num-groups {
      type string;
    }
    leaf mrouter-port {
      type empty;
    }
    leaf query-interval {
      type string;
    }
    leaf query-response-interval {
      type string;
    }
    leaf robust-count {
      type string;
    }
    leaf send-queries {
      type empty;
    }
    uses ncs_compliance_template_igmp-static-grouping;
    leaf version {
      type string;
    }
  }

  grouping ncs_compliance_template_sdp-common {
    leaf vc-id {
      type string;
    }
    leaf vc-type {
      type string;
    }
    leaf endpoint {
      type string;
    }
    leaf icb {
      type empty;
    }
    leaf shutdown {
      type string;
    }
  }

  grouping ncs_compliance_template_sdp-spoke-mesh-common {
    leaf sdp-id {
      type string;
    }
    uses ncs_compliance_template_sdp-common;
    leaf accounting-policy {
      type string;
    }
    leaf auto-learn-mac-protect {
      type empty;
    }
    leaf description {
      type string;
    }
    leaf collect-stats {
      type empty;
    }
    container hash-label {
      presence "true";
      leaf signal-capability {
        type empty;
      }
    }
    leaf control-word {
      type empty;
    }
    container igmp-snooping {
      uses ncs_compliance_template_igmp-snooping-grouping;
    }
    container egress {
      container filter {
        uses ncs_compliance_template_filter-choice;
      }
      container qos {
        leaf network-policy-id {
          tailf:cli-drop-node-name;
          type string;
        }
        leaf port-redirect-group {
          type string;
        }
        leaf instance {
          type string;
        }
      }
      leaf vc-label {
        type string;
      }
    }
    container eth-cfm {
      uses ncs_compliance_template_eth-cfm;
    }
    leaf force-vlan-vc-forwarding {
      type empty;
    }
    container ingress {
      container filter {
        uses ncs_compliance_template_filter-choice;
      }
      container qos {
        leaf network-policy-id {
          tailf:cli-drop-node-name;
          type string;
        }
        leaf fp-redirect-group {
          type string;
        }
        leaf instance {
          type string;
        }
      }
      leaf vc-label {
        type string;
      }
    }
    leaf mac-pinning {
      type empty;
    }
    list static-mac {
      // NCS patched for predictable order
      ordered-by user;
      tailf:cli-suppress-mode;
      key "address";
      leaf address {
        type ncs_compliance_template_ieee-mac;
      }
    }
    leaf restrict-protected-src {
      type string;
    }
    leaf precedence {
      type string;
    }
    leaf vlan-vc-tag {
      type string;
    }
  }

  grouping ncs_compliance_template_stp-common {
    leaf auto-edge {
      type empty;
    }
    leaf edge-port {
      type empty;
    }
    leaf link-type {
      type string;
    }
    leaf path-cost {
      type string;
    }
    leaf port-num {
      type string;
    }
    leaf priority {
      type string;
    }
    leaf shutdown {
      type string;
    }
  }

  grouping ncs_compliance_template_filter-choice {
    leaf ip {
      type ncs_compliance_template_filter-id;
    }
    leaf ipv6 {
      type ncs_compliance_template_filter-id;
    }
    leaf mac {
      type ncs_compliance_template_filter-id;
    }
  }

  grouping ncs_compliance_template_eth-test {
    leaf test-pattern {
      type ncs_compliance_template_test-pattern;
    }
    leaf crc-enable {
      type empty;
    }
  }

  grouping ncs_compliance_template_time-stamp {
    leaf start-week {
      tailf:cli-drop-node-name;
      type string;
    }
    leaf start-day {
      tailf:cli-drop-node-name;
      type ncs_compliance_template_weekday;
    }
    leaf month {
      tailf:cli-drop-node-name;
      type ncs_compliance_template_month;
    }
    leaf hours-minutes {
      tailf:cli-drop-node-name;
      type string;
    }
  }

  grouping ncs_compliance_template_ip-filter-entry-grouping {
    leaf entry-name {
      type string;
    }
    leaf description {
      type string;
    }
    leaf log {
      type string;
    }
    list match {
      // NCS patched for predictable order
      ordered-by user;
      key "protocol-type";
      leaf protocol-type {
        type string;
      }
      leaf protocol {
        type empty;
      }
      leaf dscp {
        type ncs_compliance_template_dscp-type;
      }
      container ip {
        uses ncs_compliance_template_filter-match-ip-grouping;
      }
      container src-ip {
        uses ncs_compliance_template_filter-match-ip-grouping;
      }
      leaf src-route-option {
        type string;
      }
      container dst-ip {
        uses ncs_compliance_template_filter-match-ip-grouping;
      }
      leaf icmp-type {
        type ncs_compliance_template_icmp-type;
      }
      leaf icmp-code {
        type string;
      }
      leaf fragment {
        type string;
      }
      leaf option-present {
        type string;
      }
      container ip-option {
        leaf a {
          tailf:cli-drop-node-name;
          type string;
        }
        leaf b {
          tailf:cli-drop-node-name;
          type string;
        }
      }

      grouping filter-ip-filter-port-grouping {
        choice port-choice {
          case a {
            leaf op {
              tailf:cli-drop-node-name;
              type string;
            }
            leaf port {
              tailf:cli-drop-node-name;
              // NCS drop mandatory statement
              type string;
            }
          }
          case b {
            leaf range {
              type empty;
            }
            leaf start {
              tailf:cli-drop-node-name;
              // NCS drop mandatory statement
              type string;
            }
            leaf end {
              tailf:cli-drop-node-name;
              // NCS drop mandatory statement
              type string;
            }
          }
          case c {
            leaf port-list {
              type ncs_compliance_template_string32;
            }
          }
        }
      }
      container port {
        uses filter-ip-filter-port-grouping;
      }
      container dst-port {
        uses filter-ip-filter-port-grouping;
      }
      container src-port {
        choice port-choice {
          case a {
            leaf op {
              tailf:cli-drop-node-name;
              type string;
            }
            leaf port {
              tailf:cli-drop-node-name;
              // NCS drop mandatory statement
              type string;
            }
          }
          case b {
            leaf range {
              type empty;
            }
            leaf start {
              tailf:cli-drop-node-name;
              // NCS drop mandatory statement
              type string;
            }
            leaf end {
              tailf:cli-drop-node-name;
              // NCS drop mandatory statement
              type string;
            }
          }
          case c {
            leaf src-port-number {
              tailf:cli-drop-node-name;
              type string;
            }
            leaf mask {
              tailf:cli-drop-node-name;
              type string;
            }
          }
          case d {
            leaf port-list {
              type ncs_compliance_template_string32;
            }
          }
        }
      }
      leaf tcp-ack {
        type string;
      }
      leaf tcp-syn {
        type string;
      }
    }
  }

  grouping ncs_compliance_template_ipv6-filter-entry-grouping {
    leaf entry-name {
      type string;
    }
    leaf description {
      type string;
    }
    container match {
      presence "true";
      leaf next-header {
        type string;
      }
      leaf dscp {
        type ncs_compliance_template_dscp-type;
      }
      container ip {
        uses ncs_compliance_template_filter-match-ipv6-grouping;
      }
      container src-ip {
        uses ncs_compliance_template_filter-match-ipv6-grouping;
      }
      container dst-ip {
        uses ncs_compliance_template_filter-match-ipv6-grouping;
      }
      leaf icmp-type {
        type ncs_compliance_template_icmpv6-type;
      }
      leaf icmp-code {
        type string;
      }
      leaf fragment {
        type string;
      }
      container ip-option {
        leaf a {
          tailf:cli-drop-node-name;
          type string;
        }
        leaf b {
          tailf:cli-drop-node-name;
          type string;
        }
      }

      grouping filter-ipv6-filter-port-grouping {
        choice port-choice {
          case a {
            leaf op {
              tailf:cli-drop-node-name;
              type string;
            }
            leaf port {
              tailf:cli-drop-node-name;
              type string;
            }
          }
          case b {
            leaf range {
              type empty;
            }
            leaf start {
              tailf:cli-drop-node-name;
              type string;
            }
            leaf end {
              tailf:cli-drop-node-name;
              type string;
            }
          }
          case c {
            leaf port-list {
              type ncs_compliance_template_string32;
            }
          }
        }
      }
      container dst-port {
        uses filter-ipv6-filter-port-grouping;
      }
      leaf routing-type0 {
        type string;
      }
      container src-port {
        uses filter-ipv6-filter-port-grouping;
      }
      container port {
        uses filter-ipv6-filter-port-grouping;
      }
      leaf tcp-ack {
        type string;
      }
      leaf tcp-syn {
        type string;
      }
    }
  }

  grouping ncs_compliance_template_queue-adaptation-grouping {
    container adaptation-rule {
      leaf pir {
        type string;
      }
      leaf cir {
        type string;
      }
    }
  }

  grouping ncs_compliance_template_queue-rate-grouping {
    container rate {
      leaf pir {
        tailf:cli-drop-node-name;
        type ncs_compliance_template_rate-type;
      }
      leaf cir {
        type ncs_compliance_template_rate-type;
      }
      leaf alt-pir {
        tailf:alt-name "pir";
        type ncs_compliance_template_rate-type;
      }
      leaf police {
        type empty;
      }
    }
  }

  grouping ncs_compliance_template_qos-queue-percent-rate-grouping {
    container percent-rate {
      leaf pir {
        tailf:cli-drop-node-name;
        type string;
      }
      leaf cir {
        type string;
      }
    }
  }

  grouping ncs_compliance_template_sap-queue-override-grouping {
    container queue-override {
      list queue {
        // NCS patched for predictable order
        ordered-by user;
        key "queue-id";
        leaf queue-id {
          type string;
        }
        uses ncs_compliance_template_queue-adaptation-grouping;
        leaf avg-frame-overhead {
          type string;
        }
        container mbs {
          leaf val {
            tailf:cli-drop-node-name;
            type string;
          }
          leaf unit {
            tailf:cli-drop-node-name;
            type string;
          }
        }
        leaf cbs {
          type string;
        }
        leaf high-prio-only {
          type string;
        }
        container rate {
          leaf pir {
            tailf:cli-drop-node-name;
            type string;
          }
          leaf cir {
            type string;
          }
        }
        container parent {
          leaf weight {
            type string;
          }
          leaf cir-weight {
            type string;
          }
        }
        uses ncs_compliance_template_qos-queue-percent-rate-grouping;
      }
    }
  }

  grouping ncs_compliance_template_sap-scheduler-override-grouping {
    container scheduler-override {
      list scheduler {
        // NCS patched for predictable order
        ordered-by user;
        key "scheduler-policy-name";
        leaf scheduler-policy-name {
          type string;
        }
        container parent {
          leaf weight {
            type string;
          }
          leaf cir-weight {
            type string;
          }
        }
        container rate {
          leaf rate {
            tailf:cli-drop-node-name;
            type string;
          }
          leaf cir {
            type string;
          }
        }
      }
    }
  }

  grouping ncs_compliance_template_router-segment-routing-grouping {
    container segment-routing {
      container prefix-sid-range {
        choice range {
          leaf global {
            type empty;
          }
          case other {
            leaf start-label {
              type string;
            }
            leaf max-index {
              type string;
            }
          }
        }
      }
      leaf tunnel-mtu {
        type string;
      }
      leaf tunnel-table-pref {
        type string;
      }
      leaf srlb {
        type string;
      }
      container micro-loop-avoidance {
        presence "true";
        leaf fib-delay {
          type string;
        }
      }
      leaf export-tunnel-table {
        type string;
      }
      leaf shutdown {
        type string;
      }
    }
  }

  grouping ncs_compliance_template_sap-policer-override-grouping-egress {
    container policer-override {
      list policer {
        // NCS patched for predictable order
        ordered-by user;
        key "policer-id";
        leaf policer-id {
          type string;
        }
        uses ncs_compliance_template_policer-cbs-mbs-rate-with-packet-offset-grouping;
      }
    }
  }

  grouping ncs_compliance_template_sap-policer-override-grouping-ingress {
    container policer-override {
      list policer {
        // NCS patched for predictable order
        ordered-by user;
        key "policer-id";
        leaf policer-id {
          type string;
        }
        uses ncs_compliance_template_policer-cbs-mbs-rate-with-packet-offset-grouping;
      }
    }
  }

  grouping ncs_compliance_template_ip-criteria-grouping {
    leaf dscp-only {
      type empty;
    }
    list entry {
      // NCS patched for predictable order
      ordered-by user;
      key "id";
      leaf id {
        type string;
      }
      leaf description {
        type string;
      }
      container match {
        leaf protocol {
          type ncs_compliance_template_protocol;
        }
        leaf dscp {
          type ncs_compliance_template_dscp-type;
        }
        container dst-ip {
          choice dst {
            leaf ip-address-with-mask {
              tailf:cli-drop-node-name;
              type string;
            }
            leaf ip-prefix-list {
              type ncs_compliance_template_string32;
            }
          }
        }
        container src-ip {
          choice src {
            leaf ip-address-with-mask {
              tailf:cli-drop-node-name;
              type string;
            }
            leaf ip-prefix-list {
              type ncs_compliance_template_string32;
            }
          }
        }

        grouping port-choice-grouping {
          choice port-choice {
            case a {
              leaf op {
                tailf:cli-drop-node-name;
                type string;
              }
              leaf port {
                tailf:cli-drop-node-name;
                type string;
              }
            }
            case b {
              leaf range {
                type empty;
              }
              leaf start {
                tailf:cli-drop-node-name;
                type string;
              }
              leaf end {
                tailf:cli-drop-node-name;
                type string;
              }
            }
          }
        }
        container dst-port {
          uses port-choice-grouping;
        }
        container src-port {
          uses port-choice-grouping;
        }
      }
      container action {
        presence "true";
        leaf profile {
          type string;
        }
        leaf fc {
          type ncs_compliance_template_fc-name;
        }
        leaf priority {
          type string;
        }
        leaf policer {
          type string;
        }
      }
    }
  }

  grouping ncs_compliance_template_ipv6-criteria-grouping {
    list entry {
      // NCS patched for predictable order
      ordered-by user;
      key "id";
      leaf id {
        type string;
      }
      leaf description {
        type string;
      }
      container match {
        leaf protocol {
          type ncs_compliance_template_protocol;
        }
        leaf next-header {
          type string;
        }
        leaf dscp {
          type ncs_compliance_template_dscp-type;
        }
        container src-ip {
          uses ncs_compliance_template_filter-match-ip-grouping;
        }
        container dst-ip {
          uses ncs_compliance_template_filter-match-ip-grouping;
        }

        grouping port-choice-grouping {
          choice port-choice {
            case a {
              leaf op {
                tailf:cli-drop-node-name;
                type string;
              }
              leaf port {
                tailf:cli-drop-node-name;
                type string;
              }
            }
            case b {
              leaf range {
                type empty;
              }
              leaf start {
                tailf:cli-drop-node-name;
                type string;
              }
              leaf end {
                tailf:cli-drop-node-name;
                type string;
              }
            }
          }
        }
        container dst-port {
          uses port-choice-grouping;
        }
        container src-port {
          uses port-choice-grouping;
        }
      }
      container action {
        leaf fc {
          type string;
        }
        leaf priority {
          type string;
        }
        leaf policer {
          type string;
        }
      }
    }
  }

  grouping ncs_compliance_template_mac-criteria-grouping {
    leaf match-criteria {
      tailf:cli-drop-node-name;
      type string;
    }
    leaf type {
      type string;
    }
    list entry {
      // NCS patched for predictable order
      ordered-by user;
      key "id";
      leaf id {
        type string;
      }
      leaf description {
        type string;
      }
      container match {
        leaf frame-type {
          type string;
        }
        container outer-tag {
          leaf value {
            tailf:cli-drop-node-name;
            type string;
          }
          leaf vid-mask {
            tailf:cli-drop-node-name;
            type string;
          }
        }

        grouping match-mac-grouping {
          leaf ieee-address {
            tailf:cli-drop-node-name;
            type ncs_compliance_template_ieee-mac;
          }
          leaf ieee-address-mask {
            tailf:cli-drop-node-name;
            type ncs_compliance_template_ieee-mac;
          }
        }
        container dst-mac {
          uses match-mac-grouping;
        }
        container src-mac {
          uses match-mac-grouping;
        }
        container dot1p {
          leaf dot1p-value {
            tailf:cli-drop-node-name;
            type string;
          }
          leaf dot1p-mask {
            tailf:cli-drop-node-name;
            type string;
          }
        }
        leaf etype {
          type string;
        }
      }
      container action {
        leaf fc {
          type ncs_compliance_template_fc-name;
        }
        leaf priority {
          type string;
        }
      }
    }
  }

  grouping ncs_compliance_template_meter-grouping {
    leaf meter-id {
      type string;
    }
    leaf multipoint {
      type empty;
    }
    uses ncs_compliance_template_queue-adaptation-grouping;

    grouping unit-grouping {
      leaf unit {
        tailf:cli-drop-node-name;
        type string;
      }
    }
    container cbs {
      leaf size {
        tailf:cli-drop-node-name;
        type string;
      }
      uses unit-grouping;
    }
    container mbs {
      leaf size {
        tailf:cli-drop-node-name;
        type string;
      }
      uses unit-grouping;
    }
    container rate {
      leaf cir {
        type ncs_compliance_template_rate-type;
      }
      leaf pir {
        type ncs_compliance_template_rate-type;
      }
    }
    leaf mode {
      type string;
    }
  }

  grouping ncs_compliance_template_cpm-filter-match-port-grouping {
    choice port-choice {
      case a {
        leaf port-number {
          tailf:cli-drop-node-name;
          type string;
        }
        leaf mask {
          tailf:cli-drop-node-name;
          type string;
        }
      }
      case b {
        leaf range {
          type empty;
        }
        leaf start {
          tailf:cli-drop-node-name;
          type string;
        }
        leaf end {
          tailf:cli-drop-node-name;
          type string;
        }
      }
      case c {
        leaf port-list {
          type string;
        }
      }
    }
  }

  grouping ncs_compliance_template_filter-match-ip-grouping {
    choice ip {
      leaf address {
        tailf:cli-drop-node-name;
        type string;
      }
      leaf ip-prefix-list {
        type string;
      }
      leaf ipv6-prefix-list {
        type ncs_compliance_template_string32;
      }
    }
  }

  grouping ncs_compliance_template_filter-match-ipv6-grouping {
    choice ipv6 {
      leaf address {
        tailf:cli-drop-node-name;
        type string;
      }
      leaf ipv6-prefix-list {
        type string;
      }
    }
  }

  grouping ncs_compliance_template_sap-egress-grouping {
    container agg-rate {
      container rate {
        leaf val {
          tailf:cli-drop-node-name;
          type string;
        }
        leaf cir {
          type string;
        }
      }
    }
    leaf egress-remark-policy {
      type string;
    }
    leaf vlan-qos-policy {
      type string;
    }
    leaf agg-rate-limit {
      type string;
    }
    container filter {
      uses ncs_compliance_template_filter-choice;
    }
    leaf multicast-group {
      type string;
    }
    leaf qos {
      type string;
    }
    uses ncs_compliance_template_sap-queue-override-grouping;
    leaf scheduler-policy {
      type string;
    }
    uses ncs_compliance_template_sap-scheduler-override-grouping;
    uses ncs_compliance_template_sap-policer-override-grouping-egress;
    leaf qinq-mark-top-only {
      type empty;
    }
    leaf dest-mac-rewrite {
      type string;
    }
    container qtag-manipulation {
      leaf preserve {
        type empty;
      }
    }
  }

  grouping ncs_compliance_template_sap-ingress-grouping {
    container filter {
      uses ncs_compliance_template_filter-choice;
    }
    container aggregate-meter-rate {
      leaf value {
        tailf:cli-drop-node-name;
        type string;
      }
      leaf burst {
        type string;
      }
    }
    leaf match-qinq-dot1p {
      type string;
    }
    container qos {
      leaf policy-id {
        tailf:cli-drop-node-name;
        type string;
      }
      leaf shared-queuing {
        type empty;
      }
      leaf enable-table-classification {
        type empty;
      }
    }
    uses ncs_compliance_template_sap-queue-override-grouping;
    leaf agg-shaper-rate {
      type string;
    }
    uses ncs_compliance_template_sap-policer-override-grouping-ingress;
    leaf policer-control-policy {
      type string;
    }
    leaf scheduler-policy {
      type string;
    }
    uses ncs_compliance_template_sap-scheduler-override-grouping;
    leaf vlan-translation {
      type string;
    }
    container aggregate-policer-rate {
      leaf rate {
        tailf:cli-drop-node-name;
        type string;
      }
      leaf burst {
        type string;
      }
    }
    container qtag-manipulation {
      leaf preserve {
        type empty;
      }
    }
  }

  grouping ncs_compliance_template_queue-ref-grouping {
    leaf queue-id {
      tailf:cli-drop-node-name;
      type string;
    }
    leaf group {
      type string;
    }
  }

  grouping ncs_compliance_template_policer-ref-grouping {
    leaf policer-id {
      tailf:cli-drop-node-name;
      type string;
    }
  }

  grouping ncs_compliance_template_policy-option-action-params-grouping {
    leaf add-paths-send-limit {
      type string;
    }
    leaf admin-tag-policy {
      type string;
    }
    leaf advertise-label {
      type string;
    }
    leaf bgp-leak {
      type empty;
    }
    container aigp-metric {
      leaf add {
        type empty;
      }
      leaf aigp-metric {
        tailf:cli-drop-node-name;
        type string;
      }
    }
    container as-path {
      leaf action {
        tailf:cli-drop-node-name;
        type string;
      }
      leaf name {
        tailf:cli-drop-node-name;
        type string;
      }
    }
    container as-path-prepend {
      choice as-choice {
        leaf as-number {
          tailf:cli-drop-node-name;
          type string;
        }
        leaf most-recent {
          type empty;
        }
      }
      leaf repeat {
        tailf:cli-drop-node-name;
        type string;
      }
    }
    container community {
      choice comm {
        case add-remove {
          leaf-list add {
            // NCS patched for predictable order
            ordered-by user;
            type string;
          }
          leaf-list remove {
            // NCS patched for predictable order
            ordered-by user;
            type string;
          }
        }
        leaf-list replace {
          // NCS patched for predictable order
          ordered-by user;
          type string;
        }
      }
    }
    container damping {
      leaf name {
        tailf:cli-drop-node-name;
        type string;
      }
    }
    leaf local-preference {
      type string;
    }
    container metric {
      leaf action {
        tailf:cli-drop-node-name;
        type string;
      }
      leaf metric {
        tailf:cli-drop-node-name;
        type string;
      }
    }
    container multicast-redirection {
      leaf fwd-service {
        type string;
      }
      leaf ip-int-name {
        tailf:cli-drop-node-name;
        type string;
      }
    }
    choice next-hop-choice {
      leaf next-hop {
        type string;
      }
      leaf next-hop-self {
        type empty;
      }
    }
    leaf origin {
      type string;
    }
    leaf preference {
      type string;
    }
    leaf tag {
      type ncs_compliance_template_policy-options-tag;
    }
    leaf type {
      type string;
    }
    container bgp-med {
      container set {
        leaf value {
          tailf:cli-drop-node-name;
          type string;
        }
      }
    }
    leaf sr-label-index {
      type string;
    }
  }

  grouping ncs_compliance_template_policy-options-action-fc-grouping {
    container fc {
      leaf fc {
        tailf:cli-drop-node-name;
        type ncs_compliance_template_fc-name;
      }
      leaf priority {
        type string;
      }
    }
  }

  grouping ncs_compliance_template_policy-options-default-action-grouping {
    choice action {
      leaf reject {
        type empty;
      }
      container drop {
        presence "true";
        uses ncs_compliance_template_policy-option-action-params-grouping;
      }
      container accept {
        presence "true";
        uses ncs_compliance_template_policy-option-action-params-grouping;
      }
      container next-entry {
        presence "true";
        uses ncs_compliance_template_policy-option-action-params-grouping;
      }
      container next-policy {
        presence "true";
        uses ncs_compliance_template_policy-option-action-params-grouping;
      }
    }
  }

  grouping ncs_compliance_template_policy-options-action-grouping {
    choice action {
      leaf reject {
        type empty;
      }
      container drop {
        presence "true";
        uses ncs_compliance_template_policy-option-action-params-grouping;
        uses ncs_compliance_template_policy-options-action-fc-grouping;
      }
      container accept {
        presence "true";
        uses ncs_compliance_template_policy-option-action-params-grouping;
        uses ncs_compliance_template_policy-options-action-fc-grouping;
      }
      container next-entry {
        presence "true";
        uses ncs_compliance_template_policy-option-action-params-grouping;
        uses ncs_compliance_template_policy-options-action-fc-grouping;
      }
      container next-policy {
        presence "true";
        uses ncs_compliance_template_policy-option-action-params-grouping;
        uses ncs_compliance_template_policy-options-action-fc-grouping;
      }
    }
  }

  grouping ncs_compliance_template_mbs-rate-grouping {
    leaf size {
      tailf:cli-drop-node-name;
      type string;
    }
    leaf unit {
      tailf:cli-drop-node-name;
      type string;
    }
  }

  grouping ncs_compliance_template_policer-cbs-mbs-rate-grouping {
    container cbs {
      uses ncs_compliance_template_mbs-rate-grouping;
    }
    container mbs {
      uses ncs_compliance_template_mbs-rate-grouping;
    }
    container rate {
      leaf pir {
        tailf:cli-drop-node-name;
        type ncs_compliance_template_rate-type;
      }
      leaf cir {
        type ncs_compliance_template_rate-type;
      }
    }
    leaf stat-mode {
      type ncs_compliance_template_policer-stat-mode;
    }
  }

  grouping ncs_compliance_template_policer-cbs-mbs-rate-with-packet-offset-grouping {
    uses ncs_compliance_template_policer-cbs-mbs-rate-grouping;
    container packet-byte-offset {
      choice add-delete {
        leaf add {
          type string;
        }
        leaf subtract {
          type string;
        }
      }
    }
  }

  grouping ncs_compliance_template_policer-grouping {
    uses ncs_compliance_template_queue-adaptation-grouping;
    leaf adv-config-policy {
      type string;
    }
    uses ncs_compliance_template_policer-cbs-mbs-rate-with-packet-offset-grouping;
    leaf description {
      type string;
    }
    leaf high-prio-only {
      type string;
    }
    container parent {
      leaf name {
        tailf:cli-drop-node-name;
        type string;
      }
      leaf level {
        type string;
      }
      leaf weight-level {
        tailf:alt-name "weight";
        type string;
      }
    }
    leaf profile-capped {
      type empty;
    }
  }

  grouping ncs_compliance_template_queue-grouping {
    leaf multipoint {
      type empty;
    }
    leaf queue-type {
      tailf:cli-drop-node-name;
      type ncs_compliance_template_queue-type;
    }
    leaf queue-mode-m {
      tailf:cli-drop-node-name;
      type string;
    }
    uses ncs_compliance_template_queue-adaptation-grouping;
    leaf adv-config-policy {
      type string;
    }
    leaf avg-frame-overhead {
      type string;
    }
    container burst-limit {
      leaf size {
        tailf:cli-drop-node-name;
        type string;
      }
      leaf unit {
        tailf:cli-drop-node-name;
        type string;
      }
    }
    leaf cbs {
      type string;
    }
    leaf high-prio-only {
      type string;
    }
    container mbs {
      leaf size {
        tailf:cli-drop-node-name;
        type string;
      }
      leaf unit {
        tailf:cli-drop-node-name;
        type string;
      }
    }
    container parent {
      leaf name {
        tailf:cli-drop-node-name;
        type string;
      }
      leaf level {
        type string;
      }
      leaf weight {
        type string;
      }
      leaf cir-level {
        type string;
      }
      leaf cir-weight {
        type string;
      }
    }
    container percent-rate {
      leaf pir-percent {
        tailf:cli-drop-node-name;
        type string;
      }
      leaf cir {
        type string;
      }
    }
    leaf pool {
      type string;
    }
    uses ncs_compliance_template_port-parent-grouping;
    uses ncs_compliance_template_queue-rate-grouping;
    leaf slope-policy {
      type string;
    }
    container wred-queue {
      leaf policy {
        type string;
      }
      leaf mode {
        type string;
      }
      leaf slope-usage {
        type string;
      }
    }
    container xp-specific {
      container wred-queue {
        leaf policy {
          type string;
        }
      }
      uses ncs_compliance_template_packet-byte-offset-grouping;
    }
    container drop-tail {
      container low {
        leaf percent-reduction-from-mbs {
          type string;
        }
      }
    }
  }

  grouping ncs_compliance_template_queue-group-template-entry {
    leaf queue-group-name {
      type string;
    }
    leaf description {
      type string;
    }
    list fc {
      // NCS patched for predictable order
      ordered-by user;
      key "fc-name";
      leaf fc-name {
        type ncs_compliance_template_fc-name;
      }
      leaf queue {
        type string;
      }
    }
    list policer {
      // NCS patched for predictable order
      ordered-by user;
      key "policer-id";
      leaf policer-id {
        type string;
      }
      uses ncs_compliance_template_policer-grouping;
    }
    list queue {
      // NCS patched for predictable order
      ordered-by user;
      key "queue-id";
      leaf queue-id {
        type string;
      }
      uses ncs_compliance_template_queue-grouping;
    }
  }

  grouping ncs_compliance_template_dhcp-lease-time {
    leaf days {
      type string;
    }
    leaf hrs {
      type string;
    }
    leaf min {
      type string;
    }
    leaf sec {
      type string;
    }
  }

  grouping ncs_compliance_template_bfd-grouping {
    leaf transmit-interval {
      tailf:cli-drop-node-name;
      type string;
    }
    leaf receive {
      type string;
    }
    leaf multiplier {
      type string;
    }
    leaf echo-receive {
      type string;
    }
    leaf type {
      type string;
    }
  }

  grouping ncs_compliance_template_dhcp6-grouping {
    container dhcp6-server {
      leaf max-nbr-of-leases {
        type string;
      }
    }
    container dhcp6-relay {
      leaf description {
        type string;
      }
      container lease-populate {
        presence "present";
        leaf nbr-of-leases {
          tailf:cli-drop-node-name;
          type string;
        }
        leaf route-populate {
          type empty;
        }
        leaf pd {
          type empty;
        }
        leaf exclude {
          type empty;
        }
        leaf na {
          type empty;
        }
        leaf ta {
          type empty;
        }
      }
      leaf neighbor-resolution {
        type empty;
      }
      container option {
        container interface-id {
          choice choice {
            leaf sap-id {
              type empty;
            }
            leaf ifindex {
              type empty;
            }
            leaf string {
              type string;
            }
          }
        }
        leaf remote-id {
          type empty;
        }
      }
      leaf source-address {
        type string;
      }
      leaf link-address {
        type string;
      }
      leaf-list server {
        // NCS patched for predictable order
        ordered-by user;
        type string;
      }
      leaf shutdown {
        type string;
      }
    }
  }

  grouping ncs_compliance_template_ipv6-grouping {
    list address {
      // NCS patched for predictable order
      ordered-by user;
      tailf:cli-suppress-mode;
      key "addr";
      leaf addr {
        type string;
      }
      leaf eui-64 {
        type empty;
      }
      leaf preferred {
        type empty;
      }
      leaf track-srrp {
        type string;
      }
      leaf modifier {
        type string;
      }
      leaf dad-disable {
        type empty;
      }
    }

    typedef nd-type {
      type string;
    }
    leaf nd-learn-unsolicited {
      type nd-type;
    }
    leaf nd-proactive-refresh {
      type nd-type;
    }
    container bfd {
      uses ncs_compliance_template_bfd-grouping;
    }
    leaf dad-disable {
      type empty;
    }
    container icmp6 {
      container packet-too-big {
        uses ncs_compliance_template_icmp-params-grouping;
      }
      container param-problem {
        uses ncs_compliance_template_icmp-params-grouping;
      }
      container redirects {
        uses ncs_compliance_template_icmp-params-grouping;
      }
      container time-exceeded {
        uses ncs_compliance_template_icmp-params-grouping;
      }
      container unreachables {
        uses ncs_compliance_template_icmp-params-grouping;
      }
    }
    container link-local-address {
      leaf addr {
        tailf:cli-drop-node-name;
        type string;
      }
      leaf preferred {
        type empty;
      }
      leaf dad-disable {
        type empty;
      }
    }
    leaf local-proxy-nd {
      type empty;
    }
    container neighbor {
      leaf addr {
        tailf:cli-drop-node-name;
        type string;
      }
      leaf mac-addr {
        tailf:cli-drop-node-name;
        type ncs_compliance_template_ieee-mac;
      }
    }
    container proxy-nd-policy {
      leaf name1 {
        tailf:cli-drop-node-name;
        type string;
      }
      leaf name2 {
        tailf:cli-drop-node-name;
        type string;
      }
      leaf name3 {
        tailf:cli-drop-node-name;
        type string;
      }
      leaf name4 {
        tailf:cli-drop-node-name;
        type string;
      }
      leaf name5 {
        tailf:cli-drop-node-name;
        type string;
      }
    }
    leaf qos-route-lookup {
      type string;
    }
    leaf reachable-time {
      type string;
    }
    container secure-nd {
      leaf allow-unsecured-msgs {
        type string;
      }
      leaf link-local-modifier {
        type string;
      }
      leaf public-key-min-bits {
        type string;
      }
      leaf security-parameter {
        type string;
      }
      leaf shutdown {
        type string;
      }
    }
    leaf tcp-mss {
      type string;
    }
    container urpf-check {
      presence "true";
      leaf ignore-default {
        type empty;
      }
      leaf mode {
        type string;
      }
    }
    list vrrp {
      // NCS patched for predictable order
      ordered-by user;
      key "id";
      leaf id {
        type string;
      }
      leaf owner {
        type empty;
      }
      leaf passive {
        type empty;
      }
      list backup {
        // NCS patched for predictable order
        ordered-by user;
        tailf:cli-suppress-mode;
        key "addr";
        leaf addr {
          type string;
        }
      }
      leaf init-delay {
        type string;
      }
      leaf mac {
        type ncs_compliance_template_ieee-mac;
      }
      leaf master-int-inherit {
        type string;
      }
      container message-interval {
        leaf seconds {
          tailf:cli-drop-node-name;
          type string;
        }
        leaf milliseconds {
          type string;
        }
      }
      leaf ping-reply {
        type empty;
      }
      leaf policy {
        type string;
      }
      leaf preempt {
        type string;
      }
      leaf priority {
        type string;
      }
      leaf standby-forwarding {
        type empty;
      }
      leaf telnet-reply {
        type empty;
      }
      leaf traceroute-reply {
        type empty;
      }
      leaf shutdown {
        type string;
      }
    }
  }

  grouping ncs_compliance_template_icmp-params-grouping {
    choice icmp-params-choice {
      leaf disable {
        type empty;
      }
      case enable {
        leaf number {
          tailf:cli-drop-node-name;
          type string;
        }
        leaf seconds {
          tailf:cli-drop-node-name;
          type string;
        }
      }
    }
  }

  grouping ncs_compliance_template_interface-icmp-grouping {
    container icmp {
      leaf mask-reply {
        type string;
      }
      container redirects {
        uses ncs_compliance_template_icmp-params-grouping;
      }
      container ttl-expired {
        uses ncs_compliance_template_icmp-params-grouping;
      }
      container unreachables {
        uses ncs_compliance_template_icmp-params-grouping;
      }
    }
  }

  grouping ncs_compliance_template_subscriber-interface-dhcp-common-grouping {
    container proxy-server {
      leaf emulated-server {
        type string;
      }
      container lease-time {
        leaf days {
          type string;
        }
        leaf hrs {
          type string;
        }
        leaf min {
          type string;
        }
        leaf sec {
          type string;
        }
      }
      leaf shutdown {
        type string;
      }
    }
    leaf-list server {
      // NCS patched for predictable order
      ordered-by user;
      type string;
    }
    container gi-address {
      leaf address {
        tailf:cli-drop-node-name;
        type string;
      }
      leaf src-ip-addr {
        type empty;
      }
    }
  }

  grouping ncs_compliance_template_dhcp-option-grouping {
    container option {
      leaf action {
        type string;
      }
      container remote-id {
        presence "true";
        choice remote-id {
          leaf mac {
            tailf:cli-drop-node-name;
            type string;
          }
          leaf string {
            type string;
          }
        }
      }
      container vendor-specific-option {
        leaf client-mac-address {
          type empty;
        }
        leaf pool-name {
          type empty;
        }
        leaf service-id {
          type empty;
        }
        leaf string {
          type string;
        }
      }
    }
  }

  grouping ncs_compliance_template_subscriber-interface-grouping {
    leaf id {
      type string;
    }
    leaf fwd-service {
      type ncs_compliance_template_service-id;
    }
    leaf wan-mode {
      type string;
    }
    leaf fwd-subscriber-interface {
      type string;
    }
    leaf description {
      type string;
    }
    leaf allow-unmatching-subnets {
      type empty;
    }
    list address {
      // NCS patched for predictable order
      ordered-by user;
      tailf:cli-suppress-mode;
      key "ip-address";
      leaf ip-address {
        type string;
      }
      leaf gw-ip-address {
        type string;
      }
      leaf populate-host-routes {
        type empty;
      }
      leaf track-srrp {
        type string;
      }
    }

    grouping ipoe-linking-grouping {
      container ipoe-linking {
        leaf gratuitous-rtr-adv {
          type empty;
        }
        leaf shared-circuit-id {
          type empty;
        }
        leaf shutdown {
          type string;
        }
      }
    }
    uses ipoe-linking-grouping;
    list group-interface {
      // NCS patched for predictable order
      ordered-by user;
      key "id";
      leaf id {
        type string;
      }
      leaf oper-up-while-empty {
        type empty;
      }
      uses ipoe-linking-grouping;
      leaf shcv-policy {
        type string;
      }
      leaf shcv-policy-ipv4 {
        type string;
      }
      leaf shcv-policy-ipv6 {
        type string;
      }
      container data-trigger {
        leaf shutdown {
          type string;
        }
      }
      leaf description {
        type string;
      }
      uses ncs_compliance_template_interface-icmp-grouping;
      leaf remote-proxy-arp {
        type empty;
      }
      container ipv6 {
        leaf allow-multiple-wan-addresses {
          type empty;
        }
        container router-advertisements {
          container dns-options {
            leaf include-dns {
              type empty;
            }
            leaf rdnss-lifetime {
              type string;
            }
          }
          leaf managed-configuration {
            type empty;
          }
          leaf retransmit-time {
            type string;
          }
          leaf max-advertisement {
            type string;
          }
          leaf current-hop-limit {
            type string;
          }
          leaf mtu {
            type string;
          }
          leaf reachable-time {
            type string;
          }
          leaf other-stateful-configuration {
            type empty;
          }
          leaf router-lifetime {
            type string;
          }
          container prefix-options {
            leaf autonomous {
              type empty;
            }
            leaf on-link {
              type string;
            }
            leaf preferred-lifetime {
              type string;
            }
            leaf valid-lifetime {
              type string;
            }
          }
          leaf shutdown {
            type string;
          }
        }
        container auto-reply {
          leaf neighbor-solicitation {
            type empty;
          }
          leaf router-solicitation {
            type empty;
          }
        }
        container urpf-check {
          presence "true";
          leaf mode {
            type string;
          }
        }
        container dhcp6 {
          leaf user-db {
            type string;
          }
          leaf user-ident {
            type string;
          }
          container relay {
            leaf description {
              type string;
            }
            leaf link-address {
              type string;
            }
            list server {
              // NCS patched for predictable order
              ordered-by user;
              tailf:cli-suppress-mode;
              key "ip";
              leaf ip {
                type string;
              }
            }
            leaf source-address {
              type string;
            }
            leaf shutdown {
              type string;
            }
          }
          container proxy-server {
            container lease-time {
              leaf days {
                type string;
              }
              leaf hrs {
                type string;
              }
              leaf min {
                type string;
              }
              leaf sec {
                type string;
              }
            }
            uses ncs_compliance_template_dhcp6-lease-timers-grouping;
            leaf shutdown {
              type string;
            }
          }
          leaf python-policy {
            type ncs_compliance_template_string32;
          }
          container option {
            container interface-id {
              leaf type {
                tailf:cli-drop-node-name;
                type string;
              }
              leaf stringval {
                tailf:cli-drop-node-name;
                type string;
              }
            }
            leaf remote-id {
              type empty;
            }
          }
        }
      }
      leaf arp-populate {
        type empty;
      }
      leaf authentication-policy {
        type string;
      }
      leaf redundant-interface {
        type string;
      }
      leaf srrp-enabled-routing {
        type empty;
      }
      leaf enable-ingress-stats {
        type empty;
      }
      leaf ip-mtu {
        type string;
      }
      leaf tos-marking-state {
        type string;
      }
      container host-connectivity-verify {
        leaf interval {
          type string;
        }
        leaf action {
          type string;
        }
        leaf timeout {
          type string;
        }
        leaf retry-count {
          type string;
        }
        leaf family {
          type string;
        }
      }
      container dhcp {
        leaf description {
          type string;
        }
        leaf trusted {
          type empty;
        }
        container lease-populate {
          leaf nr-of-leases {
            tailf:cli-drop-node-name;
            type string;
          }
          leaf l2-header {
            type empty;
          }
          leaf mac {
            type string;
          }
        }
        container relay-proxy {
          presence "true";
          leaf release-update-src-ip {
            type empty;
          }
          leaf siaddr-override {
            type string;
          }
        }
        leaf python-policy {
          type ncs_compliance_template_string32;
        }
        uses ncs_compliance_template_dhcp-option-grouping {
          augment "option" {
            container circuit-id {
              presence "true";
              leaf id {
                tailf:cli-drop-node-name;
                type string;
              }
            }
          }
          augment "option/vendor-specific-option" {
            leaf sap-id {
              type empty;
            }
          }
        }
        leaf user-db {
          type string;
        }
        leaf-list client-applications {
          // NCS patched for predictable order
          ordered-by user;
          type string;
        }
        uses ncs_compliance_template_subscriber-interface-dhcp-common-grouping {
          augment "proxy-server/lease-time" {
            leaf override {
              type empty;
            }
          }
        }
      }
      list sap {
        // NCS patched for predictable order
        ordered-by user;
        key "id";
        leaf id {
          type string;
        }
        leaf host-lockout-policy {
          type ncs_compliance_template_string32;
        }
        container egress {
          container filter {
            leaf ip {
              type ncs_compliance_template_filter-id;
            }
            leaf ipv6 {
              type ncs_compliance_template_filter-id;
            }
          }
          leaf qos {
            type string;
          }
        }
        container ingress {
          container filter {
            leaf ip {
              type ncs_compliance_template_filter-id;
            }
            leaf ipv6 {
              type ncs_compliance_template_filter-id;
            }
          }
          leaf qos {
            type string;
          }
        }
        leaf description {
          type string;
        }
        leaf anti-spoof {
          type string;
        }
        container sub-sla-mgmt {
          container def-sub-id {
            choice sub-id-choice {
              leaf string {
                type string;
              }
              leaf use-auto-id {
                type empty;
              }
              leaf use-sap-id {
                type empty;
              }
            }
          }
          container def-inter-dest-id {
            choice dest-id-choice {
              leaf string {
                type string;
              }
              leaf use-top-q {
                type empty;
              }
              leaf use-vpi {
                type empty;
              }
            }
          }
          leaf def-sub-profile {
            type string;
          }
          leaf def-sla-profile {
            type string;
          }
          leaf sub-ident-policy {
            type string;
          }
          container single-sub-parameters {
            leaf profiled-traffic-only {
              type empty;
            }
          }
          container multi-sub-sap {
            presence "true";
            leaf subscriber-limit {
              tailf:cli-drop-node-name;
              type string;
            }
          }
          leaf shutdown {
            type string;
          }
        }
        leaf calling-station-id {
          type string;
        }
        leaf monitor-oper-group {
          type string;
        }
        leaf shutdown {
          type string;
        }
      }
      container urpf-check {
        leaf mode {
          type string;
        }
      }
      container ipoe-session {
        container force-auth {
          choice force-auth {
            leaf disabled {
              type empty;
            }
            case cid-rid {
              leaf cid-change {
                type empty;
              }
              leaf rid-change {
                type empty;
              }
            }
          }
        }
        leaf sap-session-limit {
          type string;
        }
        leaf session-limit {
          type string;
        }
        container min-auth-interval {
          choice interval {
            leaf infinite {
              tailf:cli-drop-node-name;
              type string;
            }
            case time {
              leaf days {
                type string;
              }
              leaf hrs {
                type string;
              }
              leaf min {
                type string;
              }
              leaf sec {
                type string;
              }
            }
          }
        }
        uses ncs_compliance_template_ipoe-session-grouping;
      }
      container pppoe {
        leaf description {
          type string;
        }
        leaf policy {
          type ncs_compliance_template_string32;
        }
        leaf sap-session-limit {
          type string;
        }
        leaf session-limit {
          type string;
        }
        leaf user-db {
          type string;
        }
        leaf shutdown {
          type string;
        }
      }
      list srrp {
        // NCS patched for predictable order
        ordered-by user;
        key "srrp-id";
        leaf srrp-id {
          type string;
        }
        leaf description {
          type string;
        }
        leaf keep-alive-interval {
          type string;
        }
        leaf message-path {
          type string;
        }
        list policy {
          // NCS patched for predictable order
          ordered-by user;
          tailf:cli-suppress-mode;
          key "vrrp-policy-id";
          leaf vrrp-policy-id {
            type string;
          }
        }
        leaf priority {
          type string;
        }
        leaf shutdown {
          type string;
        }
      }
      leaf shutdown {
        type string;
      }
    }
    container pppoe {
      leaf description {
        type string;
      }
      leaf session-limit {
        type string;
      }
    }
    leaf private-retail-subnets {
      type empty;
    }
    leaf unnumbered {
      type string;
    }
  }

  grouping ncs_compliance_template_nat-pool-grouping {
    container nat {
      container inside {
        container l2-aware {
          list address {
            // NCS patched for predictable order
            ordered-by user;
            tailf:cli-suppress-mode;
            key "ip-addr";
            leaf ip-addr {
              type string;
            }
          }
        }
        leaf nat-policy {
          type string;
        }
        leaf destination-prefix {
          type string;
        }
      }
      container outside {
        list pool {
          // NCS patched for predictable order
          ordered-by user;
          key "name";
          leaf name {
            type string;
          }
          leaf nat-group {
            type string;
          }
          leaf type {
            type string;
          }
          container port-reservation {
            leaf blocks {
              type string;
            }
            leaf ports {
              type string;
            }
          }
          leaf port-forwarding-range {
            type string;
          }
          leaf subscriber-limit {
            type string;
          }
          container watermarks {
            leaf high {
              type string;
            }
            leaf low {
              type string;
            }
          }
          list address-range {
            // NCS patched for predictable order
            ordered-by user;
            key "start-ip-address end-ip-address";
            leaf start-ip-address {
              type string;
            }
            leaf end-ip-address {
              type string;
            }
          }
          leaf shutdown {
            type string;
          }
        }
      }
    }
  }

  grouping ncs_compliance_template_static-route-extras-grouping {
    leaf preference {
      type string;
    }
    leaf metric {
      type string;
    }
    choice ed {
      leaf enable {
        type empty;
      }
      leaf disable {
        type empty;
      }
    }
    leaf tag {
      type string;
    }
    leaf community {
      type string;
    }
    leaf description {
      type string;
    }
    leaf mcast-family {
      tailf:cli-drop-node-name;
      type string;
    }
    leaf bfd-enable {
      type empty;
    }
    leaf cpe-check {
      type string;
    }
    leaf interval {
      type string;
    }
    leaf drop-count {
      type string;
    }
    leaf log {
      type empty;
    }
    leaf prefix-list {
      type string;
    }
    choice an {
      leaf all {
        type empty;
      }
      leaf none {
        type empty;
      }
    }
    leaf ldp-sync {
      type empty;
    }
    leaf fc {
      type ncs_compliance_template_fc-name;
    }
    leaf priority {
      type string;
    }
  }

  grouping ncs_compliance_template_prompted-authentication-key-grouping {
    container authentication-key {
      leaf key {
        tailf:cli-drop-node-name;
        type string;
      }
      leaf method {
        tailf:cli-drop-node-name;
        type ncs_compliance_template_hash-method;
      }
    }
  }

  grouping ncs_compliance_template_prompted-hello-authentication-key-grouping {
    container hello-authentication-key {
      leaf key {
        tailf:cli-drop-node-name;
        type string;
      }
      leaf method {
        tailf:cli-drop-node-name;
        type ncs_compliance_template_hash-method;
      }
    }
    leaf hello-auth-keychain {
      type string;
    }
  }

  grouping ncs_compliance_template_bgp-import-export-grouping {
    leaf-list export {
      // NCS patched for predictable order
      ordered-by user;
      type string;
    }
    leaf-list import {
      // NCS patched for predictable order
      ordered-by user;
      type string;
    }
  }

  grouping ncs_compliance_template_max-paths-grouping {
    leaf max-paths {
      tailf:cli-drop-node-name;
      type string;
    }
    leaf ebgp {
      type string;
    }
    leaf ibgp {
      type string;
    }
    leaf restrict {
      type string;
    }
  }

  grouping ncs_compliance_template_bgp-multipath-grouping {
    container multipath {
      uses ncs_compliance_template_max-paths-grouping;
    }
  }

  grouping ncs_compliance_template_max-paths-uneqcosts-grouping {
    uses ncs_compliance_template_max-paths-grouping;
    leaf unequal-cost {
      type empty;
    }
  }

  grouping ncs_compliance_template_bgp-multi-path-grouping {
    container multi-path {
      container ipv4 {
        uses ncs_compliance_template_max-paths-uneqcosts-grouping;
      }
      container ipv6 {
        uses ncs_compliance_template_max-paths-uneqcosts-grouping;
      }
      container label-ipv4 {
        uses ncs_compliance_template_max-paths-uneqcosts-grouping;
      }
      container maximum-paths {
        uses ncs_compliance_template_max-paths-uneqcosts-grouping;
      }
    }
  }

  grouping ncs_compliance_template_bgp-graceful-restart-grouping {
    container graceful-restart {
      presence "true";
      leaf enable-notification {
        type empty;
      }
      container long-lived {
        presence "true";

        grouping bgp-graceful-override-times-grouping {
          leaf advertised-stale-time {
            type string;
          }
          leaf helper-override-stale-time {
            type string;
          }
        }
        container advertise-stale-to-all-neighbors {
          presence "true";
          leaf without-no-export {
            type empty;
          }
        }
        uses bgp-graceful-override-times-grouping;
        list family {
          // NCS patched for predictable order
          ordered-by user;
          key "family";
          leaf family {
            type ncs_compliance_template_family-names-type;
          }
          uses bgp-graceful-override-times-grouping;
        }
        leaf forwarding-bits-set {
          type string;
        }
        leaf helper-override-restart-time {
          type string;
        }
      }
      leaf restart-time {
        type string;
      }
      leaf stale-routes-time {
        type string;
      }
    }
  }

  grouping ncs_compliance_template_bgp-prefix-limit-grouping {
    container prefix-limit {
      choice apis {
        list new {
          // NCS patched for predictable order
          ordered-by user;
          tailf:cli-drop-node-name;
          tailf:cli-suppress-mode;
          key "family";
          leaf family {
            type string;
          }
          leaf limit {
            tailf:cli-drop-node-name;
            type string;
          }
          leaf log-only {
            type empty;
          }
          leaf threshold {
            type string;
          }
          leaf idle-timeout {
            type string;
          }
          leaf post-import {
            type empty;
          }
        }
        container old {
          tailf:cli-drop-node-name;
          leaf limit {
            tailf:cli-drop-node-name;
            type string;
          }
          leaf log-only {
            type empty;
          }
          leaf threshold {
            type string;
          }
          leaf idle-timeout {
            type string;
          }
        }
      }
    }
  }

  grouping ncs_compliance_template_router-bgp-add-paths-grouping {
    container add-paths {

      grouping path-proto-send-receive-grouping {
        leaf send {
          type string;
        }
        leaf receive {
          type empty;
        }
        leaf none {
          type empty;
        }
      }
      container ipv4 {
        uses path-proto-send-receive-grouping;
      }
      container ipv6 {
        uses path-proto-send-receive-grouping;
      }
      container label-ipv4 {
        uses path-proto-send-receive-grouping;
      }
      container label-ipv6 {
        uses path-proto-send-receive-grouping;
      }
      container vpn-ipv4 {
        uses path-proto-send-receive-grouping;
      }
      container vpn-ipv6 {
        uses path-proto-send-receive-grouping;
      }
    }
  }

  grouping ncs_compliance_template_router-bgp-grouping {
    uses ncs_compliance_template_router-bgp-add-paths-grouping;
    leaf advertise-inactive {
      type empty;
    }
    leaf-list advertise-ipv6-next-hops {
      // NCS patched for predictable order
      ordered-by user;
      type string;
    }
    leaf loop-detect-threshold {
      type string;
    }
    leaf def-recv-evpn-encap {
      type string;
    }
    container cluster {
      leaf cluster-id {
        tailf:cli-drop-node-name;
        type string;
      }
      leaf orr-location {
        type string;
      }
      leaf allow-local-fallback {
        type empty;
      }
    }
    leaf aggregator-id-zero {
      type empty;
    }
    leaf aigp {
      type empty;
    }
    leaf auth-keychain {
      type string;
    }
    uses ncs_compliance_template_prompted-authentication-key-grouping;
    leaf bfd-enable {
      type empty;
    }
    leaf connect-retry {
      type string;
    }
    leaf damping {
      type empty;
    }
    leaf default-route-target {
      type empty;
    }
    leaf description {
      type string;
    }
    leaf disable-4byte-asn {
      type empty;
    }
    leaf disable-capability-negotiation {
      type empty;
    }
    leaf disable-client-reflect {
      type empty;
    }
    leaf-list disable-communities {
      // NCS patched for predictable order
      ordered-by user;
      type string;
    }
    leaf disable-fast-external-failover {
      type empty;
    }
    leaf enable-peer-tracking {
      type empty;
    }
    leaf-list family {
      // NCS patched for predictable order
      ordered-by user;
      type ncs_compliance_template_family-names-type;
    }
    leaf flowspec-validate {
      type empty;
    }
    uses ncs_compliance_template_bgp-graceful-restart-grouping;
    container hold-time {
      leaf seconds {
        tailf:cli-drop-node-name;
        type string;
      }
      leaf min {
        type string;
      }
    }
    leaf keepalive {
      type string;
    }
    leaf local-address {
      type string;
    }
    uses ncs_compliance_template_bgp-local-as-grouping;
    leaf local-preference {
      type string;
    }
    leaf loop-detect {
      type string;
    }
    leaf med-out {
      type string;
    }
    leaf min-as-origination {
      type string;
    }
    leaf min-route-advertisement {
      type string;
    }
    leaf multihop {
      type string;
    }
    leaf next-hop-self {
      type empty;
    }
    container outbound-route-filtering {
      container extended-community {
        leaf accept-orf {
          type empty;
        }
        container send-orf {
          presence "true";
          leaf-list send-orf {
            // NCS patched for predictable order
            ordered-by user;
            tailf:cli-drop-node-name;
            type string;
          }
        }
      }
    }
    leaf passive {
      type empty;
    }
    leaf path-mtu-discovery {
      type empty;
    }
    leaf peer-as {
      type string;
    }
    leaf preference {
      type string;
    }
    uses ncs_compliance_template_bgp-prefix-limit-grouping;
    container remove-private {
      presence "true";
      leaf-list options {
        // NCS patched for predictable order
        ordered-by user;
        tailf:cli-drop-node-name;
        type string;
      }
    }
    leaf split-horizon {
      type empty;
    }
    container tcp-mss {
      leaf mss-val {
        tailf:cli-drop-node-name;
        type string;
      }
      leaf ip-stack {
        type empty;
      }
    }
    leaf ttl-security {
      type string;
    }
    leaf type {
      type string;
    }
    leaf vpn-apply-export {
      type empty;
    }
    leaf label-preference {
      type string;
    }
    leaf l2vpn-cisco-interop {
      type empty;
    }
    leaf vpn-apply-import {
      type empty;
    }
    leaf shutdown {
      type string;
    }
  }

  grouping ncs_compliance_template_bgp-local-as-grouping {
    container local-as {
      leaf number {
        tailf:cli-drop-node-name;
        type string;
      }
      leaf private {
        type empty;
      }
      leaf no-prepend-global-as {
        type empty;
      }
    }
  }

  grouping ncs_compliance_template_bgp-best-path-selection-grouping {
    container best-path-selection {
      container always-compare-med {
        presence "true";
        leaf strict-as {
          type empty;
        }
        leaf type {
          tailf:cli-drop-node-name;
          type string;
        }
      }
      leaf-list as-path-ignore {
        // NCS patched for predictable order
        ordered-by user;
        type string;
      }
      leaf compare-origin-validation-state {
        type empty;
      }
      leaf deterministic-med {
        type empty;
      }
      leaf ignore-nh-metric {
        type empty;
      }
      leaf ignore-router-id {
        type empty;
      }
      leaf origin-invalid-unusable {
        type empty;
      }
    }
  }

  grouping ncs_compliance_template_agg-rate-grouping {
    container agg-rate {
      leaf limit-unused-bandwidth {
        type empty;
      }
      leaf queue-frame-based-accounting {
        type empty;
      }
      leaf rate {
        type string;
      }
    }
  }

  grouping ncs_compliance_template_sap-egress-common-grouping {
    leaf policy-id {
      type string;
    }
    leaf description {
      type string;
    }
    list queue {
      // NCS patched for predictable order
      ordered-by user;
      key "queue-id";
      leaf queue-id {
        type string;
      }
      uses ncs_compliance_template_queue-grouping;
    }
  }

  grouping ncs_compliance_template_dot1p-params-grouping {
    choice dot1p {
      leaf dot1p-value {
        tailf:cli-drop-node-name;
        type string;
      }
      case in-out {
        leaf in-profile {
          type string;
        }
        leaf out-profile {
          type string;
        }
      }
    }
  }

  grouping ncs_compliance_template_sap-egress-fc-grouping {
    leaf fc-name {
      type string;
    }
    container queue {
      uses ncs_compliance_template_queue-ref-grouping;
      leaf instance {
        type string;
      }
    }
    container dot1p {
      uses ncs_compliance_template_dot1p-params-grouping;
    }
    container dot1p-inner {
      uses ncs_compliance_template_dot1p-params-grouping;
    }
    container dot1p-outer {
      uses ncs_compliance_template_dot1p-params-grouping;
    }
    container dscp {
      choice dscp {
        leaf dscp-name {
          tailf:cli-drop-node-name;
          type string;
        }
        case in-out {
          leaf in-profile {
            type string;
          }
          leaf out-profile {
            type string;
          }
        }
      }
    }
  }

  grouping ncs_compliance_template_mcac-grouping {
    container mcac {
      container mc-constraints {
        list level {
          // NCS patched for predictable order
          ordered-by user;
          tailf:cli-suppress-mode;
          key "level-id";
          leaf level-id {
            tailf:cli-drop-node-name;
            type string;
          }
          leaf bw {
            type string;
          }
        }
        list number-down {
          // NCS patched for predictable order
          ordered-by user;
          tailf:cli-suppress-mode;
          key "number-lag-port-down";
          leaf number-lag-port-down {
            type string;
          }
          leaf level {
            type string;
          }
        }
        leaf use-lag-port-weight {
          type empty;
        }
        leaf shutdown {
          type string;
        }
      }
      leaf policy {
        type string;
      }
      container unconstrained-bw {
        leaf bandwidth {
          tailf:cli-drop-node-name;
          type string;
        }
        leaf mandatory-bw {
          type string;
        }
      }
    }
  }

  grouping ncs_compliance_template_cron-schedule-grouping {
    list schedule {
      // NCS patched for predictable order
      ordered-by user;
      key "id owner";
      leaf id {
        type string;
      }
      leaf owner {
        type string;
      }
      leaf description {
        type string;
      }
      leaf interval {
        type string;
      }
      leaf count {
        type string;
      }
      leaf minute {
        type string;
      }
      leaf hour {
        type string;
      }
      leaf month {
        type string;
      }
      leaf-list day-of-month {
        // NCS patched for predictable order
        ordered-by user;
        type string;
      }
      leaf weekday {
        type string;
      }
      container end-time {
        leaf day-name {
          tailf:cli-drop-node-name;
          type string;
        }
        leaf time {
          tailf:cli-drop-node-name;
          type string;
        }
      }
      container script-policy {
        leaf policy {
          tailf:cli-drop-node-name;
          type ncs_compliance_template_string32;
        }
        leaf owner {
          type string;
        }
      }
      leaf type {
        type string;
      }
      leaf shutdown {
        type string;
      }
    }
  }

  grouping ncs_compliance_template_static-route-entry-nh-grouping {
    leaf community {
      type string;
    }
    leaf description {
      type string;
    }
    leaf metric {
      type string;
    }
    leaf preference {
      type string;
    }
    leaf tag {
      type string;
    }
    leaf bfd-enable {
      type empty;
    }
    leaf ldp-sync {
      type empty;
    }
    list cpe-check {
      // NCS patched for predictable order
      ordered-by user;
      key "address";
      leaf address {
        type string;
      }
      leaf drop-count {
        type string;
      }
      leaf interval {
        type string;
      }
      leaf log {
        type empty;
      }
    }
    container tunnel-next-hop {
      leaf resolution {
        type string;
      }
      container resolution-filter {
        container rsvp-te {
          presence "true";
          leaf lsp {
            type string;
          }
        }
        container sr-te {
          presence "true";
          leaf lsp {
            type string;
          }
        }
        container ldp {
          presence "true";
        }
        container mpls-fwd-policy {
          presence "true";
        }
        container rib-api {
          presence "true";
        }
        container sr-isis {
          presence "true";
        }
        container sr-ospf {
          presence "true";
        }
        container sr-ospf3 {
          presence "true";
        }
      }
    }
    leaf destination-class {
      type string;
    }
    leaf source-class {
      type string;
    }
    container forwarding-class {
      leaf class {
        tailf:cli-drop-node-name;
        type string;
      }
      leaf priority {
        type string;
      }
    }
    leaf shutdown {
      type string;
    }
  }

  grouping ncs_compliance_template_cflowd-params-grouping {
    container cflowd-parameters {
      list sampling {
        // NCS patched for predictable order
        ordered-by user;
        tailf:cli-suppress-mode;
        key "sampling";
        leaf sampling {
          type string;
        }
        leaf type {
          type string;
        }
        leaf direction {
          type string;
        }
      }
    }
  }

  grouping ncs_compliance_template_resolution-filter-grouping {
    container resolution-filter {
      leaf bgp {
        type empty;
      }
      leaf gre {
        type empty;
      }
      leaf ldp {
        type string;
      }
      leaf rsvp {
        type empty;
      }
      leaf sr-isis {
        type empty;
      }
      leaf sr-ospf {
        type empty;
      }
      leaf sr-te {
        type empty;
      }
    }
    leaf resolution {
      type string;
    }
  }

  grouping ncs_compliance_template_bgp-next-hop-resolution-grouping {
    container next-hop-resolution {
      leaf policy {
        type string;
      }
      leaf use-bgp-routes {
        type empty;
      }
      container label-route-transport-tunnel {
        container family {
          leaf address-family {
            tailf:cli-drop-node-name;
            type string;
          }
          // NCS expand uses statement
          container resolution-filter {
            leaf bgp {
              type empty;
            }
            leaf gre {
              type empty;
            }
            leaf ldp {
              type string;
            }
            leaf rsvp {
              type empty;
            }
            leaf sr-isis {
              type empty;
            }
            leaf sr-ospf {
              type empty;
            }
            leaf sr-te {
              type empty;
            }
          }
          leaf resolution {
            type string;
          }
        }
      }
      container labeled-routes {
        leaf prefer-transport-frr {
          type empty;
        }
        container transport-tunnel {
          list family {
            // NCS patched for predictable order
            ordered-by user;
            key "address-family";
            leaf address-family {
              type string;
            }
            // NCS expand uses statement
            container resolution-filter {
              leaf bgp {
                type empty;
              }
              leaf gre {
                type empty;
              }
              leaf ldp {
                type string;
              }
              leaf rsvp {
                type empty;
              }
              leaf sr-isis {
                type empty;
              }
              leaf sr-ospf {
                type empty;
              }
              leaf sr-te {
                type empty;
              }
            }
            leaf resolution {
              type string;
            }
          }
        }
      }
      container shortcut-tunnel {
        container family {

          grouping res-filter-grouping {
            container resolution-filter {
              leaf bgp {
                type empty;
              }
              leaf gre {
                type empty;
              }
              leaf ldp {
                type empty;
              }
              leaf rsvp {
                type empty;
              }
              leaf sr-isis {
                type empty;
              }
              leaf sr-ospf {
                type empty;
              }
              leaf sr-te {
                type empty;
              }
            }
            leaf resolution {
              type string;
            }
          }
          container ipv4 {
            uses res-filter-grouping;
          }
          container ipv6 {
            uses res-filter-grouping;
          }
        }
      }
      leaf weighted-ecmp {
        type empty;
      }
    }
  }

  grouping ncs_compliance_template_authentication-key-grouping {
    container authentication-key {
      leaf key {
        tailf:cli-drop-node-name;
        type string;
      }
      leaf method {
        tailf:cli-drop-node-name;
        type ncs_compliance_template_hash-method;
      }
    }
  }

  grouping ncs_compliance_template_hello-authentication-key-grouping {
    container hello-authentication-key {
      leaf key {
        tailf:cli-drop-node-name;
        type string;
      }
      leaf method {
        tailf:cli-drop-node-name;
        type ncs_compliance_template_hash-method;
      }
    }
  }

  grouping ncs_compliance_template_ipoe-session-grouping {
    leaf description {
      type string;
    }
    leaf ipoe-session-policy {
      type ncs_compliance_template_string32;
    }
    leaf user-db {
      type string;
    }
    leaf shutdown {
      type string;
    }
  }

  grouping ncs_compliance_template_packet-byte-offset-grouping {
    container packet-byte-offset {
      choice op {
        leaf add {
          type string;
        }
        leaf subtract {
          type string;
        }
      }
    }
  }

  grouping ncs_compliance_template_port-parent-grouping {
    container port-parent {
      presence "present";
      leaf weight {
        type string;
      }
      leaf level {
        type string;
      }
      leaf cir-weight {
        type string;
      }
      leaf cir-level {
        type string;
      }
    }
  }

  grouping ncs_compliance_template_router-aggregate-grouping {
    list aggregate {
      // NCS patched for predictable order
      ordered-by user;
      tailf:cli-suppress-mode;
      key "route";
      leaf route {
        type string;
      }
      leaf summary-only {
        type empty;
      }
      leaf discard-component-communities {
        type empty;
      }
      leaf as-set {
        type empty;
      }
      leaf aggregator {
        type string;
      }
      leaf-list community {
        // NCS patched for predictable order
        ordered-by user;
        type string;
      }
      leaf black-hole {
        type empty;
      }
      leaf description {
        type string;
      }
      leaf policy {
        type string;
      }
    }
  }

  grouping ncs_compliance_template_ospf-area-id-grouping {
    leaf area-id {
      type string;
    }
  }

  grouping ncs_compliance_template_service-id-grouping {
    leaf service-id {
      type ncs_compliance_template_service-id;
    }
  }

  grouping ncs_compliance_template_radius-server-grouping {
    list server {
      // NCS patched for predictable order
      ordered-by user;
      key "server-name";
      leaf server-name {
        type ncs_compliance_template_string32;
      }
      leaf address {
        type string;
      }
      leaf secret {
        type string;
      }
      leaf auth-port {
        type string;
      }
      leaf acct-port {
        type string;
      }
      leaf coa-script-policy {
        type ncs_compliance_template_string32;
      }
      leaf scheme {
        tailf:cli-drop-node-name;
        type ncs_compliance_template_hash-method;
      }
      leaf accept-coa {
        type empty;
      }
      leaf description {
        type string;
      }
      leaf python-policy {
        type ncs_compliance_template_string32;
      }
    }
  }

  grouping ncs_compliance_template_dhcp6-lease-timers-grouping {

    grouping dhcp6-lease-time-common-grouping {
      leaf sec {
        type string;
      }
    }
    container preferred-lifetime {
      leaf days {
        type string;
      }
      leaf hrs {
        type string;
      }
      leaf min {
        type string;
      }
      uses dhcp6-lease-time-common-grouping;
    }
    container rebind-timer {
      leaf days {
        type string;
      }
      leaf hrs {
        type string;
      }
      leaf min {
        type string;
      }
      uses dhcp6-lease-time-common-grouping;
    }
    container renew-timer {
      leaf days {
        type string;
      }
      leaf hrs {
        type string;
      }
      leaf min {
        type string;
      }
      uses dhcp6-lease-time-common-grouping;
    }
    container valid-lifetime {
      leaf days {
        type string;
      }
      leaf hrs {
        type string;
      }
      leaf min {
        type string;
      }
      uses dhcp6-lease-time-common-grouping;
    }
    container server-id {
      leaf duid {
        tailf:cli-drop-node-name;
        type string;
      }
      choice strhex {
        leaf string {
          type string;
        }
        leaf hex {
          type string;
        }
      }
    }
  }

  grouping ncs_compliance_template_snmp-community-grouping {
    list community {
      // NCS patched for predictable order
      ordered-by user;
      tailf:cli-suppress-mode;
      key "name";
      leaf name {
        type string;
      }
      leaf type {
        tailf:cli-drop-node-name;
        type ncs_compliance_template_hash-method;
      }
      leaf access-parameters {
        tailf:cli-drop-node-name;
        type string;
      }
      leaf version {
        type string;
      }
      leaf src-access-list {
        type ncs_compliance_template_string32;
      }
    }
  }

  grouping ncs_compliance_template_qos-dscp-list-grouping {
    list dscp {
      // NCS patched for predictable order
      ordered-by user;
      tailf:cli-suppress-mode;
      key "dscp-name";
      leaf dscp-name {
        type ncs_compliance_template_dscp-type;
      }
      leaf fc {
        type ncs_compliance_template_fc-name;
      }
      leaf profile {
        type ncs_compliance_template_in-out;
      }
    }
  }

  grouping ncs_compliance_template_qos-dot1p-list-grouping {
    list dot1p {
      // NCS patched for predictable order
      ordered-by user;
      tailf:cli-suppress-mode;
      key "id";
      leaf id {
        type string;
      }
      leaf fc {
        type ncs_compliance_template_fc-name;
      }
      leaf profile {
        type string;
      }
    }
    list prec {
      // NCS patched for predictable order
      ordered-by user;
      key "ip-prec-value";
      tailf:cli-suppress-mode;
      leaf ip-prec-value {
        tailf:cli-drop-node-name;
        type string;
      }
      leaf profile {
        type string;
      }
      leaf fc {
        type ncs_compliance_template_fc-name;
      }
    }
  }

  grouping ncs_compliance_template_slope-params-grouping {
    leaf start-avg {
      type string;
    }
    leaf max-avg {
      type string;
    }
    leaf max-prob {
      type string;
    }
    leaf shutdown {
      type string;
    }
  }

  grouping ncs_compliance_template_qos-lsp-exp-grouping {
    list lsp-exp {
      // NCS patched for predictable order
      ordered-by user;
      tailf:cli-suppress-mode;
      key "id";
      leaf id {
        type string;
      }
      leaf fc {
        type ncs_compliance_template_fc-name;
      }
      leaf profile {
        type string;
      }
    }
  }

  grouping ncs_compliance_template_bgp-common-grouping {
    leaf keepalive {
      type string;
    }
    container hold-time {
      leaf seconds {
        tailf:cli-drop-node-name;
        type string;
      }
      leaf min {
        type string;
      }
    }
    leaf preference {
      type string;
    }
  }

  grouping ncs_compliance_template_pim-common-grouping {
    leaf rpf6-table {
      type string;
    }
    leaf apply-to {
      type string;
    }
  }

  grouping ncs_compliance_template_local-dhcp-server-grouping {

    grouping dhcp-custom-options-grouping {
      list custom-option {
        // NCS patched for predictable order
        ordered-by user;
        tailf:cli-suppress-mode;
        key "number";
        leaf number {
          type string;
        }
        leaf-list address {
          // NCS patched for predictable order
          ordered-by user;
          type string;
        }
        leaf hex {
          type string;
        }
        leaf string {
          type string;
        }
      }
    }
    list local-dhcp-server {
      // NCS patched for predictable order
      ordered-by user;
      key "server-name";
      leaf server-name {
        type string;
      }
      leaf description {
        type string;
      }
      container use-gi-address {
        presence "true";
        leaf scope {
          type string;
        }
      }
      leaf force-renews {
        type empty;
      }
      list pool {
        // NCS patched for predictable order
        ordered-by user;
        key "pool-id";
        leaf pool-id {
          type ncs_compliance_template_string32;
        }
        leaf description {
          type string;
        }
        container max-lease-time {
          uses ncs_compliance_template_dhcp-lease-time;
        }
        container min-lease-time {
          uses ncs_compliance_template_dhcp-lease-time;
        }
        container minimum-free {
          leaf minimum-free-value {
            tailf:cli-drop-node-name;
            type string;
          }
          leaf percent {
            type empty;
          }
          leaf event-when-depleted {
            type empty;
          }
        }
        leaf nak-non-matching-subnet {
          type empty;
        }
        container offer-time {
          leaf min {
            type string;
          }
          leaf sec {
            type string;
          }
        }
        container options {
          leaf-list dns-server {
            // NCS patched for predictable order
            ordered-by user;
            type string;
          }
          leaf domain-name {
            type string;
          }
          container lease-rebind-time {
            uses ncs_compliance_template_dhcp-lease-time;
          }
          container lease-renew-time {
            uses ncs_compliance_template_dhcp-lease-time;
          }
          container lease-time {
            uses ncs_compliance_template_dhcp-lease-time;
          }
          leaf-list netbios-name-server {
            // NCS patched for predictable order
            ordered-by user;
            type string;
          }
          leaf netbios-node-type {
            type string;
          }
          uses dhcp-custom-options-grouping;
        }
        list subnet {
          // NCS patched for predictable order
          ordered-by user;
          key "subnet-id";
          leaf subnet-id {
            type string;
          }
          container address-range {
            uses ncs_compliance_template_ip-address-range {
              augment "low-high-list" {
                leaf failover {
                  type string;
                }
              }
            }
          }
          leaf drain {
            type empty;
          }
          container exclude-addresses {
            uses ncs_compliance_template_ip-address-range;
          }
          leaf maximum-declined {
            type string;
          }
          container minimum-free {
            leaf minimum-free-value {
              tailf:cli-drop-node-name;
              type string;
            }
            leaf percent {
              type empty;
            }
            leaf event-when-depleted {
              type empty;
            }
          }
          container options {
            leaf-list default-router {
              // NCS patched for predictable order
              ordered-by user;
              type string;
            }
            leaf subnet-mask {
              type string;
            }
            uses dhcp-custom-options-grouping;
          }
        }
      }
      container failover {
        leaf ignore-mclt-on-takeover {
          type empty;
        }
        container maximum-client-lead-time {
          leaf hrs {
            type string;
          }
          leaf min {
            type string;
          }
          leaf sec {
            type string;
          }
        }
        container partner-down-delay {
          leaf hrs {
            type string;
          }
          leaf min {
            type string;
          }
          leaf sec {
            type string;
          }
        }
        container peer {
          leaf ip-address {
            tailf:cli-drop-node-name;
            type string;
          }
          leaf tag {
            type string;
          }
        }
        container startup-wait-time {
          leaf min {
            type string;
          }
          leaf sec {
            type string;
          }
        }
        leaf shutdown {
          type string;
        }
      }
      container lease-hold-time {
        leaf days {
          type string;
        }
        leaf hrs {
          type string;
        }
        leaf min {
          type string;
        }
        leaf sec {
          type string;
        }
      }
      container lease-hold-time-for {
        leaf solicited-release {
          type empty;
        }
      }
      container use-pool-from-client {
        presence "true";
      }
      leaf shutdown {
        type string;
      }
    }
  }

  grouping ncs_template_src-dst-ip {
    leaf src-ip {
      type string;
    }
    leaf dst-ip {
      type string;
    }
  }

  grouping ncs_template_ip-address-range {
    list low-high-list {
      // NCS patched for predictable order
      ordered-by user;
      tailf:cli-drop-node-name;
      tailf:cli-suppress-mode;
      key "low high";
      leaf low {
        type string;
      }
      leaf high {
        type string;
      }
    }
  }

  grouping ncs_template_eth-cfm {
    leaf collect-lmm-stats {
      type empty;
    }
    list mep {
      // NCS patched for predictable order
      ordered-by user;
      key "mep-id domain association";
      leaf mep-id {
        type string;
      }
      leaf domain {
        type string;
      }
      leaf association {
        type string;
      }
      leaf direction {
        type ncs_template_direction;
      }
      container ais-enable {
        leaf-list client-meg-level {
          // NCS patched for predictable order
          ordered-by user;
          type string;
        }
        leaf description {
          type string;
        }
        leaf interval {
          type string;
        }
        leaf priority {
          type string;
        }
      }
      leaf ccm-enable {
        type empty;
      }
      leaf ccm-ltm-priority {
        type string;
      }
      leaf ccm-padding-size {
        type string;
      }
      leaf description {
        type string;
      }
      container eth-test-enable {
        uses ncs_template_eth-test;
      }
      leaf fault-propagation-enable {
        type string;
      }
      leaf install-mep {
        type empty;
      }
      leaf low-priority-defect {
        type string;
      }
      leaf mac-address {
        type ncs_template_ieee-mac;
      }
      leaf one-way-delay-threshold {
        type string;
      }
      leaf shutdown {
        type string;
      }
    }
  }

  grouping ncs_template_enable-origin-validation-grouping {
    leaf-list enable-origin-validation {
      // NCS patched for predictable order
      ordered-by user;
      type string;
    }
  }

  grouping ncs_template_igmp-static-grouping {
    container static {
      list group {
        // NCS patched for predictable order
        ordered-by user;
        key "grp-ip-addr";
        leaf grp-ip-addr {
          type string;
        }
        list source {
          // NCS patched for predictable order
          ordered-by user;
          tailf:cli-suppress-mode;
          key "ip-address";
          leaf ip-address {
            type string;
          }
        }
        leaf starg {
          type empty;
        }
      }
    }
  }

  grouping ncs_template_igmp-snooping-grouping {
    leaf disable-router-alert {
      type empty;
    }
    leaf fast-leave {
      type empty;
    }
    leaf import {
      type string;
    }
    leaf last-member-query-interval {
      type string;
    }
    leaf max-num-groups {
      type string;
    }
    leaf mrouter-port {
      type empty;
    }
    leaf query-interval {
      type string;
    }
    leaf query-response-interval {
      type string;
    }
    leaf robust-count {
      type string;
    }
    leaf send-queries {
      type empty;
    }
    uses ncs_template_igmp-static-grouping;
    leaf version {
      type string;
    }
  }

  grouping ncs_template_sdp-common {
    leaf vc-id {
      type string;
    }
    leaf vc-type {
      type string;
    }
    leaf endpoint {
      type string;
    }
    leaf icb {
      type empty;
    }
    leaf shutdown {
      type string;
    }
  }

  grouping ncs_template_sdp-spoke-mesh-common {
    leaf sdp-id {
      type string;
    }
    uses ncs_template_sdp-common;
    leaf accounting-policy {
      type string;
    }
    leaf auto-learn-mac-protect {
      type empty;
    }
    leaf description {
      type string;
    }
    leaf collect-stats {
      type empty;
    }
    container hash-label {
      presence "true";
      leaf signal-capability {
        type empty;
      }
    }
    leaf control-word {
      type empty;
    }
    container igmp-snooping {
      uses ncs_template_igmp-snooping-grouping;
    }
    container egress {
      container filter {
        uses ncs_template_filter-choice;
      }
      container qos {
        leaf network-policy-id {
          tailf:cli-drop-node-name;
          type string;
        }
        leaf port-redirect-group {
          type string;
        }
        leaf instance {
          type string;
        }
      }
      leaf vc-label {
        type string;
      }
    }
    container eth-cfm {
      uses ncs_template_eth-cfm;
    }
    leaf force-vlan-vc-forwarding {
      type empty;
    }
    container ingress {
      container filter {
        uses ncs_template_filter-choice;
      }
      container qos {
        leaf network-policy-id {
          tailf:cli-drop-node-name;
          type string;
        }
        leaf fp-redirect-group {
          type string;
        }
        leaf instance {
          type string;
        }
      }
      leaf vc-label {
        type string;
      }
    }
    leaf mac-pinning {
      type empty;
    }
    list static-mac {
      // NCS patched for predictable order
      ordered-by user;
      tailf:cli-suppress-mode;
      key "address";
      leaf address {
        type ncs_template_ieee-mac;
      }
    }
    leaf restrict-protected-src {
      type string;
    }
    leaf precedence {
      type string;
    }
    leaf vlan-vc-tag {
      type string;
    }
  }

  grouping ncs_template_stp-common {
    leaf auto-edge {
      type empty;
    }
    leaf edge-port {
      type empty;
    }
    leaf link-type {
      type string;
    }
    leaf path-cost {
      type string;
    }
    leaf port-num {
      type string;
    }
    leaf priority {
      type string;
    }
    leaf shutdown {
      type string;
    }
  }

  grouping ncs_template_filter-choice {
    leaf ip {
      type ncs_template_filter-id;
    }
    leaf ipv6 {
      type ncs_template_filter-id;
    }
    leaf mac {
      type ncs_template_filter-id;
    }
  }

  grouping ncs_template_eth-test {
    leaf test-pattern {
      type ncs_template_test-pattern;
    }
    leaf crc-enable {
      type empty;
    }
  }

  grouping ncs_template_time-stamp {
    leaf start-week {
      tailf:cli-drop-node-name;
      type string;
    }
    leaf start-day {
      tailf:cli-drop-node-name;
      type ncs_template_weekday;
    }
    leaf month {
      tailf:cli-drop-node-name;
      type ncs_template_month;
    }
    leaf hours-minutes {
      tailf:cli-drop-node-name;
      type string;
    }
  }

  grouping ncs_template_ip-filter-entry-grouping {
    leaf entry-name {
      type string;
    }
    leaf description {
      type string;
    }
    leaf log {
      type string;
    }
    list match {
      // NCS patched for predictable order
      ordered-by user;
      key "protocol-type";
      leaf protocol-type {
        type string;
      }
      leaf protocol {
        type empty;
      }
      leaf dscp {
        type ncs_template_dscp-type;
      }
      container ip {
        uses ncs_template_filter-match-ip-grouping;
      }
      container src-ip {
        uses ncs_template_filter-match-ip-grouping;
      }
      leaf src-route-option {
        type string;
      }
      container dst-ip {
        uses ncs_template_filter-match-ip-grouping;
      }
      leaf icmp-type {
        type ncs_template_icmp-type;
      }
      leaf icmp-code {
        type string;
      }
      leaf fragment {
        type string;
      }
      leaf option-present {
        type string;
      }
      container ip-option {
        leaf a {
          tailf:cli-drop-node-name;
          type string;
        }
        leaf b {
          tailf:cli-drop-node-name;
          type string;
        }
      }

      grouping filter-ip-filter-port-grouping {
        choice port-choice {
          case a {
            leaf op {
              tailf:cli-drop-node-name;
              type string;
            }
            leaf port {
              tailf:cli-drop-node-name;
              // NCS drop mandatory statement
              type string;
            }
          }
          case b {
            leaf range {
              type empty;
            }
            leaf start {
              tailf:cli-drop-node-name;
              // NCS drop mandatory statement
              type string;
            }
            leaf end {
              tailf:cli-drop-node-name;
              // NCS drop mandatory statement
              type string;
            }
          }
          case c {
            leaf port-list {
              type ncs_template_string32;
            }
          }
        }
      }
      container port {
        uses filter-ip-filter-port-grouping;
      }
      container dst-port {
        uses filter-ip-filter-port-grouping;
      }
      container src-port {
        choice port-choice {
          case a {
            leaf op {
              tailf:cli-drop-node-name;
              type string;
            }
            leaf port {
              tailf:cli-drop-node-name;
              // NCS drop mandatory statement
              type string;
            }
          }
          case b {
            leaf range {
              type empty;
            }
            leaf start {
              tailf:cli-drop-node-name;
              // NCS drop mandatory statement
              type string;
            }
            leaf end {
              tailf:cli-drop-node-name;
              // NCS drop mandatory statement
              type string;
            }
          }
          case c {
            leaf src-port-number {
              tailf:cli-drop-node-name;
              type string;
            }
            leaf mask {
              tailf:cli-drop-node-name;
              type string;
            }
          }
          case d {
            leaf port-list {
              type ncs_template_string32;
            }
          }
        }
      }
      leaf tcp-ack {
        type string;
      }
      leaf tcp-syn {
        type string;
      }
    }
  }

  grouping ncs_template_ipv6-filter-entry-grouping {
    leaf entry-name {
      type string;
    }
    leaf description {
      type string;
    }
    container match {
      presence "true";
      leaf next-header {
        type string;
      }
      leaf dscp {
        type ncs_template_dscp-type;
      }
      container ip {
        uses ncs_template_filter-match-ipv6-grouping;
      }
      container src-ip {
        uses ncs_template_filter-match-ipv6-grouping;
      }
      container dst-ip {
        uses ncs_template_filter-match-ipv6-grouping;
      }
      leaf icmp-type {
        type ncs_template_icmpv6-type;
      }
      leaf icmp-code {
        type string;
      }
      leaf fragment {
        type string;
      }
      container ip-option {
        leaf a {
          tailf:cli-drop-node-name;
          type string;
        }
        leaf b {
          tailf:cli-drop-node-name;
          type string;
        }
      }

      grouping filter-ipv6-filter-port-grouping {
        choice port-choice {
          case a {
            leaf op {
              tailf:cli-drop-node-name;
              type string;
            }
            leaf port {
              tailf:cli-drop-node-name;
              type string;
            }
          }
          case b {
            leaf range {
              type empty;
            }
            leaf start {
              tailf:cli-drop-node-name;
              type string;
            }
            leaf end {
              tailf:cli-drop-node-name;
              type string;
            }
          }
          case c {
            leaf port-list {
              type ncs_template_string32;
            }
          }
        }
      }
      container dst-port {
        uses filter-ipv6-filter-port-grouping;
      }
      leaf routing-type0 {
        type string;
      }
      container src-port {
        uses filter-ipv6-filter-port-grouping;
      }
      container port {
        uses filter-ipv6-filter-port-grouping;
      }
      leaf tcp-ack {
        type string;
      }
      leaf tcp-syn {
        type string;
      }
    }
  }

  grouping ncs_template_queue-adaptation-grouping {
    container adaptation-rule {
      leaf pir {
        type string;
      }
      leaf cir {
        type string;
      }
    }
  }

  grouping ncs_template_queue-rate-grouping {
    container rate {
      leaf pir {
        tailf:cli-drop-node-name;
        type ncs_template_rate-type;
      }
      leaf cir {
        type ncs_template_rate-type;
      }
      leaf alt-pir {
        tailf:alt-name "pir";
        type ncs_template_rate-type;
      }
      leaf police {
        type empty;
      }
    }
  }

  grouping ncs_template_qos-queue-percent-rate-grouping {
    container percent-rate {
      leaf pir {
        tailf:cli-drop-node-name;
        type string;
      }
      leaf cir {
        type string;
      }
    }
  }

  grouping ncs_template_sap-queue-override-grouping {
    container queue-override {
      list queue {
        // NCS patched for predictable order
        ordered-by user;
        key "queue-id";
        leaf queue-id {
          type string;
        }
        uses ncs_template_queue-adaptation-grouping;
        leaf avg-frame-overhead {
          type string;
        }
        container mbs {
          leaf val {
            tailf:cli-drop-node-name;
            type string;
          }
          leaf unit {
            tailf:cli-drop-node-name;
            type string;
          }
        }
        leaf cbs {
          type string;
        }
        leaf high-prio-only {
          type string;
        }
        container rate {
          leaf pir {
            tailf:cli-drop-node-name;
            type string;
          }
          leaf cir {
            type string;
          }
        }
        container parent {
          leaf weight {
            type string;
          }
          leaf cir-weight {
            type string;
          }
        }
        uses ncs_template_qos-queue-percent-rate-grouping;
      }
    }
  }

  grouping ncs_template_sap-scheduler-override-grouping {
    container scheduler-override {
      list scheduler {
        // NCS patched for predictable order
        ordered-by user;
        key "scheduler-policy-name";
        leaf scheduler-policy-name {
          type string;
        }
        container parent {
          leaf weight {
            type string;
          }
          leaf cir-weight {
            type string;
          }
        }
        container rate {
          leaf rate {
            tailf:cli-drop-node-name;
            type string;
          }
          leaf cir {
            type string;
          }
        }
      }
    }
  }

  grouping ncs_template_router-segment-routing-grouping {
    container segment-routing {
      container prefix-sid-range {
        choice range {
          leaf global {
            type empty;
          }
          case other {
            leaf start-label {
              type string;
            }
            leaf max-index {
              type string;
            }
          }
        }
      }
      leaf tunnel-mtu {
        type string;
      }
      leaf tunnel-table-pref {
        type string;
      }
      leaf srlb {
        type string;
      }
      container micro-loop-avoidance {
        presence "true";
        leaf fib-delay {
          type string;
        }
      }
      leaf export-tunnel-table {
        type string;
      }
      leaf shutdown {
        type string;
      }
    }
  }

  grouping ncs_template_sap-policer-override-grouping-egress {
    container policer-override {
      list policer {
        // NCS patched for predictable order
        ordered-by user;
        key "policer-id";
        leaf policer-id {
          type string;
        }
        uses ncs_template_policer-cbs-mbs-rate-with-packet-offset-grouping;
      }
    }
  }

  grouping ncs_template_sap-policer-override-grouping-ingress {
    container policer-override {
      list policer {
        // NCS patched for predictable order
        ordered-by user;
        key "policer-id";
        leaf policer-id {
          type string;
        }
        uses ncs_template_policer-cbs-mbs-rate-with-packet-offset-grouping;
      }
    }
  }

  grouping ncs_template_ip-criteria-grouping {
    leaf dscp-only {
      type empty;
    }
    list entry {
      // NCS patched for predictable order
      ordered-by user;
      key "id";
      leaf id {
        type string;
      }
      leaf description {
        type string;
      }
      container match {
        leaf protocol {
          type ncs_template_protocol;
        }
        leaf dscp {
          type ncs_template_dscp-type;
        }
        container dst-ip {
          choice dst {
            leaf ip-address-with-mask {
              tailf:cli-drop-node-name;
              type string;
            }
            leaf ip-prefix-list {
              type ncs_template_string32;
            }
          }
        }
        container src-ip {
          choice src {
            leaf ip-address-with-mask {
              tailf:cli-drop-node-name;
              type string;
            }
            leaf ip-prefix-list {
              type ncs_template_string32;
            }
          }
        }

        grouping port-choice-grouping {
          choice port-choice {
            case a {
              leaf op {
                tailf:cli-drop-node-name;
                type string;
              }
              leaf port {
                tailf:cli-drop-node-name;
                type string;
              }
            }
            case b {
              leaf range {
                type empty;
              }
              leaf start {
                tailf:cli-drop-node-name;
                type string;
              }
              leaf end {
                tailf:cli-drop-node-name;
                type string;
              }
            }
          }
        }
        container dst-port {
          uses port-choice-grouping;
        }
        container src-port {
          uses port-choice-grouping;
        }
      }
      container action {
        presence "true";
        leaf profile {
          type string;
        }
        leaf fc {
          type ncs_template_fc-name;
        }
        leaf priority {
          type string;
        }
        leaf policer {
          type string;
        }
      }
    }
  }

  grouping ncs_template_ipv6-criteria-grouping {
    list entry {
      // NCS patched for predictable order
      ordered-by user;
      key "id";
      leaf id {
        type string;
      }
      leaf description {
        type string;
      }
      container match {
        leaf protocol {
          type ncs_template_protocol;
        }
        leaf next-header {
          type string;
        }
        leaf dscp {
          type ncs_template_dscp-type;
        }
        container src-ip {
          uses ncs_template_filter-match-ip-grouping;
        }
        container dst-ip {
          uses ncs_template_filter-match-ip-grouping;
        }

        grouping port-choice-grouping {
          choice port-choice {
            case a {
              leaf op {
                tailf:cli-drop-node-name;
                type string;
              }
              leaf port {
                tailf:cli-drop-node-name;
                type string;
              }
            }
            case b {
              leaf range {
                type empty;
              }
              leaf start {
                tailf:cli-drop-node-name;
                type string;
              }
              leaf end {
                tailf:cli-drop-node-name;
                type string;
              }
            }
          }
        }
        container dst-port {
          uses port-choice-grouping;
        }
        container src-port {
          uses port-choice-grouping;
        }
      }
      container action {
        leaf fc {
          type string;
        }
        leaf priority {
          type string;
        }
        leaf policer {
          type string;
        }
      }
    }
  }

  grouping ncs_template_mac-criteria-grouping {
    leaf match-criteria {
      tailf:cli-drop-node-name;
      type string;
    }
    leaf type {
      type string;
    }
    list entry {
      // NCS patched for predictable order
      ordered-by user;
      key "id";
      leaf id {
        type string;
      }
      leaf description {
        type string;
      }
      container match {
        leaf frame-type {
          type string;
        }
        container outer-tag {
          leaf value {
            tailf:cli-drop-node-name;
            type string;
          }
          leaf vid-mask {
            tailf:cli-drop-node-name;
            type string;
          }
        }

        grouping match-mac-grouping {
          leaf ieee-address {
            tailf:cli-drop-node-name;
            type ncs_template_ieee-mac;
          }
          leaf ieee-address-mask {
            tailf:cli-drop-node-name;
            type ncs_template_ieee-mac;
          }
        }
        container dst-mac {
          uses match-mac-grouping;
        }
        container src-mac {
          uses match-mac-grouping;
        }
        container dot1p {
          leaf dot1p-value {
            tailf:cli-drop-node-name;
            type string;
          }
          leaf dot1p-mask {
            tailf:cli-drop-node-name;
            type string;
          }
        }
        leaf etype {
          type string;
        }
      }
      container action {
        leaf fc {
          type ncs_template_fc-name;
        }
        leaf priority {
          type string;
        }
      }
    }
  }

  grouping ncs_template_meter-grouping {
    leaf meter-id {
      type string;
    }
    leaf multipoint {
      type empty;
    }
    uses ncs_template_queue-adaptation-grouping;

    grouping unit-grouping {
      leaf unit {
        tailf:cli-drop-node-name;
        type string;
      }
    }
    container cbs {
      leaf size {
        tailf:cli-drop-node-name;
        type string;
      }
      uses unit-grouping;
    }
    container mbs {
      leaf size {
        tailf:cli-drop-node-name;
        type string;
      }
      uses unit-grouping;
    }
    container rate {
      leaf cir {
        type ncs_template_rate-type;
      }
      leaf pir {
        type ncs_template_rate-type;
      }
    }
    leaf mode {
      type string;
    }
  }

  grouping ncs_template_cpm-filter-match-port-grouping {
    choice port-choice {
      case a {
        leaf port-number {
          tailf:cli-drop-node-name;
          type string;
        }
        leaf mask {
          tailf:cli-drop-node-name;
          type string;
        }
      }
      case b {
        leaf range {
          type empty;
        }
        leaf start {
          tailf:cli-drop-node-name;
          type string;
        }
        leaf end {
          tailf:cli-drop-node-name;
          type string;
        }
      }
      case c {
        leaf port-list {
          type string;
        }
      }
    }
  }

  grouping ncs_template_filter-match-ip-grouping {
    choice ip {
      leaf address {
        tailf:cli-drop-node-name;
        type string;
      }
      leaf ip-prefix-list {
        type string;
      }
      leaf ipv6-prefix-list {
        type ncs_template_string32;
      }
    }
  }

  grouping ncs_template_filter-match-ipv6-grouping {
    choice ipv6 {
      leaf address {
        tailf:cli-drop-node-name;
        type string;
      }
      leaf ipv6-prefix-list {
        type string;
      }
    }
  }

  grouping ncs_template_sap-egress-grouping {
    container agg-rate {
      container rate {
        leaf val {
          tailf:cli-drop-node-name;
          type string;
        }
        leaf cir {
          type string;
        }
      }
    }
    leaf egress-remark-policy {
      type string;
    }
    leaf vlan-qos-policy {
      type string;
    }
    leaf agg-rate-limit {
      type string;
    }
    container filter {
      uses ncs_template_filter-choice;
    }
    leaf multicast-group {
      type string;
    }
    leaf qos {
      type string;
    }
    uses ncs_template_sap-queue-override-grouping;
    leaf scheduler-policy {
      type string;
    }
    uses ncs_template_sap-scheduler-override-grouping;
    uses ncs_template_sap-policer-override-grouping-egress;
    leaf qinq-mark-top-only {
      type empty;
    }
    leaf dest-mac-rewrite {
      type string;
    }
    container qtag-manipulation {
      leaf preserve {
        type empty;
      }
    }
  }

  grouping ncs_template_sap-ingress-grouping {
    container filter {
      uses ncs_template_filter-choice;
    }
    container aggregate-meter-rate {
      leaf value {
        tailf:cli-drop-node-name;
        type string;
      }
      leaf burst {
        type string;
      }
    }
    leaf match-qinq-dot1p {
      type string;
    }
    container qos {
      leaf policy-id {
        tailf:cli-drop-node-name;
        type string;
      }
      leaf shared-queuing {
        type empty;
      }
      leaf enable-table-classification {
        type empty;
      }
    }
    uses ncs_template_sap-queue-override-grouping;
    leaf agg-shaper-rate {
      type string;
    }
    uses ncs_template_sap-policer-override-grouping-ingress;
    leaf policer-control-policy {
      type string;
    }
    leaf scheduler-policy {
      type string;
    }
    uses ncs_template_sap-scheduler-override-grouping;
    leaf vlan-translation {
      type string;
    }
    container aggregate-policer-rate {
      leaf rate {
        tailf:cli-drop-node-name;
        type string;
      }
      leaf burst {
        type string;
      }
    }
    container qtag-manipulation {
      leaf preserve {
        type empty;
      }
    }
  }

  grouping ncs_template_queue-ref-grouping {
    leaf queue-id {
      tailf:cli-drop-node-name;
      type string;
    }
    leaf group {
      type string;
    }
  }

  grouping ncs_template_policer-ref-grouping {
    leaf policer-id {
      tailf:cli-drop-node-name;
      type string;
    }
  }

  grouping ncs_template_policy-option-action-params-grouping {
    leaf add-paths-send-limit {
      type string;
    }
    leaf admin-tag-policy {
      type string;
    }
    leaf advertise-label {
      type string;
    }
    leaf bgp-leak {
      type empty;
    }
    container aigp-metric {
      leaf add {
        type empty;
      }
      leaf aigp-metric {
        tailf:cli-drop-node-name;
        type string;
      }
    }
    container as-path {
      leaf action {
        tailf:cli-drop-node-name;
        type string;
      }
      leaf name {
        tailf:cli-drop-node-name;
        type string;
      }
    }
    container as-path-prepend {
      choice as-choice {
        leaf as-number {
          tailf:cli-drop-node-name;
          type string;
        }
        leaf most-recent {
          type empty;
        }
      }
      leaf repeat {
        tailf:cli-drop-node-name;
        type string;
      }
    }
    container community {
      choice comm {
        case add-remove {
          leaf-list add {
            // NCS patched for predictable order
            ordered-by user;
            type string;
          }
          leaf-list remove {
            // NCS patched for predictable order
            ordered-by user;
            type string;
          }
        }
        leaf-list replace {
          // NCS patched for predictable order
          ordered-by user;
          type string;
        }
      }
    }
    container damping {
      leaf name {
        tailf:cli-drop-node-name;
        type string;
      }
    }
    leaf local-preference {
      type string;
    }
    container metric {
      leaf action {
        tailf:cli-drop-node-name;
        type string;
      }
      leaf metric {
        tailf:cli-drop-node-name;
        type string;
      }
    }
    container multicast-redirection {
      leaf fwd-service {
        type string;
      }
      leaf ip-int-name {
        tailf:cli-drop-node-name;
        type string;
      }
    }
    choice next-hop-choice {
      leaf next-hop {
        type string;
      }
      leaf next-hop-self {
        type empty;
      }
    }
    leaf origin {
      type string;
    }
    leaf preference {
      type string;
    }
    leaf tag {
      type ncs_template_policy-options-tag;
    }
    leaf type {
      type string;
    }
    container bgp-med {
      container set {
        leaf value {
          tailf:cli-drop-node-name;
          type string;
        }
      }
    }
    leaf sr-label-index {
      type string;
    }
  }

  grouping ncs_template_policy-options-action-fc-grouping {
    container fc {
      leaf fc {
        tailf:cli-drop-node-name;
        type ncs_template_fc-name;
      }
      leaf priority {
        type string;
      }
    }
  }

  grouping ncs_template_policy-options-default-action-grouping {
    choice action {
      leaf reject {
        type empty;
      }
      container drop {
        presence "true";
        uses ncs_template_policy-option-action-params-grouping;
      }
      container accept {
        presence "true";
        uses ncs_template_policy-option-action-params-grouping;
      }
      container next-entry {
        presence "true";
        uses ncs_template_policy-option-action-params-grouping;
      }
      container next-policy {
        presence "true";
        uses ncs_template_policy-option-action-params-grouping;
      }
    }
  }

  grouping ncs_template_policy-options-action-grouping {
    choice action {
      leaf reject {
        type empty;
      }
      container drop {
        presence "true";
        uses ncs_template_policy-option-action-params-grouping;
        uses ncs_template_policy-options-action-fc-grouping;
      }
      container accept {
        presence "true";
        uses ncs_template_policy-option-action-params-grouping;
        uses ncs_template_policy-options-action-fc-grouping;
      }
      container next-entry {
        presence "true";
        uses ncs_template_policy-option-action-params-grouping;
        uses ncs_template_policy-options-action-fc-grouping;
      }
      container next-policy {
        presence "true";
        uses ncs_template_policy-option-action-params-grouping;
        uses ncs_template_policy-options-action-fc-grouping;
      }
    }
  }

  grouping ncs_template_mbs-rate-grouping {
    leaf size {
      tailf:cli-drop-node-name;
      type string;
    }
    leaf unit {
      tailf:cli-drop-node-name;
      type string;
    }
  }

  grouping ncs_template_policer-cbs-mbs-rate-grouping {
    container cbs {
      uses ncs_template_mbs-rate-grouping;
    }
    container mbs {
      uses ncs_template_mbs-rate-grouping;
    }
    container rate {
      leaf pir {
        tailf:cli-drop-node-name;
        type ncs_template_rate-type;
      }
      leaf cir {
        type ncs_template_rate-type;
      }
    }
    leaf stat-mode {
      type ncs_template_policer-stat-mode;
    }
  }

  grouping ncs_template_policer-cbs-mbs-rate-with-packet-offset-grouping {
    uses ncs_template_policer-cbs-mbs-rate-grouping;
    container packet-byte-offset {
      choice add-delete {
        leaf add {
          type string;
        }
        leaf subtract {
          type string;
        }
      }
    }
  }

  grouping ncs_template_policer-grouping {
    uses ncs_template_queue-adaptation-grouping;
    leaf adv-config-policy {
      type string;
    }
    uses ncs_template_policer-cbs-mbs-rate-with-packet-offset-grouping;
    leaf description {
      type string;
    }
    leaf high-prio-only {
      type string;
    }
    container parent {
      leaf name {
        tailf:cli-drop-node-name;
        type string;
      }
      leaf level {
        type string;
      }
      leaf weight-level {
        tailf:alt-name "weight";
        type string;
      }
    }
    leaf profile-capped {
      type empty;
    }
  }

  grouping ncs_template_queue-grouping {
    leaf multipoint {
      type empty;
    }
    leaf queue-type {
      tailf:cli-drop-node-name;
      type ncs_template_queue-type;
    }
    leaf queue-mode-m {
      tailf:cli-drop-node-name;
      type string;
    }
    uses ncs_template_queue-adaptation-grouping;
    leaf adv-config-policy {
      type string;
    }
    leaf avg-frame-overhead {
      type string;
    }
    container burst-limit {
      leaf size {
        tailf:cli-drop-node-name;
        type string;
      }
      leaf unit {
        tailf:cli-drop-node-name;
        type string;
      }
    }
    leaf cbs {
      type string;
    }
    leaf high-prio-only {
      type string;
    }
    container mbs {
      leaf size {
        tailf:cli-drop-node-name;
        type string;
      }
      leaf unit {
        tailf:cli-drop-node-name;
        type string;
      }
    }
    container parent {
      leaf name {
        tailf:cli-drop-node-name;
        type string;
      }
      leaf level {
        type string;
      }
      leaf weight {
        type string;
      }
      leaf cir-level {
        type string;
      }
      leaf cir-weight {
        type string;
      }
    }
    container percent-rate {
      leaf pir-percent {
        tailf:cli-drop-node-name;
        type string;
      }
      leaf cir {
        type string;
      }
    }
    leaf pool {
      type string;
    }
    uses ncs_template_port-parent-grouping;
    uses ncs_template_queue-rate-grouping;
    leaf slope-policy {
      type string;
    }
    container wred-queue {
      leaf policy {
        type string;
      }
      leaf mode {
        type string;
      }
      leaf slope-usage {
        type string;
      }
    }
    container xp-specific {
      container wred-queue {
        leaf policy {
          type string;
        }
      }
      uses ncs_template_packet-byte-offset-grouping;
    }
    container drop-tail {
      container low {
        leaf percent-reduction-from-mbs {
          type string;
        }
      }
    }
  }

  grouping ncs_template_queue-group-template-entry {
    leaf queue-group-name {
      type string;
    }
    leaf description {
      type string;
    }
    list fc {
      // NCS patched for predictable order
      ordered-by user;
      key "fc-name";
      leaf fc-name {
        type ncs_template_fc-name;
      }
      leaf queue {
        type string;
      }
    }
    list policer {
      // NCS patched for predictable order
      ordered-by user;
      key "policer-id";
      leaf policer-id {
        type string;
      }
      uses ncs_template_policer-grouping;
    }
    list queue {
      // NCS patched for predictable order
      ordered-by user;
      key "queue-id";
      leaf queue-id {
        type string;
      }
      uses ncs_template_queue-grouping;
    }
  }

  grouping ncs_template_dhcp-lease-time {
    leaf days {
      type string;
    }
    leaf hrs {
      type string;
    }
    leaf min {
      type string;
    }
    leaf sec {
      type string;
    }
  }

  grouping ncs_template_bfd-grouping {
    leaf transmit-interval {
      tailf:cli-drop-node-name;
      type string;
    }
    leaf receive {
      type string;
    }
    leaf multiplier {
      type string;
    }
    leaf echo-receive {
      type string;
    }
    leaf type {
      type string;
    }
  }

  grouping ncs_template_dhcp6-grouping {
    container dhcp6-server {
      leaf max-nbr-of-leases {
        type string;
      }
    }
    container dhcp6-relay {
      leaf description {
        type string;
      }
      container lease-populate {
        presence "present";
        leaf nbr-of-leases {
          tailf:cli-drop-node-name;
          type string;
        }
        leaf route-populate {
          type empty;
        }
        leaf pd {
          type empty;
        }
        leaf exclude {
          type empty;
        }
        leaf na {
          type empty;
        }
        leaf ta {
          type empty;
        }
      }
      leaf neighbor-resolution {
        type empty;
      }
      container option {
        container interface-id {
          choice choice {
            leaf sap-id {
              type empty;
            }
            leaf ifindex {
              type empty;
            }
            leaf string {
              type string;
            }
          }
        }
        leaf remote-id {
          type empty;
        }
      }
      leaf source-address {
        type string;
      }
      leaf link-address {
        type string;
      }
      leaf-list server {
        // NCS patched for predictable order
        ordered-by user;
        type string;
      }
      leaf shutdown {
        type string;
      }
    }
  }

  grouping ncs_template_ipv6-grouping {
    list address {
      // NCS patched for predictable order
      ordered-by user;
      tailf:cli-suppress-mode;
      key "addr";
      leaf addr {
        type string;
      }
      leaf eui-64 {
        type empty;
      }
      leaf preferred {
        type empty;
      }
      leaf track-srrp {
        type string;
      }
      leaf modifier {
        type string;
      }
      leaf dad-disable {
        type empty;
      }
    }

    typedef nd-type {
      type string;
    }
    leaf nd-learn-unsolicited {
      type nd-type;
    }
    leaf nd-proactive-refresh {
      type nd-type;
    }
    container bfd {
      uses ncs_template_bfd-grouping;
    }
    leaf dad-disable {
      type empty;
    }
    container icmp6 {
      container packet-too-big {
        uses ncs_template_icmp-params-grouping;
      }
      container param-problem {
        uses ncs_template_icmp-params-grouping;
      }
      container redirects {
        uses ncs_template_icmp-params-grouping;
      }
      container time-exceeded {
        uses ncs_template_icmp-params-grouping;
      }
      container unreachables {
        uses ncs_template_icmp-params-grouping;
      }
    }
    container link-local-address {
      leaf addr {
        tailf:cli-drop-node-name;
        type string;
      }
      leaf preferred {
        type empty;
      }
      leaf dad-disable {
        type empty;
      }
    }
    leaf local-proxy-nd {
      type empty;
    }
    container neighbor {
      leaf addr {
        tailf:cli-drop-node-name;
        type string;
      }
      leaf mac-addr {
        tailf:cli-drop-node-name;
        type ncs_template_ieee-mac;
      }
    }
    container proxy-nd-policy {
      leaf name1 {
        tailf:cli-drop-node-name;
        type string;
      }
      leaf name2 {
        tailf:cli-drop-node-name;
        type string;
      }
      leaf name3 {
        tailf:cli-drop-node-name;
        type string;
      }
      leaf name4 {
        tailf:cli-drop-node-name;
        type string;
      }
      leaf name5 {
        tailf:cli-drop-node-name;
        type string;
      }
    }
    leaf qos-route-lookup {
      type string;
    }
    leaf reachable-time {
      type string;
    }
    container secure-nd {
      leaf allow-unsecured-msgs {
        type string;
      }
      leaf link-local-modifier {
        type string;
      }
      leaf public-key-min-bits {
        type string;
      }
      leaf security-parameter {
        type string;
      }
      leaf shutdown {
        type string;
      }
    }
    leaf tcp-mss {
      type string;
    }
    container urpf-check {
      presence "true";
      leaf ignore-default {
        type empty;
      }
      leaf mode {
        type string;
      }
    }
    list vrrp {
      // NCS patched for predictable order
      ordered-by user;
      key "id";
      leaf id {
        type string;
      }
      leaf owner {
        type empty;
      }
      leaf passive {
        type empty;
      }
      list backup {
        // NCS patched for predictable order
        ordered-by user;
        tailf:cli-suppress-mode;
        key "addr";
        leaf addr {
          type string;
        }
      }
      leaf init-delay {
        type string;
      }
      leaf mac {
        type ncs_template_ieee-mac;
      }
      leaf master-int-inherit {
        type string;
      }
      container message-interval {
        leaf seconds {
          tailf:cli-drop-node-name;
          type string;
        }
        leaf milliseconds {
          type string;
        }
      }
      leaf ping-reply {
        type empty;
      }
      leaf policy {
        type string;
      }
      leaf preempt {
        type string;
      }
      leaf priority {
        type string;
      }
      leaf standby-forwarding {
        type empty;
      }
      leaf telnet-reply {
        type empty;
      }
      leaf traceroute-reply {
        type empty;
      }
      leaf shutdown {
        type string;
      }
    }
  }

  grouping ncs_template_icmp-params-grouping {
    choice icmp-params-choice {
      leaf disable {
        type empty;
      }
      case enable {
        leaf number {
          tailf:cli-drop-node-name;
          type string;
        }
        leaf seconds {
          tailf:cli-drop-node-name;
          type string;
        }
      }
    }
  }

  grouping ncs_template_interface-icmp-grouping {
    container icmp {
      leaf mask-reply {
        type string;
      }
      container redirects {
        uses ncs_template_icmp-params-grouping;
      }
      container ttl-expired {
        uses ncs_template_icmp-params-grouping;
      }
      container unreachables {
        uses ncs_template_icmp-params-grouping;
      }
    }
  }

  grouping ncs_template_subscriber-interface-dhcp-common-grouping {
    container proxy-server {
      leaf emulated-server {
        type string;
      }
      container lease-time {
        leaf days {
          type string;
        }
        leaf hrs {
          type string;
        }
        leaf min {
          type string;
        }
        leaf sec {
          type string;
        }
      }
      leaf shutdown {
        type string;
      }
    }
    leaf-list server {
      // NCS patched for predictable order
      ordered-by user;
      type string;
    }
    container gi-address {
      leaf address {
        tailf:cli-drop-node-name;
        type string;
      }
      leaf src-ip-addr {
        type empty;
      }
    }
  }

  grouping ncs_template_dhcp-option-grouping {
    container option {
      leaf action {
        type string;
      }
      container remote-id {
        presence "true";
        choice remote-id {
          leaf mac {
            tailf:cli-drop-node-name;
            type string;
          }
          leaf string {
            type string;
          }
        }
      }
      container vendor-specific-option {
        leaf client-mac-address {
          type empty;
        }
        leaf pool-name {
          type empty;
        }
        leaf service-id {
          type empty;
        }
        leaf string {
          type string;
        }
      }
    }
  }

  grouping ncs_template_subscriber-interface-grouping {
    leaf id {
      type string;
    }
    leaf fwd-service {
      type ncs_template_service-id;
    }
    leaf wan-mode {
      type string;
    }
    leaf fwd-subscriber-interface {
      type string;
    }
    leaf description {
      type string;
    }
    leaf allow-unmatching-subnets {
      type empty;
    }
    list address {
      // NCS patched for predictable order
      ordered-by user;
      tailf:cli-suppress-mode;
      key "ip-address";
      leaf ip-address {
        type string;
      }
      leaf gw-ip-address {
        type string;
      }
      leaf populate-host-routes {
        type empty;
      }
      leaf track-srrp {
        type string;
      }
    }

    grouping ipoe-linking-grouping {
      container ipoe-linking {
        leaf gratuitous-rtr-adv {
          type empty;
        }
        leaf shared-circuit-id {
          type empty;
        }
        leaf shutdown {
          type string;
        }
      }
    }
    uses ipoe-linking-grouping;
    list group-interface {
      // NCS patched for predictable order
      ordered-by user;
      key "id";
      leaf id {
        type string;
      }
      leaf oper-up-while-empty {
        type empty;
      }
      uses ipoe-linking-grouping;
      leaf shcv-policy {
        type string;
      }
      leaf shcv-policy-ipv4 {
        type string;
      }
      leaf shcv-policy-ipv6 {
        type string;
      }
      container data-trigger {
        leaf shutdown {
          type string;
        }
      }
      leaf description {
        type string;
      }
      uses ncs_template_interface-icmp-grouping;
      leaf remote-proxy-arp {
        type empty;
      }
      container ipv6 {
        leaf allow-multiple-wan-addresses {
          type empty;
        }
        container router-advertisements {
          container dns-options {
            leaf include-dns {
              type empty;
            }
            leaf rdnss-lifetime {
              type string;
            }
          }
          leaf managed-configuration {
            type empty;
          }
          leaf retransmit-time {
            type string;
          }
          leaf max-advertisement {
            type string;
          }
          leaf current-hop-limit {
            type string;
          }
          leaf mtu {
            type string;
          }
          leaf reachable-time {
            type string;
          }
          leaf other-stateful-configuration {
            type empty;
          }
          leaf router-lifetime {
            type string;
          }
          container prefix-options {
            leaf autonomous {
              type empty;
            }
            leaf on-link {
              type string;
            }
            leaf preferred-lifetime {
              type string;
            }
            leaf valid-lifetime {
              type string;
            }
          }
          leaf shutdown {
            type string;
          }
        }
        container auto-reply {
          leaf neighbor-solicitation {
            type empty;
          }
          leaf router-solicitation {
            type empty;
          }
        }
        container urpf-check {
          presence "true";
          leaf mode {
            type string;
          }
        }
        container dhcp6 {
          leaf user-db {
            type string;
          }
          leaf user-ident {
            type string;
          }
          container relay {
            leaf description {
              type string;
            }
            leaf link-address {
              type string;
            }
            list server {
              // NCS patched for predictable order
              ordered-by user;
              tailf:cli-suppress-mode;
              key "ip";
              leaf ip {
                type string;
              }
            }
            leaf source-address {
              type string;
            }
            leaf shutdown {
              type string;
            }
          }
          container proxy-server {
            container lease-time {
              leaf days {
                type string;
              }
              leaf hrs {
                type string;
              }
              leaf min {
                type string;
              }
              leaf sec {
                type string;
              }
            }
            uses ncs_template_dhcp6-lease-timers-grouping;
            leaf shutdown {
              type string;
            }
          }
          leaf python-policy {
            type ncs_template_string32;
          }
          container option {
            container interface-id {
              leaf type {
                tailf:cli-drop-node-name;
                type string;
              }
              leaf stringval {
                tailf:cli-drop-node-name;
                type string;
              }
            }
            leaf remote-id {
              type empty;
            }
          }
        }
      }
      leaf arp-populate {
        type empty;
      }
      leaf authentication-policy {
        type string;
      }
      leaf redundant-interface {
        type string;
      }
      leaf srrp-enabled-routing {
        type empty;
      }
      leaf enable-ingress-stats {
        type empty;
      }
      leaf ip-mtu {
        type string;
      }
      leaf tos-marking-state {
        type string;
      }
      container host-connectivity-verify {
        leaf interval {
          type string;
        }
        leaf action {
          type string;
        }
        leaf timeout {
          type string;
        }
        leaf retry-count {
          type string;
        }
        leaf family {
          type string;
        }
      }
      container dhcp {
        leaf description {
          type string;
        }
        leaf trusted {
          type empty;
        }
        container lease-populate {
          leaf nr-of-leases {
            tailf:cli-drop-node-name;
            type string;
          }
          leaf l2-header {
            type empty;
          }
          leaf mac {
            type string;
          }
        }
        container relay-proxy {
          presence "true";
          leaf release-update-src-ip {
            type empty;
          }
          leaf siaddr-override {
            type string;
          }
        }
        leaf python-policy {
          type ncs_template_string32;
        }
        uses ncs_template_dhcp-option-grouping {
          augment "option" {
            container circuit-id {
              presence "true";
              leaf id {
                tailf:cli-drop-node-name;
                type string;
              }
            }
          }
          augment "option/vendor-specific-option" {
            leaf sap-id {
              type empty;
            }
          }
        }
        leaf user-db {
          type string;
        }
        leaf-list client-applications {
          // NCS patched for predictable order
          ordered-by user;
          type string;
        }
        uses ncs_template_subscriber-interface-dhcp-common-grouping {
          augment "proxy-server/lease-time" {
            leaf override {
              type empty;
            }
          }
        }
      }
      list sap {
        // NCS patched for predictable order
        ordered-by user;
        key "id";
        leaf id {
          type string;
        }
        leaf host-lockout-policy {
          type ncs_template_string32;
        }
        container egress {
          container filter {
            leaf ip {
              type ncs_template_filter-id;
            }
            leaf ipv6 {
              type ncs_template_filter-id;
            }
          }
          leaf qos {
            type string;
          }
        }
        container ingress {
          container filter {
            leaf ip {
              type ncs_template_filter-id;
            }
            leaf ipv6 {
              type ncs_template_filter-id;
            }
          }
          leaf qos {
            type string;
          }
        }
        leaf description {
          type string;
        }
        leaf anti-spoof {
          type string;
        }
        container sub-sla-mgmt {
          container def-sub-id {
            choice sub-id-choice {
              leaf string {
                type string;
              }
              leaf use-auto-id {
                type empty;
              }
              leaf use-sap-id {
                type empty;
              }
            }
          }
          container def-inter-dest-id {
            choice dest-id-choice {
              leaf string {
                type string;
              }
              leaf use-top-q {
                type empty;
              }
              leaf use-vpi {
                type empty;
              }
            }
          }
          leaf def-sub-profile {
            type string;
          }
          leaf def-sla-profile {
            type string;
          }
          leaf sub-ident-policy {
            type string;
          }
          container single-sub-parameters {
            leaf profiled-traffic-only {
              type empty;
            }
          }
          container multi-sub-sap {
            presence "true";
            leaf subscriber-limit {
              tailf:cli-drop-node-name;
              type string;
            }
          }
          leaf shutdown {
            type string;
          }
        }
        leaf calling-station-id {
          type string;
        }
        leaf monitor-oper-group {
          type string;
        }
        leaf shutdown {
          type string;
        }
      }
      container urpf-check {
        leaf mode {
          type string;
        }
      }
      container ipoe-session {
        container force-auth {
          choice force-auth {
            leaf disabled {
              type empty;
            }
            case cid-rid {
              leaf cid-change {
                type empty;
              }
              leaf rid-change {
                type empty;
              }
            }
          }
        }
        leaf sap-session-limit {
          type string;
        }
        leaf session-limit {
          type string;
        }
        container min-auth-interval {
          choice interval {
            leaf infinite {
              tailf:cli-drop-node-name;
              type string;
            }
            case time {
              leaf days {
                type string;
              }
              leaf hrs {
                type string;
              }
              leaf min {
                type string;
              }
              leaf sec {
                type string;
              }
            }
          }
        }
        uses ncs_template_ipoe-session-grouping;
      }
      container pppoe {
        leaf description {
          type string;
        }
        leaf policy {
          type ncs_template_string32;
        }
        leaf sap-session-limit {
          type string;
        }
        leaf session-limit {
          type string;
        }
        leaf user-db {
          type string;
        }
        leaf shutdown {
          type string;
        }
      }
      list srrp {
        // NCS patched for predictable order
        ordered-by user;
        key "srrp-id";
        leaf srrp-id {
          type string;
        }
        leaf description {
          type string;
        }
        leaf keep-alive-interval {
          type string;
        }
        leaf message-path {
          type string;
        }
        list policy {
          // NCS patched for predictable order
          ordered-by user;
          tailf:cli-suppress-mode;
          key "vrrp-policy-id";
          leaf vrrp-policy-id {
            type string;
          }
        }
        leaf priority {
          type string;
        }
        leaf shutdown {
          type string;
        }
      }
      leaf shutdown {
        type string;
      }
    }
    container pppoe {
      leaf description {
        type string;
      }
      leaf session-limit {
        type string;
      }
    }
    leaf private-retail-subnets {
      type empty;
    }
    leaf unnumbered {
      type string;
    }
  }

  grouping ncs_template_nat-pool-grouping {
    container nat {
      container inside {
        container l2-aware {
          list address {
            // NCS patched for predictable order
            ordered-by user;
            tailf:cli-suppress-mode;
            key "ip-addr";
            leaf ip-addr {
              type string;
            }
          }
        }
        leaf nat-policy {
          type string;
        }
        leaf destination-prefix {
          type string;
        }
      }
      container outside {
        list pool {
          // NCS patched for predictable order
          ordered-by user;
          key "name";
          leaf name {
            type string;
          }
          leaf nat-group {
            type string;
          }
          leaf type {
            type string;
          }
          container port-reservation {
            leaf blocks {
              type string;
            }
            leaf ports {
              type string;
            }
          }
          leaf port-forwarding-range {
            type string;
          }
          leaf subscriber-limit {
            type string;
          }
          container watermarks {
            leaf high {
              type string;
            }
            leaf low {
              type string;
            }
          }
          list address-range {
            // NCS patched for predictable order
            ordered-by user;
            key "start-ip-address end-ip-address";
            leaf start-ip-address {
              type string;
            }
            leaf end-ip-address {
              type string;
            }
          }
          leaf shutdown {
            type string;
          }
        }
      }
    }
  }

  grouping ncs_template_static-route-extras-grouping {
    leaf preference {
      type string;
    }
    leaf metric {
      type string;
    }
    choice ed {
      leaf enable {
        type empty;
      }
      leaf disable {
        type empty;
      }
    }
    leaf tag {
      type string;
    }
    leaf community {
      type string;
    }
    leaf description {
      type string;
    }
    leaf mcast-family {
      tailf:cli-drop-node-name;
      type string;
    }
    leaf bfd-enable {
      type empty;
    }
    leaf cpe-check {
      type string;
    }
    leaf interval {
      type string;
    }
    leaf drop-count {
      type string;
    }
    leaf log {
      type empty;
    }
    leaf prefix-list {
      type string;
    }
    choice an {
      leaf all {
        type empty;
      }
      leaf none {
        type empty;
      }
    }
    leaf ldp-sync {
      type empty;
    }
    leaf fc {
      type ncs_template_fc-name;
    }
    leaf priority {
      type string;
    }
  }

  grouping ncs_template_prompted-authentication-key-grouping {
    container authentication-key {
      leaf key {
        tailf:cli-drop-node-name;
        type string;
      }
      leaf method {
        tailf:cli-drop-node-name;
        type ncs_template_hash-method;
      }
    }
  }

  grouping ncs_template_prompted-hello-authentication-key-grouping {
    container hello-authentication-key {
      leaf key {
        tailf:cli-drop-node-name;
        type string;
      }
      leaf method {
        tailf:cli-drop-node-name;
        type ncs_template_hash-method;
      }
    }
    leaf hello-auth-keychain {
      type string;
    }
  }

  grouping ncs_template_bgp-import-export-grouping {
    leaf-list export {
      // NCS patched for predictable order
      ordered-by user;
      type string;
    }
    leaf-list import {
      // NCS patched for predictable order
      ordered-by user;
      type string;
    }
  }

  grouping ncs_template_max-paths-grouping {
    leaf max-paths {
      tailf:cli-drop-node-name;
      type string;
    }
    leaf ebgp {
      type string;
    }
    leaf ibgp {
      type string;
    }
    leaf restrict {
      type string;
    }
  }

  grouping ncs_template_bgp-multipath-grouping {
    container multipath {
      uses ncs_template_max-paths-grouping;
    }
  }

  grouping ncs_template_max-paths-uneqcosts-grouping {
    uses ncs_template_max-paths-grouping;
    leaf unequal-cost {
      type empty;
    }
  }

  grouping ncs_template_bgp-multi-path-grouping {
    container multi-path {
      container ipv4 {
        uses ncs_template_max-paths-uneqcosts-grouping;
      }
      container ipv6 {
        uses ncs_template_max-paths-uneqcosts-grouping;
      }
      container label-ipv4 {
        uses ncs_template_max-paths-uneqcosts-grouping;
      }
      container maximum-paths {
        uses ncs_template_max-paths-uneqcosts-grouping;
      }
    }
  }

  grouping ncs_template_bgp-graceful-restart-grouping {
    container graceful-restart {
      presence "true";
      leaf enable-notification {
        type empty;
      }
      container long-lived {
        presence "true";

        grouping bgp-graceful-override-times-grouping {
          leaf advertised-stale-time {
            type string;
          }
          leaf helper-override-stale-time {
            type string;
          }
        }
        container advertise-stale-to-all-neighbors {
          presence "true";
          leaf without-no-export {
            type empty;
          }
        }
        uses bgp-graceful-override-times-grouping;
        list family {
          // NCS patched for predictable order
          ordered-by user;
          key "family";
          leaf family {
            type ncs_template_family-names-type;
          }
          uses bgp-graceful-override-times-grouping;
        }
        leaf forwarding-bits-set {
          type string;
        }
        leaf helper-override-restart-time {
          type string;
        }
      }
      leaf restart-time {
        type string;
      }
      leaf stale-routes-time {
        type string;
      }
    }
  }

  grouping ncs_template_bgp-prefix-limit-grouping {
    container prefix-limit {
      choice apis {
        list new {
          // NCS patched for predictable order
          ordered-by user;
          tailf:cli-drop-node-name;
          tailf:cli-suppress-mode;
          key "family";
          leaf family {
            type string;
          }
          leaf limit {
            tailf:cli-drop-node-name;
            type string;
          }
          leaf log-only {
            type empty;
          }
          leaf threshold {
            type string;
          }
          leaf idle-timeout {
            type string;
          }
          leaf post-import {
            type empty;
          }
        }
        container old {
          tailf:cli-drop-node-name;
          leaf limit {
            tailf:cli-drop-node-name;
            type string;
          }
          leaf log-only {
            type empty;
          }
          leaf threshold {
            type string;
          }
          leaf idle-timeout {
            type string;
          }
        }
      }
    }
  }

  grouping ncs_template_router-bgp-add-paths-grouping {
    container add-paths {

      grouping path-proto-send-receive-grouping {
        leaf send {
          type string;
        }
        leaf receive {
          type empty;
        }
        leaf none {
          type empty;
        }
      }
      container ipv4 {
        uses path-proto-send-receive-grouping;
      }
      container ipv6 {
        uses path-proto-send-receive-grouping;
      }
      container label-ipv4 {
        uses path-proto-send-receive-grouping;
      }
      container label-ipv6 {
        uses path-proto-send-receive-grouping;
      }
      container vpn-ipv4 {
        uses path-proto-send-receive-grouping;
      }
      container vpn-ipv6 {
        uses path-proto-send-receive-grouping;
      }
    }
  }

  grouping ncs_template_router-bgp-grouping {
    uses ncs_template_router-bgp-add-paths-grouping;
    leaf advertise-inactive {
      type empty;
    }
    leaf-list advertise-ipv6-next-hops {
      // NCS patched for predictable order
      ordered-by user;
      type string;
    }
    leaf loop-detect-threshold {
      type string;
    }
    leaf def-recv-evpn-encap {
      type string;
    }
    container cluster {
      leaf cluster-id {
        tailf:cli-drop-node-name;
        type string;
      }
      leaf orr-location {
        type string;
      }
      leaf allow-local-fallback {
        type empty;
      }
    }
    leaf aggregator-id-zero {
      type empty;
    }
    leaf aigp {
      type empty;
    }
    leaf auth-keychain {
      type string;
    }
    uses ncs_template_prompted-authentication-key-grouping;
    leaf bfd-enable {
      type empty;
    }
    leaf connect-retry {
      type string;
    }
    leaf damping {
      type empty;
    }
    leaf default-route-target {
      type empty;
    }
    leaf description {
      type string;
    }
    leaf disable-4byte-asn {
      type empty;
    }
    leaf disable-capability-negotiation {
      type empty;
    }
    leaf disable-client-reflect {
      type empty;
    }
    leaf-list disable-communities {
      // NCS patched for predictable order
      ordered-by user;
      type string;
    }
    leaf disable-fast-external-failover {
      type empty;
    }
    leaf enable-peer-tracking {
      type empty;
    }
    leaf-list family {
      // NCS patched for predictable order
      ordered-by user;
      type ncs_template_family-names-type;
    }
    leaf flowspec-validate {
      type empty;
    }
    uses ncs_template_bgp-graceful-restart-grouping;
    container hold-time {
      leaf seconds {
        tailf:cli-drop-node-name;
        type string;
      }
      leaf min {
        type string;
      }
    }
    leaf keepalive {
      type string;
    }
    leaf local-address {
      type string;
    }
    uses ncs_template_bgp-local-as-grouping;
    leaf local-preference {
      type string;
    }
    leaf loop-detect {
      type string;
    }
    leaf med-out {
      type string;
    }
    leaf min-as-origination {
      type string;
    }
    leaf min-route-advertisement {
      type string;
    }
    leaf multihop {
      type string;
    }
    leaf next-hop-self {
      type empty;
    }
    container outbound-route-filtering {
      container extended-community {
        leaf accept-orf {
          type empty;
        }
        container send-orf {
          presence "true";
          leaf-list send-orf {
            // NCS patched for predictable order
            ordered-by user;
            tailf:cli-drop-node-name;
            type string;
          }
        }
      }
    }
    leaf passive {
      type empty;
    }
    leaf path-mtu-discovery {
      type empty;
    }
    leaf peer-as {
      type string;
    }
    leaf preference {
      type string;
    }
    uses ncs_template_bgp-prefix-limit-grouping;
    container remove-private {
      presence "true";
      leaf-list options {
        // NCS patched for predictable order
        ordered-by user;
        tailf:cli-drop-node-name;
        type string;
      }
    }
    leaf split-horizon {
      type empty;
    }
    container tcp-mss {
      leaf mss-val {
        tailf:cli-drop-node-name;
        type string;
      }
      leaf ip-stack {
        type empty;
      }
    }
    leaf ttl-security {
      type string;
    }
    leaf type {
      type string;
    }
    leaf vpn-apply-export {
      type empty;
    }
    leaf label-preference {
      type string;
    }
    leaf l2vpn-cisco-interop {
      type empty;
    }
    leaf vpn-apply-import {
      type empty;
    }
    leaf shutdown {
      type string;
    }
  }

  grouping ncs_template_bgp-local-as-grouping {
    container local-as {
      leaf number {
        tailf:cli-drop-node-name;
        type string;
      }
      leaf private {
        type empty;
      }
      leaf no-prepend-global-as {
        type empty;
      }
    }
  }

  grouping ncs_template_bgp-best-path-selection-grouping {
    container best-path-selection {
      container always-compare-med {
        presence "true";
        leaf strict-as {
          type empty;
        }
        leaf type {
          tailf:cli-drop-node-name;
          type string;
        }
      }
      leaf-list as-path-ignore {
        // NCS patched for predictable order
        ordered-by user;
        type string;
      }
      leaf compare-origin-validation-state {
        type empty;
      }
      leaf deterministic-med {
        type empty;
      }
      leaf ignore-nh-metric {
        type empty;
      }
      leaf ignore-router-id {
        type empty;
      }
      leaf origin-invalid-unusable {
        type empty;
      }
    }
  }

  grouping ncs_template_agg-rate-grouping {
    container agg-rate {
      leaf limit-unused-bandwidth {
        type empty;
      }
      leaf queue-frame-based-accounting {
        type empty;
      }
      leaf rate {
        type string;
      }
    }
  }

  grouping ncs_template_sap-egress-common-grouping {
    leaf policy-id {
      type string;
    }
    leaf description {
      type string;
    }
    list queue {
      // NCS patched for predictable order
      ordered-by user;
      key "queue-id";
      leaf queue-id {
        type string;
      }
      uses ncs_template_queue-grouping;
    }
  }

  grouping ncs_template_dot1p-params-grouping {
    choice dot1p {
      leaf dot1p-value {
        tailf:cli-drop-node-name;
        type string;
      }
      case in-out {
        leaf in-profile {
          type string;
        }
        leaf out-profile {
          type string;
        }
      }
    }
  }

  grouping ncs_template_sap-egress-fc-grouping {
    leaf fc-name {
      type string;
    }
    container queue {
      uses ncs_template_queue-ref-grouping;
      leaf instance {
        type string;
      }
    }
    container dot1p {
      uses ncs_template_dot1p-params-grouping;
    }
    container dot1p-inner {
      uses ncs_template_dot1p-params-grouping;
    }
    container dot1p-outer {
      uses ncs_template_dot1p-params-grouping;
    }
    container dscp {
      choice dscp {
        leaf dscp-name {
          tailf:cli-drop-node-name;
          type string;
        }
        case in-out {
          leaf in-profile {
            type string;
          }
          leaf out-profile {
            type string;
          }
        }
      }
    }
  }

  grouping ncs_template_mcac-grouping {
    container mcac {
      container mc-constraints {
        list level {
          // NCS patched for predictable order
          ordered-by user;
          tailf:cli-suppress-mode;
          key "level-id";
          leaf level-id {
            tailf:cli-drop-node-name;
            type string;
          }
          leaf bw {
            type string;
          }
        }
        list number-down {
          // NCS patched for predictable order
          ordered-by user;
          tailf:cli-suppress-mode;
          key "number-lag-port-down";
          leaf number-lag-port-down {
            type string;
          }
          leaf level {
            type string;
          }
        }
        leaf use-lag-port-weight {
          type empty;
        }
        leaf shutdown {
          type string;
        }
      }
      leaf policy {
        type string;
      }
      container unconstrained-bw {
        leaf bandwidth {
          tailf:cli-drop-node-name;
          type string;
        }
        leaf mandatory-bw {
          type string;
        }
      }
    }
  }

  grouping ncs_template_cron-schedule-grouping {
    list schedule {
      // NCS patched for predictable order
      ordered-by user;
      key "id owner";
      leaf id {
        type string;
      }
      leaf owner {
        type string;
      }
      leaf description {
        type string;
      }
      leaf interval {
        type string;
      }
      leaf count {
        type string;
      }
      leaf minute {
        type string;
      }
      leaf hour {
        type string;
      }
      leaf month {
        type string;
      }
      leaf-list day-of-month {
        // NCS patched for predictable order
        ordered-by user;
        type string;
      }
      leaf weekday {
        type string;
      }
      container end-time {
        leaf day-name {
          tailf:cli-drop-node-name;
          type string;
        }
        leaf time {
          tailf:cli-drop-node-name;
          type string;
        }
      }
      container script-policy {
        leaf policy {
          tailf:cli-drop-node-name;
          type ncs_template_string32;
        }
        leaf owner {
          type string;
        }
      }
      leaf type {
        type string;
      }
      leaf shutdown {
        type string;
      }
    }
  }

  grouping ncs_template_static-route-entry-nh-grouping {
    leaf community {
      type string;
    }
    leaf description {
      type string;
    }
    leaf metric {
      type string;
    }
    leaf preference {
      type string;
    }
    leaf tag {
      type string;
    }
    leaf bfd-enable {
      type empty;
    }
    leaf ldp-sync {
      type empty;
    }
    list cpe-check {
      // NCS patched for predictable order
      ordered-by user;
      key "address";
      leaf address {
        type string;
      }
      leaf drop-count {
        type string;
      }
      leaf interval {
        type string;
      }
      leaf log {
        type empty;
      }
    }
    container tunnel-next-hop {
      leaf resolution {
        type string;
      }
      container resolution-filter {
        container rsvp-te {
          presence "true";
          leaf lsp {
            type string;
          }
        }
        container sr-te {
          presence "true";
          leaf lsp {
            type string;
          }
        }
        container ldp {
          presence "true";
        }
        container mpls-fwd-policy {
          presence "true";
        }
        container rib-api {
          presence "true";
        }
        container sr-isis {
          presence "true";
        }
        container sr-ospf {
          presence "true";
        }
        container sr-ospf3 {
          presence "true";
        }
      }
    }
    leaf destination-class {
      type string;
    }
    leaf source-class {
      type string;
    }
    container forwarding-class {
      leaf class {
        tailf:cli-drop-node-name;
        type string;
      }
      leaf priority {
        type string;
      }
    }
    leaf shutdown {
      type string;
    }
  }

  grouping ncs_template_cflowd-params-grouping {
    container cflowd-parameters {
      list sampling {
        // NCS patched for predictable order
        ordered-by user;
        tailf:cli-suppress-mode;
        key "sampling";
        leaf sampling {
          type string;
        }
        leaf type {
          type string;
        }
        leaf direction {
          type string;
        }
      }
    }
  }

  grouping ncs_template_resolution-filter-grouping {
    container resolution-filter {
      leaf bgp {
        type empty;
      }
      leaf gre {
        type empty;
      }
      leaf ldp {
        type string;
      }
      leaf rsvp {
        type empty;
      }
      leaf sr-isis {
        type empty;
      }
      leaf sr-ospf {
        type empty;
      }
      leaf sr-te {
        type empty;
      }
    }
    leaf resolution {
      type string;
    }
  }

  grouping ncs_template_bgp-next-hop-resolution-grouping {
    container next-hop-resolution {
      leaf policy {
        type string;
      }
      leaf use-bgp-routes {
        type empty;
      }
      container label-route-transport-tunnel {
        container family {
          leaf address-family {
            tailf:cli-drop-node-name;
            type string;
          }
          // NCS expand uses statement
          container resolution-filter {
            leaf bgp {
              type empty;
            }
            leaf gre {
              type empty;
            }
            leaf ldp {
              type string;
            }
            leaf rsvp {
              type empty;
            }
            leaf sr-isis {
              type empty;
            }
            leaf sr-ospf {
              type empty;
            }
            leaf sr-te {
              type empty;
            }
          }
          leaf resolution {
            type string;
          }
        }
      }
      container labeled-routes {
        leaf prefer-transport-frr {
          type empty;
        }
        container transport-tunnel {
          list family {
            // NCS patched for predictable order
            ordered-by user;
            key "address-family";
            leaf address-family {
              type string;
            }
            // NCS expand uses statement
            container resolution-filter {
              leaf bgp {
                type empty;
              }
              leaf gre {
                type empty;
              }
              leaf ldp {
                type string;
              }
              leaf rsvp {
                type empty;
              }
              leaf sr-isis {
                type empty;
              }
              leaf sr-ospf {
                type empty;
              }
              leaf sr-te {
                type empty;
              }
            }
            leaf resolution {
              type string;
            }
          }
        }
      }
      container shortcut-tunnel {
        container family {

          grouping res-filter-grouping {
            container resolution-filter {
              leaf bgp {
                type empty;
              }
              leaf gre {
                type empty;
              }
              leaf ldp {
                type empty;
              }
              leaf rsvp {
                type empty;
              }
              leaf sr-isis {
                type empty;
              }
              leaf sr-ospf {
                type empty;
              }
              leaf sr-te {
                type empty;
              }
            }
            leaf resolution {
              type string;
            }
          }
          container ipv4 {
            uses res-filter-grouping;
          }
          container ipv6 {
            uses res-filter-grouping;
          }
        }
      }
      leaf weighted-ecmp {
        type empty;
      }
    }
  }

  grouping ncs_template_authentication-key-grouping {
    container authentication-key {
      leaf key {
        tailf:cli-drop-node-name;
        type string;
      }
      leaf method {
        tailf:cli-drop-node-name;
        type ncs_template_hash-method;
      }
    }
  }

  grouping ncs_template_hello-authentication-key-grouping {
    container hello-authentication-key {
      leaf key {
        tailf:cli-drop-node-name;
        type string;
      }
      leaf method {
        tailf:cli-drop-node-name;
        type ncs_template_hash-method;
      }
    }
  }

  grouping ncs_template_ipoe-session-grouping {
    leaf description {
      type string;
    }
    leaf ipoe-session-policy {
      type ncs_template_string32;
    }
    leaf user-db {
      type string;
    }
    leaf shutdown {
      type string;
    }
  }

  grouping ncs_template_packet-byte-offset-grouping {
    container packet-byte-offset {
      choice op {
        leaf add {
          type string;
        }
        leaf subtract {
          type string;
        }
      }
    }
  }

  grouping ncs_template_port-parent-grouping {
    container port-parent {
      presence "present";
      leaf weight {
        type string;
      }
      leaf level {
        type string;
      }
      leaf cir-weight {
        type string;
      }
      leaf cir-level {
        type string;
      }
    }
  }

  grouping ncs_template_router-aggregate-grouping {
    list aggregate {
      // NCS patched for predictable order
      ordered-by user;
      tailf:cli-suppress-mode;
      key "route";
      leaf route {
        type string;
      }
      leaf summary-only {
        type empty;
      }
      leaf discard-component-communities {
        type empty;
      }
      leaf as-set {
        type empty;
      }
      leaf aggregator {
        type string;
      }
      leaf-list community {
        // NCS patched for predictable order
        ordered-by user;
        type string;
      }
      leaf black-hole {
        type empty;
      }
      leaf description {
        type string;
      }
      leaf policy {
        type string;
      }
    }
  }

  grouping ncs_template_ospf-area-id-grouping {
    leaf area-id {
      type string;
    }
  }

  grouping ncs_template_service-id-grouping {
    leaf service-id {
      type ncs_template_service-id;
    }
  }

  grouping ncs_template_radius-server-grouping {
    list server {
      // NCS patched for predictable order
      ordered-by user;
      key "server-name";
      leaf server-name {
        type ncs_template_string32;
      }
      leaf address {
        type string;
      }
      leaf secret {
        type string;
      }
      leaf auth-port {
        type string;
      }
      leaf acct-port {
        type string;
      }
      leaf coa-script-policy {
        type ncs_template_string32;
      }
      leaf scheme {
        tailf:cli-drop-node-name;
        type ncs_template_hash-method;
      }
      leaf accept-coa {
        type empty;
      }
      leaf description {
        type string;
      }
      leaf python-policy {
        type ncs_template_string32;
      }
    }
  }

  grouping ncs_template_dhcp6-lease-timers-grouping {

    grouping dhcp6-lease-time-common-grouping {
      leaf sec {
        type string;
      }
    }
    container preferred-lifetime {
      leaf days {
        type string;
      }
      leaf hrs {
        type string;
      }
      leaf min {
        type string;
      }
      uses dhcp6-lease-time-common-grouping;
    }
    container rebind-timer {
      leaf days {
        type string;
      }
      leaf hrs {
        type string;
      }
      leaf min {
        type string;
      }
      uses dhcp6-lease-time-common-grouping;
    }
    container renew-timer {
      leaf days {
        type string;
      }
      leaf hrs {
        type string;
      }
      leaf min {
        type string;
      }
      uses dhcp6-lease-time-common-grouping;
    }
    container valid-lifetime {
      leaf days {
        type string;
      }
      leaf hrs {
        type string;
      }
      leaf min {
        type string;
      }
      uses dhcp6-lease-time-common-grouping;
    }
    container server-id {
      leaf duid {
        tailf:cli-drop-node-name;
        type string;
      }
      choice strhex {
        leaf string {
          type string;
        }
        leaf hex {
          type string;
        }
      }
    }
  }

  grouping ncs_template_snmp-community-grouping {
    list community {
      // NCS patched for predictable order
      ordered-by user;
      tailf:cli-suppress-mode;
      key "name";
      leaf name {
        type string;
      }
      leaf type {
        tailf:cli-drop-node-name;
        type ncs_template_hash-method;
      }
      leaf access-parameters {
        tailf:cli-drop-node-name;
        type string;
      }
      leaf version {
        type string;
      }
      leaf src-access-list {
        type ncs_template_string32;
      }
    }
  }

  grouping ncs_template_qos-dscp-list-grouping {
    list dscp {
      // NCS patched for predictable order
      ordered-by user;
      tailf:cli-suppress-mode;
      key "dscp-name";
      leaf dscp-name {
        type ncs_template_dscp-type;
      }
      leaf fc {
        type ncs_template_fc-name;
      }
      leaf profile {
        type ncs_template_in-out;
      }
    }
  }

  grouping ncs_template_qos-dot1p-list-grouping {
    list dot1p {
      // NCS patched for predictable order
      ordered-by user;
      tailf:cli-suppress-mode;
      key "id";
      leaf id {
        type string;
      }
      leaf fc {
        type ncs_template_fc-name;
      }
      leaf profile {
        type string;
      }
    }
    list prec {
      // NCS patched for predictable order
      ordered-by user;
      key "ip-prec-value";
      tailf:cli-suppress-mode;
      leaf ip-prec-value {
        tailf:cli-drop-node-name;
        type string;
      }
      leaf profile {
        type string;
      }
      leaf fc {
        type ncs_template_fc-name;
      }
    }
  }

  grouping ncs_template_slope-params-grouping {
    leaf start-avg {
      type string;
    }
    leaf max-avg {
      type string;
    }
    leaf max-prob {
      type string;
    }
    leaf shutdown {
      type string;
    }
  }

  grouping ncs_template_qos-lsp-exp-grouping {
    list lsp-exp {
      // NCS patched for predictable order
      ordered-by user;
      tailf:cli-suppress-mode;
      key "id";
      leaf id {
        type string;
      }
      leaf fc {
        type ncs_template_fc-name;
      }
      leaf profile {
        type string;
      }
    }
  }

  grouping ncs_template_bgp-common-grouping {
    leaf keepalive {
      type string;
    }
    container hold-time {
      leaf seconds {
        tailf:cli-drop-node-name;
        type string;
      }
      leaf min {
        type string;
      }
    }
    leaf preference {
      type string;
    }
  }

  grouping ncs_template_pim-common-grouping {
    leaf rpf6-table {
      type string;
    }
    leaf apply-to {
      type string;
    }
  }

  grouping ncs_template_local-dhcp-server-grouping {

    grouping dhcp-custom-options-grouping {
      list custom-option {
        // NCS patched for predictable order
        ordered-by user;
        tailf:cli-suppress-mode;
        key "number";
        leaf number {
          type string;
        }
        leaf-list address {
          // NCS patched for predictable order
          ordered-by user;
          type string;
        }
        leaf hex {
          type string;
        }
        leaf string {
          type string;
        }
      }
    }
    list local-dhcp-server {
      // NCS patched for predictable order
      ordered-by user;
      key "server-name";
      leaf server-name {
        type string;
      }
      leaf description {
        type string;
      }
      container use-gi-address {
        presence "true";
        leaf scope {
          type string;
        }
      }
      leaf force-renews {
        type empty;
      }
      list pool {
        // NCS patched for predictable order
        ordered-by user;
        key "pool-id";
        leaf pool-id {
          type ncs_template_string32;
        }
        leaf description {
          type string;
        }
        container max-lease-time {
          uses ncs_template_dhcp-lease-time;
        }
        container min-lease-time {
          uses ncs_template_dhcp-lease-time;
        }
        container minimum-free {
          leaf minimum-free-value {
            tailf:cli-drop-node-name;
            type string;
          }
          leaf percent {
            type empty;
          }
          leaf event-when-depleted {
            type empty;
          }
        }
        leaf nak-non-matching-subnet {
          type empty;
        }
        container offer-time {
          leaf min {
            type string;
          }
          leaf sec {
            type string;
          }
        }
        container options {
          leaf-list dns-server {
            // NCS patched for predictable order
            ordered-by user;
            type string;
          }
          leaf domain-name {
            type string;
          }
          container lease-rebind-time {
            uses ncs_template_dhcp-lease-time;
          }
          container lease-renew-time {
            uses ncs_template_dhcp-lease-time;
          }
          container lease-time {
            uses ncs_template_dhcp-lease-time;
          }
          leaf-list netbios-name-server {
            // NCS patched for predictable order
            ordered-by user;
            type string;
          }
          leaf netbios-node-type {
            type string;
          }
          uses dhcp-custom-options-grouping;
        }
        list subnet {
          // NCS patched for predictable order
          ordered-by user;
          key "subnet-id";
          leaf subnet-id {
            type string;
          }
          container address-range {
            uses ncs_template_ip-address-range {
              augment "low-high-list" {
                leaf failover {
                  type string;
                }
              }
            }
          }
          leaf drain {
            type empty;
          }
          container exclude-addresses {
            uses ncs_template_ip-address-range;
          }
          leaf maximum-declined {
            type string;
          }
          container minimum-free {
            leaf minimum-free-value {
              tailf:cli-drop-node-name;
              type string;
            }
            leaf percent {
              type empty;
            }
            leaf event-when-depleted {
              type empty;
            }
          }
          container options {
            leaf-list default-router {
              // NCS patched for predictable order
              ordered-by user;
              type string;
            }
            leaf subnet-mask {
              type string;
            }
            uses dhcp-custom-options-grouping;
          }
        }
      }
      container failover {
        leaf ignore-mclt-on-takeover {
          type empty;
        }
        container maximum-client-lead-time {
          leaf hrs {
            type string;
          }
          leaf min {
            type string;
          }
          leaf sec {
            type string;
          }
        }
        container partner-down-delay {
          leaf hrs {
            type string;
          }
          leaf min {
            type string;
          }
          leaf sec {
            type string;
          }
        }
        container peer {
          leaf ip-address {
            tailf:cli-drop-node-name;
            type string;
          }
          leaf tag {
            type string;
          }
        }
        container startup-wait-time {
          leaf min {
            type string;
          }
          leaf sec {
            type string;
          }
        }
        leaf shutdown {
          type string;
        }
      }
      container lease-hold-time {
        leaf days {
          type string;
        }
        leaf hrs {
          type string;
        }
        leaf min {
          type string;
        }
        leaf sec {
          type string;
        }
      }
      container lease-hold-time-for {
        leaf solicited-release {
          type empty;
        }
      }
      container use-pool-from-client {
        presence "true";
      }
      leaf shutdown {
        type string;
      }
    }
  }

  grouping ncs_rpc_notif_src-dst-ip {
    leaf src-ip {
      type union {
        type inet:ipv4-prefix;
        type string;
      }
    }
    leaf dst-ip {
      type union {
        type inet:ipv4-prefix;
        type string;
      }
    }
  }

  grouping ncs_rpc_notif_ip-address-range {
    list low-high-list {
      tailf:cli-drop-node-name;
      tailf:cli-suppress-mode;
      tailf:cli-delete-when-empty;
      key "low high";
      leaf low {
        type inet:ipv4-address;
      }
      leaf high {
        type inet:ipv4-address;
      }
    }
  }

  grouping ncs_rpc_notif_eth-cfm {
    leaf collect-lmm-stats {
      type empty;
    }
    list mep {
      key "mep-id domain association";
      leaf mep-id {
        type uint16;
      }
      leaf domain {
        type uint32;
      }
      leaf association {
        type uint32;
      }
      leaf direction {
        tailf:cli-hide-in-submode;
        type ncs_rpc_notif_direction;
      }
      container ais-enable {
        tailf:cli-add-mode;
        leaf-list client-meg-level {
          tailf:cli-flat-list-syntax;
          type uint8;
        }
        leaf description {
          type string;
        }
        leaf interval {
          type enumeration {
            enum "1";
            enum "60";
          }
        }
        leaf priority {
          type uint8;
        }
      }
      leaf ccm-enable {
        type empty;
      }
      leaf ccm-ltm-priority {
        type uint8;
      }
      leaf ccm-padding-size {
        type uint32;
      }
      leaf description {
        type string;
      }
      container eth-test-enable {
        tailf:cli-add-mode;
        uses ncs_rpc_notif_eth-test;
      }
      leaf fault-propagation-enable {
        type enumeration {
          enum "use-if-tlv";
          enum "suspend-ccm";
        }
      }
      leaf install-mep {
        type empty;
      }
      leaf low-priority-defect {
        type enumeration {
          enum "allDef";
          enum "macRemErrXcon";
          enum "remErrXcon";
          enum "errXcon";
          enum "Xcon";
          enum "noXcon";
        }
      }
      leaf mac-address {
        type ncs_rpc_notif_ieee-mac;
      }
      leaf one-way-delay-threshold {
        type uint16;
      }
      leaf shutdown {
        type boolean;
      }
    }
  }

  grouping ncs_rpc_notif_enable-origin-validation-grouping {
    leaf-list enable-origin-validation {
      tailf:cli-flat-list-syntax;
      type enumeration {
        enum "ipv4";
        enum "ipv6";
        enum "label-ipv4";
        enum "label-ipv6";
      }
    }
  }

  grouping ncs_rpc_notif_igmp-static-grouping {
    container static {
      tailf:cli-add-mode;
      list group {
        key "grp-ip-addr";
        leaf grp-ip-addr {
          type inet:ipv4-address;
        }
        list source {
          tailf:cli-suppress-mode;
          tailf:cli-delete-when-empty;
          key "ip-address";
          leaf ip-address {
            type inet:ipv4-address;
          }
        }
        leaf starg {
          type empty;
        }
      }
    }
  }

  grouping ncs_rpc_notif_igmp-snooping-grouping {
    leaf disable-router-alert {
      type empty;
    }
    leaf fast-leave {
      type empty;
    }
    leaf import {
      type string;
    }
    leaf last-member-query-interval {
      type uint8;
    }
    leaf max-num-groups {
      type uint16;
    }
    leaf mrouter-port {
      type empty;
    }
    leaf query-interval {
      type uint16;
    }
    leaf query-response-interval {
      type uint16;
    }
    leaf robust-count {
      type uint8;
    }
    leaf send-queries {
      type empty;
    }
    uses ncs_rpc_notif_igmp-static-grouping;
    leaf version {
      type uint8;
    }
  }

  grouping ncs_rpc_notif_sdp-common {
    leaf vc-id {
      type uint32;
    }
    leaf vc-type {
      tailf:cli-hide-in-submode;
      type enumeration {
        enum "ether";
        enum "vlan";
      }
    }
    leaf endpoint {
      tailf:cli-hide-in-submode;
      type string;
    }
    leaf icb {
      tailf:cli-hide-in-submode;
      type empty;
    }
    leaf shutdown {
      type boolean;
    }
  }

  grouping ncs_rpc_notif_sdp-spoke-mesh-common {
    leaf sdp-id {
      type uint32;
    }
    uses ncs_rpc_notif_sdp-common;
    leaf accounting-policy {
      type uint8;
    }
    leaf auto-learn-mac-protect {
      type empty;
    }
    leaf description {
      type string;
    }
    leaf collect-stats {
      type empty;
    }
    container hash-label {
      presence "true";
      leaf signal-capability {
        type empty;
      }
    }
    leaf control-word {
      type empty;
    }
    container igmp-snooping {
      tailf:cli-add-mode;
      uses ncs_rpc_notif_igmp-snooping-grouping;
    }
    container egress {
      tailf:cli-add-mode;
      container filter {
        uses ncs_rpc_notif_filter-choice;
      }
      container qos {
        tailf:cli-sequence-commands;
        tailf:cli-compact-syntax;
        leaf network-policy-id {
          tailf:cli-drop-node-name;
          type uint16;
        }
        leaf port-redirect-group {
          type string;
        }
        leaf instance {
          type uint16;
        }
      }
      leaf vc-label {
        type uint32;
      }
    }
    container eth-cfm {
      tailf:cli-add-mode;
      uses ncs_rpc_notif_eth-cfm;
    }
    leaf force-vlan-vc-forwarding {
      type empty;
    }
    container ingress {
      tailf:cli-add-mode;
      container filter {
        uses ncs_rpc_notif_filter-choice;
      }
      container qos {
        tailf:cli-sequence-commands;
        tailf:cli-compact-syntax;
        leaf network-policy-id {
          tailf:cli-drop-node-name;
          type uint16;
        }
        leaf fp-redirect-group {
          type string;
        }
        leaf instance {
          type uint16;
        }
      }
      leaf vc-label {
        type uint32;
      }
    }
    leaf mac-pinning {
      type empty;
    }
    list static-mac {
      tailf:cli-suppress-mode;
      key "address";
      leaf address {
        type ncs_rpc_notif_ieee-mac;
      }
    }
    leaf restrict-protected-src {
      type enumeration {
        enum "alarm-only";
        enum "discard-frame";
      }
    }
    leaf precedence {
      type union {
        type enumeration {
          enum "primary";
        }
        type uint8;
      }
    }
    leaf vlan-vc-tag {
      type uint16;
    }
  }

  grouping ncs_rpc_notif_stp-common {
    leaf auto-edge {
      type empty;
    }
    leaf edge-port {
      type empty;
    }
    leaf link-type {
      type enumeration {
        enum "pt-pt";
        enum "shared";
      }
    }
    leaf path-cost {
      type uint32;
    }
    leaf port-num {
      type uint16;
    }
    leaf priority {
      type uint16;
    }
    leaf shutdown {
      type boolean;
    }
  }

  grouping ncs_rpc_notif_filter-choice {
    leaf ip {
      type ncs_rpc_notif_filter-id;
    }
    leaf ipv6 {
      type ncs_rpc_notif_filter-id;
    }
    leaf mac {
      type ncs_rpc_notif_filter-id;
    }
  }

  grouping ncs_rpc_notif_eth-test {
    leaf test-pattern {
      type ncs_rpc_notif_test-pattern;
    }
    leaf crc-enable {
      type empty;
    }
  }

  grouping ncs_rpc_notif_time-stamp {
    leaf start-week {
      tailf:cli-drop-node-name;
      type enumeration {
        enum "first";
        enum "second";
        enum "third";
        enum "fourth";
        enum "last";
      }
    }
    leaf start-day {
      tailf:cli-drop-node-name;
      type ncs_rpc_notif_weekday;
    }
    leaf month {
      tailf:cli-drop-node-name;
      type ncs_rpc_notif_month;
    }
    leaf hours-minutes {
      tailf:cli-drop-node-name;
      type string;
    }
  }

  grouping ncs_rpc_notif_ip-filter-entry-grouping {
    leaf entry-name {
      type uint32;
    }
    leaf description {
      type string;
    }
    leaf log {
      type uint32;
    }
    list match {
      key "protocol-type";
      leaf protocol-type {
        type union {
          type ncs_rpc_notif_protocol;
          type string;
        }
      }
      leaf protocol {
        tailf:cli-prefix-key;
        type empty;
      }
      leaf dscp {
        type ncs_rpc_notif_dscp-type;
      }
      container ip {
        tailf:cli-compact-syntax;
        tailf:cli-sequence-commands;
        uses ncs_rpc_notif_filter-match-ip-grouping;
      }
      container src-ip {
        tailf:cli-compact-syntax;
        tailf:cli-sequence-commands;
        uses ncs_rpc_notif_filter-match-ip-grouping;
      }
      leaf src-route-option {
        type boolean;
      }
      container dst-ip {
        tailf:cli-compact-syntax;
        tailf:cli-sequence-commands;
        uses ncs_rpc_notif_filter-match-ip-grouping;
      }
      leaf icmp-type {
        type ncs_rpc_notif_icmp-type;
      }
      leaf icmp-code {
        type uint32;
      }
      leaf fragment {
        type enumeration {
          enum "true";
          enum "false";
          enum "first-only";
          enum "non-first-only";
        }
      }
      leaf option-present {
        type boolean;
      }
      container ip-option {
        tailf:cli-compact-syntax;
        leaf a {
          tailf:cli-drop-node-name;
          type uint32;
        }
        leaf b {
          tailf:cli-drop-node-name;
          type uint32;
        }
      }

      grouping filter-ip-filter-port-grouping {
        choice port-choice {
          case a {
            leaf op {
              tailf:cli-drop-node-name;
              type enumeration {
                enum "lt";
                enum "gt";
                enum "eq";
              }
            }
            leaf port {
              tailf:cli-drop-node-name;
              mandatory true;
              type uint16;
            }
          }
          case b {
            leaf range {
              type empty;
            }
            leaf start {
              tailf:cli-drop-node-name;
              mandatory true;
              type uint16;
            }
            leaf end {
              tailf:cli-drop-node-name;
              mandatory true;
              type uint16;
            }
          }
          case c {
            leaf port-list {
              type ncs_rpc_notif_string32;
            }
          }
        }
      }
      container port {
        tailf:cli-compact-syntax;
        tailf:cli-sequence-commands;
        uses filter-ip-filter-port-grouping;
      }
      container dst-port {
        tailf:cli-compact-syntax;
        tailf:cli-sequence-commands;
        uses filter-ip-filter-port-grouping;
      }
      container src-port {
        tailf:cli-compact-syntax;
        tailf:cli-sequence-commands {
          tailf:cli-reset-all-siblings;
        }
        choice port-choice {
          case a {
            leaf op {
              tailf:cli-drop-node-name;
              type enumeration {
                enum "lt";
                enum "gt";
                enum "eq";
              }
            }
            leaf port {
              tailf:cli-drop-node-name;
              mandatory true;
              type uint16;
            }
          }
          case b {
            leaf range {
              type empty;
            }
            leaf start {
              tailf:cli-drop-node-name;
              mandatory true;
              type uint16;
            }
            leaf end {
              tailf:cli-drop-node-name;
              mandatory true;
              type uint16;
            }
          }
          case c {
            leaf src-port-number {
              tailf:cli-drop-node-name;
              type uint16;
            }
            leaf mask {
              tailf:cli-drop-node-name;
              type uint16;
            }
          }
          case d {
            leaf port-list {
              type ncs_rpc_notif_string32;
            }
          }
        }
      }
      leaf tcp-ack {
        type boolean;
      }
      leaf tcp-syn {
        type boolean;
      }
    }
  }

  grouping ncs_rpc_notif_ipv6-filter-entry-grouping {
    leaf entry-name {
      type uint32;
    }
    leaf description {
      type string;
    }
    container match {
      tailf:cli-add-mode;
      presence "true";
      leaf next-header {
        tailf:cli-hide-in-submode;
        type union {
          type enumeration {
            enum "*";
            enum "none";
            enum "icmp";
            enum "igmp";
            enum "ip";
            enum "tcp";
            enum "egp";
            enum "igp";
            enum "udp";
            enum "rdp";
            enum "ipv6";
            enum "idrp";
            enum "rsvp";
            enum "gre";
            enum "ipv6-icmp";
            enum "ipv6-no-nxt";
            enum "iso-ip";
            enum "eigrp";
            enum "ospf-igp";
            enum "ether-ip";
            enum "encap";
            enum "pnni";
            enum "pim";
            enum "vrrp";
            enum "l2tp";
            enum "stp";
            enum "ptp";
            enum "isis";
            enum "crtp";
            enum "crudp";
            enum "sctp";
          }
          type uint32;
        }
      }
      leaf dscp {
        type ncs_rpc_notif_dscp-type;
      }
      container ip {
        tailf:cli-compact-syntax;
        tailf:cli-sequence-commands {
          tailf:cli-reset-all-siblings;
        }
        uses ncs_rpc_notif_filter-match-ipv6-grouping;
      }
      container src-ip {
        tailf:cli-compact-syntax;
        tailf:cli-sequence-commands {
          tailf:cli-reset-all-siblings;
        }
        uses ncs_rpc_notif_filter-match-ipv6-grouping;
      }
      container dst-ip {
        tailf:cli-compact-syntax;
        tailf:cli-sequence-commands {
          tailf:cli-reset-all-siblings;
        }
        uses ncs_rpc_notif_filter-match-ipv6-grouping;
      }
      leaf icmp-type {
        type ncs_rpc_notif_icmpv6-type;
      }
      leaf icmp-code {
        type uint32;
      }
      leaf fragment {
        type enumeration {
          enum "true";
          enum "false";
          enum "first-only";
          enum "non-first-only";
        }
      }
      container ip-option {
        tailf:cli-compact-syntax;
        tailf:cli-sequence-commands {
          tailf:cli-reset-all-siblings;
        }
        leaf a {
          tailf:cli-drop-node-name;
          type uint32;
        }
        leaf b {
          tailf:cli-drop-node-name;
          type uint32;
        }
      }

      grouping filter-ipv6-filter-port-grouping {
        choice port-choice {
          case a {
            leaf op {
              tailf:cli-drop-node-name;
              type enumeration {
                enum "lt";
                enum "gt";
                enum "eq";
              }
            }
            leaf port {
              tailf:cli-drop-node-name;
              type uint16;
            }
          }
          case b {
            leaf range {
              type empty;
            }
            leaf start {
              tailf:cli-drop-node-name;
              type uint16;
            }
            leaf end {
              tailf:cli-drop-node-name;
              type uint16;
            }
          }
          case c {
            leaf port-list {
              type ncs_rpc_notif_string32;
            }
          }
        }
      }
      container dst-port {
        tailf:cli-compact-syntax;
        tailf:cli-sequence-commands {
          tailf:cli-reset-all-siblings;
        }
        uses filter-ipv6-filter-port-grouping;
      }
      leaf routing-type0 {
        type boolean;
      }
      container src-port {
        tailf:cli-compact-syntax;
        tailf:cli-sequence-commands {
          tailf:cli-reset-all-siblings;
        }
        uses filter-ipv6-filter-port-grouping;
      }
      container port {
        tailf:cli-compact-syntax;
        tailf:cli-sequence-commands {
          tailf:cli-reset-all-siblings;
        }
        uses filter-ipv6-filter-port-grouping;
      }
      leaf tcp-ack {
        type boolean;
      }
      leaf tcp-syn {
        type boolean;
      }
    }
  }

  grouping ncs_rpc_notif_queue-adaptation-grouping {
    container adaptation-rule {
      tailf:cli-compact-syntax;
      leaf pir {
        type enumeration {
          enum "max";
          enum "min";
          enum "closest";
        }
      }
      leaf cir {
        type enumeration {
          enum "max";
          enum "min";
          enum "closest";
        }
      }
    }
  }

  grouping ncs_rpc_notif_queue-rate-grouping {
    container rate {
      tailf:cli-compact-syntax;
      tailf:cli-sequence-commands {
        tailf:cli-reset-all-siblings;
      }
      leaf pir {
        tailf:cli-drop-node-name;
        tailf:cli-optional-in-sequence;
        type ncs_rpc_notif_rate-type;
      }
      leaf cir {
        tailf:cli-optional-in-sequence;
        type ncs_rpc_notif_rate-type;
      }
      leaf alt-pir {
        tailf:cli-optional-in-sequence;
        tailf:alt-name "pir";
        type ncs_rpc_notif_rate-type;
      }
      leaf police {
        type empty;
      }
    }
  }

  grouping ncs_rpc_notif_qos-queue-percent-rate-grouping {
    container percent-rate {
      tailf:cli-compact-syntax;
      tailf:cli-sequence-commands {
        tailf:cli-reset-all-siblings;
      }
      leaf pir {
        tailf:cli-drop-node-name;
        type decimal64 {
          fraction-digits 2;
        }
      }
      leaf cir {
        tailf:cli-optional-in-sequence;
        type decimal64 {
          fraction-digits 2;
        }
      }
    }
  }

  grouping ncs_rpc_notif_sap-queue-override-grouping {
    container queue-override {
      tailf:cli-add-mode;
      list queue {
        key "queue-id";
        leaf queue-id {
          type uint32;
        }
        uses ncs_rpc_notif_queue-adaptation-grouping;
        leaf avg-frame-overhead {
          type decimal64 {
            fraction-digits 2;
          }
        }
        container mbs {
          tailf:cli-compact-syntax;
          tailf:cli-sequence-commands {
            tailf:cli-reset-siblings;
          }
          leaf val {
            tailf:cli-drop-node-name;
            type union {
              type enumeration {
                enum "default";
              }
              type uint32;
            }
          }
          leaf unit {
            tailf:cli-drop-node-name;
            type enumeration {
              enum "bytes";
              enum "kilobytes";
            }
          }
        }
        leaf cbs {
          type union {
            type enumeration {
              enum "default";
            }
            type uint32;
          }
        }
        leaf high-prio-only {
          type union {
            type enumeration {
              enum "default";
            }
            type uint8;
          }
        }
        container rate {
          tailf:cli-compact-syntax;
          tailf:cli-sequence-commands {
            tailf:cli-reset-siblings;
          }
          leaf pir {
            tailf:cli-drop-node-name;
            type union {
              type enumeration {
                enum "max";
              }
              type uint32;
            }
          }
          leaf cir {
            type union {
              type enumeration {
                enum "max";
              }
              type uint32;
            }
          }
        }
        container parent {
          tailf:cli-compact-syntax;
          tailf:cli-sequence-commands {
            tailf:cli-reset-siblings;
          }
          leaf weight {
            type uint8;
          }
          leaf cir-weight {
            type uint8;
          }
        }
        uses ncs_rpc_notif_qos-queue-percent-rate-grouping;
      }
    }
  }

  grouping ncs_rpc_notif_sap-scheduler-override-grouping {
    container scheduler-override {
      tailf:cli-add-mode;
      list scheduler {
        key "scheduler-policy-name";
        leaf scheduler-policy-name {
          type string;
        }
        container parent {
          tailf:cli-compact-syntax;
          leaf weight {
            type uint32;
          }
          leaf cir-weight {
            type uint32;
          }
        }
        container rate {
          tailf:cli-compact-syntax;
          tailf:cli-sequence-commands {
            tailf:cli-reset-siblings;
          }
          leaf rate {
            tailf:cli-drop-node-name;
            type union {
              type uint32;
              type enumeration {
                enum "max";
              }
            }
          }
          leaf cir {
            type union {
              type uint32;
              type enumeration {
                enum "sum";
                enum "max";
              }
            }
          }
        }
      }
    }
  }

  grouping ncs_rpc_notif_router-segment-routing-grouping {
    container segment-routing {
      tailf:cli-add-mode;
      container prefix-sid-range {
        tailf:cli-compact-syntax;
        tailf:cli-sequence-commands {
          tailf:cli-reset-siblings;
        }
        choice range {
          leaf global {
            type empty;
          }
          case other {
            leaf start-label {
              type uint32;
            }
            leaf max-index {
              type uint32;
            }
          }
        }
      }
      leaf tunnel-mtu {
        type uint16;
      }
      leaf tunnel-table-pref {
        type uint8;
      }
      leaf srlb {
        type string;
      }
      container micro-loop-avoidance {
        presence "true";
        leaf fib-delay {
          type uint8;
        }
      }
      leaf export-tunnel-table {
        type enumeration {
          enum "ldp";
        }
      }
      leaf shutdown {
        type boolean;
      }
    }
  }

  grouping ncs_rpc_notif_sap-policer-override-grouping-egress {
    container policer-override {
      tailf:cli-add-mode;
      list policer {
        key "policer-id";
        leaf policer-id {
          type uint8;
        }
        uses ncs_rpc_notif_policer-cbs-mbs-rate-with-packet-offset-grouping;
      }
    }
  }

  grouping ncs_rpc_notif_sap-policer-override-grouping-ingress {
    container policer-override {
      tailf:cli-add-mode;
      list policer {
        key "policer-id";
        leaf policer-id {
          type uint8;
        }
        uses ncs_rpc_notif_policer-cbs-mbs-rate-with-packet-offset-grouping;
      }
    }
  }

  grouping ncs_rpc_notif_ip-criteria-grouping {
    leaf dscp-only {
      tailf:cli-hide-in-submode;
      type empty;
    }
    list entry {
      key "id";
      leaf id {
        type uint16;
      }
      leaf description {
        type string;
      }
      container match {
        tailf:cli-add-mode;
        leaf protocol {
          tailf:cli-hide-in-submode;
          type ncs_rpc_notif_protocol;
        }
        leaf dscp {
          type ncs_rpc_notif_dscp-type;
        }
        container dst-ip {
          tailf:cli-compact-syntax;
          choice dst {
            leaf ip-address-with-mask {
              tailf:cli-drop-node-name;
              type tailf:ipv4-address-and-prefix-length;
            }
            leaf ip-prefix-list {
              type ncs_rpc_notif_string32;
            }
          }
        }
        container src-ip {
          tailf:cli-compact-syntax;
          choice src {
            leaf ip-address-with-mask {
              tailf:cli-drop-node-name;
              type tailf:ipv4-address-and-prefix-length;
            }
            leaf ip-prefix-list {
              type ncs_rpc_notif_string32;
            }
          }
        }

        grouping port-choice-grouping {
          choice port-choice {
            case a {
              leaf op {
                tailf:cli-drop-node-name;
                type enumeration {
                  enum "lt";
                  enum "gt";
                  enum "eq";
                }
              }
              leaf port {
                tailf:cli-drop-node-name;
                type uint16;
              }
            }
            case b {
              leaf range {
                type empty;
              }
              leaf start {
                tailf:cli-drop-node-name;
                type uint16;
              }
              leaf end {
                tailf:cli-drop-node-name;
                type uint16;
              }
            }
          }
        }
        container dst-port {
          tailf:cli-compact-syntax;
          tailf:cli-sequence-commands {
            tailf:cli-reset-all-siblings;
          }
          uses port-choice-grouping;
        }
        container src-port {
          tailf:cli-compact-syntax;
          tailf:cli-sequence-commands {
            tailf:cli-reset-all-siblings;
          }
          uses port-choice-grouping;
        }
      }
      container action {
        tailf:cli-compact-syntax;
        presence "true";
        leaf profile {
          type enumeration {
            enum "in";
            enum "out";
            enum "exceed";
            enum "inplus";
          }
        }
        leaf fc {
          type ncs_rpc_notif_fc-name;
        }
        leaf priority {
          type enumeration {
            enum "high";
            enum "low";
          }
        }
        leaf policer {
          type uint8;
        }
      }
    }
  }

  grouping ncs_rpc_notif_ipv6-criteria-grouping {
    list entry {
      key "id";
      leaf id {
        type uint16;
      }
      leaf description {
        type string;
      }
      container match {
        tailf:cli-add-mode;
        leaf protocol {
          tailf:cli-hide-in-submode;
          type ncs_rpc_notif_protocol;
        }
        leaf next-header {
          tailf:cli-hide-in-submode;
          type union {
            type uint8;
            type ncs_rpc_notif_protocol;
          }
        }
        leaf dscp {
          type ncs_rpc_notif_dscp-type;
        }
        container src-ip {
          uses ncs_rpc_notif_filter-match-ip-grouping;
        }
        container dst-ip {
          uses ncs_rpc_notif_filter-match-ip-grouping;
        }

        grouping port-choice-grouping {
          choice port-choice {
            case a {
              leaf op {
                tailf:cli-drop-node-name;
                type enumeration {
                  enum "lt";
                  enum "gt";
                  enum "eq";
                }
              }
              leaf port {
                tailf:cli-drop-node-name;
                type uint16;
              }
            }
            case b {
              leaf range {
                type empty;
              }
              leaf start {
                tailf:cli-drop-node-name;
                type uint16;
              }
              leaf end {
                tailf:cli-drop-node-name;
                type uint16;
              }
            }
          }
        }
        container dst-port {
          tailf:cli-compact-syntax;
          tailf:cli-sequence-commands {
            tailf:cli-reset-all-siblings;
          }
          uses port-choice-grouping;
        }
        container src-port {
          tailf:cli-compact-syntax;
          tailf:cli-sequence-commands {
            tailf:cli-reset-all-siblings;
          }
          uses port-choice-grouping;
        }
      }
      container action {
        tailf:cli-compact-syntax;
        leaf fc {
          type string;
        }
        leaf priority {
          type enumeration {
            enum "high";
            enum "low";
          }
        }
        leaf policer {
          type uint8;
        }
      }
    }
  }

  grouping ncs_rpc_notif_mac-criteria-grouping {
    leaf match-criteria {
      tailf:cli-hide-in-submode;
      tailf:cli-drop-node-name;
      type enumeration {
        enum "any";
        enum "dot1p-only";
      }
    }
    leaf type {
      type enumeration {
        enum "normal";
        enum "vid";
      }
    }
    list entry {
      key "id";
      leaf id {
        type uint16;
      }
      leaf description {
        type string;
      }
      container match {
        tailf:cli-add-mode;
        leaf frame-type {
          tailf:cli-hide-in-submode;
          type enumeration {
            enum "802dot3";
            enum "802dot2-llc";
            enum "802dot2-snap";
            enum "ethernet-II";
            enum "atm";
          }
        }
        container outer-tag {
          tailf:cli-compact-syntax;
          leaf value {
            tailf:cli-drop-node-name;
            type union {
              type uint16;
              type string;
            }
          }
          leaf vid-mask {
            tailf:cli-drop-node-name;
            type union {
              type uint16;
              type string;
            }
          }
        }

        grouping match-mac-grouping {
          leaf ieee-address {
            tailf:cli-drop-node-name;
            type ncs_rpc_notif_ieee-mac;
          }
          leaf ieee-address-mask {
            tailf:cli-drop-node-name;
            type ncs_rpc_notif_ieee-mac;
          }
        }
        container dst-mac {
          tailf:cli-compact-syntax;
          tailf:cli-sequence-commands {
            tailf:cli-reset-siblings;
          }
          uses match-mac-grouping;
        }
        container src-mac {
          tailf:cli-compact-syntax;
          tailf:cli-sequence-commands {
            tailf:cli-reset-siblings;
          }
          uses match-mac-grouping;
        }
        container dot1p {
          tailf:cli-compact-syntax;
          tailf:cli-sequence-commands {
            tailf:cli-reset-siblings;
          }
          leaf dot1p-value {
            tailf:cli-drop-node-name;
            type uint8;
          }
          leaf dot1p-mask {
            tailf:cli-drop-node-name;
            type uint8;
          }
        }
        leaf etype {
          type string;
        }
      }
      container action {
        tailf:cli-compact-syntax;
        tailf:cli-sequence-commands {
          tailf:cli-reset-all-siblings;
        }
        leaf fc {
          type ncs_rpc_notif_fc-name;
        }
        leaf priority {
          type enumeration {
            enum "low";
            enum "high";
          }
        }
      }
    }
  }

  grouping ncs_rpc_notif_meter-grouping {
    leaf meter-id {
      type uint8;
    }
    leaf multipoint {
      tailf:cli-hide-in-submode;
      type empty;
    }
    uses ncs_rpc_notif_queue-adaptation-grouping;

    grouping unit-grouping {
      leaf unit {
        tailf:cli-drop-node-name;
        type enumeration {
          enum "kbits";
          enum "bytes";
          enum "kbytes";
        }
      }
    }
    container cbs {
      tailf:cli-compact-syntax;
      tailf:cli-sequence-commands {
        tailf:cli-reset-all-siblings;
      }
      leaf size {
        tailf:cli-drop-node-name;
        type union {
          type uint32;
          type enumeration {
            enum "default";
          }
        }
      }
      uses unit-grouping;
    }
    container mbs {
      tailf:cli-compact-syntax;
      tailf:cli-sequence-commands {
        tailf:cli-reset-all-siblings;
      }
      leaf size {
        tailf:cli-drop-node-name;
        type union {
          type uint32;
          type enumeration {
            enum "default";
          }
        }
      }
      uses unit-grouping;
    }
    container rate {
      tailf:cli-compact-syntax;
      leaf cir {
        type ncs_rpc_notif_rate-type;
      }
      leaf pir {
        type ncs_rpc_notif_rate-type;
      }
    }
    leaf mode {
      type enumeration {
        enum "trtcm1";
        enum "trtcm2";
        enum "srtcm";
      }
    }
  }

  grouping ncs_rpc_notif_cpm-filter-match-port-grouping {
    choice port-choice {
      case a {
        leaf port-number {
          tailf:cli-drop-node-name;
          type uint16;
        }
        leaf mask {
          tailf:cli-drop-node-name;
          type uint16;
        }
      }
      case b {
        leaf range {
          type empty;
        }
        leaf start {
          tailf:cli-drop-node-name;
          type uint16;
        }
        leaf end {
          tailf:cli-drop-node-name;
          type uint16;
        }
      }
      case c {
        leaf port-list {
          type string;
        }
      }
    }
  }

  grouping ncs_rpc_notif_filter-match-ip-grouping {
    choice ip {
      leaf address {
        tailf:cli-drop-node-name;
        type union {
          type inet:ipv4-address;
          type inet:ipv4-prefix;
          type string;
        }
      }
      leaf ip-prefix-list {
        type string;
      }
      leaf ipv6-prefix-list {
        type ncs_rpc_notif_string32;
      }
    }
  }

  grouping ncs_rpc_notif_filter-match-ipv6-grouping {
    choice ipv6 {
      leaf address {
        tailf:cli-drop-node-name;
        type union {
          type tailf:ipv6-address-and-prefix-length;
          type inet:ipv6-address;
          type string;
        }
      }
      leaf ipv6-prefix-list {
        type string;
      }
    }
  }

  grouping ncs_rpc_notif_sap-egress-grouping {
    container agg-rate {
      tailf:cli-add-mode;
      container rate {
        tailf:cli-compact-syntax;
        leaf val {
          tailf:cli-drop-node-name;
          type union {
            type uint32;
            type enumeration {
              enum "max";
            }
          }
        }
        leaf cir {
          type union {
            type uint32;
            type enumeration {
              enum "max";
            }
          }
        }
      }
    }
    leaf egress-remark-policy {
      type string;
    }
    leaf vlan-qos-policy {
      type string;
    }
    leaf agg-rate-limit {
      type uint32;
    }
    container filter {
      uses ncs_rpc_notif_filter-choice;
    }
    leaf multicast-group {
      type string;
    }
    leaf qos {
      type uint16;
    }
    uses ncs_rpc_notif_sap-queue-override-grouping;
    leaf scheduler-policy {
      type string;
    }
    uses ncs_rpc_notif_sap-scheduler-override-grouping;
    uses ncs_rpc_notif_sap-policer-override-grouping-egress;
    leaf qinq-mark-top-only {
      type empty;
    }
    leaf dest-mac-rewrite {
      type yang:mac-address;
    }
    container qtag-manipulation {
      tailf:cli-add-mode;
      leaf preserve {
        type empty;
      }
    }
  }

  grouping ncs_rpc_notif_sap-ingress-grouping {
    container filter {
      uses ncs_rpc_notif_filter-choice;
    }
    container aggregate-meter-rate {
      tailf:cli-compact-syntax;
      tailf:cli-sequence-commands {
        tailf:cli-reset-siblings;
      }
      leaf value {
        tailf:cli-drop-node-name;
        type uint32;
      }
      leaf burst {
        type uint32;
      }
    }
    leaf match-qinq-dot1p {
      type enumeration {
        enum "top";
        enum "bottom";
      }
    }
    container qos {
      tailf:cli-compact-syntax;
      tailf:cli-sequence-commands {
        tailf:cli-reset-all-siblings;
      }
      leaf policy-id {
        tailf:cli-drop-node-name;
        type uint16;
      }
      leaf shared-queuing {
        tailf:cli-optional-in-sequence;
        type empty;
      }
      leaf enable-table-classification {
        type empty;
      }
    }
    uses ncs_rpc_notif_sap-queue-override-grouping;
    leaf agg-shaper-rate {
      type union {
        type uint32;
        type enumeration {
          enum "max";
        }
      }
    }
    uses ncs_rpc_notif_sap-policer-override-grouping-ingress;
    leaf policer-control-policy {
      type string;
    }
    leaf scheduler-policy {
      type string;
    }
    uses ncs_rpc_notif_sap-scheduler-override-grouping;
    leaf vlan-translation {
      type union {
        type enumeration {
          enum "copy-outer";
        }
        type uint16;
      }
    }
    container aggregate-policer-rate {
      tailf:cli-compact-syntax;
      leaf rate {
        tailf:cli-drop-node-name;
        type uint32;
      }
      leaf burst {
        type union {
          type uint32;
          type enumeration {
            enum "default";
          }
        }
      }
    }
    container qtag-manipulation {
      tailf:cli-add-mode;
      leaf preserve {
        type empty;
      }
    }
  }

  grouping ncs_rpc_notif_queue-ref-grouping {
    leaf queue-id {
      tailf:cli-drop-node-name;
      type uint8;
    }
    leaf group {
      type string;
    }
  }

  grouping ncs_rpc_notif_policer-ref-grouping {
    leaf policer-id {
      tailf:cli-drop-node-name;
      type uint8;
    }
  }

  grouping ncs_rpc_notif_policy-option-action-params-grouping {
    leaf add-paths-send-limit {
      type union {
        type uint32;
        type enumeration {
          enum "multipaths";
        }
      }
    }
    leaf admin-tag-policy {
      type string;
    }
    leaf advertise-label {
      type enumeration {
        enum "per-prefix";
        enum "pop";
      }
    }
    leaf bgp-leak {
      type empty;
    }
    container aigp-metric {
      tailf:cli-compact-syntax;
      leaf add {
        type empty;
      }
      leaf aigp-metric {
        tailf:cli-drop-node-name;
        type union {
          type uint32;
          type enumeration {
            enum "igp";
          }
          type string;
        }
      }
    }
    container as-path {
      tailf:cli-compact-syntax;
      tailf:cli-sequence-commands;
      leaf action {
        tailf:cli-drop-node-name;
        type enumeration {
          enum "add";
          enum "replace";
        }
      }
      leaf name {
        tailf:cli-drop-node-name;
        type string;
      }
    }
    container as-path-prepend {
      tailf:cli-compact-syntax;
      tailf:cli-sequence-commands;
      choice as-choice {
        leaf as-number {
          tailf:cli-drop-node-name;
          type uint32;
        }
        leaf most-recent {
          type empty;
        }
      }
      leaf repeat {
        tailf:cli-drop-node-name;
        type uint8;
      }
    }
    container community {
      choice comm {
        case add-remove {
          leaf-list add {
            tailf:cli-flat-list-syntax;
            type string;
          }
          leaf-list remove {
            tailf:cli-flat-list-syntax;
            type string;
          }
        }
        leaf-list replace {
          tailf:cli-flat-list-syntax;
          type string;
        }
      }
    }
    container damping {
      leaf name {
        tailf:cli-drop-node-name;
        type union {
          type enumeration {
            enum "none";
          }
          type string;
        }
      }
    }
    leaf local-preference {
      type union {
        type uint32;
        type string;
      }
    }
    container metric {
      tailf:cli-compact-syntax;
      tailf:cli-sequence-commands;
      leaf action {
        tailf:cli-drop-node-name;
        type enumeration {
          enum "add";
          enum "set";
          enum "subtract";
        }
      }
      leaf metric {
        tailf:cli-drop-node-name;
        type union {
          type enumeration {
            enum "igp";
          }
          type uint32;
        }
      }
    }
    container multicast-redirection {
      tailf:cli-compact-syntax;
      tailf:cli-sequence-commands {
        tailf:cli-reset-siblings;
      }
      leaf fwd-service {
        tailf:cli-optional-in-sequence;
        type uint32;
      }
      leaf ip-int-name {
        tailf:cli-drop-node-name;
        type string;
      }
    }
    choice next-hop-choice {
      leaf next-hop {
        type union {
          type inet:ipv4-address;
          type inet:ipv6-address;
          type enumeration {
            enum "peer-address";
          }
        }
      }
      leaf next-hop-self {
        type empty;
      }
    }
    leaf origin {
      type enumeration {
        enum "igp";
        enum "egp";
        enum "incomplete";
      }
    }
    leaf preference {
      type uint8;
    }
    leaf tag {
      type ncs_rpc_notif_policy-options-tag;
    }
    leaf type {
      type union {
        type uint8;
        type string;
      }
    }
    container bgp-med {
      tailf:cli-compact-syntax;
      container set {
        leaf value {
          tailf:cli-drop-node-name;
          type string;
        }
      }
    }
    leaf sr-label-index {
      type union {
        type uint32;
        type string;
      }
    }
  }

  grouping ncs_rpc_notif_policy-options-action-fc-grouping {
    container fc {
      tailf:cli-compact-syntax;
      tailf:cli-sequence-commands {
        tailf:cli-reset-all-siblings;
      }
      leaf fc {
        tailf:cli-drop-node-name;
        type ncs_rpc_notif_fc-name;
      }
      leaf priority {
        type enumeration {
          enum "high";
          enum "low";
        }
      }
    }
  }

  grouping ncs_rpc_notif_policy-options-default-action-grouping {
    choice action {
      leaf reject {
        type empty;
      }
      container drop {
        tailf:cli-add-mode;
        presence "true";
        uses ncs_rpc_notif_policy-option-action-params-grouping;
      }
      container accept {
        tailf:cli-add-mode;
        presence "true";
        uses ncs_rpc_notif_policy-option-action-params-grouping;
      }
      container next-entry {
        tailf:cli-add-mode;
        presence "true";
        uses ncs_rpc_notif_policy-option-action-params-grouping;
      }
      container next-policy {
        tailf:cli-add-mode;
        presence "true";
        uses ncs_rpc_notif_policy-option-action-params-grouping;
      }
    }
  }

  grouping ncs_rpc_notif_policy-options-action-grouping {
    choice action {
      leaf reject {
        type empty;
      }
      container drop {
        tailf:cli-add-mode;
        presence "true";
        uses ncs_rpc_notif_policy-option-action-params-grouping;
        uses ncs_rpc_notif_policy-options-action-fc-grouping;
      }
      container accept {
        tailf:cli-add-mode;
        presence "true";
        uses ncs_rpc_notif_policy-option-action-params-grouping;
        uses ncs_rpc_notif_policy-options-action-fc-grouping;
      }
      container next-entry {
        tailf:cli-add-mode;
        presence "true";
        uses ncs_rpc_notif_policy-option-action-params-grouping;
        uses ncs_rpc_notif_policy-options-action-fc-grouping;
      }
      container next-policy {
        tailf:cli-add-mode;
        presence "true";
        uses ncs_rpc_notif_policy-option-action-params-grouping;
        uses ncs_rpc_notif_policy-options-action-fc-grouping;
      }
    }
  }

  grouping ncs_rpc_notif_mbs-rate-grouping {
    leaf size {
      tailf:cli-drop-node-name;
      type union {
        type uint32;
        type enumeration {
          enum "default";
        }
      }
    }
    leaf unit {
      tailf:cli-drop-node-name;
      type enumeration {
        enum "bytes";
        enum "kilobytes";
      }
    }
  }

  grouping ncs_rpc_notif_policer-cbs-mbs-rate-grouping {
    container cbs {
      tailf:cli-compact-syntax;
      tailf:cli-sequence-commands {
        tailf:cli-reset-siblings;
      }
      uses ncs_rpc_notif_mbs-rate-grouping;
    }
    container mbs {
      tailf:cli-compact-syntax;
      tailf:cli-sequence-commands {
        tailf:cli-reset-siblings;
      }
      uses ncs_rpc_notif_mbs-rate-grouping;
    }
    container rate {
      tailf:cli-compact-syntax;
      tailf:cli-sequence-commands {
        tailf:cli-reset-siblings;
      }
      leaf pir {
        tailf:cli-drop-node-name;
        type ncs_rpc_notif_rate-type;
      }
      leaf cir {
        type ncs_rpc_notif_rate-type;
      }
    }
    leaf stat-mode {
      type ncs_rpc_notif_policer-stat-mode;
    }
  }

  grouping ncs_rpc_notif_policer-cbs-mbs-rate-with-packet-offset-grouping {
    uses ncs_rpc_notif_policer-cbs-mbs-rate-grouping;
    container packet-byte-offset {
      tailf:cli-compact-syntax;
      choice add-delete {
        leaf add {
          type uint8;
        }
        leaf subtract {
          type uint8;
        }
      }
    }
  }

  grouping ncs_rpc_notif_policer-grouping {
    uses ncs_rpc_notif_queue-adaptation-grouping;
    leaf adv-config-policy {
      type string;
    }
    uses ncs_rpc_notif_policer-cbs-mbs-rate-with-packet-offset-grouping;
    leaf description {
      type string;
    }
    leaf high-prio-only {
      type union {
        type uint8;
        type enumeration {
          enum "default";
        }
      }
    }
    container parent {
      tailf:cli-compact-syntax;
      tailf:cli-sequence-commands {
        tailf:cli-reset-all-siblings;
      }
      leaf name {
        tailf:cli-drop-node-name;
        type union {
          type enumeration {
            enum "root";
          }
          type string;
        }
      }
      leaf level {
        tailf:cli-break-sequence-commands;
        type uint8;
      }
      leaf weight-level {
        tailf:alt-name "weight";
        type uint8;
      }
    }
    leaf profile-capped {
      type empty;
    }
  }

  grouping ncs_rpc_notif_queue-grouping {
    leaf multipoint {
      tailf:cli-hide-in-submode;
      type empty;
    }
    leaf queue-type {
      tailf:cli-drop-node-name;
      tailf:cli-hide-in-submode;
      type ncs_rpc_notif_queue-type;
    }
    leaf queue-mode-m {
      tailf:cli-drop-node-name;
      tailf:cli-hide-in-submode;
      type enumeration {
        enum "profile-mode";
        enum "priority-mode";
      }
    }
    uses ncs_rpc_notif_queue-adaptation-grouping;
    leaf adv-config-policy {
      type string;
    }
    leaf avg-frame-overhead {
      type decimal64 {
        fraction-digits 2;
      }
    }
    container burst-limit {
      tailf:cli-compact-syntax;
      tailf:cli-sequence-commands;
      leaf size {
        tailf:cli-drop-node-name;
        type union {
          type uint32;
          type enumeration {
            enum "default";
          }
        }
      }
      leaf unit {
        tailf:cli-drop-node-name;
        type enumeration {
          enum "bytes";
          enum "kilobytes";
        }
      }
    }
    leaf cbs {
      type union {
        type uint32;
        type enumeration {
          enum "default";
        }
      }
    }
    leaf high-prio-only {
      type union {
        type uint8;
      }
    }
    container mbs {
      tailf:cli-compact-syntax;
      tailf:cli-sequence-commands {
        tailf:cli-reset-siblings;
      }
      leaf size {
        tailf:cli-drop-node-name;
        type union {
          type uint32;
          type enumeration {
            enum "default";
          }
        }
      }
      leaf unit {
        tailf:cli-drop-node-name;
        type enumeration {
          enum "bytes";
          enum "kilobytes";
        }
      }
    }
    container parent {
      tailf:cli-compact-syntax;
      tailf:cli-sequence-commands {
        tailf:cli-reset-all-siblings;
      }
      leaf name {
        tailf:cli-drop-node-name;
        type string;
      }
      leaf level {
        tailf:cli-break-sequence-commands;
        type uint8;
      }
      leaf weight {
        type uint8;
      }
      leaf cir-level {
        type uint8;
      }
      leaf cir-weight {
        type uint8;
      }
    }
    container percent-rate {
      tailf:cli-compact-syntax;
      tailf:cli-sequence-commands {
        tailf:cli-reset-all-siblings;
      }
      leaf pir-percent {
        tailf:cli-drop-node-name;
        type decimal64 {
          fraction-digits 2;
        }
      }
      leaf cir {
        tailf:cli-optional-in-sequence;
        type decimal64 {
          fraction-digits 2;
        }
      }
    }
    leaf pool {
      type string;
    }
    uses ncs_rpc_notif_port-parent-grouping;
    uses ncs_rpc_notif_queue-rate-grouping;
    leaf slope-policy {
      type string;
    }
    container wred-queue {
      tailf:cli-compact-syntax;
      tailf:cli-sequence-commands {
        tailf:cli-reset-siblings;
      }
      leaf policy {
        tailf:cli-optional-in-sequence;
        type string;
      }
      leaf mode {
        tailf:cli-optional-in-sequence;
        type enumeration {
          enum "native";
          enum "pool-per-queue";
        }
      }
      leaf slope-usage {
        tailf:cli-optional-in-sequence;
        type enumeration {
          enum "default";
          enum "exceed-low";
        }
      }
    }
    container xp-specific {
      tailf:cli-add-mode;
      container wred-queue {
        tailf:cli-compact-syntax;
        tailf:cli-sequence-commands;
        leaf policy {
          type string;
        }
      }
      uses ncs_rpc_notif_packet-byte-offset-grouping;
    }
    container drop-tail {
      tailf:cli-add-mode;
      container low {
        tailf:cli-add-mode;
        leaf percent-reduction-from-mbs {
          type union {
            type uint8;
            type enumeration {
              enum "default";
            }
          }
        }
      }
    }
  }

  grouping ncs_rpc_notif_queue-group-template-entry {
    leaf queue-group-name {
      type string;
    }
    leaf description {
      type string;
    }
    list fc {
      key "fc-name";
      leaf fc-name {
        type ncs_rpc_notif_fc-name;
      }
      leaf queue {
        type uint8;
      }
    }
    list policer {
      key "policer-id";
      leaf policer-id {
        type uint8;
      }
      uses ncs_rpc_notif_policer-grouping;
    }
    list queue {
      key "queue-id";
      leaf queue-id {
        type uint8;
      }
      uses ncs_rpc_notif_queue-grouping;
    }
  }

  grouping ncs_rpc_notif_dhcp-lease-time {
    leaf days {
      type uint16;
    }
    leaf hrs {
      type uint16;
    }
    leaf min {
      type uint16;
    }
    leaf sec {
      type uint16;
    }
  }

  grouping ncs_rpc_notif_bfd-grouping {
    leaf transmit-interval {
      tailf:cli-drop-node-name;
      type uint32;
    }
    leaf receive {
      type uint32;
    }
    leaf multiplier {
      type uint8;
    }
    leaf echo-receive {
      type uint32;
    }
    leaf type {
      type enumeration {
        enum "cpm-np";
        enum "iom-hw";
        enum "np";
        enum "fp";
      }
    }
  }

  grouping ncs_rpc_notif_dhcp6-grouping {
    container dhcp6-server {
      tailf:cli-add-mode;
      leaf max-nbr-of-leases {
        type uint32;
      }
    }
    container dhcp6-relay {
      tailf:cli-add-mode;
      leaf description {
        type string;
      }
      container lease-populate {
        presence "present";
        tailf:cli-sequence-commands;
        tailf:cli-compact-syntax;
        leaf nbr-of-leases {
          tailf:cli-drop-node-name;
          type uint32;
        }
        leaf route-populate {
          type empty;
        }
        leaf pd {
          type empty;
        }
        leaf exclude {
          tailf:cli-break-sequence-commands;
          type empty;
        }
        leaf na {
          type empty;
        }
        leaf ta {
          type empty;
        }
      }
      leaf neighbor-resolution {
        type empty;
      }
      container option {
        tailf:cli-add-mode;
        container interface-id {
          choice choice {
            leaf sap-id {
              type empty;
            }
            leaf ifindex {
              type empty;
            }
            leaf string {
              type string;
            }
          }
        }
        leaf remote-id {
          type empty;
        }
      }
      leaf source-address {
        tailf:cli-case-insensitive;
        type inet:ipv6-address;
      }
      leaf link-address {
        type inet:ipv6-address;
      }
      leaf-list server {
        tailf:cli-flat-list-syntax;
        type inet:ipv6-address;
      }
      leaf shutdown {
        type boolean;
      }
    }
  }

  grouping ncs_rpc_notif_ipv6-grouping {
    list address {
      tailf:cli-suppress-mode;
      tailf:cli-compact-syntax;
      key "addr";
      leaf addr {
        type tailf:ipv6-address-and-prefix-length;
      }
      leaf eui-64 {
        type empty;
      }
      leaf preferred {
        type empty;
      }
      leaf track-srrp {
        type uint32;
      }
      leaf modifier {
        type string;
      }
      leaf dad-disable {
        type empty;
      }
    }

    typedef nd-type {
      type enumeration {
        enum "both";
        enum "link-local";
        enum "global";
      }
    }
    leaf nd-learn-unsolicited {
      type nd-type;
    }
    leaf nd-proactive-refresh {
      type nd-type;
    }
    container bfd {
      tailf:cli-compact-syntax;
      uses ncs_rpc_notif_bfd-grouping;
    }
    leaf dad-disable {
      type empty;
    }
    container icmp6 {
      tailf:cli-add-mode;
      container packet-too-big {
        tailf:cli-compact-syntax;
        tailf:cli-sequence-commands {
          tailf:cli-reset-all-siblings;
        }
        uses ncs_rpc_notif_icmp-params-grouping;
      }
      container param-problem {
        tailf:cli-compact-syntax;
        tailf:cli-sequence-commands {
          tailf:cli-reset-all-siblings;
        }
        uses ncs_rpc_notif_icmp-params-grouping;
      }
      container redirects {
        tailf:cli-compact-syntax;
        tailf:cli-sequence-commands {
          tailf:cli-reset-all-siblings;
        }
        uses ncs_rpc_notif_icmp-params-grouping;
      }
      container time-exceeded {
        tailf:cli-compact-syntax;
        tailf:cli-sequence-commands {
          tailf:cli-reset-all-siblings;
        }
        uses ncs_rpc_notif_icmp-params-grouping;
      }
      container unreachables {
        tailf:cli-compact-syntax;
        tailf:cli-sequence-commands {
          tailf:cli-reset-all-siblings;
        }
        uses ncs_rpc_notif_icmp-params-grouping;
      }
    }
    container link-local-address {
      tailf:cli-compact-syntax;
      tailf:cli-sequence-commands {
        tailf:cli-reset-all-siblings;
      }
      leaf addr {
        tailf:cli-drop-node-name;
        type union {
          type inet:ipv6-address;
          type tailf:ipv6-address-and-prefix-length;
        }
      }
      leaf preferred {
        tailf:cli-optional-in-sequence;
        type empty;
      }
      leaf dad-disable {
        type empty;
      }
    }
    leaf local-proxy-nd {
      type empty;
    }
    container neighbor {
      tailf:cli-compact-syntax;
      tailf:cli-sequence-commands {
        tailf:cli-reset-all-siblings;
      }
      leaf addr {
        tailf:cli-drop-node-name;
        type union {
          type inet:ipv6-address;
          type tailf:ipv6-address-and-prefix-length;
        }
      }
      leaf mac-addr {
        tailf:cli-drop-node-name;
        type ncs_rpc_notif_ieee-mac;
      }
    }
    container proxy-nd-policy {
      tailf:cli-compact-syntax;
      leaf name1 {
        tailf:cli-drop-node-name;
        type string;
      }
      leaf name2 {
        tailf:cli-drop-node-name;
        type string;
      }
      leaf name3 {
        tailf:cli-drop-node-name;
        type string;
      }
      leaf name4 {
        tailf:cli-drop-node-name;
        type string;
      }
      leaf name5 {
        tailf:cli-drop-node-name;
        type string;
      }
    }
    leaf qos-route-lookup {
      type enumeration {
        enum "source";
        enum "destination";
      }
    }
    leaf reachable-time {
      type uint32;
    }
    container secure-nd {
      tailf:cli-add-mode;
      leaf allow-unsecured-msgs {
        type boolean;
      }
      leaf link-local-modifier {
        type string;
      }
      leaf public-key-min-bits {
        type uint32;
      }
      leaf security-parameter {
        type uint32;
      }
      leaf shutdown {
        type boolean;
      }
    }
    leaf tcp-mss {
      type uint32;
    }
    container urpf-check {
      tailf:cli-add-mode;
      presence "true";
      leaf ignore-default {
        type empty;
      }
      leaf mode {
        type enumeration {
          enum "strict";
          enum "loose";
          enum "strict-no-ecmp";
        }
      }
    }
    list vrrp {
      key "id";
      leaf id {
        type uint32;
      }
      leaf owner {
        tailf:cli-hide-in-submode;
        type empty;
      }
      leaf passive {
        tailf:cli-hide-in-submode;
        type empty;
      }
      list backup {
        tailf:cli-suppress-mode;
        key "addr";
        leaf addr {
          type inet:ipv6-address;
        }
      }
      leaf init-delay {
        type uint32;
      }
      leaf mac {
        type ncs_rpc_notif_ieee-mac;
      }
      leaf master-int-inherit {
        type boolean;
      }
      container message-interval {
        tailf:cli-compact-syntax;
        tailf:cli-sequence-commands;
        leaf seconds {
          tailf:cli-drop-node-name;
          tailf:cli-optional-in-sequence;
          type uint32;
        }
        leaf milliseconds {
          type uint32;
        }
      }
      leaf ping-reply {
        type empty;
      }
      leaf policy {
        type uint16;
      }
      leaf preempt {
        type boolean;
      }
      leaf priority {
        type uint32;
      }
      leaf standby-forwarding {
        type empty;
      }
      leaf telnet-reply {
        type empty;
      }
      leaf traceroute-reply {
        type empty;
      }
      leaf shutdown {
        type boolean;
      }
    }
  }

  grouping ncs_rpc_notif_icmp-params-grouping {
    choice icmp-params-choice {
      leaf disable {
        type empty;
      }
      case enable {
        leaf number {
          tailf:cli-drop-node-name;
          type uint16;
        }
        leaf seconds {
          tailf:cli-drop-node-name;
          type uint8;
        }
      }
    }
  }

  grouping ncs_rpc_notif_interface-icmp-grouping {
    container icmp {
      tailf:cli-add-mode;
      leaf mask-reply {
        type boolean;
      }
      container redirects {
        tailf:cli-compact-syntax;
        tailf:cli-sequence-commands {
          tailf:cli-reset-siblings;
        }
        uses ncs_rpc_notif_icmp-params-grouping;
      }
      container ttl-expired {
        tailf:cli-compact-syntax;
        tailf:cli-sequence-commands {
          tailf:cli-reset-siblings;
        }
        uses ncs_rpc_notif_icmp-params-grouping;
      }
      container unreachables {
        tailf:cli-compact-syntax;
        tailf:cli-sequence-commands {
          tailf:cli-reset-siblings;
        }
        uses ncs_rpc_notif_icmp-params-grouping;
      }
    }
  }

  grouping ncs_rpc_notif_subscriber-interface-dhcp-common-grouping {
    container proxy-server {
      tailf:cli-add-mode;
      leaf emulated-server {
        type inet:ip-address;
      }
      container lease-time {
        tailf:cli-compact-syntax;
        leaf days {
          type uint16;
        }
        leaf hrs {
          type uint16;
        }
        leaf min {
          type uint16;
        }
        leaf sec {
          type uint16;
        }
      }
      leaf shutdown {
        type boolean;
      }
    }
    leaf-list server {
      tailf:cli-flat-list-syntax;
      type inet:ipv4-address;
    }
    container gi-address {
      tailf:cli-compact-syntax;
      tailf:cli-sequence-commands {
        tailf:cli-reset-siblings;
      }
      leaf address {
        tailf:cli-drop-node-name;
        type inet:ipv4-address;
      }
      leaf src-ip-addr {
        type empty;
      }
    }
  }

  grouping ncs_rpc_notif_dhcp-option-grouping {
    container option {
      tailf:cli-add-mode;
      leaf action {
        type enumeration {
          enum "replace";
          enum "drop";
          enum "keep";
        }
      }
      container remote-id {
        presence "true";
        choice remote-id {
          leaf mac {
            tailf:cli-drop-node-name;
            type string;
          }
          leaf string {
            type string;
          }
        }
      }
      container vendor-specific-option {
        tailf:cli-add-mode;
        leaf client-mac-address {
          type empty;
        }
        leaf pool-name {
          type empty;
        }
        leaf service-id {
          type empty;
        }
        leaf string {
          type string;
        }
      }
    }
  }

  grouping ncs_rpc_notif_subscriber-interface-grouping {
    leaf id {
      type string;
    }
    leaf fwd-service {
      tailf:cli-hide-in-submode;
      type ncs_rpc_notif_service-id;
    }
    leaf wan-mode {
      tailf:cli-hide-in-submode;
      type enumeration {
        enum "mode64";
        enum "mode128";
      }
    }
    leaf fwd-subscriber-interface {
      tailf:cli-hide-in-submode;
      type string;
    }
    leaf description {
      type string;
    }
    leaf allow-unmatching-subnets {
      type empty;
    }
    list address {
      tailf:cli-suppress-mode;
      tailf:cli-compact-syntax;
      tailf:cli-sequence-commands {
        tailf:cli-reset-siblings;
      }
      key "ip-address";
      leaf ip-address {
        type tailf:ipv4-address-and-prefix-length;
      }
      leaf gw-ip-address {
        tailf:cli-optional-in-sequence;
        type inet:ipv4-address;
      }
      leaf populate-host-routes {
        tailf:cli-optional-in-sequence;
        type empty;
      }
      leaf track-srrp {
        tailf:cli-optional-in-sequence;
        type uint32;
      }
    }

    grouping ipoe-linking-grouping {
      container ipoe-linking {
        tailf:cli-add-mode;
        leaf gratuitous-rtr-adv {
          type empty;
        }
        leaf shared-circuit-id {
          type empty;
        }
        leaf shutdown {
          type boolean;
        }
      }
    }
    uses ipoe-linking-grouping;
    list group-interface {
      key "id";
      leaf id {
        type string;
      }
      leaf oper-up-while-empty {
        type empty;
      }
      uses ipoe-linking-grouping;
      leaf shcv-policy {
        type string;
      }
      leaf shcv-policy-ipv4 {
        type string;
      }
      leaf shcv-policy-ipv6 {
        type string;
      }
      container data-trigger {
        tailf:cli-add-mode;
        leaf shutdown {
          type boolean;
        }
      }
      leaf description {
        type string;
      }
      uses ncs_rpc_notif_interface-icmp-grouping;
      leaf remote-proxy-arp {
        type empty;
      }
      container ipv6 {
        tailf:cli-add-mode;
        leaf allow-multiple-wan-addresses {
          type empty;
        }
        container router-advertisements {
          tailf:cli-add-mode;
          container dns-options {
            tailf:cli-add-mode;
            leaf include-dns {
              type empty;
            }
            leaf rdnss-lifetime {
              type uint32;
            }
          }
          leaf managed-configuration {
            type empty;
          }
          leaf retransmit-time {
            type uint32;
          }
          leaf max-advertisement {
            type uint32;
          }
          leaf current-hop-limit {
            type uint32;
          }
          leaf mtu {
            type uint32;
          }
          leaf reachable-time {
            type uint32;
          }
          leaf other-stateful-configuration {
            type empty;
          }
          leaf router-lifetime {
            type uint32;
          }
          container prefix-options {
            tailf:cli-add-mode;
            leaf autonomous {
              type empty;
            }
            leaf on-link {
              type boolean;
            }
            leaf preferred-lifetime {
              type union {
                type uint32;
                type enumeration {
                  enum "infinite";
                }
              }
            }
            leaf valid-lifetime {
              type union {
                type uint32;
                type enumeration {
                  enum "infinite";
                }
              }
            }
          }
          leaf shutdown {
            type boolean;
          }
        }
        container auto-reply {
          tailf:cli-add-mode;
          leaf neighbor-solicitation {
            type empty;
          }
          leaf router-solicitation {
            type empty;
          }
        }
        container urpf-check {
          tailf:cli-add-mode;
          presence "true";
          leaf mode {
            type enumeration {
              enum "strict";
              enum "loose";
              enum "strict-no-ecmp";
            }
          }
        }
        container dhcp6 {
          tailf:cli-add-mode;
          leaf user-db {
            type string;
          }
          leaf user-ident {
            type enumeration {
              enum "mac";
              enum "mac-interface-id";
            }
          }
          container relay {
            tailf:cli-add-mode;
            leaf description {
              type string;
            }
            leaf link-address {
              type inet:ipv6-address;
            }
            list server {
              tailf:cli-suppress-mode;
              key "ip";
              leaf ip {
                type inet:ipv6-address;
              }
            }
            leaf source-address {
              type inet:ipv6-address;
            }
            leaf shutdown {
              type boolean;
            }
          }
          container proxy-server {
            tailf:cli-add-mode;
            container lease-time {
              tailf:cli-compact-syntax;
              leaf days {
                type uint16;
              }
              leaf hrs {
                type uint16;
              }
              leaf min {
                type uint16;
              }
              leaf sec {
                type uint16;
              }
            }
            uses ncs_rpc_notif_dhcp6-lease-timers-grouping;
            leaf shutdown {
              type boolean;
            }
          }
          leaf python-policy {
            type ncs_rpc_notif_string32;
          }
          container option {
            tailf:cli-add-mode;
            container interface-id {
              tailf:cli-compact-syntax;
              leaf type {
                tailf:cli-drop-node-name;
                type enumeration {
                  enum "ascii-tuple";
                  enum "ifindex";
                  enum "sap-id";
                  enum "string";
                }
              }
              leaf stringval {
                tailf:cli-drop-node-name;
                type string;
              }
            }
            leaf remote-id {
              type empty;
            }
          }
        }
      }
      leaf arp-populate {
        type empty;
      }
      leaf authentication-policy {
        type string;
      }
      leaf redundant-interface {
        type string;
      }
      leaf srrp-enabled-routing {
        type empty;
      }
      leaf enable-ingress-stats {
        type empty;
      }
      leaf ip-mtu {
        type uint16;
      }
      leaf tos-marking-state {
        type enumeration {
          enum "trusted";
          enum "untrusted";
        }
      }
      container host-connectivity-verify {
        tailf:cli-compact-syntax;
        leaf interval {
          type uint16;
        }
        leaf action {
          type enumeration {
            enum "remove";
            enum "alarm";
          }
        }
        leaf timeout {
          type uint8;
        }
        leaf retry-count {
          type uint8;
        }
        leaf family {
          type enumeration {
            enum "ipv4";
            enum "ipv6";
            enum "both";
          }
        }
      }
      container dhcp {
        tailf:cli-add-mode;
        leaf description {
          type string;
        }
        leaf trusted {
          type empty;
        }
        container lease-populate {
          tailf:cli-compact-syntax;
          leaf nr-of-leases {
            tailf:cli-drop-node-name;
            type uint32;
          }
          leaf l2-header {
            type empty;
          }
          leaf mac {
            type string;
          }
        }
        container relay-proxy {
          tailf:cli-compact-syntax;
          tailf:cli-sequence-commands {
            tailf:cli-reset-siblings;
          }
          presence "true";
          leaf release-update-src-ip {
            tailf:cli-optional-in-sequence;
            type empty;
          }
          leaf siaddr-override {
            type inet:ipv4-address;
          }
        }
        leaf python-policy {
          type ncs_rpc_notif_string32;
        }
        uses ncs_rpc_notif_dhcp-option-grouping {
          augment "option" {
            container circuit-id {
              presence "true";
              leaf id {
                tailf:cli-drop-node-name;
                type enumeration {
                  enum "ascii-tuple";
                  enum "ifindex";
                  enum "sap-id";
                  enum "vlan-ascii-tuple";
                  enum "if-name";
                  enum "port-id";
                  enum "none";
                }
              }
            }
          }
          augment "option/vendor-specific-option" {
            leaf sap-id {
              type empty;
            }
          }
        }
        leaf user-db {
          type string;
        }
        leaf-list client-applications {
          tailf:cli-flat-list-syntax;
          type enumeration {
            enum "ppp";
            enum "dhcp";
          }
        }
        uses ncs_rpc_notif_subscriber-interface-dhcp-common-grouping {
          augment "proxy-server/lease-time" {
            leaf override {
              type empty;
            }
          }
        }
      }
      list sap {
        key "id";
        leaf id {
          type string;
        }
        leaf host-lockout-policy {
          type ncs_rpc_notif_string32;
        }
        container egress {
          tailf:cli-add-mode;
          container filter {
            leaf ip {
              type ncs_rpc_notif_filter-id;
            }
            leaf ipv6 {
              type ncs_rpc_notif_filter-id;
            }
          }
          leaf qos {
            type uint16;
          }
        }
        container ingress {
          tailf:cli-add-mode;
          container filter {
            leaf ip {
              type ncs_rpc_notif_filter-id;
            }
            leaf ipv6 {
              type ncs_rpc_notif_filter-id;
            }
          }
          leaf qos {
            type uint16;
          }
        }
        leaf description {
          type string;
        }
        leaf anti-spoof {
          type enumeration {
            enum "ip";
            enum "ip-mac";
            enum "nh-mac";
          }
        }
        container sub-sla-mgmt {
          tailf:cli-add-mode;
          container def-sub-id {
            choice sub-id-choice {
              leaf string {
                type string;
              }
              leaf use-auto-id {
                type empty;
              }
              leaf use-sap-id {
                type empty;
              }
            }
          }
          container def-inter-dest-id {
            choice dest-id-choice {
              leaf string {
                type string;
              }
              leaf use-top-q {
                type empty;
              }
              leaf use-vpi {
                type empty;
              }
            }
          }
          leaf def-sub-profile {
            type string;
          }
          leaf def-sla-profile {
            type string;
          }
          leaf sub-ident-policy {
            type string;
          }
          container single-sub-parameters {
            tailf:cli-add-mode;
            leaf profiled-traffic-only {
              type empty;
            }
          }
          container multi-sub-sap {
            presence "true";
            leaf subscriber-limit {
              tailf:cli-drop-node-name;
              type uint32;
            }
          }
          leaf shutdown {
            type boolean;
          }
        }
        leaf calling-station-id {
          type string;
        }
        leaf monitor-oper-group {
          type string;
        }
        leaf shutdown {
          type boolean;
        }
      }
      container urpf-check {
        tailf:cli-add-mode;
        leaf mode {
          type enumeration {
            enum "strict";
            enum "loose";
            enum "strict-no-ecmp";
          }
        }
      }
      container ipoe-session {
        tailf:cli-add-mode;
        container force-auth {
          tailf:cli-compact-syntax;
          choice force-auth {
            leaf disabled {
              type empty;
            }
            case cid-rid {
              leaf cid-change {
                type empty;
              }
              leaf rid-change {
                type empty;
              }
            }
          }
        }
        leaf sap-session-limit {
          type uint32;
        }
        leaf session-limit {
          type uint32;
        }
        container min-auth-interval {
          tailf:cli-compact-syntax;
          tailf:cli-sequence-commands {
            tailf:cli-reset-siblings;
          }
          choice interval {
            leaf infinite {
              tailf:cli-optional-in-sequence;
              tailf:cli-drop-node-name;
              type enumeration {
                enum "infinite";
              }
            }
            case time {
              leaf days {
                tailf:cli-optional-in-sequence;
                type uint16;
              }
              leaf hrs {
                tailf:cli-optional-in-sequence;
                type uint8;
              }
              leaf min {
                tailf:cli-optional-in-sequence;
                type uint8;
              }
              leaf sec {
                tailf:cli-optional-in-sequence;
                type uint8;
              }
            }
          }
        }
        uses ncs_rpc_notif_ipoe-session-grouping;
      }
      container pppoe {
        tailf:cli-add-mode;
        leaf description {
          type string;
        }
        leaf policy {
          type ncs_rpc_notif_string32;
        }
        leaf sap-session-limit {
          type uint32;
        }
        leaf session-limit {
          type uint16;
        }
        leaf user-db {
          type string;
        }
        leaf shutdown {
          type boolean;
        }
      }
      list srrp {
        key "srrp-id";
        leaf srrp-id {
          type uint32;
        }
        leaf description {
          type string;
        }
        leaf keep-alive-interval {
          type uint8;
        }
        leaf message-path {
          type string;
        }
        list policy {
          tailf:cli-suppress-mode;
          key "vrrp-policy-id";
          leaf vrrp-policy-id {
            type uint16;
          }
        }
        leaf priority {
          type uint8;
        }
        leaf shutdown {
          type boolean;
        }
      }
      leaf shutdown {
        type boolean;
      }
    }
    container pppoe {
      tailf:cli-add-mode;
      leaf description {
        type string;
      }
      leaf session-limit {
        type uint16;
      }
    }
    leaf private-retail-subnets {
      type empty;
    }
    leaf unnumbered {
      type string;
    }
  }

  grouping ncs_rpc_notif_nat-pool-grouping {
    container nat {
      tailf:cli-add-mode;
      container inside {
        tailf:cli-add-mode;
        container l2-aware {
          tailf:cli-add-mode;
          list address {
            tailf:cli-suppress-mode;
            key "ip-addr";
            leaf ip-addr {
              type tailf:ipv4-address-and-prefix-length;
            }
          }
        }
        leaf nat-policy {
          type string;
        }
        leaf destination-prefix {
          type tailf:ipv4-address-and-prefix-length;
        }
      }
      container outside {
        tailf:cli-add-mode;
        list pool {
          key "name";
          leaf name {
            type string;
          }
          leaf nat-group {
            tailf:cli-hide-in-submode;
            type uint16;
          }
          leaf type {
            tailf:cli-hide-in-submode;
            type enumeration {
              enum "l2-aware";
              enum "large-scale";
            }
          }
          container port-reservation {
            tailf:cli-compact-syntax;
            leaf blocks {
              type uint16;
            }
            leaf ports {
              type uint16;
            }
          }
          leaf port-forwarding-range {
            type uint16;
          }
          leaf subscriber-limit {
            type uint16;
          }
          container watermarks {
            tailf:cli-compact-syntax;
            leaf high {
              type uint8;
            }
            leaf low {
              type uint8;
            }
          }
          list address-range {
            key "start-ip-address end-ip-address";
            leaf start-ip-address {
              type inet:ipv4-address;
            }
            leaf end-ip-address {
              type inet:ipv4-address;
            }
          }
          leaf shutdown {
            type boolean;
          }
        }
      }
    }
  }

  grouping ncs_rpc_notif_static-route-extras-grouping {
    leaf preference {
      tailf:cli-break-sequence-commands;
      type uint8;
    }
    leaf metric {
      type uint16;
    }
    choice ed {
      leaf enable {
        type empty;
      }
      leaf disable {
        type empty;
      }
    }
    leaf tag {
      type uint32;
    }
    leaf community {
      type union {
        type enumeration {
          enum "no-export";
          enum "no-export-subconfed";
          enum "no-advertise";
        }
        type string;
      }
    }
    leaf description {
      type string;
    }
    leaf mcast-family {
      tailf:cli-drop-node-name;
      type enumeration {
        enum "mcast-ipv4";
        enum "mcast-ipv6";
      }
    }
    leaf bfd-enable {
      type empty;
    }
    leaf cpe-check {
      type inet:ipv4-address;
    }
    leaf interval {
      type uint8;
    }
    leaf drop-count {
      type uint8;
    }
    leaf log {
      type empty;
    }
    leaf prefix-list {
      type string;
    }
    choice an {
      leaf all {
        type empty;
      }
      leaf none {
        type empty;
      }
    }
    leaf ldp-sync {
      type empty;
    }
    leaf fc {
      type ncs_rpc_notif_fc-name;
    }
    leaf priority {
      type enumeration {
        enum "high";
        enum "low";
      }
    }
  }

  grouping ncs_rpc_notif_prompted-authentication-key-grouping {
    container authentication-key {
      tailf:cli-compact-syntax;
      tailf:cli-sequence-commands {
        tailf:cli-reset-all-siblings;
      }
      leaf key {
        tailf:cli-drop-node-name;
        type string;
      }
      leaf method {
        tailf:cli-drop-node-name;
        type ncs_rpc_notif_hash-method;
      }
    }
  }

  grouping ncs_rpc_notif_prompted-hello-authentication-key-grouping {
    container hello-authentication-key {
      tailf:cli-compact-syntax;
      tailf:cli-sequence-commands {
        tailf:cli-reset-all-siblings;
      }
      leaf key {
        tailf:cli-drop-node-name;
        type string;
      }
      leaf method {
        tailf:cli-drop-node-name;
        type ncs_rpc_notif_hash-method;
      }
    }
    leaf hello-auth-keychain {
      type string;
    }
  }

  grouping ncs_rpc_notif_bgp-import-export-grouping {
    leaf-list export {
      tailf:cli-flat-list-syntax;
      ordered-by user;
      type string;
    }
    leaf-list import {
      tailf:cli-flat-list-syntax;
      ordered-by user;
      type string;
    }
  }

  grouping ncs_rpc_notif_max-paths-grouping {
    leaf max-paths {
      tailf:cli-drop-node-name;
      tailf:cli-break-sequence-commands;
      type uint8;
    }
    leaf ebgp {
      type uint8;
    }
    leaf ibgp {
      type uint8;
    }
    leaf restrict {
      type enumeration {
        enum "same-neighbor-as";
        enum "exact-as-path";
      }
    }
  }

  grouping ncs_rpc_notif_bgp-multipath-grouping {
    container multipath {
      tailf:cli-compact-syntax;
      tailf:cli-sequence-commands {
        tailf:cli-reset-all-siblings;
      }
      uses ncs_rpc_notif_max-paths-grouping;
    }
  }

  grouping ncs_rpc_notif_max-paths-uneqcosts-grouping {
    uses ncs_rpc_notif_max-paths-grouping;
    leaf unequal-cost {
      type empty;
    }
  }

  grouping ncs_rpc_notif_bgp-multi-path-grouping {
    container multi-path {
      tailf:cli-add-mode;
      container ipv4 {
        tailf:cli-sequence-commands {
          tailf:cli-reset-all-siblings;
        }
        tailf:cli-compact-syntax;
        uses ncs_rpc_notif_max-paths-uneqcosts-grouping;
      }
      container ipv6 {
        tailf:cli-sequence-commands {
          tailf:cli-reset-all-siblings;
        }
        tailf:cli-compact-syntax;
        uses ncs_rpc_notif_max-paths-uneqcosts-grouping;
      }
      container label-ipv4 {
        tailf:cli-sequence-commands {
          tailf:cli-reset-all-siblings;
        }
        tailf:cli-compact-syntax;
        uses ncs_rpc_notif_max-paths-uneqcosts-grouping;
      }
      container maximum-paths {
        tailf:cli-sequence-commands {
          tailf:cli-reset-all-siblings;
        }
        tailf:cli-compact-syntax;
        uses ncs_rpc_notif_max-paths-uneqcosts-grouping;
      }
    }
  }

  grouping ncs_rpc_notif_bgp-graceful-restart-grouping {
    container graceful-restart {
      tailf:cli-add-mode;
      presence "true";
      leaf enable-notification {
        type empty;
      }
      container long-lived {
        tailf:cli-add-mode;
        presence "true";

        grouping bgp-graceful-override-times-grouping {
          leaf advertised-stale-time {
            type uint32;
          }
          leaf helper-override-stale-time {
            type uint32;
          }
        }
        container advertise-stale-to-all-neighbors {
          tailf:cli-compact-syntax;
          presence "true";
          leaf without-no-export {
            type empty;
          }
        }
        uses bgp-graceful-override-times-grouping;
        list family {
          key "family";
          leaf family {
            type ncs_rpc_notif_family-names-type;
          }
          uses bgp-graceful-override-times-grouping;
        }
        leaf forwarding-bits-set {
          type enumeration {
            enum "all";
            enum "non-fwd";
          }
        }
        leaf helper-override-restart-time {
          type uint16;
        }
      }
      leaf restart-time {
        type uint16;
      }
      leaf stale-routes-time {
        type uint16;
      }
    }
  }

  grouping ncs_rpc_notif_bgp-prefix-limit-grouping {
    container prefix-limit {
      tailf:cli-compact-syntax;
      choice apis {
        list new {
          tailf:cli-drop-node-name;
          tailf:cli-suppress-mode;
          tailf:cli-compact-syntax;
          tailf:cli-sequence-commands {
            tailf:cli-reset-all-siblings;
          }
          key "family";
          leaf family {
            type enumeration {
              enum "ipv4";
              enum "vpn-ipv4";
              enum "ipv6";
              enum "vpn-ipv6";
              enum "mcast-ipv4";
              enum "l2-vpn";
              enum "mvpn-ipv4";
              enum "mdt-safi";
              enum "ms-pw";
              enum "flow-ipv4";
              enum "route-target";
              enum "mcast-vpn-ipv4";
              enum "mvpn-ipv6";
              enum "flow-ipv6";
              enum "evpn";
              enum "mcast-ipv6";
              enum "label-ipv4";
              enum "label-ipv6";
            }
          }
          leaf limit {
            tailf:cli-drop-node-name;
            type uint32;
          }
          leaf log-only {
            tailf:cli-break-sequence-commands;
            type empty;
          }
          leaf threshold {
            type uint8;
          }
          leaf idle-timeout {
            type union {
              type uint16;
              type enumeration {
                enum "forever";
              }
            }
          }
          leaf post-import {
            type empty;
          }
        }
        container old {
          tailf:cli-drop-node-name;
          tailf:cli-compact-syntax;
          tailf:cli-sequence-commands {
            tailf:cli-reset-siblings;
          }
          leaf limit {
            tailf:cli-drop-node-name;
            type uint32;
          }
          leaf log-only {
            tailf:cli-break-sequence-commands;
            tailf:cli-optional-in-sequence;
            type empty;
          }
          leaf threshold {
            tailf:cli-optional-in-sequence;
            type uint8;
          }
          leaf idle-timeout {
            type union {
              type uint16;
              type enumeration {
                enum "forever";
              }
            }
          }
        }
      }
    }
  }

  grouping ncs_rpc_notif_router-bgp-add-paths-grouping {
    container add-paths {
      tailf:cli-add-mode;

      grouping path-proto-send-receive-grouping {
        leaf send {
          type union {
            type uint8;
            type enumeration {
              enum "none";
            }
          }
        }
        leaf receive {
          type empty;
        }
        leaf none {
          type empty;
        }
      }
      container ipv4 {
        tailf:cli-compact-syntax;
        tailf:cli-sequence-commands {
          tailf:cli-reset-all-siblings;
        }
        uses path-proto-send-receive-grouping;
      }
      container ipv6 {
        tailf:cli-compact-syntax;
        tailf:cli-sequence-commands;
        uses path-proto-send-receive-grouping;
      }
      container label-ipv4 {
        tailf:cli-compact-syntax;
        tailf:cli-sequence-commands;
        uses path-proto-send-receive-grouping;
      }
      container label-ipv6 {
        tailf:cli-compact-syntax;
        tailf:cli-sequence-commands;
        uses path-proto-send-receive-grouping;
      }
      container vpn-ipv4 {
        tailf:cli-compact-syntax;
        tailf:cli-sequence-commands;
        uses path-proto-send-receive-grouping;
      }
      container vpn-ipv6 {
        tailf:cli-compact-syntax;
        tailf:cli-sequence-commands;
        uses path-proto-send-receive-grouping;
      }
    }
  }

  grouping ncs_rpc_notif_router-bgp-grouping {
    uses ncs_rpc_notif_router-bgp-add-paths-grouping;
    leaf advertise-inactive {
      type empty;
    }
    leaf-list advertise-ipv6-next-hops {
      tailf:cli-flat-list-syntax;
      type enumeration {
        enum "vpn-ipv6";
        enum "label-ipv6";
        enum "evpn";
        enum "vpn-ipv4";
        enum "label-ipv4";
        enum "ipv4";
      }
    }
    leaf loop-detect-threshold {
      type uint32;
    }
    leaf def-recv-evpn-encap {
      type enumeration {
        enum "mpls";
        enum "vxlan";
      }
    }
    container cluster {
      tailf:cli-compact-syntax;
      tailf:cli-sequence-commands;
      leaf cluster-id {
        tailf:cli-drop-node-name;
        type inet:ipv4-address;
      }
      leaf orr-location {
        tailf:cli-optional-in-sequence;
        type uint32;
      }
      leaf allow-local-fallback {
        tailf:cli-optional-in-sequence;
        type empty;
      }
    }
    leaf aggregator-id-zero {
      type empty;
    }
    leaf aigp {
      type empty;
    }
    leaf auth-keychain {
      type string;
    }
    uses ncs_rpc_notif_prompted-authentication-key-grouping;
    leaf bfd-enable {
      type empty;
    }
    leaf connect-retry {
      type uint16;
    }
    leaf damping {
      type empty;
    }
    leaf default-route-target {
      type empty;
    }
    leaf description {
      type string;
    }
    leaf disable-4byte-asn {
      type empty;
    }
    leaf disable-capability-negotiation {
      type empty;
    }
    leaf disable-client-reflect {
      type empty;
    }
    leaf-list disable-communities {
      tailf:cli-flat-list-syntax;
      type enumeration {
        enum "standard";
        enum "extended";
      }
    }
    leaf disable-fast-external-failover {
      type empty;
    }
    leaf enable-peer-tracking {
      type empty;
    }
    leaf-list family {
      tailf:cli-flat-list-syntax;
      type ncs_rpc_notif_family-names-type;
    }
    leaf flowspec-validate {
      type empty;
    }
    uses ncs_rpc_notif_bgp-graceful-restart-grouping;
    container hold-time {
      tailf:cli-compact-syntax;
      leaf seconds {
        tailf:cli-drop-node-name;
        type uint16;
      }
      leaf min {
        type uint16;
      }
    }
    leaf keepalive {
      type uint16;
    }
    leaf local-address {
      type union {
        type inet:ipv4-address;
        type inet:ipv6-address;
        type string;
      }
    }
    uses ncs_rpc_notif_bgp-local-as-grouping;
    leaf local-preference {
      type uint32;
    }
    leaf loop-detect {
      type enumeration {
        enum "drop-peer";
        enum "discard-route";
        enum "ignore-loop";
        enum "off";
      }
    }
    leaf med-out {
      type union {
        type uint32;
        type enumeration {
          enum "igp-cost";
        }
      }
    }
    leaf min-as-origination {
      type uint8;
    }
    leaf min-route-advertisement {
      type uint8;
    }
    leaf multihop {
      type uint8;
    }
    leaf next-hop-self {
      type empty;
    }
    container outbound-route-filtering {
      tailf:cli-add-mode;
      container extended-community {
        tailf:cli-add-mode;
        leaf accept-orf {
          type empty;
        }
        container send-orf {
          presence "true";
          leaf-list send-orf {
            tailf:cli-drop-node-name;
            tailf:cli-flat-list-syntax;
            type string;
          }
        }
      }
    }
    leaf passive {
      type empty;
    }
    leaf path-mtu-discovery {
      type empty;
    }
    leaf peer-as {
      type uint32;
    }
    leaf preference {
      type uint8;
    }
    uses ncs_rpc_notif_bgp-prefix-limit-grouping;
    container remove-private {
      presence "true";
      leaf-list options {
        tailf:cli-drop-node-name;
        tailf:cli-flat-list-syntax;
        type enumeration {
          enum "limited";
          enum "skip-peer-as";
        }
      }
    }
    leaf split-horizon {
      type empty;
    }
    container tcp-mss {
      leaf mss-val {
        tailf:cli-drop-node-name;
        type uint32;
      }
      leaf ip-stack {
        type empty;
      }
    }
    leaf ttl-security {
      type uint8;
    }
    leaf type {
      type enumeration {
        enum "internal";
        enum "external";
      }
    }
    leaf vpn-apply-export {
      type empty;
    }
    leaf label-preference {
      type uint8;
    }
    leaf l2vpn-cisco-interop {
      type empty;
    }
    leaf vpn-apply-import {
      type empty;
    }
    leaf shutdown {
      type boolean;
    }
  }

  grouping ncs_rpc_notif_bgp-local-as-grouping {
    container local-as {
      tailf:cli-compact-syntax;
      tailf:cli-sequence-commands {
        tailf:cli-reset-siblings;
      }
      leaf number {
        tailf:cli-drop-node-name;
        type uint32;
      }
      leaf private {
        tailf:cli-optional-in-sequence;
        type empty;
      }
      leaf no-prepend-global-as {
        tailf:cli-optional-in-sequence;
        type empty;
      }
    }
  }

  grouping ncs_rpc_notif_bgp-best-path-selection-grouping {
    container best-path-selection {
      tailf:cli-add-mode;
      container always-compare-med {
        tailf:cli-compact-syntax;
        tailf:cli-sequence-commands {
          tailf:cli-reset-siblings;
        }
        presence "true";
        leaf strict-as {
          tailf:cli-optional-in-sequence;
          type empty;
        }
        leaf type {
          tailf:cli-drop-node-name;
          type enumeration {
            enum "zero";
            enum "infinity";
          }
        }
      }
      leaf-list as-path-ignore {
        tailf:cli-flat-list-syntax;
        type enumeration {
          enum "ipv4";
          enum "ipv6";
          enum "vpn-ipv4";
          enum "vpn-ipv6";
          enum "mcast-ipv4";
          enum "mvpn-ipv4";
          enum "l2-vpn";
          enum "mvpn-ipv6";
        }
      }
      leaf compare-origin-validation-state {
        type empty;
      }
      leaf deterministic-med {
        type empty;
      }
      leaf ignore-nh-metric {
        type empty;
      }
      leaf ignore-router-id {
        type empty;
      }
      leaf origin-invalid-unusable {
        type empty;
      }
    }
  }

  grouping ncs_rpc_notif_agg-rate-grouping {
    container agg-rate {
      tailf:cli-add-mode;
      leaf limit-unused-bandwidth {
        type empty;
      }
      leaf queue-frame-based-accounting {
        type empty;
      }
      leaf rate {
        type union {
          type enumeration {
            enum "max";
          }
          type uint32;
        }
      }
    }
  }

  grouping ncs_rpc_notif_sap-egress-common-grouping {
    leaf policy-id {
      type uint16;
    }
    leaf description {
      type string;
    }
    list queue {
      key "queue-id";
      leaf queue-id {
        type uint8;
      }
      uses ncs_rpc_notif_queue-grouping;
    }
  }

  grouping ncs_rpc_notif_dot1p-params-grouping {
    choice dot1p {
      leaf dot1p-value {
        tailf:cli-drop-node-name;
        type uint8;
      }
      case in-out {
        leaf in-profile {
          type uint8;
        }
        leaf out-profile {
          type uint8;
        }
      }
    }
  }

  grouping ncs_rpc_notif_sap-egress-fc-grouping {
    leaf fc-name {
      type string;
    }
    container queue {
      tailf:cli-compact-syntax;
      tailf:cli-sequence-commands {
        tailf:cli-reset-all-siblings;
      }
      uses ncs_rpc_notif_queue-ref-grouping;
      leaf instance {
        type uint8;
      }
    }
    container dot1p {
      tailf:cli-compact-syntax;
      tailf:cli-sequence-commands {
        tailf:cli-reset-siblings;
      }
      uses ncs_rpc_notif_dot1p-params-grouping;
    }
    container dot1p-inner {
      tailf:cli-compact-syntax;
      tailf:cli-sequence-commands {
        tailf:cli-reset-siblings;
      }
      uses ncs_rpc_notif_dot1p-params-grouping;
    }
    container dot1p-outer {
      tailf:cli-compact-syntax;
      tailf:cli-sequence-commands {
        tailf:cli-reset-siblings;
      }
      uses ncs_rpc_notif_dot1p-params-grouping;
    }
    container dscp {
      tailf:cli-compact-syntax;
      choice dscp {
        leaf dscp-name {
          tailf:cli-drop-node-name;
          type string;
        }
        case in-out {
          leaf in-profile {
            type string;
          }
          leaf out-profile {
            type string;
          }
        }
      }
    }
  }

  grouping ncs_rpc_notif_mcac-grouping {
    container mcac {
      tailf:cli-add-mode;
      container mc-constraints {
        tailf:cli-add-mode;
        list level {
          tailf:cli-suppress-mode;
          tailf:cli-compact-syntax;
          key "level-id";
          leaf level-id {
            tailf:cli-drop-node-name;
            type uint8;
          }
          leaf bw {
            type uint32;
          }
        }
        list number-down {
          tailf:cli-suppress-mode;
          tailf:cli-compact-syntax;
          key "number-lag-port-down";
          leaf number-lag-port-down {
            type uint8;
          }
          leaf level {
            type uint8;
          }
        }
        leaf use-lag-port-weight {
          type empty;
        }
        leaf shutdown {
          type boolean;
        }
      }
      leaf policy {
        type string;
      }
      container unconstrained-bw {
        tailf:cli-compact-syntax;
        tailf:cli-sequence-commands {
          tailf:cli-reset-all-siblings;
        }
        leaf bandwidth {
          tailf:cli-drop-node-name;
          type uint32;
        }
        leaf mandatory-bw {
          type uint32;
        }
      }
    }
  }

  grouping ncs_rpc_notif_cron-schedule-grouping {
    list schedule {
      key "id owner";
      leaf id {
        type string;
      }
      leaf owner {
        type string;
      }
      leaf description {
        type string;
      }
      leaf interval {
        type uint32;
      }
      leaf count {
        type uint32;
      }
      leaf minute {
        type union {
          type uint8;
          type enumeration {
            enum "all";
          }
        }
      }
      leaf hour {
        type union {
          type uint8;
          type enumeration {
            enum "all";
          }
        }
      }
      leaf month {
        type union {
          type ncs_rpc_notif_month;
          type enumeration {
            enum "all" {
              value 1000;
            }
          }
        }
      }
      leaf-list day-of-month {
        tailf:cli-flat-list-syntax;
        type union {
          type uint8;
          type enumeration {
            enum "all";
          }
        }
      }
      leaf weekday {
        type union {
          type ncs_rpc_notif_weekday;
          type enumeration {
            enum "all" {
              value 1000;
            }
          }
        }
      }
      container end-time {
        tailf:cli-compact-syntax;
        tailf:cli-sequence-commands {
          tailf:cli-reset-siblings;
        }
        leaf day-name {
          tailf:cli-drop-node-name;
          type union {
            type ncs_rpc_notif_weekday;
            type ncs_rpc_notif_date;
          }
        }
        leaf time {
          tailf:cli-drop-node-name;
          type string;
        }
      }
      container script-policy {
        tailf:cli-compact-syntax;
        tailf:cli-sequence-commands {
          tailf:cli-reset-all-siblings;
        }
        leaf policy {
          tailf:cli-drop-node-name;
          type ncs_rpc_notif_string32;
        }
        leaf owner {
          type string;
        }
      }
      leaf type {
        type enumeration {
          enum "periodic";
          enum "calendar";
          enum "oneshot";
        }
      }
      leaf shutdown {
        type boolean;
      }
    }
  }

  grouping ncs_rpc_notif_static-route-entry-nh-grouping {
    leaf community {
      type union {
        type enumeration {
          enum "no-export";
          enum "no-export-subconfed";
          enum "no-advertise";
        }
        type string;
      }
    }
    leaf description {
      type string;
    }
    leaf metric {
      type uint16;
    }
    leaf preference {
      type uint8;
    }
    leaf tag {
      type uint32;
    }
    leaf bfd-enable {
      type empty;
    }
    leaf ldp-sync {
      type empty;
    }
    list cpe-check {
      key "address";
      leaf address {
        type union {
          type inet:ipv4-address;
          type inet:ipv6-address;
        }
      }
      leaf drop-count {
        type uint8;
      }
      leaf interval {
        type uint8;
      }
      leaf log {
        type empty;
      }
    }
    container tunnel-next-hop {
      tailf:cli-add-mode;
      leaf resolution {
        type enumeration {
          enum "any";
          enum "disabled";
          enum "filter";
        }
      }
      container resolution-filter {
        tailf:cli-add-mode;
        container rsvp-te {
          presence "true";
          leaf lsp {
            type string;
          }
        }
        container sr-te {
          presence "true";
          leaf lsp {
            type string;
          }
        }
        container ldp {
          presence "true";
        }
        container mpls-fwd-policy {
          presence "true";
        }
        container rib-api {
          presence "true";
        }
        container sr-isis {
          presence "true";
        }
        container sr-ospf {
          presence "true";
        }
        container sr-ospf3 {
          presence "true";
        }
      }
    }
    leaf destination-class {
      type uint32;
    }
    leaf source-class {
      type uint32;
    }
    container forwarding-class {
      tailf:cli-add-mode;
      leaf class {
        tailf:cli-drop-node-name;
        tailf:cli-hide-in-submode;
        type enumeration {
          enum "be";
          enum "l2";
          enum "af";
          enum "l1";
          enum "h2";
          enum "ef";
          enum "h1";
          enum "nc";
        }
      }
      leaf priority {
        type enumeration {
          enum "low";
          enum "high";
        }
      }
    }
    leaf shutdown {
      type boolean;
    }
  }

  grouping ncs_rpc_notif_cflowd-params-grouping {
    container cflowd-parameters {
      tailf:cli-add-mode;
      list sampling {
        tailf:cli-suppress-mode;
        tailf:cli-compact-syntax;
        tailf:cli-sequence-commands {
          tailf:cli-reset-siblings;
        }
        key "sampling";
        leaf sampling {
          type enumeration {
            enum "unicast";
            enum "multicast";
          }
        }
        leaf type {
          type enumeration {
            enum "acl";
            enum "interface";
          }
        }
        leaf direction {
          type enumeration {
            enum "ingress-only";
            enum "egress-only";
            enum "both";
          }
        }
      }
    }
  }

  grouping ncs_rpc_notif_resolution-filter-grouping {
    container resolution-filter {
      tailf:cli-add-mode;
      leaf bgp {
        type empty;
      }
      leaf gre {
        type empty;
      }
      leaf ldp {
        type boolean;
      }
      leaf rsvp {
        type empty;
      }
      leaf sr-isis {
        type empty;
      }
      leaf sr-ospf {
        type empty;
      }
      leaf sr-te {
        type empty;
      }
    }
    leaf resolution {
      type enumeration {
        enum "disabled";
        enum "any";
        enum "filter";
      }
    }
  }

  grouping ncs_rpc_notif_bgp-next-hop-resolution-grouping {
    container next-hop-resolution {
      tailf:cli-add-mode;
      leaf policy {
        type string;
      }
      leaf use-bgp-routes {
        type empty;
      }
      container label-route-transport-tunnel {
        tailf:cli-add-mode;
        container family {
          tailf:cli-add-mode;
          leaf address-family {
            tailf:cli-drop-node-name;
            tailf:cli-hide-in-submode;
            type enumeration {
              enum "label-ipv4";
              enum "label-ipv6";
              enum "vpn";
            }
          }
          // NCS expand uses statement
          container resolution-filter {
            tailf:cli-add-mode;
            leaf bgp {
              type empty;
            }
            leaf gre {
              type empty;
            }
            leaf ldp {
              type boolean;
            }
            leaf rsvp {
              type empty;
            }
            leaf sr-isis {
              type empty;
            }
            leaf sr-ospf {
              type empty;
            }
            leaf sr-te {
              type empty;
            }
          }
          leaf resolution {
            type enumeration {
              enum "disabled";
              enum "any";
              enum "filter";
            }
          }
        }
      }
      container labeled-routes {
        tailf:cli-add-mode;
        leaf prefer-transport-frr {
          type empty;
        }
        container transport-tunnel {
          tailf:cli-add-mode;
          list family {
            key "address-family";
            leaf address-family {
              type enumeration {
                enum "label-ipv4";
                enum "label-ipv6";
                enum "vpn";
              }
            }
            // NCS expand uses statement
            container resolution-filter {
              tailf:cli-add-mode;
              leaf bgp {
                type empty;
              }
              leaf gre {
                type empty;
              }
              leaf ldp {
                type boolean;
              }
              leaf rsvp {
                type empty;
              }
              leaf sr-isis {
                type empty;
              }
              leaf sr-ospf {
                type empty;
              }
              leaf sr-te {
                type empty;
              }
            }
            leaf resolution {
              type enumeration {
                enum "disabled";
                enum "any";
                enum "filter";
              }
            }
          }
        }
      }
      container shortcut-tunnel {
        tailf:cli-add-mode;
        container family {

          grouping res-filter-grouping {
            container resolution-filter {
              tailf:cli-add-mode;
              leaf bgp {
                type empty;
              }
              leaf gre {
                type empty;
              }
              leaf ldp {
                type empty;
              }
              leaf rsvp {
                type empty;
              }
              leaf sr-isis {
                type empty;
              }
              leaf sr-ospf {
                type empty;
              }
              leaf sr-te {
                type empty;
              }
            }
            leaf resolution {
              type enumeration {
                enum "disabled";
                enum "any";
                enum "filter";
              }
            }
          }
          container ipv4 {
            tailf:cli-add-mode;
            tailf:cli-delete-when-empty;
            uses res-filter-grouping;
          }
          container ipv6 {
            tailf:cli-add-mode;
            tailf:cli-delete-when-empty;
            uses res-filter-grouping;
          }
        }
      }
      leaf weighted-ecmp {
        type empty;
      }
    }
  }

  grouping ncs_rpc_notif_authentication-key-grouping {
    container authentication-key {
      tailf:cli-compact-syntax;
      tailf:cli-sequence-commands {
        tailf:cli-reset-siblings;
      }
      leaf key {
        tailf:cli-drop-node-name;
        type string;
      }
      leaf method {
        tailf:cli-drop-node-name;
        type ncs_rpc_notif_hash-method;
      }
    }
  }

  grouping ncs_rpc_notif_hello-authentication-key-grouping {
    container hello-authentication-key {
      tailf:cli-compact-syntax;
      tailf:cli-sequence-commands {
        tailf:cli-reset-all-siblings;
      }
      leaf key {
        tailf:cli-drop-node-name;
        type string;
      }
      leaf method {
        tailf:cli-drop-node-name;
        type ncs_rpc_notif_hash-method;
      }
    }
  }

  grouping ncs_rpc_notif_ipoe-session-grouping {
    leaf description {
      type string;
    }
    leaf ipoe-session-policy {
      type ncs_rpc_notif_string32;
    }
    leaf user-db {
      type string;
    }
    leaf shutdown {
      type boolean;
    }
  }

  grouping ncs_rpc_notif_packet-byte-offset-grouping {
    container packet-byte-offset {
      tailf:cli-compact-syntax;
      choice op {
        leaf add {
          type uint8;
        }
        leaf subtract {
          type uint8;
        }
      }
    }
  }

  grouping ncs_rpc_notif_port-parent-grouping {
    container port-parent {
      presence "present";
      tailf:cli-compact-syntax;
      leaf weight {
        type uint8;
      }
      leaf level {
        type uint8;
      }
      leaf cir-weight {
        type uint8;
      }
      leaf cir-level {
        type uint8;
      }
    }
  }

  grouping ncs_rpc_notif_router-aggregate-grouping {
    list aggregate {
      tailf:cli-compact-syntax;
      tailf:cli-suppress-mode;
      key "route";
      leaf route {
        type union {
          type tailf:ipv4-address-and-prefix-length;
          type tailf:ipv6-address-and-prefix-length;
        }
      }
      leaf summary-only {
        type empty;
      }
      leaf discard-component-communities {
        type empty;
      }
      leaf as-set {
        type empty;
      }
      leaf aggregator {
        type string;
      }
      leaf-list community {
        tailf:cli-flat-list-syntax;
        type string;
      }
      leaf black-hole {
        type empty;
      }
      leaf description {
        type string;
      }
      leaf policy {
        type string;
      }
    }
  }

  grouping ncs_rpc_notif_ospf-area-id-grouping {
    leaf area-id {
      type union {
        type inet:ipv4-address;
        type uint32;
      }
    }
  }

  grouping ncs_rpc_notif_service-id-grouping {
    leaf service-id {
      type ncs_rpc_notif_service-id;
    }
  }

  grouping ncs_rpc_notif_radius-server-grouping {
    list server {
      key "server-name";
      leaf server-name {
        type ncs_rpc_notif_string32;
      }
      leaf address {
        tailf:cli-hide-in-submode;
        type union {
          type inet:ipv4-address;
          type inet:ipv6-address;
        }
      }
      leaf secret {
        tailf:cli-hide-in-submode;
        type string;
      }
      leaf auth-port {
        type uint32;
      }
      leaf acct-port {
        type uint32;
      }
      leaf coa-script-policy {
        type ncs_rpc_notif_string32;
      }
      leaf scheme {
        tailf:cli-drop-node-name;
        tailf:cli-hide-in-submode;
        type ncs_rpc_notif_hash-method;
      }
      leaf accept-coa {
        type empty;
      }
      leaf description {
        type string;
      }
      leaf python-policy {
        type ncs_rpc_notif_string32;
      }
    }
  }

  grouping ncs_rpc_notif_dhcp6-lease-timers-grouping {

    grouping dhcp6-lease-time-common-grouping {
      leaf sec {
        type uint16;
      }
    }
    container preferred-lifetime {
      tailf:cli-compact-syntax;
      leaf days {
        type uint8;
      }
      leaf hrs {
        type uint8;
      }
      leaf min {
        type uint8;
      }
      uses dhcp6-lease-time-common-grouping;
    }
    container rebind-timer {
      tailf:cli-compact-syntax;
      leaf days {
        type uint8;
      }
      leaf hrs {
        type uint8;
      }
      leaf min {
        type uint8;
      }
      uses dhcp6-lease-time-common-grouping;
    }
    container renew-timer {
      tailf:cli-compact-syntax;
      leaf days {
        type uint8;
      }
      leaf hrs {
        type uint8;
      }
      leaf min {
        type uint8;
      }
      uses dhcp6-lease-time-common-grouping;
    }
    container valid-lifetime {
      tailf:cli-compact-syntax;
      leaf days {
        type uint8;
      }
      leaf hrs {
        type uint8;
      }
      leaf min {
        type uint8;
      }
      uses dhcp6-lease-time-common-grouping;
    }
    container server-id {
      tailf:cli-compact-syntax;
      leaf duid {
        tailf:cli-drop-node-name;
        type enumeration {
          enum "duid-en";
          enum "duid-ll";
        }
      }
      choice strhex {
        leaf string {
          type string;
        }
        leaf hex {
          type string;
        }
      }
    }
  }

  grouping ncs_rpc_notif_snmp-community-grouping {
    list community {
      tailf:cli-suppress-mode;
      tailf:cli-compact-syntax;
      tailf:cli-sequence-commands {
        tailf:cli-reset-all-siblings;
      }
      key "name";
      leaf name {
        type string;
      }
      leaf type {
        tailf:cli-drop-node-name;
        tailf:cli-optional-in-sequence;
        type ncs_rpc_notif_hash-method;
      }
      leaf access-parameters {
        tailf:cli-drop-node-name;
        tailf:cli-optional-in-sequence;
        type enumeration {
          enum "r";
          enum "rw";
          enum "rwa";
          enum "mgmt";
          enum "vpls-mgmt";
        }
      }
      leaf version {
        tailf:cli-optional-in-sequence;
        type enumeration {
          enum "v2c";
          enum "v1";
          enum "both";
        }
      }
      leaf src-access-list {
        type ncs_rpc_notif_string32;
      }
    }
  }

  grouping ncs_rpc_notif_qos-dscp-list-grouping {
    list dscp {
      tailf:cli-suppress-mode;
      tailf:cli-compact-syntax;
      tailf:cli-sequence-commands {
        tailf:cli-reset-all-siblings;
      }
      key "dscp-name";
      leaf dscp-name {
        type ncs_rpc_notif_dscp-type;
      }
      leaf fc {
        tailf:cli-optional-in-sequence;
        type ncs_rpc_notif_fc-name;
      }
      leaf profile {
        type ncs_rpc_notif_in-out;
      }
    }
  }

  grouping ncs_rpc_notif_qos-dot1p-list-grouping {
    list dot1p {
      tailf:cli-compact-syntax;
      tailf:cli-suppress-mode;
      key "id";
      leaf id {
        type uint8;
      }
      leaf fc {
        type ncs_rpc_notif_fc-name;
      }
      leaf profile {
        type enumeration {
          enum "in";
          enum "out";
          enum "use-de";
          enum "exceed";
          enum "inplus";
        }
      }
    }
    list prec {
      key "ip-prec-value";
      tailf:cli-compact-syntax;
      tailf:cli-suppress-mode;
      leaf ip-prec-value {
        tailf:cli-drop-node-name;
        type uint16;
      }
      leaf profile {
        type enumeration {
          enum "in";
          enum "out";
          enum "exceed";
          enum "inplus";
        }
      }
      leaf fc {
        type ncs_rpc_notif_fc-name;
      }
    }
  }

  grouping ncs_rpc_notif_slope-params-grouping {
    leaf start-avg {
      type uint8;
    }
    leaf max-avg {
      type uint8;
    }
    leaf max-prob {
      type uint8;
    }
    leaf shutdown {
      type boolean;
    }
  }

  grouping ncs_rpc_notif_qos-lsp-exp-grouping {
    list lsp-exp {
      tailf:cli-compact-syntax;
      tailf:cli-suppress-mode;
      tailf:cli-sequence-commands {
        tailf:cli-reset-all-siblings;
      }
      key "id";
      leaf id {
        type uint8;
      }
      leaf fc {
        type ncs_rpc_notif_fc-name;
      }
      leaf profile {
        type enumeration {
          enum "in";
          enum "out";
        }
      }
    }
  }

  grouping ncs_rpc_notif_bgp-common-grouping {
    leaf keepalive {
      type uint16;
    }
    container hold-time {
      tailf:cli-compact-syntax;
      leaf seconds {
        tailf:cli-drop-node-name;
        type uint16;
      }
      leaf min {
        type uint16;
      }
    }
    leaf preference {
      type uint8;
    }
  }

  grouping ncs_rpc_notif_pim-common-grouping {
    leaf rpf6-table {
      type enumeration {
        enum "rtable6-m";
        enum "rtable6-u";
        enum "both";
      }
    }
    leaf apply-to {
      type enumeration {
        enum "all";
        enum "ies";
        enum "non-ies";
        enum "none";
      }
    }
  }

  grouping ncs_rpc_notif_local-dhcp-server-grouping {

    grouping dhcp-custom-options-grouping {
      list custom-option {
        tailf:cli-suppress-mode;
        key "number";
        leaf number {
          type uint8;
        }
        leaf-list address {
          tailf:cli-flat-list-syntax;
          type inet:ipv4-address;
        }
        leaf hex {
          type string;
        }
        leaf string {
          type string;
        }
      }
    }
    list local-dhcp-server {
      key "server-name";
      leaf server-name {
        type string;
      }
      leaf description {
        type string;
      }
      container use-gi-address {
        tailf:cli-compact-syntax;
        presence "true";
        leaf scope {
          type enumeration {
            enum "pool";
            enum "subnet";
          }
        }
      }
      leaf force-renews {
        type empty;
      }
      list pool {
        key "pool-id";
        leaf pool-id {
          type ncs_rpc_notif_string32;
        }
        leaf description {
          type string;
        }
        container max-lease-time {
          tailf:cli-compact-syntax;
          uses ncs_rpc_notif_dhcp-lease-time;
        }
        container min-lease-time {
          tailf:cli-compact-syntax;
          uses ncs_rpc_notif_dhcp-lease-time;
        }
        container minimum-free {
          tailf:cli-compact-syntax;
          tailf:cli-sequence-commands {
            tailf:cli-reset-siblings;
          }
          leaf minimum-free-value {
            tailf:cli-drop-node-name;
            type uint16;
          }
          leaf percent {
            tailf:cli-optional-in-sequence;
            type empty;
          }
          leaf event-when-depleted {
            type empty;
          }
        }
        leaf nak-non-matching-subnet {
          type empty;
        }
        container offer-time {
          tailf:cli-compact-syntax;
          tailf:cli-sequence-commands {
            tailf:cli-reset-siblings;
          }
          leaf min {
            type uint16;
          }
          leaf sec {
            type uint16;
          }
        }
        container options {
          tailf:cli-add-mode;
          leaf-list dns-server {
            tailf:cli-flat-list-syntax;
            type inet:ipv4-address;
          }
          leaf domain-name {
            type string;
          }
          container lease-rebind-time {
            tailf:cli-compact-syntax;
            uses ncs_rpc_notif_dhcp-lease-time;
          }
          container lease-renew-time {
            tailf:cli-compact-syntax;
            uses ncs_rpc_notif_dhcp-lease-time;
          }
          container lease-time {
            tailf:cli-compact-syntax;
            uses ncs_rpc_notif_dhcp-lease-time;
          }
          leaf-list netbios-name-server {
            tailf:cli-flat-list-syntax;
            type inet:ipv4-address;
          }
          leaf netbios-node-type {
            type enumeration {
              enum "B";
              enum "P";
              enum "M";
              enum "H";
            }
          }
          uses dhcp-custom-options-grouping;
        }
        list subnet {
          key "subnet-id";
          leaf subnet-id {
            type tailf:ipv4-address-and-prefix-length;
          }
          container address-range {
            uses ncs_rpc_notif_ip-address-range {
              augment "low-high-list" {
                leaf failover {
                  type enumeration {
                    enum "local";
                    enum "remote";
                    enum "access-driven";
                  }
                }
              }
            }
          }
          leaf drain {
            type empty;
          }
          container exclude-addresses {
            uses ncs_rpc_notif_ip-address-range;
          }
          leaf maximum-declined {
            type uint32;
          }
          container minimum-free {
            tailf:cli-compact-syntax;
            tailf:cli-sequence-commands {
              tailf:cli-reset-siblings;
            }
            leaf minimum-free-value {
              tailf:cli-drop-node-name;
              type uint16;
            }
            leaf percent {
              type empty;
            }
            leaf event-when-depleted {
              type empty;
            }
          }
          container options {
            tailf:cli-add-mode;
            leaf-list default-router {
              tailf:cli-flat-list-syntax;
              type inet:ipv4-address;
            }
            leaf subnet-mask {
              type inet:ipv4-address;
            }
            uses dhcp-custom-options-grouping;
          }
        }
      }
      container failover {
        tailf:cli-add-mode;
        leaf ignore-mclt-on-takeover {
          type empty;
        }
        container maximum-client-lead-time {
          tailf:cli-compact-syntax;
          leaf hrs {
            type uint8;
          }
          leaf min {
            type uint8;
          }
          leaf sec {
            type uint8;
          }
        }
        container partner-down-delay {
          tailf:cli-compact-syntax;
          leaf hrs {
            type uint8;
          }
          leaf min {
            type uint8;
          }
          leaf sec {
            type uint8;
          }
        }
        container peer {
          tailf:cli-compact-syntax;
          tailf:cli-sequence-commands {
            tailf:cli-reset-all-siblings;
          }
          leaf ip-address {
            tailf:cli-drop-node-name;
            type inet:ipv4-address;
          }
          leaf tag {
            type string;
          }
        }
        container startup-wait-time {
          tailf:cli-compact-syntax;
          tailf:cli-sequence-commands {
            tailf:cli-reset-all-siblings;
          }
          leaf min {
            type uint8;
          }
          leaf sec {
            type uint8;
          }
        }
        leaf shutdown {
          type boolean;
        }
      }
      container lease-hold-time {
        tailf:cli-compact-syntax;
        leaf days {
          type uint32;
        }
        leaf hrs {
          type uint32;
        }
        leaf min {
          type uint32;
        }
        leaf sec {
          type uint32;
        }
      }
      container lease-hold-time-for {
        tailf:cli-add-mode;
        leaf solicited-release {
          type empty;
        }
      }
      container use-pool-from-client {
        tailf:cli-compact-syntax;
        presence "true";
      }
      leaf shutdown {
        type boolean;
      }
    }
  }

  grouping src-dst-ip {
    leaf src-ip {
      type union {
        type inet:ipv4-prefix;
        type string;
      }
    }
    leaf dst-ip {
      type union {
        type inet:ipv4-prefix;
        type string;
      }
    }
  }

  grouping ip-address-range {
    list low-high-list {
      tailf:cli-drop-node-name;
      tailf:cli-suppress-mode;
      tailf:cli-delete-when-empty;
      key "low high";
      leaf low {
        type inet:ipv4-address;
      }
      leaf high {
        type inet:ipv4-address;
      }
    }
  }

  grouping eth-cfm {
    leaf collect-lmm-stats {
      type empty;
    }
    list mep {
      key "mep-id domain association";
      leaf mep-id {
        type uint16;
      }
      leaf domain {
        type uint32;
      }
      leaf association {
        type uint32;
      }
      leaf direction {
        tailf:cli-hide-in-submode;
        type direction;
      }
      container ais-enable {
        tailf:cli-add-mode;
        leaf-list client-meg-level {
          tailf:cli-flat-list-syntax;
          type uint8;
        }
        leaf description {
          type string;
        }
        leaf interval {
          type enumeration {
            enum "1";
            enum "60";
          }
        }
        leaf priority {
          type uint8;
        }
      }
      leaf ccm-enable {
        type empty;
      }
      leaf ccm-ltm-priority {
        type uint8;
      }
      leaf ccm-padding-size {
        type uint32;
      }
      leaf description {
        type string;
      }
      container eth-test-enable {
        tailf:cli-add-mode;
        uses eth-test;
      }
      leaf fault-propagation-enable {
        type enumeration {
          enum "use-if-tlv";
          enum "suspend-ccm";
        }
      }
      leaf install-mep {
        type empty;
      }
      leaf low-priority-defect {
        type enumeration {
          enum "allDef";
          enum "macRemErrXcon";
          enum "remErrXcon";
          enum "errXcon";
          enum "Xcon";
          enum "noXcon";
        }
      }
      leaf mac-address {
        type ieee-mac;
      }
      leaf one-way-delay-threshold {
        type uint16;
      }
      leaf shutdown {
        type boolean;
      }
    }
  }

  grouping enable-origin-validation-grouping {
    leaf-list enable-origin-validation {
      tailf:cli-flat-list-syntax;
      type enumeration {
        enum "ipv4";
        enum "ipv6";
        enum "label-ipv4";
        enum "label-ipv6";
      }
    }
  }

  grouping igmp-static-grouping {
    container static {
      tailf:cli-add-mode;
      list group {
        key "grp-ip-addr";
        leaf grp-ip-addr {
          type inet:ipv4-address;
        }
        list source {
          tailf:cli-suppress-mode;
          tailf:cli-delete-when-empty;
          key "ip-address";
          leaf ip-address {
            type inet:ipv4-address;
          }
        }
        leaf starg {
          type empty;
        }
      }
    }
  }

  grouping igmp-snooping-grouping {
    leaf disable-router-alert {
      type empty;
    }
    leaf fast-leave {
      type empty;
    }
    leaf import {
      type string;
    }
    leaf last-member-query-interval {
      type uint8;
    }
    leaf max-num-groups {
      type uint16;
    }
    leaf mrouter-port {
      type empty;
    }
    leaf query-interval {
      type uint16;
    }
    leaf query-response-interval {
      type uint16;
    }
    leaf robust-count {
      type uint8;
    }
    leaf send-queries {
      type empty;
    }
    uses igmp-static-grouping;
    leaf version {
      type uint8;
    }
  }

  grouping sdp-common {
    leaf vc-id {
      type uint32;
    }
    leaf vc-type {
      tailf:cli-hide-in-submode;
      type enumeration {
        enum "ether";
        enum "vlan";
      }
    }
    leaf endpoint {
      tailf:cli-hide-in-submode;
      type string;
    }
    leaf icb {
      tailf:cli-hide-in-submode;
      type empty;
    }
    leaf shutdown {
      type boolean;
    }
  }

  grouping sdp-spoke-mesh-common {
    leaf sdp-id {
      type uint32;
    }
    uses sdp-common;
    leaf accounting-policy {
      type uint8;
    }
    leaf auto-learn-mac-protect {
      type empty;
    }
    leaf description {
      type string;
    }
    leaf collect-stats {
      type empty;
    }
    container hash-label {
      presence "true";
      leaf signal-capability {
        type empty;
      }
    }
    leaf control-word {
      type empty;
    }
    container igmp-snooping {
      tailf:cli-add-mode;
      uses igmp-snooping-grouping;
    }
    container egress {
      tailf:cli-add-mode;
      container filter {
        uses filter-choice;
      }
      container qos {
        tailf:cli-sequence-commands;
        tailf:cli-compact-syntax;
        leaf network-policy-id {
          tailf:cli-drop-node-name;
          type uint16;
        }
        leaf port-redirect-group {
          type string;
        }
        leaf instance {
          type uint16;
        }
      }
      leaf vc-label {
        type uint32;
      }
    }
    container eth-cfm {
      tailf:cli-add-mode;
      uses eth-cfm;
    }
    leaf force-vlan-vc-forwarding {
      type empty;
    }
    container ingress {
      tailf:cli-add-mode;
      container filter {
        uses filter-choice;
      }
      container qos {
        tailf:cli-sequence-commands;
        tailf:cli-compact-syntax;
        leaf network-policy-id {
          tailf:cli-drop-node-name;
          type uint16;
        }
        leaf fp-redirect-group {
          type string;
        }
        leaf instance {
          type uint16;
        }
      }
      leaf vc-label {
        type uint32;
      }
    }
    leaf mac-pinning {
      type empty;
    }
    list static-mac {
      tailf:cli-suppress-mode;
      key "address";
      leaf address {
        type ieee-mac;
      }
    }
    leaf restrict-protected-src {
      type enumeration {
        enum "alarm-only";
        enum "discard-frame";
      }
    }
    leaf precedence {
      type union {
        type enumeration {
          enum "primary";
        }
        type uint8;
      }
    }
    leaf vlan-vc-tag {
      type uint16;
    }
  }

  grouping stp-common {
    leaf auto-edge {
      type empty;
    }
    leaf edge-port {
      type empty;
    }
    leaf link-type {
      type enumeration {
        enum "pt-pt";
        enum "shared";
      }
    }
    leaf path-cost {
      type uint32;
    }
    leaf port-num {
      type uint16;
    }
    leaf priority {
      type uint16;
    }
    leaf shutdown {
      type boolean;
    }
  }

  grouping filter-choice {
    leaf ip {
      type filter-id;
    }
    leaf ipv6 {
      type filter-id;
    }
    leaf mac {
      type filter-id;
    }
  }

  grouping eth-test {
    leaf test-pattern {
      type test-pattern;
    }
    leaf crc-enable {
      type empty;
    }
  }

  grouping time-stamp {
    leaf start-week {
      tailf:cli-drop-node-name;
      type enumeration {
        enum "first";
        enum "second";
        enum "third";
        enum "fourth";
        enum "last";
      }
    }
    leaf start-day {
      tailf:cli-drop-node-name;
      type weekday;
    }
    leaf month {
      tailf:cli-drop-node-name;
      type month;
    }
    leaf hours-minutes {
      tailf:cli-drop-node-name;
      type string;
    }
  }

  grouping ip-filter-entry-grouping {
    leaf entry-name {
      type uint32;
    }
    leaf description {
      type string;
    }
    leaf log {
      type uint32;
    }
    list match {
      key "protocol-type";
      leaf protocol-type {
        type union {
          type protocol;
          type string;
        }
      }
      leaf protocol {
        tailf:cli-prefix-key;
        type empty;
      }
      leaf dscp {
        type dscp-type;
      }
      container ip {
        tailf:cli-compact-syntax;
        tailf:cli-sequence-commands;
        uses filter-match-ip-grouping;
      }
      container src-ip {
        tailf:cli-compact-syntax;
        tailf:cli-sequence-commands;
        uses filter-match-ip-grouping;
      }
      leaf src-route-option {
        type boolean;
      }
      container dst-ip {
        tailf:cli-compact-syntax;
        tailf:cli-sequence-commands;
        uses filter-match-ip-grouping;
      }
      leaf icmp-type {
        type icmp-type;
      }
      leaf icmp-code {
        type uint32;
      }
      leaf fragment {
        type enumeration {
          enum "true";
          enum "false";
          enum "first-only";
          enum "non-first-only";
        }
      }
      leaf option-present {
        type boolean;
      }
      container ip-option {
        tailf:cli-compact-syntax;
        leaf a {
          tailf:cli-drop-node-name;
          type uint32;
        }
        leaf b {
          tailf:cli-drop-node-name;
          type uint32;
        }
      }

      grouping filter-ip-filter-port-grouping {
        choice port-choice {
          case a {
            leaf op {
              tailf:cli-drop-node-name;
              type enumeration {
                enum "lt";
                enum "gt";
                enum "eq";
              }
            }
            leaf port {
              tailf:cli-drop-node-name;
              mandatory true;
              type uint16;
            }
          }
          case b {
            leaf range {
              type empty;
            }
            leaf start {
              tailf:cli-drop-node-name;
              mandatory true;
              type uint16;
            }
            leaf end {
              tailf:cli-drop-node-name;
              mandatory true;
              type uint16;
            }
          }
          case c {
            leaf port-list {
              type string32;
            }
          }
        }
      }
      container port {
        tailf:cli-compact-syntax;
        tailf:cli-sequence-commands;
        uses filter-ip-filter-port-grouping;
      }
      container dst-port {
        tailf:cli-compact-syntax;
        tailf:cli-sequence-commands;
        uses filter-ip-filter-port-grouping;
      }
      container src-port {
        tailf:cli-compact-syntax;
        tailf:cli-sequence-commands {
          tailf:cli-reset-all-siblings;
        }
        choice port-choice {
          case a {
            leaf op {
              tailf:cli-drop-node-name;
              type enumeration {
                enum "lt";
                enum "gt";
                enum "eq";
              }
            }
            leaf port {
              tailf:cli-drop-node-name;
              mandatory true;
              type uint16;
            }
          }
          case b {
            leaf range {
              type empty;
            }
            leaf start {
              tailf:cli-drop-node-name;
              mandatory true;
              type uint16;
            }
            leaf end {
              tailf:cli-drop-node-name;
              mandatory true;
              type uint16;
            }
          }
          case c {
            leaf src-port-number {
              tailf:cli-drop-node-name;
              type uint16;
            }
            leaf mask {
              tailf:cli-drop-node-name;
              type uint16;
            }
          }
          case d {
            leaf port-list {
              type string32;
            }
          }
        }
      }
      leaf tcp-ack {
        type boolean;
      }
      leaf tcp-syn {
        type boolean;
      }
    }
  }

  grouping ipv6-filter-entry-grouping {
    leaf entry-name {
      type uint32;
    }
    leaf description {
      type string;
    }
    container match {
      tailf:cli-add-mode;
      presence "true";
      leaf next-header {
        tailf:cli-hide-in-submode;
        type union {
          type enumeration {
            enum "*";
            enum "none";
            enum "icmp";
            enum "igmp";
            enum "ip";
            enum "tcp";
            enum "egp";
            enum "igp";
            enum "udp";
            enum "rdp";
            enum "ipv6";
            enum "idrp";
            enum "rsvp";
            enum "gre";
            enum "ipv6-icmp";
            enum "ipv6-no-nxt";
            enum "iso-ip";
            enum "eigrp";
            enum "ospf-igp";
            enum "ether-ip";
            enum "encap";
            enum "pnni";
            enum "pim";
            enum "vrrp";
            enum "l2tp";
            enum "stp";
            enum "ptp";
            enum "isis";
            enum "crtp";
            enum "crudp";
            enum "sctp";
          }
          type uint32;
        }
      }
      leaf dscp {
        type dscp-type;
      }
      container ip {
        tailf:cli-compact-syntax;
        tailf:cli-sequence-commands {
          tailf:cli-reset-all-siblings;
        }
        uses filter-match-ipv6-grouping;
      }
      container src-ip {
        tailf:cli-compact-syntax;
        tailf:cli-sequence-commands {
          tailf:cli-reset-all-siblings;
        }
        uses filter-match-ipv6-grouping;
      }
      container dst-ip {
        tailf:cli-compact-syntax;
        tailf:cli-sequence-commands {
          tailf:cli-reset-all-siblings;
        }
        uses filter-match-ipv6-grouping;
      }
      leaf icmp-type {
        type icmpv6-type;
      }
      leaf icmp-code {
        type uint32;
      }
      leaf fragment {
        type enumeration {
          enum "true";
          enum "false";
          enum "first-only";
          enum "non-first-only";
        }
      }
      container ip-option {
        tailf:cli-compact-syntax;
        tailf:cli-sequence-commands {
          tailf:cli-reset-all-siblings;
        }
        leaf a {
          tailf:cli-drop-node-name;
          type uint32;
        }
        leaf b {
          tailf:cli-drop-node-name;
          type uint32;
        }
      }

      grouping filter-ipv6-filter-port-grouping {
        choice port-choice {
          case a {
            leaf op {
              tailf:cli-drop-node-name;
              type enumeration {
                enum "lt";
                enum "gt";
                enum "eq";
              }
            }
            leaf port {
              tailf:cli-drop-node-name;
              type uint16;
            }
          }
          case b {
            leaf range {
              type empty;
            }
            leaf start {
              tailf:cli-drop-node-name;
              type uint16;
            }
            leaf end {
              tailf:cli-drop-node-name;
              type uint16;
            }
          }
          case c {
            leaf port-list {
              type string32;
            }
          }
        }
      }
      container dst-port {
        tailf:cli-compact-syntax;
        tailf:cli-sequence-commands {
          tailf:cli-reset-all-siblings;
        }
        uses filter-ipv6-filter-port-grouping;
      }
      leaf routing-type0 {
        type boolean;
      }
      container src-port {
        tailf:cli-compact-syntax;
        tailf:cli-sequence-commands {
          tailf:cli-reset-all-siblings;
        }
        uses filter-ipv6-filter-port-grouping;
      }
      container port {
        tailf:cli-compact-syntax;
        tailf:cli-sequence-commands {
          tailf:cli-reset-all-siblings;
        }
        uses filter-ipv6-filter-port-grouping;
      }
      leaf tcp-ack {
        type boolean;
      }
      leaf tcp-syn {
        type boolean;
      }
    }
  }

  grouping queue-adaptation-grouping {
    container adaptation-rule {
      tailf:cli-compact-syntax;
      leaf pir {
        type enumeration {
          enum "max";
          enum "min";
          enum "closest";
        }
      }
      leaf cir {
        type enumeration {
          enum "max";
          enum "min";
          enum "closest";
        }
      }
    }
  }

  grouping queue-rate-grouping {
    container rate {
      tailf:cli-compact-syntax;
      tailf:cli-sequence-commands {
        tailf:cli-reset-all-siblings;
      }
      leaf pir {
        tailf:cli-drop-node-name;
        tailf:cli-optional-in-sequence;
        type rate-type;
      }
      leaf cir {
        tailf:cli-optional-in-sequence;
        type rate-type;
      }
      leaf alt-pir {
        tailf:cli-optional-in-sequence;
        tailf:alt-name "pir";
        type rate-type;
      }
      leaf police {
        type empty;
      }
    }
  }

  grouping qos-queue-percent-rate-grouping {
    container percent-rate {
      tailf:cli-compact-syntax;
      tailf:cli-sequence-commands {
        tailf:cli-reset-all-siblings;
      }
      leaf pir {
        tailf:cli-drop-node-name;
        type decimal64 {
          fraction-digits 2;
        }
      }
      leaf cir {
        tailf:cli-optional-in-sequence;
        type decimal64 {
          fraction-digits 2;
        }
      }
    }
  }

  grouping sap-queue-override-grouping {
    container queue-override {
      tailf:cli-add-mode;
      list queue {
        key "queue-id";
        leaf queue-id {
          type uint32;
        }
        uses queue-adaptation-grouping;
        leaf avg-frame-overhead {
          type decimal64 {
            fraction-digits 2;
          }
        }
        container mbs {
          tailf:cli-compact-syntax;
          tailf:cli-sequence-commands {
            tailf:cli-reset-siblings;
          }
          leaf val {
            tailf:cli-drop-node-name;
            type union {
              type enumeration {
                enum "default";
              }
              type uint32;
            }
          }
          leaf unit {
            tailf:cli-drop-node-name;
            type enumeration {
              enum "bytes";
              enum "kilobytes";
            }
          }
        }
        leaf cbs {
          type union {
            type enumeration {
              enum "default";
            }
            type uint32;
          }
        }
        leaf high-prio-only {
          type union {
            type enumeration {
              enum "default";
            }
            type uint8;
          }
        }
        container rate {
          tailf:cli-compact-syntax;
          tailf:cli-sequence-commands {
            tailf:cli-reset-siblings;
          }
          leaf pir {
            tailf:cli-drop-node-name;
            type union {
              type enumeration {
                enum "max";
              }
              type uint32;
            }
          }
          leaf cir {
            type union {
              type enumeration {
                enum "max";
              }
              type uint32;
            }
          }
        }
        container parent {
          tailf:cli-compact-syntax;
          tailf:cli-sequence-commands {
            tailf:cli-reset-siblings;
          }
          leaf weight {
            type uint8;
          }
          leaf cir-weight {
            type uint8;
          }
        }
        uses qos-queue-percent-rate-grouping;
      }
    }
  }

  grouping sap-scheduler-override-grouping {
    container scheduler-override {
      tailf:cli-add-mode;
      list scheduler {
        key "scheduler-policy-name";
        leaf scheduler-policy-name {
          type string;
        }
        container parent {
          tailf:cli-compact-syntax;
          leaf weight {
            type uint32;
          }
          leaf cir-weight {
            type uint32;
          }
        }
        container rate {
          tailf:cli-compact-syntax;
          tailf:cli-sequence-commands {
            tailf:cli-reset-siblings;
          }
          leaf rate {
            tailf:cli-drop-node-name;
            type union {
              type uint32;
              type enumeration {
                enum "max";
              }
            }
          }
          leaf cir {
            type union {
              type uint32;
              type enumeration {
                enum "sum";
                enum "max";
              }
            }
          }
        }
      }
    }
  }

  grouping router-segment-routing-grouping {
    container segment-routing {
      tailf:cli-add-mode;
      container prefix-sid-range {
        tailf:cli-compact-syntax;
        tailf:cli-sequence-commands {
          tailf:cli-reset-siblings;
        }
        choice range {
          leaf global {
            type empty;
          }
          case other {
            leaf start-label {
              type uint32;
            }
            leaf max-index {
              type uint32;
            }
          }
        }
      }
      leaf tunnel-mtu {
        type uint16;
      }
      leaf tunnel-table-pref {
        type uint8;
      }
      leaf srlb {
        type string;
      }
      container micro-loop-avoidance {
        presence "true";
        leaf fib-delay {
          type uint8;
        }
      }
      leaf export-tunnel-table {
        type enumeration {
          enum "ldp";
        }
      }
      leaf shutdown {
        type boolean;
      }
    }
  }

  grouping sap-policer-override-grouping-egress {
    container policer-override {
      tailf:cli-add-mode;
      list policer {
        key "policer-id";
        leaf policer-id {
          type uint8;
        }
        uses policer-cbs-mbs-rate-with-packet-offset-grouping;
      }
    }
  }

  grouping sap-policer-override-grouping-ingress {
    container policer-override {
      tailf:cli-add-mode;
      list policer {
        key "policer-id";
        leaf policer-id {
          type uint8;
        }
        uses policer-cbs-mbs-rate-with-packet-offset-grouping;
      }
    }
  }

  grouping ip-criteria-grouping {
    leaf dscp-only {
      tailf:cli-hide-in-submode;
      type empty;
    }
    list entry {
      key "id";
      leaf id {
        type uint16;
      }
      leaf description {
        type string;
      }
      container match {
        tailf:cli-add-mode;
        leaf protocol {
          tailf:cli-hide-in-submode;
          type protocol;
        }
        leaf dscp {
          type dscp-type;
        }
        container dst-ip {
          tailf:cli-compact-syntax;
          choice dst {
            leaf ip-address-with-mask {
              tailf:cli-drop-node-name;
              type tailf:ipv4-address-and-prefix-length;
            }
            leaf ip-prefix-list {
              type string32;
            }
          }
        }
        container src-ip {
          tailf:cli-compact-syntax;
          choice src {
            leaf ip-address-with-mask {
              tailf:cli-drop-node-name;
              type tailf:ipv4-address-and-prefix-length;
            }
            leaf ip-prefix-list {
              type string32;
            }
          }
        }

        grouping port-choice-grouping {
          choice port-choice {
            case a {
              leaf op {
                tailf:cli-drop-node-name;
                type enumeration {
                  enum "lt";
                  enum "gt";
                  enum "eq";
                }
              }
              leaf port {
                tailf:cli-drop-node-name;
                type uint16;
              }
            }
            case b {
              leaf range {
                type empty;
              }
              leaf start {
                tailf:cli-drop-node-name;
                type uint16;
              }
              leaf end {
                tailf:cli-drop-node-name;
                type uint16;
              }
            }
          }
        }
        container dst-port {
          tailf:cli-compact-syntax;
          tailf:cli-sequence-commands {
            tailf:cli-reset-all-siblings;
          }
          uses port-choice-grouping;
        }
        container src-port {
          tailf:cli-compact-syntax;
          tailf:cli-sequence-commands {
            tailf:cli-reset-all-siblings;
          }
          uses port-choice-grouping;
        }
      }
      container action {
        tailf:cli-compact-syntax;
        presence "true";
        leaf profile {
          type enumeration {
            enum "in";
            enum "out";
            enum "exceed";
            enum "inplus";
          }
        }
        leaf fc {
          type fc-name;
        }
        leaf priority {
          type enumeration {
            enum "high";
            enum "low";
          }
        }
        leaf policer {
          type uint8;
        }
      }
    }
  }

  grouping ipv6-criteria-grouping {
    list entry {
      key "id";
      leaf id {
        type uint16;
      }
      leaf description {
        type string;
      }
      container match {
        tailf:cli-add-mode;
        leaf protocol {
          tailf:cli-hide-in-submode;
          type protocol;
        }
        leaf next-header {
          tailf:cli-hide-in-submode;
          type union {
            type uint8;
            type protocol;
          }
        }
        leaf dscp {
          type dscp-type;
        }
        container src-ip {
          uses filter-match-ip-grouping;
        }
        container dst-ip {
          uses filter-match-ip-grouping;
        }

        grouping port-choice-grouping {
          choice port-choice {
            case a {
              leaf op {
                tailf:cli-drop-node-name;
                type enumeration {
                  enum "lt";
                  enum "gt";
                  enum "eq";
                }
              }
              leaf port {
                tailf:cli-drop-node-name;
                type uint16;
              }
            }
            case b {
              leaf range {
                type empty;
              }
              leaf start {
                tailf:cli-drop-node-name;
                type uint16;
              }
              leaf end {
                tailf:cli-drop-node-name;
                type uint16;
              }
            }
          }
        }
        container dst-port {
          tailf:cli-compact-syntax;
          tailf:cli-sequence-commands {
            tailf:cli-reset-all-siblings;
          }
          uses port-choice-grouping;
        }
        container src-port {
          tailf:cli-compact-syntax;
          tailf:cli-sequence-commands {
            tailf:cli-reset-all-siblings;
          }
          uses port-choice-grouping;
        }
      }
      container action {
        tailf:cli-compact-syntax;
        leaf fc {
          type string;
        }
        leaf priority {
          type enumeration {
            enum "high";
            enum "low";
          }
        }
        leaf policer {
          type uint8;
        }
      }
    }
  }

  grouping mac-criteria-grouping {
    leaf match-criteria {
      tailf:cli-hide-in-submode;
      tailf:cli-drop-node-name;
      type enumeration {
        enum "any";
        enum "dot1p-only";
      }
    }
    leaf type {
      type enumeration {
        enum "normal";
        enum "vid";
      }
    }
    list entry {
      key "id";
      leaf id {
        type uint16;
      }
      leaf description {
        type string;
      }
      container match {
        tailf:cli-add-mode;
        leaf frame-type {
          tailf:cli-hide-in-submode;
          type enumeration {
            enum "802dot3";
            enum "802dot2-llc";
            enum "802dot2-snap";
            enum "ethernet-II";
            enum "atm";
          }
        }
        container outer-tag {
          tailf:cli-compact-syntax;
          leaf value {
            tailf:cli-drop-node-name;
            type union {
              type uint16;
              type string;
            }
          }
          leaf vid-mask {
            tailf:cli-drop-node-name;
            type union {
              type uint16;
              type string;
            }
          }
        }

        grouping match-mac-grouping {
          leaf ieee-address {
            tailf:cli-drop-node-name;
            type ieee-mac;
          }
          leaf ieee-address-mask {
            tailf:cli-drop-node-name;
            type ieee-mac;
          }
        }
        container dst-mac {
          tailf:cli-compact-syntax;
          tailf:cli-sequence-commands {
            tailf:cli-reset-siblings;
          }
          uses match-mac-grouping;
        }
        container src-mac {
          tailf:cli-compact-syntax;
          tailf:cli-sequence-commands {
            tailf:cli-reset-siblings;
          }
          uses match-mac-grouping;
        }
        container dot1p {
          tailf:cli-compact-syntax;
          tailf:cli-sequence-commands {
            tailf:cli-reset-siblings;
          }
          leaf dot1p-value {
            tailf:cli-drop-node-name;
            type uint8;
          }
          leaf dot1p-mask {
            tailf:cli-drop-node-name;
            type uint8;
          }
        }
        leaf etype {
          type string;
        }
      }
      container action {
        tailf:cli-compact-syntax;
        tailf:cli-sequence-commands {
          tailf:cli-reset-all-siblings;
        }
        leaf fc {
          type fc-name;
        }
        leaf priority {
          type enumeration {
            enum "low";
            enum "high";
          }
        }
      }
    }
  }

  grouping meter-grouping {
    leaf meter-id {
      type uint8;
    }
    leaf multipoint {
      tailf:cli-hide-in-submode;
      type empty;
    }
    uses queue-adaptation-grouping;

    grouping unit-grouping {
      leaf unit {
        tailf:cli-drop-node-name;
        type enumeration {
          enum "kbits";
          enum "bytes";
          enum "kbytes";
        }
      }
    }
    container cbs {
      tailf:cli-compact-syntax;
      tailf:cli-sequence-commands {
        tailf:cli-reset-all-siblings;
      }
      leaf size {
        tailf:cli-drop-node-name;
        type union {
          type uint32;
          type enumeration {
            enum "default";
          }
        }
      }
      uses unit-grouping;
    }
    container mbs {
      tailf:cli-compact-syntax;
      tailf:cli-sequence-commands {
        tailf:cli-reset-all-siblings;
      }
      leaf size {
        tailf:cli-drop-node-name;
        type union {
          type uint32;
          type enumeration {
            enum "default";
          }
        }
      }
      uses unit-grouping;
    }
    container rate {
      tailf:cli-compact-syntax;
      leaf cir {
        type rate-type;
      }
      leaf pir {
        type rate-type;
      }
    }
    leaf mode {
      type enumeration {
        enum "trtcm1";
        enum "trtcm2";
        enum "srtcm";
      }
    }
  }

  grouping cpm-filter-match-port-grouping {
    choice port-choice {
      case a {
        leaf port-number {
          tailf:cli-drop-node-name;
          type uint16;
        }
        leaf mask {
          tailf:cli-drop-node-name;
          type uint16;
        }
      }
      case b {
        leaf range {
          type empty;
        }
        leaf start {
          tailf:cli-drop-node-name;
          type uint16;
        }
        leaf end {
          tailf:cli-drop-node-name;
          type uint16;
        }
      }
      case c {
        leaf port-list {
          type string;
        }
      }
    }
  }

  grouping filter-match-ip-grouping {
    choice ip {
      leaf address {
        tailf:cli-drop-node-name;
        type union {
          type inet:ipv4-address;
          type inet:ipv4-prefix;
          type string;
        }
      }
      leaf ip-prefix-list {
        type string;
      }
      leaf ipv6-prefix-list {
        type string32;
      }
    }
  }

  grouping filter-match-ipv6-grouping {
    choice ipv6 {
      leaf address {
        tailf:cli-drop-node-name;
        type union {
          type tailf:ipv6-address-and-prefix-length;
          type inet:ipv6-address;
          type string;
        }
      }
      leaf ipv6-prefix-list {
        type string;
      }
    }
  }

  grouping sap-egress-grouping {
    container agg-rate {
      tailf:cli-add-mode;
      container rate {
        tailf:cli-compact-syntax;
        leaf val {
          tailf:cli-drop-node-name;
          type union {
            type uint32;
            type enumeration {
              enum "max";
            }
          }
        }
        leaf cir {
          type union {
            type uint32;
            type enumeration {
              enum "max";
            }
          }
        }
      }
    }
    leaf egress-remark-policy {
      type string;
    }
    leaf vlan-qos-policy {
      type string;
    }
    leaf agg-rate-limit {
      type uint32;
    }
    container filter {
      uses filter-choice;
    }
    leaf multicast-group {
      type string;
    }
    leaf qos {
      type uint16;
    }
    uses sap-queue-override-grouping;
    leaf scheduler-policy {
      type string;
    }
    uses sap-scheduler-override-grouping;
    uses sap-policer-override-grouping-egress;
    leaf qinq-mark-top-only {
      type empty;
    }
    leaf dest-mac-rewrite {
      type yang:mac-address;
    }
    container qtag-manipulation {
      tailf:cli-add-mode;
      leaf preserve {
        type empty;
      }
    }
  }

  grouping sap-ingress-grouping {
    container filter {
      uses filter-choice;
    }
    container aggregate-meter-rate {
      tailf:cli-compact-syntax;
      tailf:cli-sequence-commands {
        tailf:cli-reset-siblings;
      }
      leaf value {
        tailf:cli-drop-node-name;
        type uint32;
      }
      leaf burst {
        type uint32;
      }
    }
    leaf match-qinq-dot1p {
      type enumeration {
        enum "top";
        enum "bottom";
      }
    }
    container qos {
      tailf:cli-compact-syntax;
      tailf:cli-sequence-commands {
        tailf:cli-reset-all-siblings;
      }
      leaf policy-id {
        tailf:cli-drop-node-name;
        type uint16;
      }
      leaf shared-queuing {
        tailf:cli-optional-in-sequence;
        type empty;
      }
      leaf enable-table-classification {
        type empty;
      }
    }
    uses sap-queue-override-grouping;
    leaf agg-shaper-rate {
      type union {
        type uint32;
        type enumeration {
          enum "max";
        }
      }
    }
    uses sap-policer-override-grouping-ingress;
    leaf policer-control-policy {
      type string;
    }
    leaf scheduler-policy {
      type string;
    }
    uses sap-scheduler-override-grouping;
    leaf vlan-translation {
      type union {
        type enumeration {
          enum "copy-outer";
        }
        type uint16;
      }
    }
    container aggregate-policer-rate {
      tailf:cli-compact-syntax;
      leaf rate {
        tailf:cli-drop-node-name;
        type uint32;
      }
      leaf burst {
        type union {
          type uint32;
          type enumeration {
            enum "default";
          }
        }
      }
    }
    container qtag-manipulation {
      tailf:cli-add-mode;
      leaf preserve {
        type empty;
      }
    }
  }

  grouping queue-ref-grouping {
    leaf queue-id {
      tailf:cli-drop-node-name;
      type uint8;
    }
    leaf group {
      type string;
    }
  }

  grouping policer-ref-grouping {
    leaf policer-id {
      tailf:cli-drop-node-name;
      type uint8;
    }
  }

  grouping policy-option-action-params-grouping {
    leaf add-paths-send-limit {
      type union {
        type uint32;
        type enumeration {
          enum "multipaths";
        }
      }
    }
    leaf admin-tag-policy {
      type string;
    }
    leaf advertise-label {
      type enumeration {
        enum "per-prefix";
        enum "pop";
      }
    }
    leaf bgp-leak {
      type empty;
    }
    container aigp-metric {
      tailf:cli-compact-syntax;
      leaf add {
        type empty;
      }
      leaf aigp-metric {
        tailf:cli-drop-node-name;
        type union {
          type uint32;
          type enumeration {
            enum "igp";
          }
          type string;
        }
      }
    }
    container as-path {
      tailf:cli-compact-syntax;
      tailf:cli-sequence-commands;
      leaf action {
        tailf:cli-drop-node-name;
        type enumeration {
          enum "add";
          enum "replace";
        }
      }
      leaf name {
        tailf:cli-drop-node-name;
        type string;
      }
    }
    container as-path-prepend {
      tailf:cli-compact-syntax;
      tailf:cli-sequence-commands;
      choice as-choice {
        leaf as-number {
          tailf:cli-drop-node-name;
          type uint32;
        }
        leaf most-recent {
          type empty;
        }
      }
      leaf repeat {
        tailf:cli-drop-node-name;
        type uint8;
      }
    }
    container community {
      choice comm {
        case add-remove {
          leaf-list add {
            tailf:cli-flat-list-syntax;
            type string;
          }
          leaf-list remove {
            tailf:cli-flat-list-syntax;
            type string;
          }
        }
        leaf-list replace {
          tailf:cli-flat-list-syntax;
          type string;
        }
      }
    }
    container damping {
      leaf name {
        tailf:cli-drop-node-name;
        type union {
          type enumeration {
            enum "none";
          }
          type string;
        }
      }
    }
    leaf local-preference {
      type union {
        type uint32;
        type string;
      }
    }
    container metric {
      tailf:cli-compact-syntax;
      tailf:cli-sequence-commands;
      leaf action {
        tailf:cli-drop-node-name;
        type enumeration {
          enum "add";
          enum "set";
          enum "subtract";
        }
      }
      leaf metric {
        tailf:cli-drop-node-name;
        type union {
          type enumeration {
            enum "igp";
          }
          type uint32;
        }
      }
    }
    container multicast-redirection {
      tailf:cli-compact-syntax;
      tailf:cli-sequence-commands {
        tailf:cli-reset-siblings;
      }
      leaf fwd-service {
        tailf:cli-optional-in-sequence;
        type uint32;
      }
      leaf ip-int-name {
        tailf:cli-drop-node-name;
        type string;
      }
    }
    choice next-hop-choice {
      leaf next-hop {
        type union {
          type inet:ipv4-address;
          type inet:ipv6-address;
          type enumeration {
            enum "peer-address";
          }
        }
      }
      leaf next-hop-self {
        type empty;
      }
    }
    leaf origin {
      type enumeration {
        enum "igp";
        enum "egp";
        enum "incomplete";
      }
    }
    leaf preference {
      type uint8;
    }
    leaf tag {
      type policy-options-tag;
    }
    leaf type {
      type union {
        type uint8;
        type string;
      }
    }
    container bgp-med {
      tailf:cli-compact-syntax;
      container set {
        leaf value {
          tailf:cli-drop-node-name;
          type string;
        }
      }
    }
    leaf sr-label-index {
      type union {
        type uint32;
        type string;
      }
    }
  }

  grouping policy-options-action-fc-grouping {
    container fc {
      tailf:cli-compact-syntax;
      tailf:cli-sequence-commands {
        tailf:cli-reset-all-siblings;
      }
      leaf fc {
        tailf:cli-drop-node-name;
        type fc-name;
      }
      leaf priority {
        type enumeration {
          enum "high";
          enum "low";
        }
      }
    }
  }

  grouping policy-options-default-action-grouping {
    choice action {
      leaf reject {
        type empty;
      }
      container drop {
        tailf:cli-add-mode;
        presence "true";
        uses policy-option-action-params-grouping;
      }
      container accept {
        tailf:cli-add-mode;
        presence "true";
        uses policy-option-action-params-grouping;
      }
      container next-entry {
        tailf:cli-add-mode;
        presence "true";
        uses policy-option-action-params-grouping;
      }
      container next-policy {
        tailf:cli-add-mode;
        presence "true";
        uses policy-option-action-params-grouping;
      }
    }
  }

  grouping policy-options-action-grouping {
    choice action {
      leaf reject {
        type empty;
      }
      container drop {
        tailf:cli-add-mode;
        presence "true";
        uses policy-option-action-params-grouping;
        uses policy-options-action-fc-grouping;
      }
      container accept {
        tailf:cli-add-mode;
        presence "true";
        uses policy-option-action-params-grouping;
        uses policy-options-action-fc-grouping;
      }
      container next-entry {
        tailf:cli-add-mode;
        presence "true";
        uses policy-option-action-params-grouping;
        uses policy-options-action-fc-grouping;
      }
      container next-policy {
        tailf:cli-add-mode;
        presence "true";
        uses policy-option-action-params-grouping;
        uses policy-options-action-fc-grouping;
      }
    }
  }

  grouping mbs-rate-grouping {
    leaf size {
      tailf:cli-drop-node-name;
      type union {
        type uint32;
        type enumeration {
          enum "default";
        }
      }
    }
    leaf unit {
      tailf:cli-drop-node-name;
      type enumeration {
        enum "bytes";
        enum "kilobytes";
      }
    }
  }

  grouping policer-cbs-mbs-rate-grouping {
    container cbs {
      tailf:cli-compact-syntax;
      tailf:cli-sequence-commands {
        tailf:cli-reset-siblings;
      }
      uses mbs-rate-grouping;
    }
    container mbs {
      tailf:cli-compact-syntax;
      tailf:cli-sequence-commands {
        tailf:cli-reset-siblings;
      }
      uses mbs-rate-grouping;
    }
    container rate {
      tailf:cli-compact-syntax;
      tailf:cli-sequence-commands {
        tailf:cli-reset-siblings;
      }
      leaf pir {
        tailf:cli-drop-node-name;
        type rate-type;
      }
      leaf cir {
        type rate-type;
      }
    }
    leaf stat-mode {
      type policer-stat-mode;
    }
  }

  grouping policer-cbs-mbs-rate-with-packet-offset-grouping {
    uses policer-cbs-mbs-rate-grouping;
    container packet-byte-offset {
      tailf:cli-compact-syntax;
      choice add-delete {
        leaf add {
          type uint8;
        }
        leaf subtract {
          type uint8;
        }
      }
    }
  }

  grouping policer-grouping {
    uses queue-adaptation-grouping;
    leaf adv-config-policy {
      type string;
    }
    uses policer-cbs-mbs-rate-with-packet-offset-grouping;
    leaf description {
      type string;
    }
    leaf high-prio-only {
      type union {
        type uint8;
        type enumeration {
          enum "default";
        }
      }
    }
    container parent {
      tailf:cli-compact-syntax;
      tailf:cli-sequence-commands {
        tailf:cli-reset-all-siblings;
      }
      leaf name {
        tailf:cli-drop-node-name;
        type union {
          type enumeration {
            enum "root";
          }
          type string;
        }
      }
      leaf level {
        tailf:cli-break-sequence-commands;
        type uint8;
      }
      leaf weight-level {
        tailf:alt-name "weight";
        type uint8;
      }
    }
    leaf profile-capped {
      type empty;
    }
  }

  grouping queue-grouping {
    leaf multipoint {
      tailf:cli-hide-in-submode;
      type empty;
    }
    leaf queue-type {
      tailf:cli-drop-node-name;
      tailf:cli-hide-in-submode;
      type queue-type;
    }
    leaf queue-mode-m {
      tailf:cli-drop-node-name;
      tailf:cli-hide-in-submode;
      type enumeration {
        enum "profile-mode";
        enum "priority-mode";
      }
    }
    uses queue-adaptation-grouping;
    leaf adv-config-policy {
      type string;
    }
    leaf avg-frame-overhead {
      type decimal64 {
        fraction-digits 2;
      }
    }
    container burst-limit {
      tailf:cli-compact-syntax;
      tailf:cli-sequence-commands;
      leaf size {
        tailf:cli-drop-node-name;
        type union {
          type uint32;
          type enumeration {
            enum "default";
          }
        }
      }
      leaf unit {
        tailf:cli-drop-node-name;
        type enumeration {
          enum "bytes";
          enum "kilobytes";
        }
      }
    }
    leaf cbs {
      type union {
        type uint32;
        type enumeration {
          enum "default";
        }
      }
    }
    leaf high-prio-only {
      type union {
        type uint8;
      }
    }
    container mbs {
      tailf:cli-compact-syntax;
      tailf:cli-sequence-commands {
        tailf:cli-reset-siblings;
      }
      leaf size {
        tailf:cli-drop-node-name;
        type union {
          type uint32;
          type enumeration {
            enum "default";
          }
        }
      }
      leaf unit {
        tailf:cli-drop-node-name;
        type enumeration {
          enum "bytes";
          enum "kilobytes";
        }
      }
    }
    container parent {
      tailf:cli-compact-syntax;
      tailf:cli-sequence-commands {
        tailf:cli-reset-all-siblings;
      }
      leaf name {
        tailf:cli-drop-node-name;
        type string;
      }
      leaf level {
        tailf:cli-break-sequence-commands;
        type uint8;
      }
      leaf weight {
        type uint8;
      }
      leaf cir-level {
        type uint8;
      }
      leaf cir-weight {
        type uint8;
      }
    }
    container percent-rate {
      tailf:cli-compact-syntax;
      tailf:cli-sequence-commands {
        tailf:cli-reset-all-siblings;
      }
      leaf pir-percent {
        tailf:cli-drop-node-name;
        type decimal64 {
          fraction-digits 2;
        }
      }
      leaf cir {
        tailf:cli-optional-in-sequence;
        type decimal64 {
          fraction-digits 2;
        }
      }
    }
    leaf pool {
      type string;
    }
    uses port-parent-grouping;
    uses queue-rate-grouping;
    leaf slope-policy {
      type string;
    }
    container wred-queue {
      tailf:cli-compact-syntax;
      tailf:cli-sequence-commands {
        tailf:cli-reset-siblings;
      }
      leaf policy {
        tailf:cli-optional-in-sequence;
        type string;
      }
      leaf mode {
        tailf:cli-optional-in-sequence;
        type enumeration {
          enum "native";
          enum "pool-per-queue";
        }
      }
      leaf slope-usage {
        tailf:cli-optional-in-sequence;
        type enumeration {
          enum "default";
          enum "exceed-low";
        }
      }
    }
    container xp-specific {
      tailf:cli-add-mode;
      container wred-queue {
        tailf:cli-compact-syntax;
        tailf:cli-sequence-commands;
        leaf policy {
          type string;
        }
      }
      uses packet-byte-offset-grouping;
    }
    container drop-tail {
      tailf:cli-add-mode;
      container low {
        tailf:cli-add-mode;
        leaf percent-reduction-from-mbs {
          type union {
            type uint8;
            type enumeration {
              enum "default";
            }
          }
        }
      }
    }
  }

  grouping queue-group-template-entry {
    leaf queue-group-name {
      type string;
    }
    leaf description {
      type string;
    }
    list fc {
      key "fc-name";
      leaf fc-name {
        type fc-name;
      }
      leaf queue {
        type uint8;
      }
    }
    list policer {
      key "policer-id";
      leaf policer-id {
        type uint8;
      }
      uses policer-grouping;
    }
    list queue {
      key "queue-id";
      leaf queue-id {
        type uint8;
      }
      uses queue-grouping;
    }
  }

  grouping dhcp-lease-time {
    leaf days {
      type uint16;
    }
    leaf hrs {
      type uint16;
    }
    leaf min {
      type uint16;
    }
    leaf sec {
      type uint16;
    }
  }

  grouping bfd-grouping {
    leaf transmit-interval {
      tailf:cli-drop-node-name;
      type uint32;
    }
    leaf receive {
      type uint32;
    }
    leaf multiplier {
      type uint8;
    }
    leaf echo-receive {
      type uint32;
    }
    leaf type {
      type enumeration {
        enum "cpm-np";
        enum "iom-hw";
        enum "np";
        enum "fp";
      }
    }
  }

  grouping dhcp6-grouping {
    container dhcp6-server {
      tailf:cli-add-mode;
      leaf max-nbr-of-leases {
        type uint32;
      }
    }
    container dhcp6-relay {
      tailf:cli-add-mode;
      leaf description {
        type string;
      }
      container lease-populate {
        presence "present";
        tailf:cli-sequence-commands;
        tailf:cli-compact-syntax;
        leaf nbr-of-leases {
          tailf:cli-drop-node-name;
          type uint32;
        }
        leaf route-populate {
          type empty;
        }
        leaf pd {
          type empty;
        }
        leaf exclude {
          tailf:cli-break-sequence-commands;
          type empty;
        }
        leaf na {
          type empty;
        }
        leaf ta {
          type empty;
        }
      }
      leaf neighbor-resolution {
        type empty;
      }
      container option {
        tailf:cli-add-mode;
        container interface-id {
          choice choice {
            leaf sap-id {
              type empty;
            }
            leaf ifindex {
              type empty;
            }
            leaf string {
              type string;
            }
          }
        }
        leaf remote-id {
          type empty;
        }
      }
      leaf source-address {
        tailf:cli-case-insensitive;
        type inet:ipv6-address;
      }
      leaf link-address {
        type inet:ipv6-address;
      }
      leaf-list server {
        tailf:cli-flat-list-syntax;
        type inet:ipv6-address;
      }
      leaf shutdown {
        type boolean;
      }
    }
  }

  grouping ipv6-grouping {
    list address {
      tailf:cli-suppress-mode;
      tailf:cli-compact-syntax;
      key "addr";
      leaf addr {
        type tailf:ipv6-address-and-prefix-length;
      }
      leaf eui-64 {
        type empty;
      }
      leaf preferred {
        type empty;
      }
      leaf track-srrp {
        type uint32;
      }
      leaf modifier {
        type string;
      }
      leaf dad-disable {
        type empty;
      }
    }

    typedef nd-type {
      type enumeration {
        enum "both";
        enum "link-local";
        enum "global";
      }
    }
    leaf nd-learn-unsolicited {
      type nd-type;
    }
    leaf nd-proactive-refresh {
      type nd-type;
    }
    container bfd {
      tailf:cli-compact-syntax;
      uses bfd-grouping;
    }
    leaf dad-disable {
      type empty;
    }
    container icmp6 {
      tailf:cli-add-mode;
      container packet-too-big {
        tailf:cli-compact-syntax;
        tailf:cli-sequence-commands {
          tailf:cli-reset-all-siblings;
        }
        uses icmp-params-grouping;
      }
      container param-problem {
        tailf:cli-compact-syntax;
        tailf:cli-sequence-commands {
          tailf:cli-reset-all-siblings;
        }
        uses icmp-params-grouping;
      }
      container redirects {
        tailf:cli-compact-syntax;
        tailf:cli-sequence-commands {
          tailf:cli-reset-all-siblings;
        }
        uses icmp-params-grouping;
      }
      container time-exceeded {
        tailf:cli-compact-syntax;
        tailf:cli-sequence-commands {
          tailf:cli-reset-all-siblings;
        }
        uses icmp-params-grouping;
      }
      container unreachables {
        tailf:cli-compact-syntax;
        tailf:cli-sequence-commands {
          tailf:cli-reset-all-siblings;
        }
        uses icmp-params-grouping;
      }
    }
    container link-local-address {
      tailf:cli-compact-syntax;
      tailf:cli-sequence-commands {
        tailf:cli-reset-all-siblings;
      }
      leaf addr {
        tailf:cli-drop-node-name;
        type union {
          type inet:ipv6-address;
          type tailf:ipv6-address-and-prefix-length;
        }
      }
      leaf preferred {
        tailf:cli-optional-in-sequence;
        type empty;
      }
      leaf dad-disable {
        type empty;
      }
    }
    leaf local-proxy-nd {
      type empty;
    }
    container neighbor {
      tailf:cli-compact-syntax;
      tailf:cli-sequence-commands {
        tailf:cli-reset-all-siblings;
      }
      leaf addr {
        tailf:cli-drop-node-name;
        type union {
          type inet:ipv6-address;
          type tailf:ipv6-address-and-prefix-length;
        }
      }
      leaf mac-addr {
        tailf:cli-drop-node-name;
        type ieee-mac;
      }
    }
    container proxy-nd-policy {
      tailf:cli-compact-syntax;
      leaf name1 {
        tailf:cli-drop-node-name;
        type string;
      }
      leaf name2 {
        tailf:cli-drop-node-name;
        type string;
      }
      leaf name3 {
        tailf:cli-drop-node-name;
        type string;
      }
      leaf name4 {
        tailf:cli-drop-node-name;
        type string;
      }
      leaf name5 {
        tailf:cli-drop-node-name;
        type string;
      }
    }
    leaf qos-route-lookup {
      type enumeration {
        enum "source";
        enum "destination";
      }
    }
    leaf reachable-time {
      type uint32;
    }
    container secure-nd {
      tailf:cli-add-mode;
      leaf allow-unsecured-msgs {
        type boolean;
      }
      leaf link-local-modifier {
        type string;
      }
      leaf public-key-min-bits {
        type uint32;
      }
      leaf security-parameter {
        type uint32;
      }
      leaf shutdown {
        type boolean;
      }
    }
    leaf tcp-mss {
      type uint32;
    }
    container urpf-check {
      tailf:cli-add-mode;
      presence "true";
      leaf ignore-default {
        type empty;
      }
      leaf mode {
        type enumeration {
          enum "strict";
          enum "loose";
          enum "strict-no-ecmp";
        }
      }
    }
    list vrrp {
      key "id";
      leaf id {
        type uint32;
      }
      leaf owner {
        tailf:cli-hide-in-submode;
        type empty;
      }
      leaf passive {
        tailf:cli-hide-in-submode;
        type empty;
      }
      list backup {
        tailf:cli-suppress-mode;
        key "addr";
        leaf addr {
          type inet:ipv6-address;
        }
      }
      leaf init-delay {
        type uint32;
      }
      leaf mac {
        type ieee-mac;
      }
      leaf master-int-inherit {
        type boolean;
      }
      container message-interval {
        tailf:cli-compact-syntax;
        tailf:cli-sequence-commands;
        leaf seconds {
          tailf:cli-drop-node-name;
          tailf:cli-optional-in-sequence;
          type uint32;
        }
        leaf milliseconds {
          type uint32;
        }
      }
      leaf ping-reply {
        type empty;
      }
      leaf policy {
        type uint16;
      }
      leaf preempt {
        type boolean;
      }
      leaf priority {
        type uint32;
      }
      leaf standby-forwarding {
        type empty;
      }
      leaf telnet-reply {
        type empty;
      }
      leaf traceroute-reply {
        type empty;
      }
      leaf shutdown {
        type boolean;
      }
    }
  }

  grouping icmp-params-grouping {
    choice icmp-params-choice {
      leaf disable {
        type empty;
      }
      case enable {
        leaf number {
          tailf:cli-drop-node-name;
          type uint16;
        }
        leaf seconds {
          tailf:cli-drop-node-name;
          type uint8;
        }
      }
    }
  }

  grouping interface-icmp-grouping {
    container icmp {
      tailf:cli-add-mode;
      leaf mask-reply {
        type boolean;
      }
      container redirects {
        tailf:cli-compact-syntax;
        tailf:cli-sequence-commands {
          tailf:cli-reset-siblings;
        }
        uses icmp-params-grouping;
      }
      container ttl-expired {
        tailf:cli-compact-syntax;
        tailf:cli-sequence-commands {
          tailf:cli-reset-siblings;
        }
        uses icmp-params-grouping;
      }
      container unreachables {
        tailf:cli-compact-syntax;
        tailf:cli-sequence-commands {
          tailf:cli-reset-siblings;
        }
        uses icmp-params-grouping;
      }
    }
  }

  grouping subscriber-interface-dhcp-common-grouping {
    container proxy-server {
      tailf:cli-add-mode;
      leaf emulated-server {
        type inet:ip-address;
      }
      container lease-time {
        tailf:cli-compact-syntax;
        leaf days {
          type uint16;
        }
        leaf hrs {
          type uint16;
        }
        leaf min {
          type uint16;
        }
        leaf sec {
          type uint16;
        }
      }
      leaf shutdown {
        type boolean;
      }
    }
    leaf-list server {
      tailf:cli-flat-list-syntax;
      type inet:ipv4-address;
    }
    container gi-address {
      tailf:cli-compact-syntax;
      tailf:cli-sequence-commands {
        tailf:cli-reset-siblings;
      }
      leaf address {
        tailf:cli-drop-node-name;
        type inet:ipv4-address;
      }
      leaf src-ip-addr {
        type empty;
      }
    }
  }

  grouping dhcp-option-grouping {
    container option {
      tailf:cli-add-mode;
      leaf action {
        type enumeration {
          enum "replace";
          enum "drop";
          enum "keep";
        }
      }
      container remote-id {
        presence "true";
        choice remote-id {
          leaf mac {
            tailf:cli-drop-node-name;
            type string;
          }
          leaf string {
            type string;
          }
        }
      }
      container vendor-specific-option {
        tailf:cli-add-mode;
        leaf client-mac-address {
          type empty;
        }
        leaf pool-name {
          type empty;
        }
        leaf service-id {
          type empty;
        }
        leaf string {
          type string;
        }
      }
    }
  }

  grouping subscriber-interface-grouping {
    leaf id {
      type string;
    }
    leaf fwd-service {
      tailf:cli-hide-in-submode;
      type service-id;
    }
    leaf wan-mode {
      tailf:cli-hide-in-submode;
      type enumeration {
        enum "mode64";
        enum "mode128";
      }
    }
    leaf fwd-subscriber-interface {
      tailf:cli-hide-in-submode;
      type string;
    }
    leaf description {
      type string;
    }
    leaf allow-unmatching-subnets {
      type empty;
    }
    list address {
      tailf:cli-suppress-mode;
      tailf:cli-compact-syntax;
      tailf:cli-sequence-commands {
        tailf:cli-reset-siblings;
      }
      key "ip-address";
      leaf ip-address {
        type tailf:ipv4-address-and-prefix-length;
      }
      leaf gw-ip-address {
        tailf:cli-optional-in-sequence;
        type inet:ipv4-address;
      }
      leaf populate-host-routes {
        tailf:cli-optional-in-sequence;
        type empty;
      }
      leaf track-srrp {
        tailf:cli-optional-in-sequence;
        type uint32;
      }
    }

    grouping ipoe-linking-grouping {
      container ipoe-linking {
        tailf:cli-add-mode;
        leaf gratuitous-rtr-adv {
          type empty;
        }
        leaf shared-circuit-id {
          type empty;
        }
        leaf shutdown {
          type boolean;
        }
      }
    }
    uses ipoe-linking-grouping;
    list group-interface {
      key "id";
      leaf id {
        type string;
      }
      leaf oper-up-while-empty {
        type empty;
      }
      uses ipoe-linking-grouping;
      leaf shcv-policy {
        type string;
      }
      leaf shcv-policy-ipv4 {
        type string;
      }
      leaf shcv-policy-ipv6 {
        type string;
      }
      container data-trigger {
        tailf:cli-add-mode;
        leaf shutdown {
          type boolean;
        }
      }
      leaf description {
        type string;
      }
      uses interface-icmp-grouping;
      leaf remote-proxy-arp {
        type empty;
      }
      container ipv6 {
        tailf:cli-add-mode;
        leaf allow-multiple-wan-addresses {
          type empty;
        }
        container router-advertisements {
          tailf:cli-add-mode;
          container dns-options {
            tailf:cli-add-mode;
            leaf include-dns {
              type empty;
            }
            leaf rdnss-lifetime {
              type uint32;
            }
          }
          leaf managed-configuration {
            type empty;
          }
          leaf retransmit-time {
            type uint32;
          }
          leaf max-advertisement {
            type uint32;
          }
          leaf current-hop-limit {
            type uint32;
          }
          leaf mtu {
            type uint32;
          }
          leaf reachable-time {
            type uint32;
          }
          leaf other-stateful-configuration {
            type empty;
          }
          leaf router-lifetime {
            type uint32;
          }
          container prefix-options {
            tailf:cli-add-mode;
            leaf autonomous {
              type empty;
            }
            leaf on-link {
              type boolean;
            }
            leaf preferred-lifetime {
              type union {
                type uint32;
                type enumeration {
                  enum "infinite";
                }
              }
            }
            leaf valid-lifetime {
              type union {
                type uint32;
                type enumeration {
                  enum "infinite";
                }
              }
            }
          }
          leaf shutdown {
            type boolean;
          }
        }
        container auto-reply {
          tailf:cli-add-mode;
          leaf neighbor-solicitation {
            type empty;
          }
          leaf router-solicitation {
            type empty;
          }
        }
        container urpf-check {
          tailf:cli-add-mode;
          presence "true";
          leaf mode {
            type enumeration {
              enum "strict";
              enum "loose";
              enum "strict-no-ecmp";
            }
          }
        }
        container dhcp6 {
          tailf:cli-add-mode;
          leaf user-db {
            type string;
          }
          leaf user-ident {
            type enumeration {
              enum "mac";
              enum "mac-interface-id";
            }
          }
          container relay {
            tailf:cli-add-mode;
            leaf description {
              type string;
            }
            leaf link-address {
              type inet:ipv6-address;
            }
            list server {
              tailf:cli-suppress-mode;
              key "ip";
              leaf ip {
                type inet:ipv6-address;
              }
            }
            leaf source-address {
              type inet:ipv6-address;
            }
            leaf shutdown {
              type boolean;
            }
          }
          container proxy-server {
            tailf:cli-add-mode;
            container lease-time {
              tailf:cli-compact-syntax;
              leaf days {
                type uint16;
              }
              leaf hrs {
                type uint16;
              }
              leaf min {
                type uint16;
              }
              leaf sec {
                type uint16;
              }
            }
            uses dhcp6-lease-timers-grouping;
            leaf shutdown {
              type boolean;
            }
          }
          leaf python-policy {
            type string32;
          }
          container option {
            tailf:cli-add-mode;
            container interface-id {
              tailf:cli-compact-syntax;
              leaf type {
                tailf:cli-drop-node-name;
                type enumeration {
                  enum "ascii-tuple";
                  enum "ifindex";
                  enum "sap-id";
                  enum "string";
                }
              }
              leaf stringval {
                tailf:cli-drop-node-name;
                type string;
              }
            }
            leaf remote-id {
              type empty;
            }
          }
        }
      }
      leaf arp-populate {
        type empty;
      }
      leaf authentication-policy {
        type string;
      }
      leaf redundant-interface {
        type string;
      }
      leaf srrp-enabled-routing {
        type empty;
      }
      leaf enable-ingress-stats {
        type empty;
      }
      leaf ip-mtu {
        type uint16;
      }
      leaf tos-marking-state {
        type enumeration {
          enum "trusted";
          enum "untrusted";
        }
      }
      container host-connectivity-verify {
        tailf:cli-compact-syntax;
        leaf interval {
          type uint16;
        }
        leaf action {
          type enumeration {
            enum "remove";
            enum "alarm";
          }
        }
        leaf timeout {
          type uint8;
        }
        leaf retry-count {
          type uint8;
        }
        leaf family {
          type enumeration {
            enum "ipv4";
            enum "ipv6";
            enum "both";
          }
        }
      }
      container dhcp {
        tailf:cli-add-mode;
        leaf description {
          type string;
        }
        leaf trusted {
          type empty;
        }
        container lease-populate {
          tailf:cli-compact-syntax;
          leaf nr-of-leases {
            tailf:cli-drop-node-name;
            type uint32;
          }
          leaf l2-header {
            type empty;
          }
          leaf mac {
            type string;
          }
        }
        container relay-proxy {
          tailf:cli-compact-syntax;
          tailf:cli-sequence-commands {
            tailf:cli-reset-siblings;
          }
          presence "true";
          leaf release-update-src-ip {
            tailf:cli-optional-in-sequence;
            type empty;
          }
          leaf siaddr-override {
            type inet:ipv4-address;
          }
        }
        leaf python-policy {
          type string32;
        }
        uses dhcp-option-grouping {
          augment "option" {
            container circuit-id {
              presence "true";
              leaf id {
                tailf:cli-drop-node-name;
                type enumeration {
                  enum "ascii-tuple";
                  enum "ifindex";
                  enum "sap-id";
                  enum "vlan-ascii-tuple";
                  enum "if-name";
                  enum "port-id";
                  enum "none";
                }
              }
            }
          }
          augment "option/vendor-specific-option" {
            leaf sap-id {
              type empty;
            }
          }
        }
        leaf user-db {
          type string;
        }
        leaf-list client-applications {
          tailf:cli-flat-list-syntax;
          type enumeration {
            enum "ppp";
            enum "dhcp";
          }
        }
        uses subscriber-interface-dhcp-common-grouping {
          augment "proxy-server/lease-time" {
            leaf override {
              type empty;
            }
          }
        }
      }
      list sap {
        key "id";
        leaf id {
          type string;
        }
        leaf host-lockout-policy {
          type string32;
        }
        container egress {
          tailf:cli-add-mode;
          container filter {
            leaf ip {
              type filter-id;
            }
            leaf ipv6 {
              type filter-id;
            }
          }
          leaf qos {
            type uint16;
          }
        }
        container ingress {
          tailf:cli-add-mode;
          container filter {
            leaf ip {
              type filter-id;
            }
            leaf ipv6 {
              type filter-id;
            }
          }
          leaf qos {
            type uint16;
          }
        }
        leaf description {
          type string;
        }
        leaf anti-spoof {
          type enumeration {
            enum "ip";
            enum "ip-mac";
            enum "nh-mac";
          }
        }
        container sub-sla-mgmt {
          tailf:cli-add-mode;
          container def-sub-id {
            choice sub-id-choice {
              leaf string {
                type string;
              }
              leaf use-auto-id {
                type empty;
              }
              leaf use-sap-id {
                type empty;
              }
            }
          }
          container def-inter-dest-id {
            choice dest-id-choice {
              leaf string {
                type string;
              }
              leaf use-top-q {
                type empty;
              }
              leaf use-vpi {
                type empty;
              }
            }
          }
          leaf def-sub-profile {
            type string;
          }
          leaf def-sla-profile {
            type string;
          }
          leaf sub-ident-policy {
            type string;
          }
          container single-sub-parameters {
            tailf:cli-add-mode;
            leaf profiled-traffic-only {
              type empty;
            }
          }
          container multi-sub-sap {
            presence "true";
            leaf subscriber-limit {
              tailf:cli-drop-node-name;
              type uint32;
            }
          }
          leaf shutdown {
            type boolean;
          }
        }
        leaf calling-station-id {
          type string;
        }
        leaf monitor-oper-group {
          type string;
        }
        leaf shutdown {
          type boolean;
        }
      }
      container urpf-check {
        tailf:cli-add-mode;
        leaf mode {
          type enumeration {
            enum "strict";
            enum "loose";
            enum "strict-no-ecmp";
          }
        }
      }
      container ipoe-session {
        tailf:cli-add-mode;
        container force-auth {
          tailf:cli-compact-syntax;
          choice force-auth {
            leaf disabled {
              type empty;
            }
            case cid-rid {
              leaf cid-change {
                type empty;
              }
              leaf rid-change {
                type empty;
              }
            }
          }
        }
        leaf sap-session-limit {
          type uint32;
        }
        leaf session-limit {
          type uint32;
        }
        container min-auth-interval {
          tailf:cli-compact-syntax;
          tailf:cli-sequence-commands {
            tailf:cli-reset-siblings;
          }
          choice interval {
            leaf infinite {
              tailf:cli-optional-in-sequence;
              tailf:cli-drop-node-name;
              type enumeration {
                enum "infinite";
              }
            }
            case time {
              leaf days {
                tailf:cli-optional-in-sequence;
                type uint16;
              }
              leaf hrs {
                tailf:cli-optional-in-sequence;
                type uint8;
              }
              leaf min {
                tailf:cli-optional-in-sequence;
                type uint8;
              }
              leaf sec {
                tailf:cli-optional-in-sequence;
                type uint8;
              }
            }
          }
        }
        uses ipoe-session-grouping;
      }
      container pppoe {
        tailf:cli-add-mode;
        leaf description {
          type string;
        }
        leaf policy {
          type string32;
        }
        leaf sap-session-limit {
          type uint32;
        }
        leaf session-limit {
          type uint16;
        }
        leaf user-db {
          type string;
        }
        leaf shutdown {
          type boolean;
        }
      }
      list srrp {
        key "srrp-id";
        leaf srrp-id {
          type uint32;
        }
        leaf description {
          type string;
        }
        leaf keep-alive-interval {
          type uint8;
        }
        leaf message-path {
          type string;
        }
        list policy {
          tailf:cli-suppress-mode;
          key "vrrp-policy-id";
          leaf vrrp-policy-id {
            type uint16;
          }
        }
        leaf priority {
          type uint8;
        }
        leaf shutdown {
          type boolean;
        }
      }
      leaf shutdown {
        type boolean;
      }
    }
    container pppoe {
      tailf:cli-add-mode;
      leaf description {
        type string;
      }
      leaf session-limit {
        type uint16;
      }
    }
    leaf private-retail-subnets {
      type empty;
    }
    leaf unnumbered {
      type string;
    }
  }

  grouping nat-pool-grouping {
    container nat {
      tailf:cli-add-mode;
      container inside {
        tailf:cli-add-mode;
        container l2-aware {
          tailf:cli-add-mode;
          list address {
            tailf:cli-suppress-mode;
            key "ip-addr";
            leaf ip-addr {
              type tailf:ipv4-address-and-prefix-length;
            }
          }
        }
        leaf nat-policy {
          type string;
        }
        leaf destination-prefix {
          type tailf:ipv4-address-and-prefix-length;
        }
      }
      container outside {
        tailf:cli-add-mode;
        list pool {
          key "name";
          leaf name {
            type string;
          }
          leaf nat-group {
            tailf:cli-hide-in-submode;
            type uint16;
          }
          leaf type {
            tailf:cli-hide-in-submode;
            type enumeration {
              enum "l2-aware";
              enum "large-scale";
            }
          }
          container port-reservation {
            tailf:cli-compact-syntax;
            leaf blocks {
              type uint16;
            }
            leaf ports {
              type uint16;
            }
          }
          leaf port-forwarding-range {
            type uint16;
          }
          leaf subscriber-limit {
            type uint16;
          }
          container watermarks {
            tailf:cli-compact-syntax;
            leaf high {
              type uint8;
            }
            leaf low {
              type uint8;
            }
          }
          list address-range {
            key "start-ip-address end-ip-address";
            leaf start-ip-address {
              type inet:ipv4-address;
            }
            leaf end-ip-address {
              type inet:ipv4-address;
            }
          }
          leaf shutdown {
            type boolean;
          }
        }
      }
    }
  }

  grouping static-route-extras-grouping {
    leaf preference {
      tailf:cli-break-sequence-commands;
      type uint8;
    }
    leaf metric {
      type uint16;
    }
    choice ed {
      leaf enable {
        type empty;
      }
      leaf disable {
        type empty;
      }
    }
    leaf tag {
      type uint32;
    }
    leaf community {
      type union {
        type enumeration {
          enum "no-export";
          enum "no-export-subconfed";
          enum "no-advertise";
        }
        type string;
      }
    }
    leaf description {
      type string;
    }
    leaf mcast-family {
      tailf:cli-drop-node-name;
      type enumeration {
        enum "mcast-ipv4";
        enum "mcast-ipv6";
      }
    }
    leaf bfd-enable {
      type empty;
    }
    leaf cpe-check {
      type inet:ipv4-address;
    }
    leaf interval {
      type uint8;
    }
    leaf drop-count {
      type uint8;
    }
    leaf log {
      type empty;
    }
    leaf prefix-list {
      type string;
    }
    choice an {
      leaf all {
        type empty;
      }
      leaf none {
        type empty;
      }
    }
    leaf ldp-sync {
      type empty;
    }
    leaf fc {
      type fc-name;
    }
    leaf priority {
      type enumeration {
        enum "high";
        enum "low";
      }
    }
  }

  grouping prompted-authentication-key-grouping {
    container authentication-key {
      tailf:cli-compact-syntax;
      tailf:cli-sequence-commands {
        tailf:cli-reset-all-siblings;
      }
      leaf key {
        tailf:cli-drop-node-name;
        type string;
      }
      leaf method {
        tailf:cli-drop-node-name;
        type hash-method;
      }
    }
  }

  grouping prompted-hello-authentication-key-grouping {
    container hello-authentication-key {
      tailf:cli-compact-syntax;
      tailf:cli-sequence-commands {
        tailf:cli-reset-all-siblings;
      }
      leaf key {
        tailf:cli-drop-node-name;
        type string;
      }
      leaf method {
        tailf:cli-drop-node-name;
        type hash-method;
      }
    }
    leaf hello-auth-keychain {
      type string;
    }
  }

  grouping bgp-import-export-grouping {
    leaf-list export {
      tailf:cli-flat-list-syntax;
      ordered-by user;
      type string;
    }
    leaf-list import {
      tailf:cli-flat-list-syntax;
      ordered-by user;
      type string;
    }
  }

  grouping max-paths-grouping {
    leaf max-paths {
      tailf:cli-drop-node-name;
      tailf:cli-break-sequence-commands;
      type uint8;
    }
    leaf ebgp {
      type uint8;
    }
    leaf ibgp {
      type uint8;
    }
    leaf restrict {
      type enumeration {
        enum "same-neighbor-as";
        enum "exact-as-path";
      }
    }
  }

  grouping bgp-multipath-grouping {
    container multipath {
      tailf:cli-compact-syntax;
      tailf:cli-sequence-commands {
        tailf:cli-reset-all-siblings;
      }
      uses max-paths-grouping;
    }
  }

  grouping max-paths-uneqcosts-grouping {
    uses max-paths-grouping;
    leaf unequal-cost {
      type empty;
    }
  }

  grouping bgp-multi-path-grouping {
    container multi-path {
      tailf:cli-add-mode;
      container ipv4 {
        tailf:cli-sequence-commands {
          tailf:cli-reset-all-siblings;
        }
        tailf:cli-compact-syntax;
        uses max-paths-uneqcosts-grouping;
      }
      container ipv6 {
        tailf:cli-sequence-commands {
          tailf:cli-reset-all-siblings;
        }
        tailf:cli-compact-syntax;
        uses max-paths-uneqcosts-grouping;
      }
      container label-ipv4 {
        tailf:cli-sequence-commands {
          tailf:cli-reset-all-siblings;
        }
        tailf:cli-compact-syntax;
        uses max-paths-uneqcosts-grouping;
      }
      container maximum-paths {
        tailf:cli-sequence-commands {
          tailf:cli-reset-all-siblings;
        }
        tailf:cli-compact-syntax;
        uses max-paths-uneqcosts-grouping;
      }
    }
  }

  grouping bgp-graceful-restart-grouping {
    container graceful-restart {
      tailf:cli-add-mode;
      presence "true";
      leaf enable-notification {
        type empty;
      }
      container long-lived {
        tailf:cli-add-mode;
        presence "true";

        grouping bgp-graceful-override-times-grouping {
          leaf advertised-stale-time {
            type uint32;
          }
          leaf helper-override-stale-time {
            type uint32;
          }
        }
        container advertise-stale-to-all-neighbors {
          tailf:cli-compact-syntax;
          presence "true";
          leaf without-no-export {
            type empty;
          }
        }
        uses bgp-graceful-override-times-grouping;
        list family {
          key "family";
          leaf family {
            type family-names-type;
          }
          uses bgp-graceful-override-times-grouping;
        }
        leaf forwarding-bits-set {
          type enumeration {
            enum "all";
            enum "non-fwd";
          }
        }
        leaf helper-override-restart-time {
          type uint16;
        }
      }
      leaf restart-time {
        type uint16;
      }
      leaf stale-routes-time {
        type uint16;
      }
    }
  }

  grouping bgp-prefix-limit-grouping {
    container prefix-limit {
      tailf:cli-compact-syntax;
      choice apis {
        list new {
          tailf:cli-drop-node-name;
          tailf:cli-suppress-mode;
          tailf:cli-compact-syntax;
          tailf:cli-sequence-commands {
            tailf:cli-reset-all-siblings;
          }
          key "family";
          leaf family {
            type enumeration {
              enum "ipv4";
              enum "vpn-ipv4";
              enum "ipv6";
              enum "vpn-ipv6";
              enum "mcast-ipv4";
              enum "l2-vpn";
              enum "mvpn-ipv4";
              enum "mdt-safi";
              enum "ms-pw";
              enum "flow-ipv4";
              enum "route-target";
              enum "mcast-vpn-ipv4";
              enum "mvpn-ipv6";
              enum "flow-ipv6";
              enum "evpn";
              enum "mcast-ipv6";
              enum "label-ipv4";
              enum "label-ipv6";
            }
          }
          leaf limit {
            tailf:cli-drop-node-name;
            type uint32;
          }
          leaf log-only {
            tailf:cli-break-sequence-commands;
            type empty;
          }
          leaf threshold {
            type uint8;
          }
          leaf idle-timeout {
            type union {
              type uint16;
              type enumeration {
                enum "forever";
              }
            }
          }
          leaf post-import {
            type empty;
          }
        }
        container old {
          tailf:cli-drop-node-name;
          tailf:cli-compact-syntax;
          tailf:cli-sequence-commands {
            tailf:cli-reset-siblings;
          }
          leaf limit {
            tailf:cli-drop-node-name;
            type uint32;
          }
          leaf log-only {
            tailf:cli-break-sequence-commands;
            tailf:cli-optional-in-sequence;
            type empty;
          }
          leaf threshold {
            tailf:cli-optional-in-sequence;
            type uint8;
          }
          leaf idle-timeout {
            type union {
              type uint16;
              type enumeration {
                enum "forever";
              }
            }
          }
        }
      }
    }
  }

  grouping router-bgp-add-paths-grouping {
    container add-paths {
      tailf:cli-add-mode;

      grouping path-proto-send-receive-grouping {
        leaf send {
          type union {
            type uint8;
            type enumeration {
              enum "none";
            }
          }
        }
        leaf receive {
          type empty;
        }
        leaf none {
          type empty;
        }
      }
      container ipv4 {
        tailf:cli-compact-syntax;
        tailf:cli-sequence-commands {
          tailf:cli-reset-all-siblings;
        }
        uses path-proto-send-receive-grouping;
      }
      container ipv6 {
        tailf:cli-compact-syntax;
        tailf:cli-sequence-commands;
        uses path-proto-send-receive-grouping;
      }
      container label-ipv4 {
        tailf:cli-compact-syntax;
        tailf:cli-sequence-commands;
        uses path-proto-send-receive-grouping;
      }
      container label-ipv6 {
        tailf:cli-compact-syntax;
        tailf:cli-sequence-commands;
        uses path-proto-send-receive-grouping;
      }
      container vpn-ipv4 {
        tailf:cli-compact-syntax;
        tailf:cli-sequence-commands;
        uses path-proto-send-receive-grouping;
      }
      container vpn-ipv6 {
        tailf:cli-compact-syntax;
        tailf:cli-sequence-commands;
        uses path-proto-send-receive-grouping;
      }
    }
  }

  grouping router-bgp-grouping {
    uses router-bgp-add-paths-grouping;
    leaf advertise-inactive {
      type empty;
    }
    leaf-list advertise-ipv6-next-hops {
      tailf:cli-flat-list-syntax;
      type enumeration {
        enum "vpn-ipv6";
        enum "label-ipv6";
        enum "evpn";
        enum "vpn-ipv4";
        enum "label-ipv4";
        enum "ipv4";
      }
    }
    leaf loop-detect-threshold {
      type uint32;
    }
    leaf def-recv-evpn-encap {
      type enumeration {
        enum "mpls";
        enum "vxlan";
      }
    }
    container cluster {
      tailf:cli-compact-syntax;
      tailf:cli-sequence-commands;
      leaf cluster-id {
        tailf:cli-drop-node-name;
        type inet:ipv4-address;
      }
      leaf orr-location {
        tailf:cli-optional-in-sequence;
        type uint32;
      }
      leaf allow-local-fallback {
        tailf:cli-optional-in-sequence;
        type empty;
      }
    }
    leaf aggregator-id-zero {
      type empty;
    }
    leaf aigp {
      type empty;
    }
    leaf auth-keychain {
      type string;
    }
    uses prompted-authentication-key-grouping;
    leaf bfd-enable {
      type empty;
    }
    leaf connect-retry {
      type uint16;
    }
    leaf damping {
      type empty;
    }
    leaf default-route-target {
      type empty;
    }
    leaf description {
      type string;
    }
    leaf disable-4byte-asn {
      type empty;
    }
    leaf disable-capability-negotiation {
      type empty;
    }
    leaf disable-client-reflect {
      type empty;
    }
    leaf-list disable-communities {
      tailf:cli-flat-list-syntax;
      type enumeration {
        enum "standard";
        enum "extended";
      }
    }
    leaf disable-fast-external-failover {
      type empty;
    }
    leaf enable-peer-tracking {
      type empty;
    }
    leaf-list family {
      tailf:cli-flat-list-syntax;
      type family-names-type;
    }
    leaf flowspec-validate {
      type empty;
    }
    uses bgp-graceful-restart-grouping;
    container hold-time {
      tailf:cli-compact-syntax;
      leaf seconds {
        tailf:cli-drop-node-name;
        type uint16;
      }
      leaf min {
        type uint16;
      }
    }
    leaf keepalive {
      type uint16;
    }
    leaf local-address {
      type union {
        type inet:ipv4-address;
        type inet:ipv6-address;
        type string;
      }
    }
    uses bgp-local-as-grouping;
    leaf local-preference {
      type uint32;
    }
    leaf loop-detect {
      type enumeration {
        enum "drop-peer";
        enum "discard-route";
        enum "ignore-loop";
        enum "off";
      }
    }
    leaf med-out {
      type union {
        type uint32;
        type enumeration {
          enum "igp-cost";
        }
      }
    }
    leaf min-as-origination {
      type uint8;
    }
    leaf min-route-advertisement {
      type uint8;
    }
    leaf multihop {
      type uint8;
    }
    leaf next-hop-self {
      type empty;
    }
    container outbound-route-filtering {
      tailf:cli-add-mode;
      container extended-community {
        tailf:cli-add-mode;
        leaf accept-orf {
          type empty;
        }
        container send-orf {
          presence "true";
          leaf-list send-orf {
            tailf:cli-drop-node-name;
            tailf:cli-flat-list-syntax;
            type string;
          }
        }
      }
    }
    leaf passive {
      type empty;
    }
    leaf path-mtu-discovery {
      type empty;
    }
    leaf peer-as {
      type uint32;
    }
    leaf preference {
      type uint8;
    }
    uses bgp-prefix-limit-grouping;
    container remove-private {
      presence "true";
      leaf-list options {
        tailf:cli-drop-node-name;
        tailf:cli-flat-list-syntax;
        type enumeration {
          enum "limited";
          enum "skip-peer-as";
        }
      }
    }
    leaf split-horizon {
      type empty;
    }
    container tcp-mss {
      leaf mss-val {
        tailf:cli-drop-node-name;
        type uint32;
      }
      leaf ip-stack {
        type empty;
      }
    }
    leaf ttl-security {
      type uint8;
    }
    leaf type {
      type enumeration {
        enum "internal";
        enum "external";
      }
    }
    leaf vpn-apply-export {
      type empty;
    }
    leaf label-preference {
      type uint8;
    }
    leaf l2vpn-cisco-interop {
      type empty;
    }
    leaf vpn-apply-import {
      type empty;
    }
    leaf shutdown {
      type boolean;
    }
  }

  grouping bgp-local-as-grouping {
    container local-as {
      tailf:cli-compact-syntax;
      tailf:cli-sequence-commands {
        tailf:cli-reset-siblings;
      }
      leaf number {
        tailf:cli-drop-node-name;
        type uint32;
      }
      leaf private {
        tailf:cli-optional-in-sequence;
        type empty;
      }
      leaf no-prepend-global-as {
        tailf:cli-optional-in-sequence;
        type empty;
      }
    }
  }

  grouping bgp-best-path-selection-grouping {
    container best-path-selection {
      tailf:cli-add-mode;
      container always-compare-med {
        tailf:cli-compact-syntax;
        tailf:cli-sequence-commands {
          tailf:cli-reset-siblings;
        }
        presence "true";
        leaf strict-as {
          tailf:cli-optional-in-sequence;
          type empty;
        }
        leaf type {
          tailf:cli-drop-node-name;
          type enumeration {
            enum "zero";
            enum "infinity";
          }
        }
      }
      leaf-list as-path-ignore {
        tailf:cli-flat-list-syntax;
        type enumeration {
          enum "ipv4";
          enum "ipv6";
          enum "vpn-ipv4";
          enum "vpn-ipv6";
          enum "mcast-ipv4";
          enum "mvpn-ipv4";
          enum "l2-vpn";
          enum "mvpn-ipv6";
        }
      }
      leaf compare-origin-validation-state {
        type empty;
      }
      leaf deterministic-med {
        type empty;
      }
      leaf ignore-nh-metric {
        type empty;
      }
      leaf ignore-router-id {
        type empty;
      }
      leaf origin-invalid-unusable {
        type empty;
      }
    }
  }

  grouping agg-rate-grouping {
    container agg-rate {
      tailf:cli-add-mode;
      leaf limit-unused-bandwidth {
        type empty;
      }
      leaf queue-frame-based-accounting {
        type empty;
      }
      leaf rate {
        type union {
          type enumeration {
            enum "max";
          }
          type uint32;
        }
      }
    }
  }

  grouping sap-egress-common-grouping {
    leaf policy-id {
      type uint16;
    }
    leaf description {
      type string;
    }
    list queue {
      key "queue-id";
      leaf queue-id {
        type uint8;
      }
      uses queue-grouping;
    }
  }

  grouping dot1p-params-grouping {
    choice dot1p {
      leaf dot1p-value {
        tailf:cli-drop-node-name;
        type uint8;
      }
      case in-out {
        leaf in-profile {
          type uint8;
        }
        leaf out-profile {
          type uint8;
        }
      }
    }
  }

  grouping sap-egress-fc-grouping {
    leaf fc-name {
      type string;
    }
    container queue {
      tailf:cli-compact-syntax;
      tailf:cli-sequence-commands {
        tailf:cli-reset-all-siblings;
      }
      uses queue-ref-grouping;
      leaf instance {
        type uint8;
      }
    }
    container dot1p {
      tailf:cli-compact-syntax;
      tailf:cli-sequence-commands {
        tailf:cli-reset-siblings;
      }
      uses dot1p-params-grouping;
    }
    container dot1p-inner {
      tailf:cli-compact-syntax;
      tailf:cli-sequence-commands {
        tailf:cli-reset-siblings;
      }
      uses dot1p-params-grouping;
    }
    container dot1p-outer {
      tailf:cli-compact-syntax;
      tailf:cli-sequence-commands {
        tailf:cli-reset-siblings;
      }
      uses dot1p-params-grouping;
    }
    container dscp {
      tailf:cli-compact-syntax;
      choice dscp {
        leaf dscp-name {
          tailf:cli-drop-node-name;
          type string;
        }
        case in-out {
          leaf in-profile {
            type string;
          }
          leaf out-profile {
            type string;
          }
        }
      }
    }
  }

  grouping mcac-grouping {
    container mcac {
      tailf:cli-add-mode;
      container mc-constraints {
        tailf:cli-add-mode;
        list level {
          tailf:cli-suppress-mode;
          tailf:cli-compact-syntax;
          key "level-id";
          leaf level-id {
            tailf:cli-drop-node-name;
            type uint8;
          }
          leaf bw {
            type uint32;
          }
        }
        list number-down {
          tailf:cli-suppress-mode;
          tailf:cli-compact-syntax;
          key "number-lag-port-down";
          leaf number-lag-port-down {
            type uint8;
          }
          leaf level {
            type uint8;
          }
        }
        leaf use-lag-port-weight {
          type empty;
        }
        leaf shutdown {
          type boolean;
        }
      }
      leaf policy {
        type string;
      }
      container unconstrained-bw {
        tailf:cli-compact-syntax;
        tailf:cli-sequence-commands {
          tailf:cli-reset-all-siblings;
        }
        leaf bandwidth {
          tailf:cli-drop-node-name;
          type uint32;
        }
        leaf mandatory-bw {
          type uint32;
        }
      }
    }
  }

  grouping cron-schedule-grouping {
    list schedule {
      key "id owner";
      leaf id {
        type string;
      }
      leaf owner {
        type string;
      }
      leaf description {
        type string;
      }
      leaf interval {
        type uint32;
      }
      leaf count {
        type uint32;
      }
      leaf minute {
        type union {
          type uint8;
          type enumeration {
            enum "all";
          }
        }
      }
      leaf hour {
        type union {
          type uint8;
          type enumeration {
            enum "all";
          }
        }
      }
      leaf month {
        type union {
          type month;
          type enumeration {
            enum "all" {
              value 1000;
            }
          }
        }
      }
      leaf-list day-of-month {
        tailf:cli-flat-list-syntax;
        type union {
          type uint8;
          type enumeration {
            enum "all";
          }
        }
      }
      leaf weekday {
        type union {
          type weekday;
          type enumeration {
            enum "all" {
              value 1000;
            }
          }
        }
      }
      container end-time {
        tailf:cli-compact-syntax;
        tailf:cli-sequence-commands {
          tailf:cli-reset-siblings;
        }
        leaf day-name {
          tailf:cli-drop-node-name;
          type union {
            type weekday;
            type date;
          }
        }
        leaf time {
          tailf:cli-drop-node-name;
          type string;
        }
      }
      container script-policy {
        tailf:cli-compact-syntax;
        tailf:cli-sequence-commands {
          tailf:cli-reset-all-siblings;
        }
        leaf policy {
          tailf:cli-drop-node-name;
          type string32;
        }
        leaf owner {
          type string;
        }
      }
      leaf type {
        type enumeration {
          enum "periodic";
          enum "calendar";
          enum "oneshot";
        }
      }
      leaf shutdown {
        type boolean;
      }
    }
  }

  grouping static-route-entry-nh-grouping {
    leaf community {
      type union {
        type enumeration {
          enum "no-export";
          enum "no-export-subconfed";
          enum "no-advertise";
        }
        type string;
      }
    }
    leaf description {
      type string;
    }
    leaf metric {
      type uint16;
    }
    leaf preference {
      type uint8;
    }
    leaf tag {
      type uint32;
    }
    leaf bfd-enable {
      type empty;
    }
    leaf ldp-sync {
      type empty;
    }
    list cpe-check {
      key "address";
      leaf address {
        type union {
          type inet:ipv4-address;
          type inet:ipv6-address;
        }
      }
      leaf drop-count {
        type uint8;
      }
      leaf interval {
        type uint8;
      }
      leaf log {
        type empty;
      }
    }
    container tunnel-next-hop {
      tailf:cli-add-mode;
      leaf resolution {
        type enumeration {
          enum "any";
          enum "disabled";
          enum "filter";
        }
      }
      container resolution-filter {
        tailf:cli-add-mode;
        container rsvp-te {
          presence "true";
          leaf lsp {
            type string;
          }
        }
        container sr-te {
          presence "true";
          leaf lsp {
            type string;
          }
        }
        container ldp {
          presence "true";
        }
        container mpls-fwd-policy {
          presence "true";
        }
        container rib-api {
          presence "true";
        }
        container sr-isis {
          presence "true";
        }
        container sr-ospf {
          presence "true";
        }
        container sr-ospf3 {
          presence "true";
        }
      }
    }
    leaf destination-class {
      type uint32;
    }
    leaf source-class {
      type uint32;
    }
    container forwarding-class {
      tailf:cli-add-mode;
      leaf class {
        tailf:cli-drop-node-name;
        tailf:cli-hide-in-submode;
        type enumeration {
          enum "be";
          enum "l2";
          enum "af";
          enum "l1";
          enum "h2";
          enum "ef";
          enum "h1";
          enum "nc";
        }
      }
      leaf priority {
        type enumeration {
          enum "low";
          enum "high";
        }
      }
    }
    leaf shutdown {
      type boolean;
    }
  }

  grouping cflowd-params-grouping {
    container cflowd-parameters {
      tailf:cli-add-mode;
      list sampling {
        tailf:cli-suppress-mode;
        tailf:cli-compact-syntax;
        tailf:cli-sequence-commands {
          tailf:cli-reset-siblings;
        }
        key "sampling";
        leaf sampling {
          type enumeration {
            enum "unicast";
            enum "multicast";
          }
        }
        leaf type {
          type enumeration {
            enum "acl";
            enum "interface";
          }
        }
        leaf direction {
          type enumeration {
            enum "ingress-only";
            enum "egress-only";
            enum "both";
          }
        }
      }
    }
  }

  grouping resolution-filter-grouping {
    container resolution-filter {
      tailf:cli-add-mode;
      leaf bgp {
        type empty;
      }
      leaf gre {
        type empty;
      }
      leaf ldp {
        type boolean;
      }
      leaf rsvp {
        type empty;
      }
      leaf sr-isis {
        type empty;
      }
      leaf sr-ospf {
        type empty;
      }
      leaf sr-te {
        type empty;
      }
    }
    leaf resolution {
      type enumeration {
        enum "disabled";
        enum "any";
        enum "filter";
      }
    }
  }

  grouping bgp-next-hop-resolution-grouping {
    container next-hop-resolution {
      tailf:cli-add-mode;
      leaf policy {
        type string;
      }
      leaf use-bgp-routes {
        type empty;
      }
      container label-route-transport-tunnel {
        tailf:cli-add-mode;
        container family {
          tailf:cli-add-mode;
          leaf address-family {
            tailf:cli-drop-node-name;
            tailf:cli-hide-in-submode;
            type enumeration {
              enum "label-ipv4";
              enum "label-ipv6";
              enum "vpn";
            }
          }
          // NCS expand uses statement
          container resolution-filter {
            tailf:cli-add-mode;
            leaf bgp {
              type empty;
            }
            leaf gre {
              type empty;
            }
            leaf ldp {
              type boolean;
            }
            leaf rsvp {
              type empty;
            }
            leaf sr-isis {
              type empty;
            }
            leaf sr-ospf {
              type empty;
            }
            leaf sr-te {
              type empty;
            }
          }
          leaf resolution {
            type enumeration {
              enum "disabled";
              enum "any";
              enum "filter";
            }
          }
        }
      }
      container labeled-routes {
        tailf:cli-add-mode;
        leaf prefer-transport-frr {
          type empty;
        }
        container transport-tunnel {
          tailf:cli-add-mode;
          list family {
            key "address-family";
            leaf address-family {
              type enumeration {
                enum "label-ipv4";
                enum "label-ipv6";
                enum "vpn";
              }
            }
            // NCS expand uses statement
            container resolution-filter {
              tailf:cli-add-mode;
              leaf bgp {
                type empty;
              }
              leaf gre {
                type empty;
              }
              leaf ldp {
                type boolean;
              }
              leaf rsvp {
                type empty;
              }
              leaf sr-isis {
                type empty;
              }
              leaf sr-ospf {
                type empty;
              }
              leaf sr-te {
                type empty;
              }
            }
            leaf resolution {
              type enumeration {
                enum "disabled";
                enum "any";
                enum "filter";
              }
            }
          }
        }
      }
      container shortcut-tunnel {
        tailf:cli-add-mode;
        container family {

          grouping res-filter-grouping {
            container resolution-filter {
              tailf:cli-add-mode;
              leaf bgp {
                type empty;
              }
              leaf gre {
                type empty;
              }
              leaf ldp {
                type empty;
              }
              leaf rsvp {
                type empty;
              }
              leaf sr-isis {
                type empty;
              }
              leaf sr-ospf {
                type empty;
              }
              leaf sr-te {
                type empty;
              }
            }
            leaf resolution {
              type enumeration {
                enum "disabled";
                enum "any";
                enum "filter";
              }
            }
          }
          container ipv4 {
            tailf:cli-add-mode;
            tailf:cli-delete-when-empty;
            uses res-filter-grouping;
          }
          container ipv6 {
            tailf:cli-add-mode;
            tailf:cli-delete-when-empty;
            uses res-filter-grouping;
          }
        }
      }
      leaf weighted-ecmp {
        type empty;
      }
    }
  }

  grouping authentication-key-grouping {
    container authentication-key {
      tailf:cli-compact-syntax;
      tailf:cli-sequence-commands {
        tailf:cli-reset-siblings;
      }
      leaf key {
        tailf:cli-drop-node-name;
        type string;
      }
      leaf method {
        tailf:cli-drop-node-name;
        type hash-method;
      }
    }
  }

  grouping hello-authentication-key-grouping {
    container hello-authentication-key {
      tailf:cli-compact-syntax;
      tailf:cli-sequence-commands {
        tailf:cli-reset-all-siblings;
      }
      leaf key {
        tailf:cli-drop-node-name;
        type string;
      }
      leaf method {
        tailf:cli-drop-node-name;
        type hash-method;
      }
    }
  }

  grouping ipoe-session-grouping {
    leaf description {
      type string;
    }
    leaf ipoe-session-policy {
      type string32;
    }
    leaf user-db {
      type string;
    }
    leaf shutdown {
      type boolean;
    }
  }

  grouping packet-byte-offset-grouping {
    container packet-byte-offset {
      tailf:cli-compact-syntax;
      choice op {
        leaf add {
          type uint8;
        }
        leaf subtract {
          type uint8;
        }
      }
    }
  }

  grouping port-parent-grouping {
    container port-parent {
      presence "present";
      tailf:cli-compact-syntax;
      leaf weight {
        type uint8;
      }
      leaf level {
        type uint8;
      }
      leaf cir-weight {
        type uint8;
      }
      leaf cir-level {
        type uint8;
      }
    }
  }

  grouping router-aggregate-grouping {
    list aggregate {
      tailf:cli-compact-syntax;
      tailf:cli-suppress-mode;
      key "route";
      leaf route {
        type union {
          type tailf:ipv4-address-and-prefix-length;
          type tailf:ipv6-address-and-prefix-length;
        }
      }
      leaf summary-only {
        type empty;
      }
      leaf discard-component-communities {
        type empty;
      }
      leaf as-set {
        type empty;
      }
      leaf aggregator {
        type string;
      }
      leaf-list community {
        tailf:cli-flat-list-syntax;
        type string;
      }
      leaf black-hole {
        type empty;
      }
      leaf description {
        type string;
      }
      leaf policy {
        type string;
      }
    }
  }

  grouping ospf-area-id-grouping {
    leaf area-id {
      type union {
        type inet:ipv4-address;
        type uint32;
      }
    }
  }

  grouping service-id-grouping {
    leaf service-id {
      type service-id;
    }
  }

  grouping radius-server-grouping {
    list server {
      key "server-name";
      leaf server-name {
        type string32;
      }
      leaf address {
        tailf:cli-hide-in-submode;
        type union {
          type inet:ipv4-address;
          type inet:ipv6-address;
        }
      }
      leaf secret {
        tailf:cli-hide-in-submode;
        type string;
      }
      leaf auth-port {
        type uint32;
      }
      leaf acct-port {
        type uint32;
      }
      leaf coa-script-policy {
        type string32;
      }
      leaf scheme {
        tailf:cli-drop-node-name;
        tailf:cli-hide-in-submode;
        type hash-method;
      }
      leaf accept-coa {
        type empty;
      }
      leaf description {
        type string;
      }
      leaf python-policy {
        type string32;
      }
    }
  }

  grouping dhcp6-lease-timers-grouping {

    grouping dhcp6-lease-time-common-grouping {
      leaf sec {
        type uint16;
      }
    }
    container preferred-lifetime {
      tailf:cli-compact-syntax;
      leaf days {
        type uint8;
      }
      leaf hrs {
        type uint8;
      }
      leaf min {
        type uint8;
      }
      uses dhcp6-lease-time-common-grouping;
    }
    container rebind-timer {
      tailf:cli-compact-syntax;
      leaf days {
        type uint8;
      }
      leaf hrs {
        type uint8;
      }
      leaf min {
        type uint8;
      }
      uses dhcp6-lease-time-common-grouping;
    }
    container renew-timer {
      tailf:cli-compact-syntax;
      leaf days {
        type uint8;
      }
      leaf hrs {
        type uint8;
      }
      leaf min {
        type uint8;
      }
      uses dhcp6-lease-time-common-grouping;
    }
    container valid-lifetime {
      tailf:cli-compact-syntax;
      leaf days {
        type uint8;
      }
      leaf hrs {
        type uint8;
      }
      leaf min {
        type uint8;
      }
      uses dhcp6-lease-time-common-grouping;
    }
    container server-id {
      tailf:cli-compact-syntax;
      leaf duid {
        tailf:cli-drop-node-name;
        type enumeration {
          enum "duid-en";
          enum "duid-ll";
        }
      }
      choice strhex {
        leaf string {
          type string;
        }
        leaf hex {
          type string;
        }
      }
    }
  }

  grouping snmp-community-grouping {
    list community {
      tailf:cli-suppress-mode;
      tailf:cli-compact-syntax;
      tailf:cli-sequence-commands {
        tailf:cli-reset-all-siblings;
      }
      key "name";
      leaf name {
        type string;
      }
      leaf type {
        tailf:cli-drop-node-name;
        tailf:cli-optional-in-sequence;
        type hash-method;
      }
      leaf access-parameters {
        tailf:cli-drop-node-name;
        tailf:cli-optional-in-sequence;
        type enumeration {
          enum "r";
          enum "rw";
          enum "rwa";
          enum "mgmt";
          enum "vpls-mgmt";
        }
      }
      leaf version {
        tailf:cli-optional-in-sequence;
        type enumeration {
          enum "v2c";
          enum "v1";
          enum "both";
        }
      }
      leaf src-access-list {
        type string32;
      }
    }
  }

  grouping qos-dscp-list-grouping {
    list dscp {
      tailf:cli-suppress-mode;
      tailf:cli-compact-syntax;
      tailf:cli-sequence-commands {
        tailf:cli-reset-all-siblings;
      }
      key "dscp-name";
      leaf dscp-name {
        type dscp-type;
      }
      leaf fc {
        tailf:cli-optional-in-sequence;
        type fc-name;
      }
      leaf profile {
        type in-out;
      }
    }
  }

  grouping qos-dot1p-list-grouping {
    list dot1p {
      tailf:cli-compact-syntax;
      tailf:cli-suppress-mode;
      key "id";
      leaf id {
        type uint8;
      }
      leaf fc {
        type fc-name;
      }
      leaf profile {
        type enumeration {
          enum "in";
          enum "out";
          enum "use-de";
          enum "exceed";
          enum "inplus";
        }
      }
    }
    list prec {
      key "ip-prec-value";
      tailf:cli-compact-syntax;
      tailf:cli-suppress-mode;
      leaf ip-prec-value {
        tailf:cli-drop-node-name;
        type uint16;
      }
      leaf profile {
        type enumeration {
          enum "in";
          enum "out";
          enum "exceed";
          enum "inplus";
        }
      }
      leaf fc {
        type fc-name;
      }
    }
  }

  grouping slope-params-grouping {
    leaf start-avg {
      type uint8;
    }
    leaf max-avg {
      type uint8;
    }
    leaf max-prob {
      type uint8;
    }
    leaf shutdown {
      type boolean;
    }
  }

  grouping qos-lsp-exp-grouping {
    list lsp-exp {
      tailf:cli-compact-syntax;
      tailf:cli-suppress-mode;
      tailf:cli-sequence-commands {
        tailf:cli-reset-all-siblings;
      }
      key "id";
      leaf id {
        type uint8;
      }
      leaf fc {
        type fc-name;
      }
      leaf profile {
        type enumeration {
          enum "in";
          enum "out";
        }
      }
    }
  }

  grouping bgp-common-grouping {
    leaf keepalive {
      type uint16;
    }
    container hold-time {
      tailf:cli-compact-syntax;
      leaf seconds {
        tailf:cli-drop-node-name;
        type uint16;
      }
      leaf min {
        type uint16;
      }
    }
    leaf preference {
      type uint8;
    }
  }

  grouping pim-common-grouping {
    leaf rpf6-table {
      type enumeration {
        enum "rtable6-m";
        enum "rtable6-u";
        enum "both";
      }
    }
    leaf apply-to {
      type enumeration {
        enum "all";
        enum "ies";
        enum "non-ies";
        enum "none";
      }
    }
  }

  grouping local-dhcp-server-grouping {

    grouping dhcp-custom-options-grouping {
      list custom-option {
        tailf:cli-suppress-mode;
        key "number";
        leaf number {
          type uint8;
        }
        leaf-list address {
          tailf:cli-flat-list-syntax;
          type inet:ipv4-address;
        }
        leaf hex {
          type string;
        }
        leaf string {
          type string;
        }
      }
    }
    list local-dhcp-server {
      key "server-name";
      leaf server-name {
        type string;
      }
      leaf description {
        type string;
      }
      container use-gi-address {
        tailf:cli-compact-syntax;
        presence "true";
        leaf scope {
          type enumeration {
            enum "pool";
            enum "subnet";
          }
        }
      }
      leaf force-renews {
        type empty;
      }
      list pool {
        key "pool-id";
        leaf pool-id {
          type string32;
        }
        leaf description {
          type string;
        }
        container max-lease-time {
          tailf:cli-compact-syntax;
          uses dhcp-lease-time;
        }
        container min-lease-time {
          tailf:cli-compact-syntax;
          uses dhcp-lease-time;
        }
        container minimum-free {
          tailf:cli-compact-syntax;
          tailf:cli-sequence-commands {
            tailf:cli-reset-siblings;
          }
          leaf minimum-free-value {
            tailf:cli-drop-node-name;
            type uint16;
          }
          leaf percent {
            tailf:cli-optional-in-sequence;
            type empty;
          }
          leaf event-when-depleted {
            type empty;
          }
        }
        leaf nak-non-matching-subnet {
          type empty;
        }
        container offer-time {
          tailf:cli-compact-syntax;
          tailf:cli-sequence-commands {
            tailf:cli-reset-siblings;
          }
          leaf min {
            type uint16;
          }
          leaf sec {
            type uint16;
          }
        }
        container options {
          tailf:cli-add-mode;
          leaf-list dns-server {
            tailf:cli-flat-list-syntax;
            type inet:ipv4-address;
          }
          leaf domain-name {
            type string;
          }
          container lease-rebind-time {
            tailf:cli-compact-syntax;
            uses dhcp-lease-time;
          }
          container lease-renew-time {
            tailf:cli-compact-syntax;
            uses dhcp-lease-time;
          }
          container lease-time {
            tailf:cli-compact-syntax;
            uses dhcp-lease-time;
          }
          leaf-list netbios-name-server {
            tailf:cli-flat-list-syntax;
            type inet:ipv4-address;
          }
          leaf netbios-node-type {
            type enumeration {
              enum "B";
              enum "P";
              enum "M";
              enum "H";
            }
          }
          uses dhcp-custom-options-grouping;
        }
        list subnet {
          key "subnet-id";
          leaf subnet-id {
            type tailf:ipv4-address-and-prefix-length;
          }
          container address-range {
            uses ip-address-range {
              augment "low-high-list" {
                leaf failover {
                  type enumeration {
                    enum "local";
                    enum "remote";
                    enum "access-driven";
                  }
                }
              }
            }
          }
          leaf drain {
            type empty;
          }
          container exclude-addresses {
            uses ip-address-range;
          }
          leaf maximum-declined {
            type uint32;
          }
          container minimum-free {
            tailf:cli-compact-syntax;
            tailf:cli-sequence-commands {
              tailf:cli-reset-siblings;
            }
            leaf minimum-free-value {
              tailf:cli-drop-node-name;
              type uint16;
            }
            leaf percent {
              type empty;
            }
            leaf event-when-depleted {
              type empty;
            }
          }
          container options {
            tailf:cli-add-mode;
            leaf-list default-router {
              tailf:cli-flat-list-syntax;
              type inet:ipv4-address;
            }
            leaf subnet-mask {
              type inet:ipv4-address;
            }
            uses dhcp-custom-options-grouping;
          }
        }
      }
      container failover {
        tailf:cli-add-mode;
        leaf ignore-mclt-on-takeover {
          type empty;
        }
        container maximum-client-lead-time {
          tailf:cli-compact-syntax;
          leaf hrs {
            type uint8;
          }
          leaf min {
            type uint8;
          }
          leaf sec {
            type uint8;
          }
        }
        container partner-down-delay {
          tailf:cli-compact-syntax;
          leaf hrs {
            type uint8;
          }
          leaf min {
            type uint8;
          }
          leaf sec {
            type uint8;
          }
        }
        container peer {
          tailf:cli-compact-syntax;
          tailf:cli-sequence-commands {
            tailf:cli-reset-all-siblings;
          }
          leaf ip-address {
            tailf:cli-drop-node-name;
            type inet:ipv4-address;
          }
          leaf tag {
            type string;
          }
        }
        container startup-wait-time {
          tailf:cli-compact-syntax;
          tailf:cli-sequence-commands {
            tailf:cli-reset-all-siblings;
          }
          leaf min {
            type uint8;
          }
          leaf sec {
            type uint8;
          }
        }
        leaf shutdown {
          type boolean;
        }
      }
      container lease-hold-time {
        tailf:cli-compact-syntax;
        leaf days {
          type uint32;
        }
        leaf hrs {
          type uint32;
        }
        leaf min {
          type uint32;
        }
        leaf sec {
          type uint32;
        }
      }
      container lease-hold-time-for {
        tailf:cli-add-mode;
        leaf solicited-release {
          type empty;
        }
      }
      container use-pool-from-client {
        tailf:cli-compact-syntax;
        presence "true";
      }
      leaf shutdown {
        type boolean;
      }
    }
  }

  augment "/ncs:devices/ncs:device/ncs:config" {
    leaf model {
      tailf:ncs-device-type "cli-ned";
      tailf:display-when "not(../../ncs:module) or ../../ncs:module[ncs:name='netsim-ned-alu-sr']";
      tailf:alt-name "nedAluModel";
      type union {
        type enumeration {
          enum "7950";
          enum "7750";
          enum "7450";
          enum "7705";
          enum "7210";
        }
        type string;
      }
    }
    leaf model-name {
      tailf:ncs-device-type "cli-ned";
      tailf:display-when "not(../../ncs:module) or ../../ncs:module[ncs:name='netsim-ned-alu-sr']";
      tailf:alt-name "nedAluModelName";
      type string;
    }
    leaf os-major {
      tailf:ncs-device-type "cli-ned";
      tailf:display-when "not(../../ncs:module) or ../../ncs:module[ncs:name='netsim-ned-alu-sr']";
      tailf:alt-name "nedAluOsMajor";
      type union {
        type uint32;
        type enumeration {
          enum "12";
          enum "14";
          enum "15";
        }
      }
    }
    leaf os-minor {
      tailf:ncs-device-type "cli-ned";
      tailf:display-when "not(../../ncs:module) or ../../ncs:module[ncs:name='netsim-ned-alu-sr']";
      tailf:alt-name "nedAluOsMinor";
      type uint32;
    }
    leaf os-patch {
      tailf:ncs-device-type "cli-ned";
      tailf:display-when "not(../../ncs:module) or ../../ncs:module[ncs:name='netsim-ned-alu-sr']";
      tailf:alt-name "nedAluOsPatch";
      type uint32;
    }
    leaf mode {
      tailf:ncs-device-type "cli-ned";
      tailf:display-when "not(../../ncs:module) or ../../ncs:module[ncs:name='netsim-ned-alu-sr']";
      tailf:alt-name "nedAluUseMode";
      type union {
        type enumeration {
          enum "use-list";
        }
        type string;
      }
    }
    leaf use-extra-get-port-speed {
      tailf:ncs-device-type "cli-ned";
      tailf:display-when "not(../../ncs:module) or ../../ncs:module[ncs:name='netsim-ned-alu-sr']";
      tailf:alt-name "nedAluUseExtraGetPortSpeed";
      type boolean;
    }
    leaf force-no-filter-name {
      tailf:ncs-device-type "cli-ned";
      tailf:display-when "not(../../ncs:module) or ../../ncs:module[ncs:name='netsim-ned-alu-sr']";
      tailf:alt-name "nedAluForceNoFilterName";
      type boolean;
    }
    container bfd {
      tailf:ncs-device-type "cli-ned";
      tailf:display-when "not(../../ncs:module) or ../../ncs:module[ncs:name='netsim-ned-alu-sr']";
      tailf:cli-add-mode;
      container seamless-bfd {
        tailf:cli-add-mode;
        list reflector {
          key "reflector-name";
          leaf reflector-name {
            type string;
          }
          leaf description {
            type string;
          }
          leaf local-state {
            type enumeration {
              enum "admin-down";
              enum "up";
            }
          }
          leaf discriminator {
            type uint32;
          }
          leaf shutdown {
            type boolean;
          }
        }
      }
    }
    container bmp {
      tailf:ncs-device-type "cli-ned";
      tailf:display-when "not(../../ncs:module) or ../../ncs:module[ncs:name='netsim-ned-alu-sr']";
      tailf:cli-add-mode;
      list station {
        key "station-name";
        leaf station-name {
          type string;
        }
        container connection {
          tailf:cli-add-mode;
          leaf connect-retry {
            type uint32;
          }
          leaf local-address {
            type union {
              type inet:ipv4-address;
              type inet:ipv6-address;
            }
          }
          container station-address {
            tailf:cli-compact-syntax;
            tailf:cli-sequence-commands;
            leaf address {
              tailf:cli-drop-node-name;
              type union {
                type inet:ipv4-address;
                type inet:ipv6-address;
              }
            }
            leaf port {
              type uint32;
            }
          }
          leaf router {
            type string;
          }
          container tcp-keepalive {
            tailf:cli-add-mode;
            leaf keep-count {
              type uint32;
            }
            leaf keep-idle {
              type uint32;
            }
            leaf keep-interval {
              type uint32;
            }
            leaf shutdown {
              type boolean;
            }
          }
        }
        leaf description {
          type string;
        }
        leaf-list family {
          tailf:cli-flat-list-syntax;
          type enumeration {
            enum "ipv4";
            enum "ipv6";
            enum "label-ipv4";
            enum "label-ipv6";
            enum "mcast-ipv4";
            enum "mcast-ipv6";
            enum "vpn-ipv4";
            enum "vpn-ipv6";
            enum "mcast-vpn-ipv4";
            enum "mcast-vpn-ipv6";
            enum "evpn";
            enum "l2-vpn";
          }
        }
        leaf initiation-message {
          type string;
        }
        leaf report-local-routes {
          type empty;
        }
        leaf stats-report-interval {
          type uint32;
        }
        leaf shutdown {
          type boolean;
        }
      }
      leaf shutdown {
        type boolean;
      }
    }
    container call-trace {
      tailf:ncs-device-type "cli-ned";
      tailf:display-when "not(../../ncs:module) or ../../ncs:module[ncs:name='netsim-ned-alu-sr']";
      tailf:cli-add-mode;
      container location {

        grouping cf-group {
          leaf disable {
            type empty;
          }
          leaf size-limit {
            type uint32;
          }
        }
        container cf1 {
          tailf:cli-add-mode;
          uses cf-group;
        }
        container cf2 {
          tailf:cli-add-mode;
          uses cf-group;
        }
      }
      list trace-profile {
        key "profile-name";
        leaf profile-name {
          type string;
        }
        leaf description {
          type string;
        }
        leaf debug-output {
          type empty;
        }
        leaf size-limit {
          type uint16;
        }
      }
    }
    list card {
      tailf:ncs-device-type "cli-ned";
      tailf:display-when "not(../ncs:module) or ../ncs:module[ncs:name='netsim-ned-alu-sr']";
      key "slot-number";
      leaf slot-number {
        type string;
      }
      container card-type {
        tailf:cli-compact-syntax;
        leaf card-type {
          tailf:cli-drop-node-name;
          type string;
        }
        leaf level {
          type string;
        }
      }
      leaf fail-on-error {
        type empty;
      }
      list mda {
        key "mda-slot";
        leaf mda-slot {
          type string;
        }
        list event {
          key "event-name";
          leaf event-name {
            type enumeration {
              enum "soft-error";
              enum "internal-frame-loss";
              enum "memory-error";
            }
          }
          leaf action {
            type enumeration {
              enum "log-only";
              enum "reset-mda";
              enum "fail-mda";
            }
          }
          leaf action-alt {
            tailf:alt-name "action";
            type enumeration {
              enum "log-only";
              enum "reset-mda";
              enum "fail-mda";
            }
          }
        }
        container mda-type {
          tailf:cli-compact-syntax;
          presence "true";
          leaf type {
            tailf:cli-drop-node-name;
            type string;
          }
          leaf level {
            type string;
          }
        }
        container access {
          tailf:cli-add-mode;
          container ingress {
            tailf:cli-add-mode;
            leaf fabric-policy {
              type uint16;
            }
          }
        }
        leaf fail-on-error {
          type empty;
        }
        container egress-xpl {
          tailf:cli-add-mode;
          leaf window {
            type uint32;
          }
        }
        container ingress {
          tailf:cli-add-mode;
          container mcast-path-management {
            tailf:cli-add-mode;
            leaf shutdown {
              type boolean;
            }
          }
        }
        container ingress-xpl {
          tailf:cli-add-mode;
          leaf window {
            type uint32;
          }
        }
        container network {
          tailf:cli-add-mode;
          container ingress {
            tailf:cli-add-mode;
            leaf fabric-policy {
              type uint16;
            }
            container pool {
              tailf:cli-add-mode;
              leaf slope-policy {
                type string;
              }
            }
            leaf queue-policy {
              type string;
            }
          }
        }
        leaf sync-e {
          type empty;
        }
        list upgrade {
          tailf:cli-compact-syntax;
          tailf:cli-suppress-mode;
          key "number";
          leaf number {
            type uint32;
          }
          leaf path {
            type string;
          }
        }
        leaf shutdown {
          type boolean;
        }
      }
      list fp {
        key "id";
        leaf id {
          type uint32;
        }
        leaf fp-resource-policy {
          type string;
        }
        leaf init-extract-prio-mode {
          type enumeration {
            enum "uniform";
            enum "l3-classify";
          }
        }
        container egress {
          tailf:cli-add-mode;
          container wred-queue-control {
            tailf:cli-add-mode;

            grouping max-min-grouping {
              leaf min {
                type decimal64 {
                  fraction-digits 2;
                }
              }
              leaf max {
                type decimal64 {
                  fraction-digits 2;
                }
              }
            }
            container buffer-allocation {
              tailf:cli-compact-syntax;
              tailf:cli-sequence-commands {
                tailf:cli-reset-siblings;
              }
              uses max-min-grouping;
            }
            container resv-cbs {
              tailf:cli-compact-syntax;
              tailf:cli-sequence-commands {
                tailf:cli-reset-siblings;
              }
              uses max-min-grouping;
            }
            leaf slope-policy {
              type string;
            }
            leaf shutdown {
              type boolean;
            }
          }
        }
        container ingress {
          tailf:cli-add-mode;
          container mcast-path-management {
            tailf:cli-add-mode;
            leaf bandwidth-policy {
              type string;
            }
            leaf shutdown {
              type boolean;
            }
          }
          container network {
            tailf:cli-add-mode;
            list queue-group {
              key "name instance";
              leaf name {
                type string;
              }
              leaf instance {
                type uint32;
              }
            }
            leaf queue-policy {
              type string;
            }
          }
        }
        container hi-bw-mcast-src {
          tailf:cli-compact-syntax;
          tailf:cli-sequence-commands {
            tailf:cli-reset-siblings;
          }
          leaf alarm {
            tailf:cli-optional-in-sequence;
            type empty;
          }
          leaf default-paths-only {
            tailf:cli-optional-in-sequence;
            type empty;
          }
          leaf group {
            type uint8;
          }
        }
      }
      container xiom {
        container x1 {
          tailf:cli-add-mode;
          presence "true";
          container xiom-type {
            tailf:cli-compact-syntax;
            leaf type {
              tailf:cli-drop-node-name;
              type enumeration {
                enum "iom-s-1.5t";
                enum "iom-s-3.0t";
              }
            }
            leaf level {
              type string;
            }
          }
          list upgrade {
            tailf:cli-suppress-mode;
            key "id";
            leaf id {
              type uint32;
            }
            leaf path {
              type string;
            }
          }
          list mda {
            key "id";
            leaf id {
              type uint32;
            }
            leaf mda-type {
              type enumeration {
                enum "ms16-100gb-sfpdd+4-100gb-qsfp28";
                enum "ms18-100gb-qsfp28";
                enum "ms2-400gb-qsfpdd+2-100gb-qsfp28";
                enum "ms24-10/100gb-sfpdd";
                enum "ms3-200gb-cfp2-dco";
                enum "ms4-400gb-qsfpdd+4-100gb-qsfp28";
                enum "ms6-200gb-cfp2-dco";
                enum "ms8-100gb-sfpdd+2-100gb-qsfp28";
              }
            }
            leaf shutdown {
              type boolean;
            }
          }
          leaf shutdown {
            type boolean;
          }
        }
        container x2 {
          tailf:cli-add-mode;
          presence "true";
          container xiom-type {
            tailf:cli-compact-syntax;
            leaf type {
              tailf:cli-drop-node-name;
              type enumeration {
                enum "iom-s-1.5t";
                enum "iom-s-3.0t";
              }
            }
            leaf level {
              type string;
            }
          }
          list upgrade {
            tailf:cli-suppress-mode;
            key "id";
            leaf id {
              type uint32;
            }
            leaf path {
              type string;
            }
          }
          list mda {
            key "id";
            leaf id {
              type uint32;
            }
            leaf mda-type {
              type enumeration {
                enum "ms16-100gb-sfpdd+4-100gb-qsfp28";
                enum "ms18-100gb-qsfp28";
                enum "ms2-400gb-qsfpdd+2-100gb-qsfp28";
                enum "ms24-10/100gb-sfpdd";
                enum "ms3-200gb-cfp2-dco";
                enum "ms4-400gb-qsfpdd+4-100gb-qsfp28";
                enum "ms6-200gb-cfp2-dco";
                enum "ms8-100gb-sfpdd+2-100gb-qsfp28";
              }
            }
            leaf shutdown {
              type boolean;
            }
          }
          leaf shutdown {
            type boolean;
          }
        }
      }
      leaf reset-on-recoverable-error {
        type empty;
      }
      leaf shutdown {
        type boolean;
      }
      container redundancy {
        tailf:cli-add-mode;
        leaf revertive {
          type empty;
        }
        container takeover {
          tailf:cli-compact-syntax;
          leaf delay {
            type uint32;
          }
        }
      }
    }
    container cflowd {
      tailf:ncs-device-type "cli-ned";
      tailf:display-when "not(../../ncs:module) or ../../ncs:module[ncs:name='netsim-ned-alu-sr']";
      presence "present";
      tailf:cli-add-mode;
      leaf active-timeout {
        type uint16;
      }
      leaf active-flow-timeout {
        type uint16;
      }
      leaf cache-size {
        type uint32;
      }
      list collector {
        key "collector-id";
        leaf collector-id {
          type union {
            type inet:ipv4-address;
            type inet:ipv6-address;
            type string;
            type string;
          }
        }
        leaf version {
          tailf:cli-hide-in-submode;
          type enumeration {
            enum "5";
            enum "8";
            enum "9";
            enum "10";
          }
        }
        leaf description {
          type string;
        }
        leaf template-set {
          type enumeration {
            enum "basic";
            enum "mpls-ip";
            enum "l2-ip";
            enum "mpls-transport";
          }
        }
        leaf router {
          type router-type;
        }
        container export-filter {
          tailf:cli-add-mode;
          container interface-list {
            tailf:cli-add-mode;
            list router {
              tailf:cli-suppress-mode;
              key "router-id interface";
              leaf router-id {
                type router-type;
              }
              leaf interface {
                type string;
              }
            }
            container service {
              tailf:cli-add-mode;
              list ies {
                tailf:cli-suppress-mode;
                key "ies-name interface";
                leaf ies-name {
                  type string;
                }
                leaf interface {
                  type string;
                }
              }
              list vprn {
                tailf:cli-suppress-mode;
                key "vprn-name interface";
                leaf vprn-name {
                  type string;
                }
                leaf interface {
                  type string;
                }
              }
            }
          }
        }
        leaf autonomous-system-type {
          type enumeration {
            enum "origin";
            enum "peer";
          }
        }
        leaf shutdown {
          type empty;
        }
      }
      leaf export-mode {
        type enumeration {
          enum "automatic";
          enum "manual";
        }
      }
      leaf inactive-timeout {
        type uint16;
      }
      leaf inactive-flow-timeout {
        type uint16;
      }
      leaf overflow {
        type uint8;
      }
      leaf rate {
        type uint16;
      }
      leaf template-retransmit {
        type uint16;
      }
      list sample-profile {
        key "profile-id";
        leaf profile-id {
          type uint8;
        }
        leaf sample-rate {
          type uint32;
        }
      }
      leaf shutdown {
        type empty;
      }
    }
    list interface-group-handler {
      tailf:ncs-device-type "cli-ned";
      tailf:display-when "not(../ncs:module) or ../ncs:module[ncs:name='netsim-ned-alu-sr']";
      key "index";
      leaf index {
        type uint8;
      }
      leaf shutdown {
        type boolean;
      }
    }
    container ipsec {
      tailf:ncs-device-type "cli-ned";
      tailf:display-when "not(../../ncs:module) or ../../ncs:module[ncs:name='netsim-ned-alu-sr']";
      tailf:cli-add-mode;
      list ike-policy {
        key "ike-policy-id";
        leaf ike-policy-id {
          type uint16;
        }
        leaf auth-algorithm {
          type enumeration {
            enum "md5";
            enum "sha1";
            enum "sha256";
            enum "sha384";
            enum "sha512";
            enum "aes-xcbc";
          }
        }
        leaf auth-method {
          type enumeration {
            enum "psk";
            enum "plain-psk-xauth";
            enum "cert-auth";
            enum "psk-radius";
            enum "cert-radius";
            enum "eap";
            enum "auto-eap-radius";
            enum "auto-eap";
          }
        }
        leaf auto-eap-method {
          type enumeration {
            enum "psk";
            enum "cert";
            enum "psk-or-cert";
          }
        }
        leaf auto-eap-own-method {
          type enumeration {
            enum "psk";
            enum "cert";
          }
        }
        leaf description {
          type string;
        }
        leaf dh-group {
          type enumeration {
            enum "1";
            enum "2";
            enum "5";
            enum "14";
            enum "15";
          }
        }
        container dpd {
          presence "present";
          tailf:cli-compact-syntax;
          leaf interval {
            type uint16;
          }
          leaf max-retries {
            type uint8;
          }
          leaf reply-only {
            type empty;
          }
        }
        leaf encryption-algorithm {
          type enumeration {
            enum "des";
            enum "3des";
            enum "aes128";
            enum "aes192";
            enum "aes256";
          }
        }
        leaf ike-mode {
          type enumeration {
            enum "main";
            enum "aggressive";
          }
        }
        leaf ike-transform {
          type uint16;
        }
        leaf ike-version {
          type uint8;
        }
        leaf ipsec-lifetime {
          type uint32;
        }
        leaf isakmp-lifetime {
          type uint32;
        }
        leaf match-peer-id-to-cert {
          type empty;
        }
        container nat-traversal {
          presence "present";
          tailf:cli-compact-syntax;
          tailf:cli-sequence-commands {
            tailf:cli-reset-all-siblings;
          }
          leaf force {
            tailf:cli-optional-in-sequence;
            type empty;
          }
          leaf keep-alive-interval {
            tailf:cli-optional-in-sequence;
            type uint16;
          }
          leaf force-keep-alive {
            type empty;
          }
        }
        leaf own-auth-method {
          type enumeration {
            enum "psk";
            enum "cert";
            enum "eap-only";
          }
        }
        container pfs {
          presence "present";
          tailf:cli-compact-syntax;
          leaf dh-group {
            type enumeration {
              enum "1";
              enum "2";
              enum "5";
              enum "14";
              enum "15";
            }
          }
        }
      }
      list ike-transform {
        key "ike-transform-id";
        leaf ike-transform-id {
          type uint16;
        }
        leaf dh-group {
          type uint32;
        }
        leaf ike-auth-algorithm {
          type enumeration {
            enum "md5";
            enum "sha1";
            enum "sha256";
            enum "sha384";
            enum "sha512";
            enum "aes-xcbc";
            enum "auth-encryption";
          }
        }
        leaf ike-encryption-algorithm {
          type enumeration {
            enum "des";
            enum "3des";
            enum "aes128";
            enum "aes192";
            enum "aes256";
            enum "aes128-gcm8";
            enum "aes128-gcm16";
            enum "aes256-gcm8";
            enum "aes256-gcm16";
          }
        }
        leaf isakmp-lifetime {
          type uint32;
        }
      }
      list ipsec-transform {
        key "transform-id";
        leaf transform-id {
          type uint16;
        }
        leaf esp-auth-algorithm {
          type enumeration {
            enum "null";
            enum "md5";
            enum "sha1";
            enum "sha256";
            enum "sha384";
            enum "sha512";
            enum "aes-xcbc";
          }
        }
        leaf esp-encryption-algorithm {
          type enumeration {
            enum "null";
            enum "des";
            enum "3des";
            enum "aes128";
            enum "aes192";
            enum "aes256";
          }
        }
        leaf ipsec-lifetime {
          type union {
            type uint32;
            type enumeration {
              enum "inherit";
            }
          }
        }
        leaf pfs-dh-group {
          type union {
            type uint32;
            type enumeration {
              enum "inherit";
            }
          }
        }
      }
      list cert-profile {
        key "profile-name";
        leaf profile-name {
          type string32;
        }
        list entry {
          key "entry-id";
          leaf entry-id {
            type uint8;
          }
          leaf cert {
            type string;
          }
          leaf key {
            type string;
          }
          container send-chain {
            tailf:cli-add-mode;
            list ca-profile {
              tailf:cli-suppress-mode;
              key "name";
              leaf name {
                type string32;
              }
            }
          }
        }
        leaf shutdown {
          type boolean;
        }
      }
      list static-sa {
        key "sa-name";
        leaf sa-name {
          type string;
        }
        container authentication {
          tailf:cli-compact-syntax;
          tailf:cli-sequence-commands {
            tailf:cli-reset-siblings;
          }
          leaf auth-algorithm {
            tailf:cli-drop-node-name;
            type enumeration {
              enum "md5";
              enum "sha1";
            }
          }
          leaf hex-or-ascii {
            tailf:cli-drop-node-name;
            type enumeration {
              enum "hex-key";
              enum "ascii-key";
            }
          }
          leaf key-value {
            tailf:cli-drop-node-name;
            type string;
          }
          leaf hash-type {
            tailf:cli-drop-node-name;
            type hash-method;
          }
        }
        leaf description {
          type string;
        }
        leaf protocol {
          type enumeration {
            enum "ah";
            enum "esp";
          }
        }
        leaf spi {
          type uint16;
        }
      }
      list trust-anchor-profile {
        key "name";
        leaf name {
          type string32;
        }
        list trust-anchor {
          tailf:cli-suppress-mode;
          key "ca-profile-name";
          leaf ca-profile-name {
            type string32;
          }
        }
      }
      list tunnel-template {
        key "tunnel-template-id";
        leaf tunnel-template-id {
          type uint16;
        }
        leaf description {
          type string;
        }
        leaf clear-df-bit {
          type empty;
        }
        leaf ip-mtu {
          type uint32;
        }
        leaf encapsulated-ip-mtu {
          type uint32;
        }
        leaf sp-reverse-route {
          type empty;
        }
        leaf replay-window {
          type enumeration {
            enum "32";
            enum "64";
            enum "128";
            enum "256";
            enum "512";
          }
        }
        leaf-list transform {
          tailf:cli-flat-list-syntax;
          ordered-by user;
          type uint16;
        }
      }
    }
    list pw-port {
      tailf:ncs-device-type "cli-ned";
      tailf:display-when "not(../ncs:module) or ../ncs:module[ncs:name='netsim-ned-alu-sr']";
      key "pw-port-id";
      leaf pw-port-id {
        type string;
      }
      leaf description {
        type string;
      }
      leaf encap-type {
        type enumeration {
          enum "dot1q";
          enum "qinq";
        }
      }
    }
    list port {
      tailf:ncs-device-type "cli-ned";
      tailf:display-when "not(../ncs:module) or ../ncs:module[ncs:name='netsim-ned-alu-sr']";
      key "port-id";
      leaf port-id {
        type string;
      }
      leaf description {
        type string;
      }
      container access {
        tailf:cli-add-mode;

        grouping port-xgress-grouping {
          container pool {
            tailf:cli-add-mode;
            leaf amber-alarm-threshold {
              type uint16;
            }
            leaf red-alarm-threshold {
              type uint16;
            }
            leaf resv-cbs {
              type union {
                type uint8;
                type enumeration {
                  enum "default";
                }
              }
            }
            leaf slope-policy {
              type string;
            }
          }
        }
        container egress {
          tailf:cli-add-mode;
          uses port-xgress-grouping;
        }
        container ingress {
          tailf:cli-add-mode;
          uses port-xgress-grouping;
        }
      }
      leaf type {
        type string;
      }
      container aps {
        tailf:cli-add-mode;
        leaf neighbor {
          type union {
            type inet:ipv4-address;
            type inet:ipv6-address;
          }
        }
        leaf switching-mode {
          type enumeration {
            enum "bi-directional";
            enum "uni-1plus1";
          }
        }
        leaf protect-circuit {
          type string;
        }
        container working-circuit {
          tailf:cli-compact-syntax;
          tailf:cli-sequence-commands {
            tailf:cli-reset-siblings;
          }
          leaf port-id {
            tailf:cli-drop-node-name;
            type string;
          }
          leaf number {
            type uint8;
          }
        }
      }
      container connector {
        tailf:cli-add-mode;
        presence "true";
        container breakout {
          presence "true";
          leaf extra {
            tailf:cli-drop-node-name;
            type enumeration {
              enum "c1-40g" {
                value 2;
              }
              enum "c4-10g" {
                value 3;
              }
              enum "c1-100g" {
                value 4;
              }
              enum "c4-25g" {
                value 5;
              }
              enum "c10-10g" {
                value 6;
              }
              enum "c1-400g" {
                value 8;
              }
              enum "c2-100g" {
                value 9;
              }
              enum "c4-100g" {
                value 10;
              }
              enum "c1-10g" {
                value 11;
              }
              enum "c1-25g" {
                value 13;
              }
              enum "c1-50g" {
                value 14;
              }
              enum "c8-50g" {
                value 15;
              }
            }
          }
        }
        leaf rs-fec-mode {
          type enumeration {
            enum "cl91-514-528";
            enum "cl91-514-544";
          }
        }
      }
      container ethernet {
        tailf:cli-add-mode;
        leaf eth-bn-egress-rate-changes {
          type empty;
        }
        leaf egress-port-qos-policy {
          type string;
        }
        leaf connection-type {
          type enumeration {
            enum "sfp";
            enum "copper";
            enum "auto";
          }
        }
        leaf mode {
          tailf:cli-diff-create-before "../network" {
            tailf:xpath-root 3;
          }
          tailf:cli-diff-create-before "../access" {
            tailf:xpath-root 3;
          }
          tailf:cli-diff-create-before "/alu:service/vprn/interface/sap[contains(sap-id,current()/../../port-id)]" {
            tailf:xpath-root 3;
          }
          tailf:cli-diff-create-before "/alu:service/vprn/subscriber-interface/group-interface/sap[contains(id,current()/../../port-id)]" {
            tailf:xpath-root 3;
          }
          tailf:cli-diff-create-before "/alu:service/ies/interface/sap[contains(sap-id,current()/../../port-id)]" {
            tailf:xpath-root 3;
          }
          tailf:cli-diff-create-before "/alu:service/ies/subscriber-interface/group-interface/sap[contains(id,current()/../../port-id)]" {
            tailf:xpath-root 3;
          }
          tailf:cli-diff-create-before "/alu:service/vpls/sap[contains(sap-id,current()/../../port-id)]" {
            tailf:xpath-root 3;
          }
          tailf:cli-diff-create-before "/alu:service/epipe/sap[contains(sap-id,current()/../../port-id)]" {
            tailf:xpath-root 3;
          }
          tailf:cli-diff-create-before "/alu:service/cpipe/sap[contains(sap-id,current()/../../port-id)]" {
            tailf:xpath-root 3;
          }
          type enumeration {
            enum "access";
            enum "network";
            enum "hybrid";
          }
        }
        leaf mode-alt {
          tailf:alt-name "mode";
          tailf:cli-diff-create-before "../network" {
            tailf:xpath-root 3;
          }
          tailf:cli-diff-create-before "../access" {
            tailf:xpath-root 3;
          }
          tailf:cli-diff-create-before "/alu:service/vprn/interface/sap[contains(sap-id,current()/../../port-id)]" {
            tailf:xpath-root 3;
          }
          tailf:cli-diff-create-before "/alu:service/vprn/subscriber-interface/group-interface/sap[contains(id,current()/../../port-id)]" {
            tailf:xpath-root 3;
          }
          tailf:cli-diff-create-before "/alu:service/ies/interface/sap[contains(sap-id,current()/../../port-id)]" {
            tailf:xpath-root 3;
          }
          tailf:cli-diff-create-before "/alu:service/ies/subscriber-interface/group-interface/sap[contains(id,current()/../../port-id)]" {
            tailf:xpath-root 3;
          }
          tailf:cli-diff-create-before "/alu:service/vpls/sap[contains(sap-id,current()/../../port-id)]" {
            tailf:xpath-root 3;
          }
          tailf:cli-diff-create-before "/alu:service/epipe/sap[contains(sap-id,current()/../../port-id)]" {
            tailf:xpath-root 3;
          }
          tailf:cli-diff-create-before "/alu:service/cpipe/sap[contains(sap-id,current()/../../port-id)]" {
            tailf:xpath-root 3;
          }
          type enumeration {
            enum "access";
            enum "network";
            enum "hybrid";
          }
        }
        container dampening {
          tailf:cli-add-mode;
          container suppress-threshold {
            tailf:cli-compact-syntax;
            leaf threshold {
              tailf:cli-drop-node-name;
              type uint32;
            }
            leaf reuse-threshold {
              type uint32;
            }
          }
          container half-life {
            tailf:cli-compact-syntax;
            leaf time {
              tailf:cli-drop-node-name;
              type uint32;
            }
            leaf max-suppress-time {
              type uint32;
            }
          }
          leaf shutdown {
            type boolean;
          }
        }
        leaf-list report-alarm {
          tailf:cli-flat-list-syntax;
          type enumeration {
            enum "signal-fail";
            enum "no-frame-lock";
            enum "high-ber";
            enum "no-block-lock";
            enum "no-am-lock";
            enum "duplicate-lane";
          }
        }
        container disable {
          leaf-list report-alarm {
            tailf:cli-flat-list-syntax;
            type enumeration {
              enum "local";
              enum "remote";
              enum "no-block-lock";
              enum "no-am-lock";
              enum "duplicate-lane";
            }
          }
        }
        container access {
          tailf:cli-add-mode;
          leaf accounting-policy {
            type uint8;
          }
          leaf bandwidth {
            type uint32;
          }
          container egress {
            tailf:cli-add-mode;
            list vport {
              key "name";
              leaf name {
                type string32;
              }
              container agg-rate {
                tailf:cli-add-mode;
                leaf limit-unused-bandwidth {
                  type empty;
                }
                leaf rate {
                  type union {
                    type enumeration {
                      enum "max";
                    }
                    type uint32;
                  }
                }
              }
              leaf description {
                type string;
              }
              leaf egress-rate-modify {
                type empty;
              }
              container host-match {
                list dest {
                  tailf:cli-suppress-mode;
                  key "destination-string";
                  leaf destination-string {
                    type string32;
                  }
                }
              }
              leaf mon-port-sch {
                type empty;
              }
              leaf port-scheduler-policy {
                type string;
              }
              leaf scheduler-policy {
                type string;
              }
            }
            list queue-group {
              key "queue-group-name";
              leaf queue-group-name {
                type string;
              }
              leaf instance {
                tailf:cli-hide-in-submode;
                type uint16;
              }
              leaf description {
                type string;
              }
              container host-match {
                list dest {
                  tailf:cli-suppress-mode;
                  key "destination-string";
                  leaf destination-string {
                    type string32;
                  }
                }
              }
            }
            leaf qos {
              type uint16;
            }
          }
          container ingress {
            tailf:cli-add-mode;
            list queue-group {
              key "id";
              leaf id {
                type string;
              }
            }
          }
        }
        container crc-monitor {
          tailf:cli-add-mode;
          container sd-threshold {
            tailf:cli-compact-syntax;
            tailf:cli-sequence-commands {
              tailf:cli-reset-siblings;
            }
            leaf treshold {
              tailf:cli-drop-node-name;
              type uint8;
            }
            leaf multiplier {
              type uint8;
            }
          }
          container sf-threshold {
            tailf:cli-compact-syntax;
            tailf:cli-sequence-commands {
              tailf:cli-reset-siblings;
            }
            leaf treshold {
              tailf:cli-drop-node-name;
              type uint8;
            }
            leaf multiplier {
              type uint8;
            }
          }
          leaf window-size {
            type uint8;
          }
        }
        leaf collect-stats {
          type empty;
        }
        container autonegotiate {
          choice autonegotiate-choice {
            leaf disable {
              type empty;
            }
            leaf limited {
              type empty;
            }
          }
        }
        leaf dot1q-etype {
          type string;
        }
        container dot1x {
          tailf:cli-add-mode;
          container macsec {
            tailf:cli-add-mode;
            leaf rx-must-be-encrypted {
              type empty;
            }
            leaf-list exclude-protocol {
              tailf:cli-flat-list-syntax;
              type enumeration {
                enum "lacp";
                enum "lldp";
                enum "cdp";
                enum "eapol-start";
                enum "efm-oam";
                enum "eth-cfm";
                enum "ptp";
                enum "ubfd";
              }
            }
            list sub-port {
              key "port-id";
              leaf port-id {
                type uint32;
              }
              unique "ca-name";
              leaf ca-name {
                type string;
              }
              container encap-match {
                tailf:cli-compact-syntax;
                leaf encap {
                  tailf:cli-drop-node-name;
                  type enumeration {
                    enum "all-encap";
                    enum "double-tag";
                    enum "single-tag";
                    enum "untagged";
                  }
                }
                leaf encap-value {
                  tailf:cli-drop-node-name;
                  type string;
                }
              }
              leaf max-peer {
                type uint8;
              }
              leaf shutdown {
                type boolean;
              }
            }
          }
          leaf tunneling {
            type empty;
          }
        }
        container down-when-looped {
          tailf:cli-add-mode;
          leaf use-broadcast-address {
            type empty;
          }
          leaf shutdown {
            type boolean;
          }
        }
        leaf lacp-tunnel {
          type empty;
        }
        container efm-oam {
          tailf:cli-add-mode;
          leaf accept-remote-loopback {
            type empty;
          }
          leaf hold-time {
            type uint8;
          }
          container transmit-interval {
            tailf:cli-compact-syntax;
            tailf:cli-sequence-commands;
            leaf interval {
              tailf:cli-drop-node-name;
              type uint16;
            }
            leaf multiplier {
              type uint8;
            }
          }
          container link-monitoring {
            tailf:cli-add-mode;
            leaf shutdown {
              type boolean;
            }
          }
          leaf tunneling {
            type empty;
          }
          leaf shutdown {
            type boolean;
          }
        }
        container egress {
          tailf:cli-add-mode;
          list exp-secondary-shaper {
            key "secondary-shaper-name";
            leaf secondary-shaper-name {
              type string;
            }
            container agg-burst {
              tailf:cli-add-mode;
              container high-burst-increase {
                tailf:cli-compact-syntax;
                tailf:cli-sequence-commands {
                  tailf:cli-reset-siblings;
                }
                leaf size {
                  tailf:cli-drop-node-name;
                  type uint16;
                }
                leaf rate {
                  tailf:cli-drop-node-name;
                  type enumeration {
                    enum "bytes";
                    enum "kilobytes";
                  }
                }
              }
              container low-burst-limit {
                tailf:cli-compact-syntax;
                tailf:cli-sequence-commands {
                  tailf:cli-reset-siblings;
                }
                leaf size {
                  tailf:cli-drop-node-name;
                  type uint32;
                }
                leaf rate {
                  tailf:cli-drop-node-name;
                  type enumeration {
                    enum "bytes";
                    enum "kilobytes";
                  }
                }
              }
            }
            container class {
              tailf:cli-compact-syntax;
              tailf:cli-sequence-commands {
                tailf:cli-reset-siblings;
              }
              leaf class-number {
                tailf:cli-drop-node-name;
                type uint8;
              }
              leaf rate {
                type union {
                  type enumeration {
                    enum "max";
                  }
                  type uint32;
                }
              }
            }
            leaf low-burst-max-class {
              type uint8;
            }
            container rate {
              tailf:cli-compact-syntax;
              tailf:cli-sequence-commands {
                tailf:cli-reset-siblings;
              }
              leaf rate {
                tailf:cli-drop-node-name;
                type union {
                  type enumeration {
                    enum "max";
                  }
                  type uint32;
                }
              }
              leaf monitor-threshold {
                type uint16;
              }
            }
          }
          list queue-group {
            key "name";
            leaf name {
              type string;
            }
          }
          leaf scheduler-policy {
            type string;
          }
        }
        leaf egress-rate {
          type uint32;
        }
        leaf egress-scheduler-policy {
          tailf:cli-diff-create-before "../egress-scheduler-override" {
            tailf:xpath-root 3;
          }
          type string;
        }
        container egress-scheduler-override {
          tailf:cli-add-mode;
          presence "true";
          list level {
            tailf:cli-suppress-mode;
            tailf:cli-compact-syntax;
            tailf:cli-sequence-commands {
              tailf:cli-reset-siblings;
            }
            key "priority-level";
            leaf priority-level {
              type uint8;
            }
            leaf rate {
              type union {
                type uint32;
                type enumeration {
                  enum "max";
                }
              }
            }
            leaf cir {
              type union {
                type uint32;
                type enumeration {
                  enum "max";
                }
              }
            }
          }
          leaf max-rate {
            type union {
              type uint32;
              type enumeration {
                enum "max";
              }
            }
          }
        }
        container hold-time {
          tailf:cli-compact-syntax;
          tailf:cli-sequence-commands {
            tailf:cli-reset-all-siblings;
          }
          leaf up {
            tailf:cli-optional-in-sequence;
            type uint32;
          }
          leaf down {
            tailf:cli-optional-in-sequence;
            type uint32;
          }
          leaf unit {
            tailf:cli-drop-node-name;
            type enumeration {
              enum "seconds";
              enum "centiseconds";
            }
          }
        }
        leaf ingress-rate {
          type uint32;
        }
        container alt-ingress-rate {
          tailf:alt-name "ingress-rate";
          tailf:cli-add-mode;
          presence "true";
          leaf ingress-rate {
            tailf:cli-drop-node-name;
            tailf:cli-hide-in-submode;
            type uint16;
          }
          leaf cbs {
            tailf:cli-hide-in-submode;
            type union {
              type uint32;
              type enumeration {
                enum "default";
              }
            }
          }
          choice unit {
            leaf bytes {
              tailf:cli-hide-in-submode;
              type empty;
            }
            leaf kilobytes {
              tailf:cli-hide-in-submode;
              type empty;
            }
          }
          leaf src-pause {
            type empty;
          }
        }
        container lldp {
          tailf:cli-add-mode;
          list dest-mac {
            key "id";
            leaf id {
              type enumeration {
                enum "nearest-bridge";
                enum "nearest-non-tpmr";
                enum "nearest-customer";
              }
            }
            leaf tunnel-nearest-bridge {
              type empty;
            }
            leaf notification {
              type empty;
            }
            leaf admin-status {
              type enumeration {
                enum "rx";
                enum "tx";
                enum "tx-rx";
                enum "disabled";
              }
            }
            leaf port-id-subtype {
              type enumeration {
                enum "tx-if-alias";
                enum "tx-if-name";
                enum "tx-local";
              }
            }
            leaf-list tx-mgmt-address {
              tailf:cli-flat-list-syntax;
              type enumeration {
                enum "system";
                enum "system-ipv6";
              }
            }
            leaf-list tx-tlvs {
              tailf:cli-flat-list-syntax;
              type enumeration {
                enum "port-desc";
                enum "sys-name";
                enum "sys-desc";
                enum "sys-cap";
              }
            }
          }
        }
        leaf encap-type {
          tailf:cli-diff-create-before "/alu:service/vprn/interface/sap[contains(sap-id,current()/../../port-id)]" {
            tailf:xpath-root 3;
          }
          tailf:cli-diff-create-before "/alu:service/vprn/subscriber-interface/group-interface/sap[contains(id,current()/../../port-id)]" {
            tailf:xpath-root 3;
          }
          tailf:cli-diff-create-before "/alu:service/ies/interface/sap[contains(sap-id,current()/../../port-id)]" {
            tailf:xpath-root 3;
          }
          tailf:cli-diff-create-before "/alu:service/ies/subscriber-interface/group-interface/sap[contains(id,current()/../../port-id)]" {
            tailf:xpath-root 3;
          }
          tailf:cli-diff-create-before "/alu:service/vpls/sap[contains(sap-id,current()/../../port-id)]" {
            tailf:xpath-root 3;
          }
          tailf:cli-diff-create-before "/alu:service/epipe/sap[contains(sap-id,current()/../../port-id)]" {
            tailf:xpath-root 3;
          }
          tailf:cli-diff-create-before "/alu:service/cpipe/sap[contains(sap-id,current()/../../port-id)]" {
            tailf:xpath-root 3;
          }
          type enumeration {
            enum "dot1q";
            enum "null";
            enum "qinq";
          }
        }
        leaf mac {
          type ieee-mac;
        }
        leaf mtu {
          type uint16;
        }
        leaf duplex {
          type enumeration {
            enum "full";
            enum "half";
          }
        }
        leaf speed {
          type port-speed;
        }
        leaf alt-speed {
          tailf:alt-name "speed";
          type port-speed;
        }
        container network {
          tailf:cli-add-mode;
          leaf accounting-policy {
            type uint8;
          }
          leaf collect-stats {
            type empty;
          }
          container egress {
            tailf:cli-add-mode;
            list queue-group {
              key "id";
              leaf id {
                type string;
              }
              leaf instance {
                tailf:cli-hide-in-submode;
                type uint16;
              }
              leaf accounting-policy {
                type uint8;
              }
              uses agg-rate-grouping;
              leaf collect-stats {
                type empty;
              }
              leaf description {
                type string;
              }
              leaf policer-control-policy {
                type string;
              }
              container queue-overrides {
                tailf:cli-add-mode;
                list queue {
                  key "queue-id";
                  leaf queue-id {
                    type uint8;
                  }
                }
              }
              leaf scheduler-policy {
                type string;
              }
            }
          }
          leaf queue-policy {
            type string;
          }
          leaf scheduler-mode {
            type scheduler-mode;
          }
          leaf qos {
            type uint32;
          }
        }
        leaf qinq-etype {
          type string;
        }
        container ssm {
          tailf:cli-add-mode;
          leaf code-type {
            type enumeration {
              enum "sonet";
              enum "sdh";
            }
          }
          leaf tx-dus {
            type empty;
          }
          leaf shutdown {
            type boolean;
          }
        }
        leaf util-stats-interval {
          type uint16;
        }
        leaf xgig {
          type enumeration {
            enum "lan";
            enum "wan";
          }
        }
        leaf xor-mode {
          type enumeration {
            enum "rj45";
            enum "sfp";
          }
        }
        container down-on-internal-error {
          presence "true";
          leaf tx-disable {
            type empty;
          }
        }
        leaf rs-fec-mode {
          type enumeration {
            enum "cl91-514-528";
            enum "cl74";
            enum "cl108";
          }
        }
      }
      container hybrid-buffer-allocation {
        tailf:cli-add-mode;

        grouping xgress-weights {
          leaf access {
            type uint8;
          }
          leaf network {
            type uint8;
          }
        }
        container egr-weight {
          tailf:cli-compact-syntax;
          uses xgress-weights;
        }
        container ing-weight {
          tailf:cli-compact-syntax;
          uses xgress-weights;
        }
      }
      container transceiver {
        tailf:cli-add-mode;
        leaf digital-coherent-optics {
          type empty;
        }
      }
      container dwdm {
        tailf:cli-add-mode;
        container amplifier {
          tailf:cli-add-mode;
          leaf-list report-alarms {
            tailf:cli-flat-list-syntax;
            type enumeration {
              enum "ild";
              enum "tmp";
              enum "mth";
              enum "mtl";
              enum "los";
              enum "lop";
              enum "com";
            }
          }
        }
        leaf channel {
          type uint16;
        }
        container coherent {
          tailf:cli-add-mode;
          leaf target-power {
            type decimal64 {
              fraction-digits 3;
            }
          }
          leaf compatibility {
            type enumeration {
              enum "long-haul";
              enum "interop";
              enum "interop2";
            }
          }
          container sweep {
            tailf:cli-compact-syntax;
            leaf start {
              type int32;
            }
            leaf end {
              type int32;
            }
          }
          leaf channel {
            type uint16;
          }
          leaf mode {
            type enumeration {
              enum "manual";
            }
          }
          leaf rx-los-thresh {
            type decimal64 {
              fraction-digits 2;
            }
          }
        }
        leaf frequency {
          type uint32;
        }
        leaf rxdtv-adjust {
          type empty;
        }
        container tdcm {
          tailf:cli-add-mode;
          leaf channel {
            type uint16;
          }
          leaf dispersion {
            type int32;
          }
          leaf mode {
            type enumeration {
              enum "automatic";
              enum "manual";
            }
          }
          leaf-list report-alarms {
            tailf:cli-flat-list-syntax;
            type enumeration {
              enum "ild";
              enum "tmp";
              enum "mth";
              enum "mtl";
              enum "los";
              enum "lop";
              enum "com";
            }
          }
          container sweep {
            tailf:cli-compact-syntax;
            tailf:cli-sequence-commands;
            leaf start {
              type int32;
            }
            leaf end {
              type int32;
            }
          }
          leaf shutdown {
            type boolean;
          }
        }
      }
      container modify-buffer-allocation-rate {
        tailf:cli-add-mode;
        leaf egr-percentage-of-rate {
          type uint16;
        }
        leaf ing-percentage-of-rate {
          type uint16;
        }
      }
      container multilink-bundle {
        tailf:cli-add-mode;
        leaf fragment-threshold {
          type union {
            type uint16;
            type enumeration {
              enum "unlimited";
            }
          }
        }
        list member {
          tailf:cli-suppress-mode;
          key "id";
          leaf id {
            type string;
          }
        }
      }
      container network {
        tailf:cli-add-mode;
        container egress {
          tailf:cli-add-mode;
          container pool {
            tailf:cli-add-mode;
            leaf slope-policy {
              type string;
            }
          }
        }
      }
      container otu {
        tailf:cli-add-mode;
        presence "present";
        leaf async-mapping {
          type empty;
        }
        leaf fec {
          type enumeration {
            enum "g709";
            enum "enhanced";
          }
        }
        leaf otu2-lan-data-rate {
          type enumeration {
            enum "11.049";
            enum "11.096";
          }
        }
        leaf-list report-alarm {
          tailf:cli-flat-list-syntax;
          type enumeration {
            enum "loc";
            enum "los";
            enum "lof";
            enum "lom";
            enum "otu-ais";
            enum "otu-ber-sf";
            enum "otu-ber-sd";
            enum "otu-bdi";
            enum "otu-tim";
            enum "otu-iae";
            enum "otu-biae";
            enum "fec-sf";
            enum "fec-sd";
            enum "fec-fail";
            enum "fec-uncorr";
            enum "odu-ais";
            enum "odu-oci";
            enum "odu-lck";
            enum "odu-bdi";
            enum "odu-tim";
            enum "opu-tim";
            enum "opu-plm";
          }
        }
        leaf sd-threshold {
          type uint8;
        }
        leaf sf-sd-method {
          type enumeration {
            enum "bip8";
            enum "fec";
          }
        }
        leaf sf-threshold {
          type uint8;
        }
        container sm-tti {
          tailf:cli-add-mode;
          container expected {
            choice expected {
              leaf string {
                type string;
              }
              leaf bytes {
                tailf:cli-multi-value;
                type string;
              }
              leaf use-rx {
                type empty;
              }
            }
          }
          container tx {
            choice tx {
              leaf string {
                type string;
              }
              leaf bytes {
                tailf:cli-multi-value;
                type string;
              }
            }
          }
        }
      }
      container sonet-sdh {
        tailf:cli-add-mode;
        leaf clock-source {
          type enumeration {
            enum "loop-timed";
            enum "node-timed";
          }
        }
        leaf framing {
          type enumeration {
            enum "sonet";
            enum "sdh";
          }
        }
        list group {
          tailf:cli-suppress-mode;
          tailf:cli-diff-create-before "../path" {
            tailf:xpath-root 3;
          }
          key "sonet-sdh-index";
          leaf sonet-sdh-index {
            type union {
              type enumeration {
                enum "tug3-1";
                enum "tug3-2";
                enum "tug3-3";
              }
              type string;
            }
          }
          leaf payload {
            type enumeration {
              enum "tu3";
              enum "vt2";
              enum "vt15";
            }
          }
        }
        container hold-time {
          tailf:cli-compact-syntax;
          leaf up {
            type uint8;
          }
          leaf down {
            type uint8;
          }
        }
        leaf loopback {
          type enumeration {
            enum "line";
            enum "internal";
          }
        }

        grouping port-sonet-sdh-path-grouping {
          leaf mode {
            type union {
              type enumeration {
                enum "access";
                enum "network";
              }
              type string;
            }
          }
          leaf encap-type {
            type union {
              type enumeration {
                enum "atm";
                enum "bcp-null";
                enum "bcp-dot1q";
                enum "ipcp";
                enum "ppp-auto";
                enum "frame-relay";
                enum "wan-mirror";
                enum "cisco-hdlc";
              }
              type string;
            }
          }
          leaf egress-scheduler-policy {
            type string;
          }
          leaf crc {
            type enumeration {
              enum "32";
              enum "16";
            }
          }
          leaf scramble {
            type empty;
          }
          container network {
            tailf:cli-add-mode;
            leaf queue-policy {
              type string;
            }
          }
          leaf payload {
            type enumeration {
              enum "sts3";
              enum "tug3";
              enum "ds3";
              enum "vt2";
              enum "vt15";
              enum "ds1";
              enum "e1";
            }
          }
          container frame-relay {
            tailf:cli-add-mode;
            leaf lmi-type {
              type enumeration {
                enum "ansi";
                enum "itu";
                enum "none";
                enum "rev1";
              }
            }
            leaf mode {
              type union {
                type enumeration {
                  enum "dce";
                  enum "dte";
                  enum "bidir";
                }
                type string;
              }
            }
          }
          leaf-list report-alarm {
            tailf:cli-flat-list-syntax;
            type enumeration {
              enum "pais";
              enum "plop";
              enum "prdi";
              enum "pplm";
              enum "prei";
              enum "puneq";
              enum "plcd";
            }
          }
          leaf shutdown {
            type boolean;
          }
        }
        container path-sts3-wrapper {
          tailf:cli-drop-node-name;
          container path {
            container sts3 {
              tailf:cli-add-mode;
              presence "true";
              uses port-sonet-sdh-path-grouping;
            }
          }
        }
        list path {
          key "sonet-sdh-index";
          leaf sonet-sdh-index {
            type string;
          }
          uses port-sonet-sdh-path-grouping;
        }
        leaf-list report-alarm {
          tailf:cli-flat-list-syntax;
          type enumeration {
            enum "lais";
            enum "lrdi";
            enum "ss1f";
            enum "lb2er-sd";
            enum "lb2er-sf";
            enum "slof";
            enum "slos";
            enum "lrei";
            enum "loc";
          }
        }
        container section-trace {
          choice a {
            leaf increment-z0 {
              type empty;
            }
            leaf byte {
              type uint8;
            }
            leaf string {
              type string;
            }
          }
        }
        leaf single-fiber {
          type empty;
        }
        leaf speed {
          type enumeration {
            enum "oc3";
            enum "oc8";
          }
        }
        leaf suppress-lo-alarm {
          type empty;
        }
        container threshold {
          tailf:cli-compact-syntax;
          tailf:cli-sequence-commands;
          leaf value {
            tailf:cli-drop-node-name;
            type enumeration {
              enum "ber-sd";
              enum "ber-sf";
            }
          }
          leaf rate {
            type uint8;
          }
        }
        leaf tx-dus {
          type empty;
        }
      }
      container tdm {
        tailf:cli-add-mode;
        leaf buildout {
          type enumeration {
            enum "long";
            enum "short";
          }
        }
        list ds1 {
          key "ds1-id";
          leaf ds1-id {
            type string;
          }
          container bert {
            tailf:cli-compact-syntax;
            tailf:cli-sequence-commands;
            leaf value {
              type enumeration {
                enum "2e3";
                enum "2e9";
                enum "2e11";
                enum "2e15";
                enum "2e20";
                enum "2e20q";
                enum "2e23";
                enum "ones";
                enum "zeros";
                enum "alternating";
              }
            }
            leaf duration {
              type string;
            }
          }
          leaf bit-error-insertion {
            type uint8;
          }
          leaf framing {
            type enumeration {
              enum "esf";
              enum "sf";
              enum "ds1-unframed";
            }
          }
          list channel-group {
            key "id";
            leaf id {
              type uint8;
            }
            leaf clock-source {
              type enumeration {
                enum "loop-timed";
                enum "node-timed";
              }
            }
            leaf encap-type {
              type enumeration {
                enum "atm";
                enum "bcp-null";
                enum "bcp-dot1q";
                enum "ipcp";
                enum "ppp-auto";
                enum "frame-relay";
                enum "wan-mirror";
                enum "cisco-hdlc";
                enum "cem";
              }
            }
            container ppp {
              tailf:cli-add-mode;
              leaf ber-sf-link-down {
                type empty;
              }
            }
            leaf timeslots {
              type string;
            }
            leaf shutdown {
              type boolean;
            }
          }
          leaf clock-source {
            type enumeration {
              enum "loop-timed";
              enum "node-timed";
              enum "adaptive";
              enum "differential";
            }
          }
          leaf invert-data {
            type empty;
          }
          leaf loopback {
            type enumeration {
              enum "line";
              enum "internal";
              enum "fdl-ansi";
              enum "fdl-bellcore";
              enum "payload-ansi";
              enum "inband-ansi";
              enum "inband-bellcore";
            }
          }
          leaf remote-loop-respond {
            type empty;
          }
          leaf-list report-alarm {
            tailf:cli-flat-list-syntax;
            type enumeration {
              enum "ais";
              enum "los";
              enum "oof";
              enum "rai";
              enum "looped";
              enum "ber-sd";
              enum "ber-sf";
            }
          }
          leaf signal-mode {
            type enumeration {
              enum "cas";
            }
          }
          container threshold {
            tailf:cli-compact-syntax;
            tailf:cli-sequence-commands;
            leaf value {
              type enumeration {
                enum "ber-sd";
                enum "ber-sf";
              }
            }
            leaf rate {
              type enumeration {
                enum "1";
                enum "5";
                enum "10";
                enum "50";
                enum "100";
              }
            }
          }
          leaf shutdown {
            type boolean;
          }
        }
        list ds3 {
          key "ds3-id";
          leaf ds3-id {
            type string;
          }
          container bert {
            tailf:cli-compact-syntax;
            tailf:cli-sequence-commands;
            leaf value {
              type enumeration {
                enum "2e3";
                enum "2e9";
                enum "2e11";
                enum "2e15";
                enum "2e20";
                enum "2e20q";
                enum "2e23";
                enum "ones";
                enum "zeros";
                enum "alternating";
              }
            }
          }
          leaf channelized {
            type enumeration {
              enum "ds1";
              enum "e1";
            }
          }
          leaf clock-source {
            type enumeration {
              enum "loop-timed";
              enum "node-timed";
            }
          }
          leaf encap-type {
            type enumeration {
              enum "atm";
              enum "bcp-null";
              enum "bcp-dot1q";
              enum "ipcp";
              enum "ppp-auto";
              enum "frame-relay";
              enum "wan-mirror";
              enum "cisco-hdlc";
              enum "cem";
            }
          }
          leaf shutdown {
            type boolean;
          }
        }
        list e1 {
          key "e1-id";
          leaf e1-id {
            type string;
          }
          leaf framing {
            type enumeration {
              enum "no-crc-g704";
              enum "g704";
              enum "e1-unframed";
            }
          }
          leaf clock-source {
            type enumeration {
              enum "loop-timed";
              enum "node-timed";
              enum "adaptive";
              enum "differential";
            }
          }
          list channel-group {
            key "channel-group-id";
            leaf channel-group-id {
              type uint8;
            }
            leaf encap-type {
              type enumeration {
                enum "atm";
                enum "bcp-null";
                enum "bcp-dot1q";
                enum "ipcp";
                enum "ppp-auto";
                enum "frame-relay";
                enum "wan-mirror";
                enum "cisco-hdlc";
                enum "cem";
                enum "hdlc";
              }
            }
            leaf-list timeslots {
              tailf:cli-range-list-syntax;
              type uint32;
            }
            leaf shutdown {
              type boolean;
            }
          }
          leaf shutdown {
            type boolean;
          }
        }
        leaf lbo {
          type enumeration {
            enum "0dB";
            enum "-7.5dB";
            enum "-15.0dB";
            enum "-22.5dB";
          }
        }
        leaf length {
          type enumeration {
            enum "133";
            enum "266";
            enum "399";
            enum "533";
            enum "655";
          }
        }
      }
      leaf shutdown {
        type boolean;
      }
    }
    container isa {
      tailf:ncs-device-type "cli-ned";
      tailf:display-when "not(../../ncs:module) or ../../ncs:module[ncs:name='netsim-ned-alu-sr']";
      tailf:cli-add-mode;
      tailf:cli-delete-when-empty;
      list application-assurance-group {
        key "aa-group-id";
        leaf aa-group-id {
          type uint8;
        }
        leaf aa-sub-scale {
          tailf:cli-hide-in-submode;
          type enumeration {
            enum "residential";
            enum "vpn";
            enum "mobile-gateway";
            enum "lightweight-internet";
          }
        }
        leaf shutdown {
          type boolean;
        }
      }
      list tunnel-group {
        key "tunnel-group-id";
        leaf tunnel-group-id {
          type uint16;
        }
        leaf isa-scale-mode {
          tailf:cli-hide-in-submode;
          type enumeration {
            enum "tunnel-limit-32k";
            enum "tunnel-limit-2k";
          }
        }
        leaf active-mda-number {
          type uint8;
        }
        leaf ipsec-responder-only {
          type empty;
        }
        leaf description {
          type string;
        }
        leaf multi-active {
          type empty;
        }
        list mda {
          tailf:cli-suppress-mode;
          key "mda";
          leaf mda {
            type string;
          }
        }
        leaf primary {
          type string;
        }
        list esa-vm {
          tailf:cli-suppress-mode;
          key "esa-id vm-id";
          leaf esa-id {
            type uint8;
          }
          leaf vm-id {
            type uint8;
          }
        }
        leaf reassembly {
          type uint32;
        }
        leaf shutdown {
          type boolean;
        }
      }
      list nat-group {
        key "nat-group-id";
        leaf nat-group-id {
          type uint16;
        }
        leaf description {
          type string;
        }
        leaf active-mda-limit {
          type uint8;
        }
        leaf mda {
          type string;
        }
        leaf shutdown {
          type boolean;
        }
      }
    }
    container port-xc {
      tailf:ncs-device-type "cli-ned";
      tailf:display-when "not(../../ncs:module) or ../../ncs:module[ncs:name='netsim-ned-alu-sr']";
      tailf:cli-add-mode;
      list pxc {
        tailf:cli-diff-create-before "/alu:port" {
          tailf:xpath-root 3;
        }
        key "pxc-id";
        leaf pxc-id {
          type uint8;
        }
        leaf description {
          type string;
        }
        leaf port {
          type string;
        }
        leaf shutdown {
          type boolean;
        }
      }
    }
    container macsec {
      tailf:ncs-device-type "cli-ned";
      tailf:display-when "not(../../ncs:module) or ../../ncs:module[ncs:name='netsim-ned-alu-sr']";
      tailf:cli-add-mode;
      list connectivity-association {
        key "name";
        leaf name {
          type string;
        }
        leaf description {
          type string;
        }
        container static-cak {
          tailf:cli-add-mode;
          list pre-shared-key {
            key "key-id encryption-type";
            leaf key-id {
              type uint8;
            }
            leaf encryption-type {
              type enumeration {
                enum "aes-128-cmac";
                enum "aes-256-cmac";
              }
            }
            container cak {
              tailf:cli-compact-syntax;
              leaf val {
                tailf:cli-drop-node-name;
                type string;
              }
              leaf algo {
                tailf:cli-drop-node-name;
                type enumeration {
                  enum "hash";
                  enum "hash2";
                  enum "custom";
                }
              }
            }
            leaf ckn {
              type string;
            }
          }
        }
        leaf shutdown {
          type boolean;
        }
      }
    }
    list lag {
      tailf:ncs-device-type "cli-ned";
      tailf:display-when "not(../ncs:module) or ../ncs:module[ncs:name='netsim-ned-alu-sr']";
      tailf:cli-diff-create-before "/alu:service/vprn/interface/sap[starts-with(sap-id,'lag')][contains(sap-id,current()/id)]" {
        tailf:xpath-root 3;
      }
      tailf:cli-diff-create-before "/alu:service/vprn/subscriber-interface/group-interface/sap[starts-with(id,'lag')][contains(id,current()/id)]" {
        tailf:xpath-root 3;
      }
      tailf:cli-diff-create-before "/alu:service/ies/interface/sap[starts-with(sap-id,'lag')][contains(sap-id,current()/id)]" {
        tailf:xpath-root 3;
      }
      tailf:cli-diff-create-before "/alu:service/ies/subscriber-interface/group-interface/sap[starts-with(id,'lag')][contains(id,current()/id)]" {
        tailf:xpath-root 3;
      }
      tailf:cli-diff-create-before "/alu:service/vpls/sap[starts-with(sap-id,'lag')][contains(sap-id,current()/id)]" {
        tailf:xpath-root 3;
      }
      tailf:cli-diff-create-before "/alu:service/epipe/sap[starts-with(sap-id,'lag')][contains(sap-id,current()/id)]" {
        tailf:xpath-root 3;
      }
      tailf:cli-diff-create-before "/alu:service/cpipe/sap[starts-with(sap-id,'lag')][contains(sap-id,current()/id)]" {
        tailf:xpath-root 3;
      }
      key "id";
      leaf id {
        type uint32;
      }
      leaf name {
        tailf:cli-hide-in-submode;
        type string;
      }
      leaf description {
        type string;
      }
      container hash-weight-threshold {
        tailf:cli-compact-syntax;
        tailf:cli-sequence-commands {
          tailf:cli-reset-all-siblings;
        }
        leaf weight {
          tailf:cli-drop-node-name;
          type uint32;
        }
        leaf action {
          type enumeration {
            enum "down";
            enum "dynamic-cost";
            enum "static-cost";
          }
        }
        leaf cost {
          tailf:cli-optional-in-sequence;
          type uint32;
        }
      }
      leaf port-weight-speed {
        type uint32;
      }
      container hold-time {
        leaf down {
          type uint32;
        }
      }
      container bfd {
        tailf:cli-add-mode;
        list family {
          key "family";
          leaf family {
            type enumeration {
              enum "ipv4";
              enum "ipv6";
            }
          }
          leaf bfd-on-distributing-only {
            type empty;
          }
          leaf local-ip-address {
            type union {
              type inet:ipv4-address;
              type inet:ipv6-address;
            }
          }
          leaf max-admin-down-time {
            type union {
              type int16;
              type enumeration {
                enum "infinite";
              }
            }
          }
          leaf max-setup-time {
            type union {
              type int32;
              type enumeration {
                enum "infinite";
              }
            }
          }
          leaf multiplier {
            type uint8;
          }
          leaf receive-interval {
            type uint32;
          }
          leaf remote-ip-address {
            type union {
              type inet:ipv4-address;
              type inet:ipv6-address;
            }
          }
          leaf transmit-interval {
            type uint32;
          }
          leaf shutdown {
            type boolean;
          }
        }
      }
      leaf port-type {
        type enumeration {
          enum "standard";
          enum "hsmda";
        }
      }
      list port {
        tailf:cli-suppress-mode;
        tailf:cli-diff-create-before "/alu:router/interface/qos/egress-port-redirect-group" {
          tailf:xpath-root 3;
          tailf:cli-when-target-set;
        }
        key "port-id";
        leaf port-id {
          type string;
        }
        leaf sub-group {
          type uint32;
        }
        container priority {
          tailf:cli-compact-syntax;
          tailf:cli-sequence-commands {
            tailf:cli-reset-siblings;
          }
          leaf priority {
            tailf:cli-drop-node-name;
            type uint32;
          }
          leaf sub-group {
            type uint32;
          }
        }
      }
      container per-link-hash {
        tailf:cli-drop-node-name;
        tailf:cli-compact-syntax;
        tailf:cli-sequence-commands {
          tailf:cli-reset-all-siblings;
        }
        leaf per-link-hash {
          tailf:cli-diff-create-before "../../access/per-fp-egr-queuing" {
            tailf:xpath-root 3;
            tailf:cli-when-target-delete;
          }
          tailf:cli-diff-create-before "../../access/per-fp-ing-queuing" {
            tailf:xpath-root 3;
            tailf:cli-when-target-create;
          }
          tailf:cli-diff-create-before "../../access/per-fp-sap-instance" {
            tailf:xpath-root 3;
            tailf:cli-when-target-create;
          }
          tailf:cli-diff-create-before "../../port" {
            tailf:xpath-root 3;
            tailf:cli-when-target-create;
          }
          tailf:cli-diff-create-before "../../shutdown" {
            tailf:xpath-root 3;
          }
          type empty;
        }
        leaf weighted {
          type empty;
        }
        leaf auto-rebalance {
          type empty;
        }
      }
      container access {
        tailf:cli-add-mode;
        container adapt-qos {
          tailf:cli-compact-syntax;
          tailf:cli-sequence-commands {
            tailf:cli-reset-all-siblings;
          }
          leaf adapt {
            tailf:cli-drop-node-name;
            type enumeration {
              enum "link";
              enum "port-fair";
              enum "distribute";
            }
          }
          leaf include-egr-hash-cfg {
            type empty;
          }
        }
        leaf per-fp-egr-queuing {
          type empty;
        }
        leaf per-fp-ing-queuing {
          type empty;
        }
        leaf per-fp-sap-instance {
          type empty;
        }
      }
      leaf mode {
        tailf:cli-diff-create-before "/alu:lag/port/port-id" {
          tailf:xpath-root 3;
        }
        tailf:cli-diff-create-before "/alu:service/vprn/interface/sap[starts-with(sap-id,'lag')][contains(sap-id,current()/../id)]" {
          tailf:xpath-root 3;
        }
        tailf:cli-diff-create-before "/alu:service/vprn/subscriber-interface/group-interface/sap[starts-with(id,'lag')][contains(id,current()/../id)]" {
          tailf:xpath-root 3;
        }
        tailf:cli-diff-create-before "/alu:service/ies/interface/sap[starts-with(sap-id,'lag')][contains(sap-id,current()/../id)]" {
          tailf:xpath-root 3;
        }
        tailf:cli-diff-create-before "/alu:service/ies/subscriber-interface/group-interface/sap[starts-with(id,'lag')][contains(id,current()/../id)]" {
          tailf:xpath-root 3;
        }
        tailf:cli-diff-create-before "/alu:service/vpls/sap[starts-with(sap-id,'lag')][contains(sap-id,current()/../id)]" {
          tailf:xpath-root 3;
        }
        tailf:cli-diff-create-before "/alu:service/epipe/sap[starts-with(sap-id,'lag')][contains(sap-id,current()/../id)]" {
          tailf:xpath-root 3;
        }
        tailf:cli-diff-create-before "/alu:service/cpipe/sap[starts-with(sap-id,'lag')][contains(sap-id,current()/../id)]" {
          tailf:xpath-root 3;
        }
        type enumeration {
          enum "access";
          enum "network";
          enum "hybrid";
        }
      }
      leaf monitor-oper-group {
        type string;
      }
      leaf encap-type {
        tailf:cli-diff-create-before "/alu:service/vprn/interface/sap[starts-with(sap-id,'lag')][contains(sap-id,current()/../id)]" {
          tailf:xpath-root 3;
        }
        tailf:cli-diff-create-before "/alu:service/vprn/subscriber-interface/group-interface/sap[starts-with(id,'lag')][contains(id,current()/../id)]" {
          tailf:xpath-root 3;
        }
        tailf:cli-diff-create-before "/alu:service/ies/interface/sap[starts-with(sap-id,'lag')][contains(sap-id,current()/../id)]" {
          tailf:xpath-root 3;
        }
        tailf:cli-diff-create-before "/alu:service/ies/subscriber-interface/group-interface/sap[starts-with(id,'lag')][contains(id,current()/../id)]" {
          tailf:xpath-root 3;
        }
        tailf:cli-diff-create-before "/alu:service/vpls/sap[starts-with(sap-id,'lag')][contains(sap-id,current()/../id)]" {
          tailf:xpath-root 3;
        }
        tailf:cli-diff-create-before "/alu:service/epipe/sap[starts-with(sap-id,'lag')][contains(sap-id,current()/../id)]" {
          tailf:xpath-root 3;
        }
        tailf:cli-diff-create-before "/alu:service/cpipe/sap[starts-with(sap-id,'lag')][contains(sap-id,current()/../id)]" {
          tailf:xpath-root 3;
        }
        type enumeration {
          enum "dot1q";
          enum "null";
          enum "qinq";
        }
      }
      leaf dynamic-cost {
        type empty;
      }
      leaf mac {
        type string;
      }
      list link-map-profile {
        key "link-map-profile-id";
        leaf link-map-profile-id {
          type uint8;
        }
        leaf description {
          type string;
        }
        leaf failure-mode {
          type enumeration {
            enum "per-link-hash";
            enum "discard";
          }
        }
        list link {
          tailf:cli-suppress-mode;
          key "port-id";
          leaf port-id {
            type string;
          }
          leaf role {
            tailf:cli-drop-node-name;
            type enumeration {
              enum "primary";
              enum "secondary";
            }
          }
        }
      }
      container port-threshold {
        tailf:cli-compact-syntax;
        tailf:cli-sequence-commands;
        leaf value {
          tailf:cli-drop-node-name;
          type uint8;
        }
        leaf action {
          type enumeration {
            enum "dynamic-cost";
            enum "down";
          }
        }
      }
      container scheduler-mode {
        container vlan-qos {
          tailf:cli-add-mode;
          presence "true";
          list vlan-qos-policy {
            key "vlan-qos-policy-name";
            leaf vlan-qos-policy-name {
              type string;
            }
            container agg-rate {
              tailf:cli-add-mode;
              container rate {
                tailf:cli-compact-syntax;
                tailf:cli-sequence-commands {
                  tailf:cli-reset-all-siblings;
                }
                leaf pir {
                  tailf:cli-drop-node-name;
                  type union {
                    type enumeration {
                      enum "max";
                    }
                    type uint32;
                  }
                }
                leaf cir {
                  type union {
                    type uint32;
                    type enumeration {
                      enum "max";
                    }
                  }
                }
              }
            }
          }
        }
      }
      container lacp {
        tailf:cli-compact-syntax;
        tailf:cli-sequence-commands;
        leaf mode {
          tailf:cli-drop-node-name;
          type enumeration {
            enum "passive";
            enum "active";
          }
        }
        leaf administrative-key {
          tailf:cli-optional-in-sequence;
          type uint16;
        }
        leaf system-id {
          tailf:cli-optional-in-sequence;
          type string;
        }
        leaf system-priority {
          type uint16;
        }
      }
      leaf lacp-mux-control {
        type enumeration {
          enum "coupled";
          enum "independent";
        }
      }
      leaf lacp-xmit-interval {
        type enumeration {
          enum "slow";
          enum "fast";
        }
      }
      leaf lacp-xmit-standby {
        type empty;
      }
      container selection-criteria {
        tailf:cli-compact-syntax;
        tailf:cli-sequence-commands {
          tailf:cli-reset-all-siblings;
        }
        leaf criteria {
          tailf:cli-drop-node-name;
          type enumeration {
            enum "best-port";
            enum "highest-count";
            enum "highest-weight";
          }
        }
        leaf slave-to-partner {
          tailf:cli-optional-in-sequence;
          type empty;
        }
        leaf subgroup-hold-time {
          type union {
            type enumeration {
              enum "infinite";
            }
            type uint16;
          }
        }
      }
      leaf standby-signaling {
        type enumeration {
          enum "lacp";
          enum "power-off";
        }
      }
      container weight-threshold {
        tailf:cli-compact-syntax;
        tailf:cli-sequence-commands {
          tailf:cli-reset-all-siblings;
        }
        leaf value {
          tailf:cli-drop-node-name;
          type uint8;
        }
        leaf action {
          type enumeration {
            enum "dynamic-cost";
            enum "down";
          }
        }
      }
      leaf shutdown {
        type boolean;
      }
    }
    container fwd-path-ext {
      tailf:ncs-device-type "cli-ned";
      tailf:display-when "not(../../ncs:module) or ../../ncs:module[ncs:name='netsim-ned-alu-sr']";
      tailf:cli-add-mode;
      container sdp-id-range {
        tailf:cli-compact-syntax;
        tailf:cli-sequence-commands {
          tailf:cli-reset-siblings;
        }
        leaf from {
          type uint16;
        }
        leaf to {
          type uint16;
        }
      }
      list fpe {
        key "fpe-id";
        leaf fpe-id {
          type uint8;
        }
        container path {
          tailf:cli-compact-syntax;
          tailf:cli-sequence-commands {
            tailf:cli-reset-siblings;
          }
          leaf pxc {
            tailf:cli-optional-in-sequence;
            type uint8;
          }
          leaf xc-a {
            type string;
          }
          leaf xc-b {
            type string;
          }
        }
        leaf pw-port {
          type empty;
        }
      }
    }
    container cron {
      tailf:ncs-device-type "cli-ned";
      tailf:display-when "not(../../ncs:module) or ../../ncs:module[ncs:name='netsim-ned-alu-sr']";
      tailf:cli-add-mode;
      list script {
        key "id";
        leaf id {
          type string;
        }
        leaf description {
          type string;
        }
        leaf location {
          type string;
        }
        leaf shutdown {
          type boolean;
        }
      }
      list action {
        key "id";
        leaf id {
          type string;
        }
        leaf max-completed {
          type uint8;
        }
        leaf expire-time {
          type expire-time;
        }
        leaf lifetime {
          type expire-time;
        }
        leaf results {
          type string;
        }
        leaf script {
          type string;
        }
        leaf shutdown {
          type boolean;
        }
      }
      uses cron-schedule-grouping {
        augment "schedule" {
          leaf action {
            type string;
          }
        }
      }
    }
    container mcast-management {
      tailf:ncs-device-type "cli-ned";
      tailf:display-when "not(../../ncs:module) or ../../ncs:module[ncs:name='netsim-ned-alu-sr']";
      tailf:cli-add-mode;
      list bandwidth-policy {
        key "policy-name";
        leaf policy-name {
          type string32;
        }

        grouping path-grouping {
          leaf path-limit {
            type uint16;
          }
        }
        container primary-path {
          tailf:cli-add-mode;
          uses path-grouping;
        }
        container secondary-path {
          tailf:cli-add-mode;
          uses path-grouping;
        }
      }
      container chassis-level {
        tailf:cli-add-mode;
        leaf round-robin-inactive-records {
          type empty;
        }
        container per-mcast-plane-capacity {
          tailf:cli-add-mode;

          grouping capacity-percentage-grouping {
            leaf primary-percentage {
              tailf:cli-drop-node-name;
              type decimal64 {
                fraction-digits 2;
              }
            }
            leaf secondary {
              type decimal64 {
                fraction-digits 2;
              }
            }
          }
          container mcast-capacity {
            tailf:cli-compact-syntax;
            tailf:cli-sequence-commands {
              tailf:cli-reset-siblings;
            }
            uses capacity-percentage-grouping;
          }
          container redundant-mcast-capacity {
            tailf:cli-compact-syntax;
            tailf:cli-sequence-commands {
              tailf:cli-reset-siblings;
            }
            uses capacity-percentage-grouping;
          }
          leaf total-capacity {
            type enumeration {
              enum "2000";
              enum "4000";
              enum "5250";
              enum "8250";
              enum "dynamic";
            }
          }
        }
      }
      list multicast-info-policy {
        key "policy-name";
        leaf policy-name {
          type string32;
        }
        list bundle {
          key "bundle-name";
          leaf bundle-name {
            type string32;
          }
          leaf keepalive-override {
            type uint32;
          }
          list channel {
            key "ip-address";
            leaf ip-address {
              type union {
                type inet:ipv4-address;
                type inet:ipv6-address;
              }
            }
            leaf second-ip-address {
              tailf:cli-drop-node-name;
              tailf:cli-hide-in-submode;
              type union {
                type inet:ipv4-address;
                type inet:ipv6-address;
              }
            }
            container bw-activity {
              tailf:cli-compact-syntax;
              tailf:cli-sequence-commands {
                tailf:cli-reset-siblings;
              }
              leaf activity {
                tailf:cli-drop-node-name;
                type enumeration {
                  enum "use-admin-bw";
                  enum "dynamic";
                }
              }
              leaf falling-delay {
                tailf:cli-optional-in-sequence;
                type uint16;
              }
              leaf black-hole-rate {
                type uint32;
              }
            }
          }
          leaf description {
            type string;
          }
        }
      }
    }
    container oam-pm {
      tailf:ncs-device-type "cli-ned";
      tailf:display-when "not(../../ncs:module) or ../../ncs:module[ncs:name='netsim-ned-alu-sr']";
      tailf:cli-add-mode;
      list bin-group {
        key "bin-group-number";
        leaf bin-group-number {
          type uint8;
        }
        leaf fd-bin-count {
          tailf:cli-hide-in-submode;
          type uint8;
        }
        leaf fdr-bin-count {
          tailf:cli-hide-in-submode;
          type uint8;
        }
        leaf ifdv-bin-count {
          tailf:cli-hide-in-submode;
          type uint8;
        }
        leaf description {
          type string;
        }
        list bin-type {
          key "bt";
          leaf bt {
            type enumeration {
              enum "fd";
              enum "fdr";
              enum "ifdv";
            }
          }
          list bin {
            key "bin-number";
            leaf bin-number {
              type uint8;
            }
            leaf lower-bound {
              type uint32;
            }
          }

          typedef bin-group-event-type {
            type enumeration {
              enum "forward";
              enum "backward";
              enum "round-trip";
            }
          }
          list delay-event {
            tailf:cli-suppress-mode;
            tailf:cli-compact-syntax;
            tailf:cli-sequence-commands {
              tailf:cli-reset-siblings;
            }
            tailf:cli-delete-when-empty;
            key "event-type";
            leaf event-type {
              type bin-group-event-type;
            }
            leaf lowest-bin {
              type uint8;
            }
            leaf threshold {
              type uint32;
            }
            leaf clear {
              type uint32;
            }
          }
          list delay-event-exclusion {
            tailf:cli-suppress-mode;
            tailf:cli-compact-syntax;
            tailf:cli-sequence-commands {
              tailf:cli-reset-siblings;
            }
            tailf:cli-delete-when-empty;
            key "event-type";
            leaf event-type {
              type bin-group-event-type;
            }
            leaf lowest-bin {
              type uint8;
            }
          }
        }
        leaf shutdown {
          type boolean;
        }
      }
      list session {
        key "session-name";
        leaf session-name {
          type string32;
        }
        leaf test-family {
          tailf:cli-hide-in-submode;
          type enumeration {
            enum "ethernet";
            enum "ip";
          }
        }
        leaf session-type {
          tailf:cli-hide-in-submode;
          type enumeration {
            enum "proactive";
            enum "on-demand";
          }
        }
        leaf bin-group {
          type uint8;
        }
        leaf description {
          type string;
        }
        list meas-interval {
          tailf:cli-diff-create-before "../ethernet/dmm/shutdown" {
            tailf:xpath-root 3;
          }
          key "interval";
          leaf interval {
            type enumeration {
              enum "5-mins";
              enum "15-mins";
              enum "1-hour";
              enum "1-day";
            }
          }
          leaf accounting-policy {
            type uint8;
          }
          leaf intervals-stored {
            type uint8;
          }
          container event-mon {
            tailf:cli-add-mode;
            leaf delay-events {
              type empty;
            }
            leaf loss-events {
              type empty;
            }
            leaf shutdown {
              type boolean;
            }
          }
        }
        container ip {
          tailf:cli-add-mode;
          leaf router-instance {
            type string;
          }
          leaf source-udp-port {
            type uint32;
          }
          leaf destination {
            type inet:ipv4-address;
          }
          leaf source {
            type inet:ipv4-address;
          }
          leaf dest-udp-port {
            type uint32;
          }
          list twamp-light {
            key "test-id";
            leaf test-id {
              type uint32;
            }
            leaf record-stats {
              type enumeration {
                enum "delay";
                enum "loss";
                enum "delay-and-loss";
              }
            }
            leaf shutdown {
              type boolean;
            }
          }
        }
        container ethernet {
          tailf:cli-add-mode;
          leaf dest-mac {
            type ieee-mac;
          }
          leaf priority {
            type uint8;
          }
          container source {
            tailf:cli-compact-syntax;
            tailf:cli-sequence-commands {
              tailf:cli-reset-all-siblings;
            }
            leaf mep {
              type uint16;
            }
            leaf domain {
              type uint32;
            }
            leaf association {
              type uint32;
            }
          }
          container dmm {
            tailf:cli-add-mode;
            leaf test-id {
              tailf:cli-hide-in-submode;
              type uint32;
            }
            leaf shutdown {
              type boolean;
            }
          }
        }
      }
    }
    container qos {
      tailf:ncs-device-type "cli-ned";
      tailf:display-when "not(../../ncs:module) or ../../ncs:module[ncs:name='netsim-ned-alu-sr']";
      tailf:cli-add-mode;
      list adv-config-policy {
        key "adv-config-policy-name";
        leaf adv-config-policy-name {
          type string;
        }
        container child-control {
          tailf:cli-add-mode;
          container offered-measurement {
            tailf:cli-add-mode;
            leaf fast-start {
              type empty;
            }
            leaf fast-stop {
              type empty;
            }
          }
        }
        leaf description {
          type string;
        }
      }
      list dot1p-fc-map {
        key "name";
        leaf name {
          type string;
        }
        container default-action {
          tailf:cli-sequence-commands {
            tailf:cli-reset-all-siblings;
          }
          tailf:cli-compact-syntax;
          leaf fc {
            type enumeration {
              enum "be";
              enum "l2";
              enum "af";
              enum "l1";
              enum "h2";
              enum "ef";
              enum "h1";
              enum "nc";
            }
          }
          leaf profile {
            type enumeration {
              enum "in";
              enum "out";
              enum "use-de";
            }
          }
        }
        list dot1p {
          tailf:cli-suppress-mode;
          tailf:cli-compact-syntax;
          key "priority";
          leaf priority {
            type uint8;
          }
          leaf fc {
            type enumeration {
              enum "be";
              enum "l2";
              enum "af";
              enum "l1";
              enum "h2";
              enum "ef";
              enum "h1";
              enum "nc";
            }
          }
          leaf profile {
            type enumeration {
              enum "in";
              enum "out";
              enum "use-de";
            }
          }
        }
      }
      list egress-remark-policy {
        key "egress-remark-policy-name";
        leaf egress-remark-policy-name {
          type string;
        }
        leaf description {
          type string;
        }
        list fc {
          key "fc-name";
          leaf fc-name {
            type fc-name;
          }
          container dscp {
            tailf:cli-compact-syntax;
            choice dscp {
              leaf dscp-name {
                tailf:cli-drop-node-name;
                type string;
              }
              case in-out {
                leaf in-profile {
                  type string;
                }
                leaf out-profile {
                  type string;
                }
              }
            }
          }
          container dot1p {
            tailf:cli-compact-syntax;
            tailf:cli-sequence-commands {
              tailf:cli-reset-all-siblings;
            }
            uses dot1p-params-grouping;
          }
          container lsp-exp {
            tailf:cli-compact-syntax;
            tailf:cli-sequence-commands {
              tailf:cli-reset-all-siblings;
            }
            choice lsp-exp {
              leaf lsp-exp-value {
                tailf:cli-drop-node-name;
                type uint8;
              }
              case in-out {
                leaf in-profile {
                  type uint8;
                }
                leaf out-profile {
                  type uint8;
                }
              }
            }
          }
        }
      }
      list fp-resource-policy {
        key "policy-id";
        leaf policy-id {
          type string;
        }
        leaf description {
          type string;
        }
      }
      container packet-byte-offset {
        tailf:cli-add-mode;
        leaf shutdown {
          type boolean;
        }
      }
      list ingress-classification-policy {
        key "name";
        leaf name {
          type string;
        }
        leaf description {
          type string;
        }
        leaf allow-attachment {
          tailf:cli-hide-in-submode;
          type enumeration {
            enum "non-epipe";
            enum "any";
          }
        }
        container default-action {
          tailf:cli-compact-syntax;
          tailf:cli-sequence-commands {
            tailf:cli-reset-all-siblings;
          }
          leaf fc {
            type fc-name;
          }
          leaf profile {
            type in-out;
          }
        }
        uses qos-dscp-list-grouping;
        uses qos-lsp-exp-grouping;
        uses qos-dot1p-list-grouping;
      }
      list network-ingress {
        key "name";
        leaf name {
          type string;
        }
        leaf description {
          type string;
        }
        leaf ingress-classification-policy {
          type string;
        }
        list policer {
          key "policer-id";
          leaf policer-id {
            type uint8;
          }
          // NCS expand uses statement
          container cbs {
            tailf:cli-compact-syntax;
            tailf:cli-sequence-commands {
              tailf:cli-reset-siblings;
            }
            // NCS expand uses statement
            leaf size {
              tailf:cli-drop-node-name;
              type union {
                type uint32;
                type enumeration {
                  enum "default";
                }
              }
            }
            leaf unit {
              tailf:cli-drop-node-name;
              type enumeration {
                enum "bytes";
                enum "kilobytes";
              }
            }
          }
          container mbs {
            tailf:cli-compact-syntax;
            tailf:cli-sequence-commands {
              tailf:cli-reset-siblings;
            }
            // NCS expand uses statement
            leaf size {
              tailf:cli-drop-node-name;
              type union {
                type uint32;
                type enumeration {
                  enum "default";
                }
              }
            }
            leaf unit {
              tailf:cli-drop-node-name;
              type enumeration {
                enum "bytes";
                enum "kilobytes";
              }
            }
          }
          container rate {
            tailf:cli-compact-syntax;
            tailf:cli-sequence-commands {
              tailf:cli-reset-siblings;
            }
            leaf pir {
              tailf:cli-drop-node-name;
              type rate-type;
            }
            leaf cir {
              type rate-type;
            }
          }
          leaf stat-mode {
            type policer-stat-mode;
          }
        }
        list fc {
          key "fc-name";
          leaf fc-name {
            type fc-name;
          }
          leaf multicast-policer {
            type uint8;
          }
          leaf policer {
            type uint8;
          }
        }
      }
      list port-qos-policy {
        key "port-qos-policy-name";
        leaf port-qos-policy-name {
          type string;
        }
        leaf description {
          type string;
        }
        list queue {
          key "queue-id";
          leaf queue-id {
            type uint8;
          }
          leaf queue-mgmt {
            type string;
          }
          container scheduler-mode {
            tailf:cli-add-mode;
            leaf scheduler-mode {
              tailf:cli-drop-node-name;
              tailf:cli-hide-in-submode;
              type enumeration {
                enum "wfq";
              }
            }
            leaf pir-weight {
              type uint8;
            }
            uses qos-queue-percent-rate-grouping;
          }
        }
        container packet-byte-offset {
          leaf add {
            type enumeration {
              enum "4";
              enum "8";
            }
          }
          leaf subtract {
            type enumeration {
              enum "4";
              enum "8";
            }
          }
        }
        list wrr-weights {
          key "wrr-weights-id";
          leaf wrr-weights-id {
            type uint8;
          }
          leaf mc-weight {
            type uint8;
          }
          leaf uc-weight {
            type uint8;
          }
        }
      }
      list queue-mgmt-policy {
        key "queue-mgmt-name";
        leaf queue-mgmt-name {
          type string;
        }
        leaf description {
          type string;
        }
        container high-slope {
          tailf:cli-add-mode;
          uses slope-params-grouping;
        }
        container low-slope {
          tailf:cli-add-mode;
          uses slope-params-grouping;
        }
        container exceed-slope {
          tailf:cli-add-mode;
          uses slope-params-grouping;
        }
        container highplus-slope {
          tailf:cli-add-mode;
          uses slope-params-grouping;
        }
        leaf mbs {
          type uint32;
        }
      }
      list vlan-qos-policy {
        key "policy-id";
        leaf policy-id {
          type string;
        }
        leaf description {
          type string;
        }
        container packet-byte-offset {
          leaf add {
            type enumeration {
              enum "4";
              enum "8";
            }
          }
          leaf subtract {
            type enumeration {
              enum "4";
              enum "8";
            }
          }
        }
        leaf stat-mode {
          type string;
        }
        list cir-weight-profile {
          key "profile-id";
          leaf profile-id {
            type uint8;
          }
          leaf weight {
            type uint16;
          }
        }
        list queue {
          key "queue-id";
          leaf queue-id {
            type uint8;
          }
          uses qos-queue-percent-rate-grouping;
          leaf queue-mgmt {
            type string;
          }
          container queue-type {
            tailf:cli-add-mode;
            leaf queue-type-alt1 {
              tailf:cli-hide-in-submode;
              tailf:cli-drop-node-name;
              type queue-type;
            }
            leaf queue-type-alt2 {
              tailf:cli-hide-in-submode;
              tailf:cli-drop-node-name;
              type queue-type;
            }
            leaf queue-type-alt3 {
              tailf:cli-hide-in-submode;
              tailf:cli-drop-node-name;
              type queue-type;
            }
            uses qos-queue-percent-rate-grouping;
            leaf cir-weight-profile {
              type uint8;
            }
          }
        }
      }
      leaf ldp-local-fc-enable {
        type boolean;
      }
      list dscp-classification {
        key "classification-id";
        leaf classification-id {
          type uint16;
        }
        leaf description {
          type string;
        }
        uses qos-dscp-list-grouping;
      }
      list fabric-profile {
        key "policy-id";
        leaf policy-id {
          type uint16;
        }
        leaf mode {
          tailf:cli-drop-node-name;
          tailf:cli-hide-in-submode;
          type enumeration {
            enum "aggregate-mode";
            enum "destination-mode";
          }
        }
        container aggregate-rate {
          tailf:cli-compact-syntax;
          tailf:cli-sequence-commands {
            tailf:cli-reset-siblings;
          }
          leaf rate {
            tailf:cli-drop-node-name;
            type union {
              type enumeration {
                enum "default";
              }
              type uint32;
            }
          }
          leaf unshaped-sap-cir {
            type uint16;
          }
        }
        leaf description {
          type string;
        }
        list dest-mda {
          key "id";
          leaf id {
            type union {
              type enumeration {
                enum "multipoint";
              }
              type uint32;
            }
          }
          leaf rate {
            type union {
              type enumeration {
                enum "default";
              }
              type uint32;
            }
          }
        }
      }
      container match-list {
        tailf:cli-add-mode;
        list ip-prefix-list {
          key "ip-prefix-list-name";
          leaf ip-prefix-list-name {
            type string32;
          }
          leaf description {
            type string;
          }
          list prefix {
            tailf:cli-suppress-mode;
            key "ip-prefix";
            leaf ip-prefix {
              type tailf:ipv4-address-and-prefix-length;
            }
          }
        }
        list ipv6-prefix-list {
          key "name";
          leaf name {
            type string32;
          }
          leaf description {
            type string;
          }
          list prefix {
            tailf:cli-suppress-mode;
            key "ip-prefix";
            leaf ip-prefix {
              type tailf:ipv6-address-and-prefix-length;
            }
          }
        }
      }
      container mc-mlppp {
        tailf:cli-add-mode;
        list sap-egress {
          key "policy-id";
          uses sap-egress-common-grouping;
          list fc {
            key "fc-name";
            uses sap-egress-fc-grouping;
          }
          leaf scope {
            type enumeration {
              enum "exclusive";
              enum "template";
            }
          }
        }
      }
      list network-queue {
        key "network-queue-name";
        leaf network-queue-name {
          type string;
        }
        leaf description {
          type string;
        }
        list queue {
          key "id";
          leaf id {
            type uint32;
          }
          leaf multipoint {
            tailf:cli-hide-in-submode;
            type empty;
          }
          leaf queue-type {
            tailf:cli-drop-node-name;
            tailf:cli-hide-in-submode;
            type queue-type;
          }
          leaf mbs {
            type decimal64 {
              fraction-digits 2;
            }
          }
          leaf cbs {
            type decimal64 {
              fraction-digits 2;
            }
          }
          leaf high-prio-only {
            type union {
              type enumeration {
                enum "default";
              }
              type uint8;
            }
          }
          container rate {
            tailf:cli-compact-syntax;
            tailf:cli-sequence-commands {
              tailf:cli-reset-siblings;
            }
            leaf percent {
              tailf:cli-drop-node-name;
              tailf:cli-optional-in-sequence;
              type uint8;
            }
            leaf cir {
              type uint8;
            }
            leaf pir {
              type uint8;
            }
          }
          uses port-parent-grouping;
          leaf queue-mgmt {
            type string;
          }
          leaf queue-mode {
            type enumeration {
              enum "strict";
              enum "weighted";
            }
          }
          uses queue-adaptation-grouping;
          container drop-tail {
            tailf:cli-add-mode;
            container low {
              tailf:cli-add-mode;
              leaf percent-reduction-from-mbs {
                type uint8;
              }
            }
          }
        }
        list fc {
          key "id";
          leaf id {
            type string;
          }
          leaf multicast-queue {
            type uint32;
          }
          leaf queue {
            type uint8;
          }
          container egress-hsmda {
            tailf:cli-add-mode;
            leaf queue {
              type uint8;
            }
          }
        }
      }
      container queue-group-templates {
        tailf:cli-add-mode;
        container egress {
          tailf:cli-add-mode;
          list queue-group {
            key "queue-group-name";
            uses queue-group-template-entry {
              augment "queue" {
                uses packet-byte-offset-grouping;
                leaf dynamic-mbs {
                  type empty;
                }
                leaf queue-delay {
                  type uint32;
                }
              }
            }
            leaf queues-hqos-manageable {
              type enumeration {
                enum "enable";
                enum "disable";
              }
            }
          }
        }
        container ingress {
          tailf:cli-add-mode;
          list queue-group {
            key "queue-group-name";
            uses queue-group-template-entry;
          }
        }
      }
      list scheduler-policy {
        key "scheduler-policy-name";
        leaf scheduler-policy-name {
          type string;
        }
        leaf description {
          type string;
        }
        leaf frame-based-accounting {
          type empty;
        }
        list tier {
          key "tier";
          leaf tier {
            type uint8;
          }
          list scheduler {
            key "scheduler-name";
            leaf scheduler-name {
              type string;
            }
            leaf description {
              type string;
            }
            container parent {
              presence "present";
              tailf:cli-compact-syntax;
              leaf scheduler-name {
                tailf:cli-drop-node-name;
                type string;
              }
              leaf weight {
                type string;
              }
              leaf level {
                type string;
              }
              leaf cir-weight {
                type string;
              }
              leaf cir-level {
                type string;
              }
            }
            container port-parent {
              presence "present";
              tailf:cli-compact-syntax;
              leaf weight {
                type string;
              }
              leaf level {
                type string;
              }
              leaf cir-weight {
                type string;
              }
              leaf cir-level {
                type string;
              }
            }
            container rate {
              presence "present";
              tailf:cli-sequence-commands;
              tailf:cli-compact-syntax;
              leaf pir-rate {
                tailf:cli-drop-node-name;
                mandatory true;
                type string;
              }
              leaf cir {
                type string;
              }
            }
            container mbs {
              tailf:cli-compact-syntax;
              leaf size {
                tailf:cli-drop-node-name;
                type uint32;
              }
              leaf unit {
                tailf:cli-drop-node-name;
                type enumeration {
                  enum "bytes";
                  enum "kilobytes";
                }
              }
            }
          }
        }
      }
      list shared-queue {
        key "policy-name";
        leaf policy-name {
          type string;
        }
        leaf description {
          type string;
        }
        container fc {
          presence "present";
          tailf:cli-sequence-commands;
          tailf:cli-compact-syntax;
          leaf fc-name {
            tailf:cli-drop-node-name;
            mandatory true;
            type string;
          }
          leaf broadcast-queue {
            type string;
          }
          leaf multicast-queue {
            type string;
          }
          leaf queue {
            type string;
          }
          leaf unknown-queue {
            type string;
          }
        }
        list queue {
          key "queue-id";
          leaf queue-id {
            type string;
          }
          leaf queue-type {
            tailf:cli-hide-in-submode;
            tailf:cli-drop-node-name;
            type queue-type;
          }
          leaf multipoint {
            tailf:cli-hide-in-submode;
            type empty;
          }
          leaf cbs {
            type string;
          }
          leaf high-prio-only {
            type string;
          }
          leaf mbs {
            type string;
          }
          leaf pool {
            type string;
          }
          container rate {
            tailf:cli-sequence-commands {
              tailf:cli-reset-all-siblings;
            }
            tailf:cli-compact-syntax;
            leaf percent {
              tailf:cli-drop-node-name;
              type string;
            }
            leaf cir {
              type string;
            }
          }
        }
      }
      list mpls-lsp-exp-profile-map {
        tailf:cli-diff-create-before "../network" {
          tailf:xpath-root 3;
        }
        key "policy-id";
        leaf policy-id {
          type uint16;
        }
        leaf description {
          type string;
        }
        list lsp-exp {
          tailf:cli-suppress-mode;
          tailf:cli-compact-syntax;
          tailf:cli-sequence-commands {
            tailf:cli-reset-all-siblings;
          }
          key "lsp-exp-value";
          leaf lsp-exp-value {
            type uint8;
          }
          leaf profile {
            type enumeration {
              enum "in";
              enum "out";
            }
          }
        }
      }
      list access-egress {
        key "policy-id";
        leaf policy-id {
          type uint16;
        }
        leaf remark {
          type uint32;
        }
        list fc {
          key "fc-name";
          leaf fc-name {
            type fc-name;
          }
          leaf dscp-in-profile {
            type dscp-type;
          }
          leaf dscp-out-profile {
            type dscp-type;
          }
          leaf dot1p-in-profile {
            type uint8;
          }
          leaf dot1p-out-profile {
            type uint8;
          }
        }
        leaf description {
          type string;
        }
        list queue {
          key "queue-id";
          leaf queue-id {
            type uint8;
          }
          uses queue-adaptation-grouping;
          leaf queue-mode {
            type enumeration {
              enum "strict";
              enum "weighted";
            }
          }
          leaf queue-mgmt {
            type string;
          }
          container rate {
            tailf:cli-compact-syntax;
            tailf:cli-sequence-commands {
              tailf:cli-reset-siblings;
            }
            leaf cir {
              type union {
                type uint32;
                type enumeration {
                  enum "max";
                }
              }
            }
            leaf pir {
              type union {
                type uint32;
                type enumeration {
                  enum "max";
                }
              }
            }
          }
        }
        container remarking {
          presence "true";
          leaf remarking {
            tailf:cli-drop-node-name;
            type enumeration {
              enum "use-dot1p";
              enum "use-dscp";
              enum "all";
            }
          }
        }
        leaf scope {
          type enumeration {
            enum "exclusive";
            enum "template";
          }
        }
      }
      list sap-egress {
        key "policy-id";
        leaf name {
          tailf:cli-hide-in-submode;
          type string;
        }
        uses qos-dot1p-list-grouping;
        uses sap-egress-common-grouping {
          augment "queue" {
            uses packet-byte-offset-grouping;
            leaf queue-mode {
              type enumeration {
                enum "strict";
                enum "weighted";
              }
            }
            leaf queue-mgmt {
              type string;
            }
            leaf weight {
              type uint8;
            }
          }
          augment "queue/percent-rate" {
            leaf limit {
              tailf:cli-drop-node-name;
              type enumeration {
                enum "local-limit";
                enum "port-limit";
              }
            }
          }
        }
        leaf policers-hqos-manageable {
          type empty;
        }
        list fc {
          key "fc-name";
          uses sap-egress-fc-grouping;
          container policer {
            tailf:cli-compact-syntax;
            tailf:cli-sequence-commands;
            uses policer-ref-grouping;
            leaf port-redirect-group-queue {
              tailf:cli-optional-in-sequence;
              type empty;
            }
            leaf queue {
              type uint8;
            }
          }
        }
        leaf parent-location {
          type enumeration {
            enum "sla";
            enum "default";
          }
        }
        list policer {
          key "policer-id";
          leaf policer-id {
            type uint8;
          }
          uses policer-grouping;
          uses port-parent-grouping;
          container percent-rate {
            tailf:cli-compact-syntax;
            tailf:cli-sequence-commands {
              tailf:cli-reset-all-siblings;
            }
            leaf pir {
              tailf:cli-drop-node-name;
              type decimal64 {
                fraction-digits 2;
              }
            }
            leaf cir {
              tailf:cli-optional-in-sequence;
              type decimal64 {
                fraction-digits 2;
              }
            }
          }
        }
        leaf policy-name {
          type string;
        }
        container ip-criteria {
          tailf:cli-add-mode;
          uses ip-criteria-grouping;
        }
        container ipv6-criteria {
          tailf:cli-add-mode;
          uses ipv6-criteria-grouping;
        }
        list dscp {
          tailf:cli-suppress-mode;
          tailf:cli-compact-syntax;
          key "id";
          leaf id {
            type dscp-type;
          }
          leaf fc {
            type union {
              type fc-name;
              type string;
            }
          }
          leaf profile {
            type enumeration {
              enum "in";
              enum "out";
              enum "exceed";
              enum "inplus";
            }
          }
        }
        leaf remarking {
          type empty;
        }
        leaf remark {
          type uint32;
        }
        leaf scope {
          type enumeration {
            enum "exclusive";
            enum "template";
          }
        }
      }
      list sap-ingress {
        key "policy-id";
        leaf policy-id {
          type uint16;
        }
        leaf name {
          tailf:cli-hide-in-submode;
          type string;
        }
        leaf policer-allocation {
          tailf:cli-hide-in-submode;
          type enumeration {
            enum "none";
            enum "per-fc";
            enum "per-fc-unicast-multipoint";
            enum "per-fc-unicast-multicast";
            enum "per-fc-unicast-broadcast-unknown-multicast";
          }
        }
        leaf description {
          type string;
        }
        leaf ingress-classification-policy {
          type string;
        }
        leaf policy-name {
          type string;
        }
        list meter {
          key "meter-id";
          uses meter-grouping;
        }
        container num-qos-classifiers {
          tailf:cli-compact-syntax;
          leaf num-resources {
            tailf:cli-drop-node-name;
            type uint16;
          }
          leaf keyword {
            tailf:cli-drop-node-name;
            type enumeration {
              enum "ipv6";
              enum "no-ipv6";
            }
          }
        }
        list prec {
          key "ip-prec-value";
          tailf:cli-compact-syntax;
          tailf:cli-suppress-mode;
          leaf ip-prec-value {
            tailf:cli-drop-node-name;
            type uint16;
          }
          leaf fc {
            type fc-name;
          }
          leaf priority {
            type enumeration {
              enum "low";
              enum "high";
            }
          }
        }
        list queue {
          key "queue-id";
          leaf queue-id {
            type uint8;
          }
          uses queue-grouping {
            augment "percent-rate" {
              leaf limit {
                tailf:cli-drop-node-name;
                type enumeration {
                  enum "local-limit";
                  enum "port-limit";
                }
              }
            }
          }
          uses packet-byte-offset-grouping;
        }
        list policer {
          key "policer-id";
          leaf policer-id {
            type uint8;
          }
          uses policer-grouping;
        }
        list fc {
          key "fc-name";
          leaf fc-name {
            type string;
          }
          leaf egress-fc {
            type fc-name;
          }
          container queue {
            tailf:cli-compact-syntax;
            tailf:cli-sequence-commands;
            uses queue-ref-grouping;
          }
          container broadcast-queue {
            tailf:cli-compact-syntax;
            tailf:cli-sequence-commands;
            uses queue-ref-grouping;
          }
          container multicast-queue {
            tailf:cli-compact-syntax;
            tailf:cli-sequence-commands;
            uses queue-ref-grouping;
          }
          container unknown-queue {
            tailf:cli-compact-syntax;
            tailf:cli-sequence-commands;
            uses queue-ref-grouping;
          }
          container policer {
            tailf:cli-compact-syntax;
            tailf:cli-sequence-commands {
              tailf:cli-reset-all-siblings;
            }
            uses policer-ref-grouping;
            leaf fp-redirect-group {
              type empty;
            }
          }
          container broadcast-policer {
            tailf:cli-compact-syntax;
            tailf:cli-sequence-commands {
              tailf:cli-reset-all-siblings;
            }
            uses policer-ref-grouping;
            leaf fp-redirect-group {
              type empty;
            }
          }
          container multicast-policer {
            tailf:cli-compact-syntax;
            tailf:cli-sequence-commands {
              tailf:cli-reset-all-siblings;
            }
            uses policer-ref-grouping;
            leaf fp-redirect-group {
              type empty;
            }
          }
          container unknown-policer {
            tailf:cli-compact-syntax;
            tailf:cli-sequence-commands {
              tailf:cli-reset-all-siblings;
            }
            uses policer-ref-grouping;
            leaf fp-redirect-group {
              type empty;
            }
          }
          leaf profile {
            type enumeration {
              enum "in";
              enum "out";
            }
          }
          leaf broadcast-meter {
            type string;
          }
          leaf meter {
            type string;
          }
          leaf multicast-meter {
            type string;
          }
          leaf unknown-meter {
            type string;
          }

          grouping remark-choice-grouping {
            choice remark-choice {
              leaf dscp {
                type dscp-type;
              }
              leaf prec {
                type uint8;
              }
            }
          }
          container in-remark {
            uses remark-choice-grouping;
          }
          container out-remark {
            uses remark-choice-grouping;
          }
          leaf de-1-out-profile {
            type empty;
          }
        }
        container ip-criteria {
          tailf:cli-add-mode;
          uses ip-criteria-grouping;
        }
        container ipv6-criteria {
          tailf:cli-add-mode;
          uses ipv6-criteria-grouping;
        }
        container mac-criteria {
          tailf:cli-add-mode;
          uses mac-criteria-grouping;
        }
        leaf default-fc {
          type fc-name;
        }
        leaf default-priority {
          type enumeration {
            enum "low";
            enum "high";
          }
        }
        leaf dscp-classification {
          type uint16;
        }
        list dot1p {
          tailf:cli-suppress-mode;
          tailf:cli-delete-when-empty;
          key "id";
          tailf:cli-compact-syntax;
          leaf id {
            type uint8;
          }
          leaf fc {
            type fc-name;
          }
          leaf priority {
            type enumeration {
              enum "high";
              enum "low";
            }
          }
        }
        list lsp-exp {
          tailf:cli-suppress-mode;
          tailf:cli-delete-when-empty;
          key "id";
          tailf:cli-compact-syntax;
          leaf id {
            type uint8;
          }
          leaf fc {
            type fc-name;
          }
          leaf priority {
            type enumeration {
              enum "high";
              enum "low";
            }
          }
        }
        list dscp {
          tailf:cli-suppress-mode;
          tailf:cli-compact-syntax;
          key "id";
          leaf id {
            type dscp-type;
          }
          leaf fc {
            type union {
              type fc-name;
              type string;
            }
          }
          leaf priority {
            type enumeration {
              enum "high";
              enum "low";
            }
          }
        }
      }
      list network {
        key "id";
        leaf id {
          type uint16;
        }
        leaf network-policy-type {
          tailf:cli-hide-in-submode;
          type enumeration {
            enum "ip-interface";
            enum "port";
          }
        }
        leaf name {
          tailf:cli-hide-in-submode;
          type string;
        }
        leaf description {
          type string;
        }
        container ingress {
          tailf:cli-add-mode;
          list dscp {
            tailf:cli-compact-syntax;
            tailf:cli-suppress-mode;
            tailf:cli-sequence-commands {
              tailf:cli-reset-all-siblings;
            }
            key "id";
            leaf id {
              type dscp-type;
            }
            leaf fc {
              type union {
                type fc-name;
                type string;
              }
            }
            leaf profile {
              type in-out;
            }
          }
          leaf ler-use-dscp {
            type empty;
          }
          uses qos-lsp-exp-grouping;
          uses qos-dot1p-list-grouping;
          container default-action {
            tailf:cli-compact-syntax;
            tailf:cli-sequence-commands {
              tailf:cli-reset-siblings;
            }
            leaf fc {
              type fc-name;
            }
            leaf profile {
              type enumeration {
                enum "in";
                enum "out";
              }
            }
          }
          list meter {
            key "meter-id";
            uses meter-grouping;
          }
          leaf mpls-lsp-exp-profile {
            type uint16;
          }
          list fc {
            key "class";
            leaf class {
              type union {
                type fc-name;
                type string;
              }
            }
            leaf meter {
              type uint8;
            }
            leaf multicast-meter {
              type uint8;
            }
            list fp-redirect-group {
              tailf:cli-suppress-mode;
              key "policer-type";
              leaf policer-type {
                type enumeration {
                  enum "broadcast-policer";
                  enum "mcast-policer";
                  enum "unknown-policer";
                  enum "policer";
                }
              }
              leaf policer-id {
                tailf:cli-drop-node-name;
                type uint8;
              }
            }
          }
        }
        container egress {
          tailf:cli-add-mode;

          grouping egress-fc-settings-grouping {
            leaf dscp-in-profile {
              type dscp-type;
            }
            leaf dscp-out-profile {
              type dscp-type;
            }
            leaf lsp-exp-in-profile {
              type string;
            }
            leaf lsp-exp-out-profile {
              type string;
            }
            leaf dot1p-in-profile {
              type string;
            }
            leaf dot1p-out-profile {
              type string;
            }
            leaf de-mark {
              type boolean;
            }
            container port-redirect-group {
              tailf:cli-compact-syntax;
              tailf:cli-sequence-commands {
                tailf:cli-reset-all-siblings;
              }
              leaf policer {
                tailf:cli-optional-in-sequence;
                type uint8;
              }
              leaf queue {
                type uint8;
              }
            }
          }
          list dscp {
            tailf:cli-compact-syntax;
            tailf:cli-suppress-mode;
            tailf:cli-sequence-commands {
              tailf:cli-reset-all-siblings;
            }
            key "id";
            leaf id {
              type dscp-type;
            }
            leaf fc {
              type string;
            }
            leaf profile {
              type in-out;
            }
          }
          container fc {
            container af {
              tailf:cli-add-mode;
              // NCS expand uses statement
              leaf dscp-in-profile {
                type dscp-type;
              }
              leaf dscp-out-profile {
                type dscp-type;
              }
              leaf lsp-exp-in-profile {
                type string;
              }
              leaf lsp-exp-out-profile {
                type string;
              }
              leaf dot1p-in-profile {
                type string;
              }
              leaf dot1p-out-profile {
                type string;
              }
              leaf de-mark {
                type boolean;
              }
              container port-redirect-group {
                tailf:cli-compact-syntax;
                tailf:cli-sequence-commands {
                  tailf:cli-reset-all-siblings;
                }
                leaf policer {
                  tailf:cli-optional-in-sequence;
                  type uint8;
                }
                leaf queue {
                  type uint8;
                }
              }
            }
            container be {
              tailf:cli-add-mode;
              // NCS expand uses statement
              leaf dscp-in-profile {
                type dscp-type;
              }
              leaf dscp-out-profile {
                type dscp-type;
              }
              leaf lsp-exp-in-profile {
                type string;
              }
              leaf lsp-exp-out-profile {
                type string;
              }
              leaf dot1p-in-profile {
                type string;
              }
              leaf dot1p-out-profile {
                type string;
              }
              leaf de-mark {
                type boolean;
              }
              container port-redirect-group {
                tailf:cli-compact-syntax;
                tailf:cli-sequence-commands {
                  tailf:cli-reset-all-siblings;
                }
                leaf policer {
                  tailf:cli-optional-in-sequence;
                  type uint8;
                }
                leaf queue {
                  type uint8;
                }
              }
            }
            container ef {
              tailf:cli-add-mode;
              // NCS expand uses statement
              leaf dscp-in-profile {
                type dscp-type;
              }
              leaf dscp-out-profile {
                type dscp-type;
              }
              leaf lsp-exp-in-profile {
                type string;
              }
              leaf lsp-exp-out-profile {
                type string;
              }
              leaf dot1p-in-profile {
                type string;
              }
              leaf dot1p-out-profile {
                type string;
              }
              leaf de-mark {
                type boolean;
              }
              container port-redirect-group {
                tailf:cli-compact-syntax;
                tailf:cli-sequence-commands {
                  tailf:cli-reset-all-siblings;
                }
                leaf policer {
                  tailf:cli-optional-in-sequence;
                  type uint8;
                }
                leaf queue {
                  type uint8;
                }
              }
            }
            container h1 {
              tailf:cli-add-mode;
              // NCS expand uses statement
              leaf dscp-in-profile {
                type dscp-type;
              }
              leaf dscp-out-profile {
                type dscp-type;
              }
              leaf lsp-exp-in-profile {
                type string;
              }
              leaf lsp-exp-out-profile {
                type string;
              }
              leaf dot1p-in-profile {
                type string;
              }
              leaf dot1p-out-profile {
                type string;
              }
              leaf de-mark {
                type boolean;
              }
              container port-redirect-group {
                tailf:cli-compact-syntax;
                tailf:cli-sequence-commands {
                  tailf:cli-reset-all-siblings;
                }
                leaf policer {
                  tailf:cli-optional-in-sequence;
                  type uint8;
                }
                leaf queue {
                  type uint8;
                }
              }
            }
            container h2 {
              tailf:cli-add-mode;
              // NCS expand uses statement
              leaf dscp-in-profile {
                type dscp-type;
              }
              leaf dscp-out-profile {
                type dscp-type;
              }
              leaf lsp-exp-in-profile {
                type string;
              }
              leaf lsp-exp-out-profile {
                type string;
              }
              leaf dot1p-in-profile {
                type string;
              }
              leaf dot1p-out-profile {
                type string;
              }
              leaf de-mark {
                type boolean;
              }
              container port-redirect-group {
                tailf:cli-compact-syntax;
                tailf:cli-sequence-commands {
                  tailf:cli-reset-all-siblings;
                }
                leaf policer {
                  tailf:cli-optional-in-sequence;
                  type uint8;
                }
                leaf queue {
                  type uint8;
                }
              }
            }
            container l1 {
              tailf:cli-add-mode;
              // NCS expand uses statement
              leaf dscp-in-profile {
                type dscp-type;
              }
              leaf dscp-out-profile {
                type dscp-type;
              }
              leaf lsp-exp-in-profile {
                type string;
              }
              leaf lsp-exp-out-profile {
                type string;
              }
              leaf dot1p-in-profile {
                type string;
              }
              leaf dot1p-out-profile {
                type string;
              }
              leaf de-mark {
                type boolean;
              }
              container port-redirect-group {
                tailf:cli-compact-syntax;
                tailf:cli-sequence-commands {
                  tailf:cli-reset-all-siblings;
                }
                leaf policer {
                  tailf:cli-optional-in-sequence;
                  type uint8;
                }
                leaf queue {
                  type uint8;
                }
              }
            }
            container l2 {
              tailf:cli-add-mode;
              // NCS expand uses statement
              leaf dscp-in-profile {
                type dscp-type;
              }
              leaf dscp-out-profile {
                type dscp-type;
              }
              leaf lsp-exp-in-profile {
                type string;
              }
              leaf lsp-exp-out-profile {
                type string;
              }
              leaf dot1p-in-profile {
                type string;
              }
              leaf dot1p-out-profile {
                type string;
              }
              leaf de-mark {
                type boolean;
              }
              container port-redirect-group {
                tailf:cli-compact-syntax;
                tailf:cli-sequence-commands {
                  tailf:cli-reset-all-siblings;
                }
                leaf policer {
                  tailf:cli-optional-in-sequence;
                  type uint8;
                }
                leaf queue {
                  type uint8;
                }
              }
            }
            container nc {
              tailf:cli-add-mode;
              // NCS expand uses statement
              leaf dscp-in-profile {
                type dscp-type;
              }
              leaf dscp-out-profile {
                type dscp-type;
              }
              leaf lsp-exp-in-profile {
                type string;
              }
              leaf lsp-exp-out-profile {
                type string;
              }
              leaf dot1p-in-profile {
                type string;
              }
              leaf dot1p-out-profile {
                type string;
              }
              leaf de-mark {
                type boolean;
              }
              container port-redirect-group {
                tailf:cli-compact-syntax;
                tailf:cli-sequence-commands {
                  tailf:cli-reset-all-siblings;
                }
                leaf policer {
                  tailf:cli-optional-in-sequence;
                  type uint8;
                }
                leaf queue {
                  type uint8;
                }
              }
            }
          }
          leaf remark {
            type uint32;
          }
          container remarking {
            presence "true";
            leaf force {
              type empty;
            }
          }
          list prec {
            tailf:cli-suppress-mode;
            tailf:cli-compact-syntax;
            tailf:cli-sequence-commands {
              tailf:cli-reset-all-siblings;
            }
            key "prec-value";
            leaf prec-value {
              tailf:cli-drop-node-name;
              type uint8;
            }
            leaf fc {
              type fc-name;
            }
            leaf profile {
              type enumeration {
                enum "in";
                enum "out";
              }
            }
          }
        }
      }
      list slope-policy {
        key "name";
        leaf name {
          type string;
        }
        leaf description {
          type string;
        }
        container exceed-slope {
          tailf:cli-add-mode;
          uses slope-params-grouping;
        }
        container high-slope {
          tailf:cli-add-mode;
          uses slope-params-grouping;
        }
        container highplus-slope {
          tailf:cli-add-mode;
          uses slope-params-grouping;
        }
        container low-slope {
          tailf:cli-add-mode;
          uses slope-params-grouping;
        }
      }
      list port-scheduler-policy {
        key "name";
        leaf name {
          type string;
        }
        leaf description {
          type string;
        }
        leaf dist-lag-rate-shared {
          type empty;
        }
        list group {
          key "name";
          leaf name {
            type string32;
          }
          container percent {
            tailf:cli-drop-node-name;
            tailf:cli-sequence-commands;
            tailf:cli-compact-syntax;
            leaf percent-rate {
              type decimal64 {
                fraction-digits 2;
              }
            }
            leaf cir {
              type decimal64 {
                fraction-digits 2;
              }
            }
          }
        }
        list level {
          tailf:cli-suppress-mode;
          tailf:cli-compact-syntax;
          tailf:cli-sequence-commands {
            tailf:cli-reset-all-siblings;
          }
          key "priority-level";
          leaf priority-level {
            type uint8;
          }
          choice rate-choice {
            container pir {
              tailf:cli-flatten-container;
              tailf:cli-drop-node-name;
              tailf:cli-sequence-commands;
              tailf:cli-compact-syntax;
              leaf rate {
                type union {
                  type uint32;
                  type enumeration {
                    enum "max";
                  }
                }
              }
              leaf cir {
                type union {
                  type uint32;
                  type enumeration {
                    enum "max";
                  }
                }
              }
            }
            container percent {
              tailf:cli-drop-node-name;
              tailf:cli-flatten-container;
              tailf:cli-sequence-commands;
              tailf:cli-compact-syntax;
              leaf percent-rate {
                type decimal64 {
                  fraction-digits 2;
                }
              }
              leaf percent-cir {
                type decimal64 {
                  fraction-digits 2;
                }
              }
            }
          }
          leaf group {
            type string32;
          }
          leaf weight {
            type uint8;
          }
        }
        container max-rate {
          choice max-rate {
            leaf pir-rate {
              tailf:cli-drop-node-name;
              type uint32;
            }
            leaf percent {
              type decimal64 {
                fraction-digits 2;
              }
            }
          }
        }
        container orphan-override {
          tailf:cli-compact-syntax;
          leaf weight {
            type uint8;
          }
          leaf level {
            type uint8;
          }
          leaf cir-weight {
            type uint8;
          }
          leaf cir-level {
            type uint8;
          }
        }
      }
      list policer-control-policy {
        key "name";
        leaf name {
          type string;
        }
        leaf description {
          type string;
        }
        container root {
          tailf:cli-add-mode;
          leaf max-rate {
            type rate-type;
          }
        }
        container priority-mbs-thresholds {
          tailf:cli-add-mode;
          container min-thresh-separation {
            tailf:cli-sequence-commands;
            tailf:cli-compact-syntax;
            leaf size {
              tailf:cli-drop-node-name;
              type union {
                type uint32;
                type enumeration {
                  enum "default";
                }
              }
            }
            leaf unit {
              tailf:cli-drop-node-name;
              type enumeration {
                enum "bytes";
                enum "kilobytes";
              }
            }
          }
          list priority {
            key "level";
            leaf level {
              type uint8;
            }
            container mbs-contribution {
              tailf:cli-compact-syntax;
              tailf:cli-sequence-commands;
              leaf size {
                tailf:cli-drop-node-name;
                type union {
                  type uint32;
                  type enumeration {
                    enum "default";
                  }
                }
              }
              leaf unit {
                tailf:cli-drop-node-name;
                type enumeration {
                  enum "bytes";
                  enum "kilobytes";
                }
              }
              leaf fixed {
                type empty;
              }
            }
          }
        }
      }
      list queue-mgmt {
        key "id";
        leaf id {
          type string;
        }
        leaf description {
          type string;
        }
        leaf mbs {
          type union {
            type enumeration {
              enum "default";
            }
            type uint32;
          }
        }
        leaf cbs {
          type union {
            type enumeration {
              enum "default";
            }
            type uint32;
          }
        }
        container high-slope {
          tailf:cli-add-mode;
          leaf shutdown {
            type boolean;
          }
        }
        container low-slope {
          tailf:cli-add-mode;
          leaf shutdown {
            type boolean;
          }
        }
      }
      list remark {
        key "policy-id";
        leaf policy-id {
          type uint32;
        }
        leaf remark-type {
          tailf:cli-hide-in-submode;
          type enumeration {
            enum "dot1p";
            enum "dscp";
            enum "dot1p-dscp";
            enum "lsp-exp";
            enum "dot1p-lsp-exp-shared";
          }
        }
        leaf description {
          type string;
        }
        list fc {
          key "fc-name";
          leaf fc-name {
            type fc-name;
          }
          leaf dot1p-in-profile {
            type uint8;
          }
          leaf dot1p-out-profile {
            type uint8;
          }
          leaf dot1p-lsp-exp-in-profile {
            type uint8;
          }
          leaf dot1p-lsp-exp-out-profile {
            type uint8;
          }
        }
      }
      leaf use-global-mpls-lsp-exp-profile {
        type uint32;
      }
    }
    list sfm {
      tailf:ncs-device-type "cli-ned";
      tailf:display-when "not(../ncs:module) or ../ncs:module[ncs:name='netsim-ned-alu-sr']";
      key "id";
      leaf id {
        type uint8;
      }
      leaf sfm-type {
        type union {
          type enumeration {
            enum "m-sfm5-12e";
            enum "m-sfm5-12";
            enum "sfm-x20-b";
          }
          type string;
        }
      }
      leaf shutdown {
        type boolean;
      }
    }
    container eth-cfm {
      tailf:ncs-device-type "cli-ned";
      tailf:display-when "not(../../ncs:module) or ../../ncs:module[ncs:name='netsim-ned-alu-sr']";
      tailf:cli-add-mode;
      container default-domain {
        tailf:cli-add-mode;
        list bridge-identifier {
          key "bridge-id";
          leaf bridge-id {
            type uint32;
          }
          leaf vlan {
            tailf:cli-hide-in-submode;
            type union {
              type uint32;
              type enumeration {
                enum "none";
              }
            }
          }
          container mhf-creation {
            tailf:cli-compact-syntax;
            leaf mhf {
              tailf:cli-drop-node-name;
              type enumeration {
                enum "none";
                enum "default";
                enum "explicit";
                enum "defer";
              }
            }
            leaf level {
              type union {
                type uint32;
                type enumeration {
                  enum "defer";
                }
              }
            }
          }
        }
      }
      list domain {
        key "id";
        leaf id {
          type uint32;
        }
        leaf format {
          tailf:cli-hide-in-submode;
          type string;
        }
        leaf level {
          tailf:cli-hide-in-submode;
          type uint8;
        }
        leaf name {
          tailf:cli-hide-in-submode;
          type string;
        }
        leaf admin-name {
          tailf:cli-hide-in-submode;
          type string;
        }
        list association {
          key "ma-index";
          leaf ma-index {
            type uint32;
          }
          leaf auto-mep-discovery {
            type empty;
          }
          leaf format {
            tailf:cli-hide-in-submode;
            type enumeration {
              enum "icc-based";
              enum "integer";
              enum "string";
              enum "vid";
              enum "vpn-id";
            }
          }
          leaf name {
            tailf:cli-hide-in-submode;
            type string;
          }
          leaf admin-name {
            tailf:cli-hide-in-submode;
            type string;
          }
          container ccm-hold-time {
            leaf down {
              type uint32;
            }
          }
          leaf ccm-interval {
            type enumeration {
              enum "10ms";
              enum "100ms";
              enum "1";
              enum "10";
              enum "60";
              enum "600";
            }
          }
          list remote-mepid {
            tailf:cli-suppress-mode;
            key "mep-id";
            leaf mep-id {
              type uint16;
            }
            leaf remote-mac {
              type union {
                type enumeration {
                  enum "default";
                }
                type ieee-mac;
              }
            }
          }
          list bridge-identifier {
            key "id";
            leaf id {
              type union {
                type uint32;
                type string;
              }
            }
            leaf bridge-name {
              tailf:cli-prefix-key;
              type empty;
            }
            leaf mhf-creation {
              type enumeration {
                enum "default";
                enum "none";
                enum "explicit";
              }
            }
            leaf vlan {
              type uint16;
            }
          }
        }
      }
    }
    list esa {
      tailf:ncs-device-type "cli-ned";
      tailf:display-when "not(../ncs:module) or ../ncs:module[ncs:name='netsim-ned-alu-sr']";
      key "id";
      leaf id {
        type uint8;
      }
      leaf description {
        type string;
      }
      list host-port {
        tailf:cli-suppress-mode;
        key "port";
        leaf port {
          type string;
        }
      }
      list vm {
        key "vm-id";
        leaf vm-id {
          type uint8;
        }
        leaf cores {
          type uint8;
        }
        leaf description {
          type string;
        }
        leaf host-port {
          type string;
        }
        leaf memory {
          type uint32;
        }
        leaf vm-type {
          type enumeration {
            enum "aa";
            enum "bb";
            enum "tunnel";
            enum "video";
          }
        }
        leaf shutdown {
          type boolean;
        }
      }
      leaf shutdown {
        type boolean;
      }
    }
    container log {
      tailf:ncs-device-type "cli-ned";
      tailf:display-when "not(../../ncs:module) or ../../ncs:module[ncs:name='netsim-ned-alu-sr']";
      tailf:cli-add-mode;

      typedef severity-levels {
        type enumeration {
          enum "cleared";
          enum "indeterminate";
          enum "critical";
          enum "major";
          enum "minor";
          enum "warning";
        }
      }
      leaf event-damping {
        type enumeration {
          enum "enable";
          enum "disable";
        }
      }
      container event-handling {
        tailf:cli-add-mode;
        list handler {
          key "name";
          leaf name {
            type string;
          }
          leaf description {
            type string;
          }
          container action-list {
            tailf:cli-add-mode;
            list entry {
              key "entry-id";
              leaf entry-id {
                type uint32;
              }
              leaf script-policy {
                type string32;
              }
              leaf shutdown {
                type boolean;
              }
            }
          }
          leaf shutdown {
            type boolean;
          }
        }
      }
      list file-id {
        key "id";
        leaf id {
          type uint32;
        }
        leaf name {
          tailf:cli-hide-in-submode;
          type string;
        }
        leaf description {
          type string;
        }
        leaf location {
          type string;
        }
        container rollover {
          tailf:cli-compact-syntax;
          tailf:cli-sequence-commands;
          leaf id {
            tailf:cli-drop-node-name;
            type uint32;
          }
          leaf retention {
            type uint32;
          }
        }
      }
      list accounting-policy {
        key "acct-policy-id";
        leaf acct-policy-id {
          type uint8;
        }
        leaf collection-interval {
          type uint8;
        }
        leaf description {
          type string;
        }
        container custom-record {
          tailf:cli-add-mode;
          list queue {
            key "id";
            leaf id {
              type uint8;
            }

            grouping custom-record-counters-grouping {
              leaf in-profile-octets-forwarded-count {
                type empty;
              }
              leaf out-profile-octets-forwarded-count {
                type empty;
              }
            }
            container e-counters {
              tailf:cli-add-mode;
              uses custom-record-counters-grouping;
            }
            container i-counters {
              tailf:cli-add-mode;
              uses custom-record-counters-grouping;
            }
          }
        }
        leaf include-system-info {
          type empty;
        }
        leaf record {
          type enumeration {
            enum "aa-app-group";
            enum "aa-application";
            enum "aa-partition";
            enum "aa-performance";
            enum "aa-protocol";
            enum "aa-subscriber-application";
            enum "aa-subscriber-protocol";
            enum "combined-ldp-lsp-egress";
            enum "combined-mpls-lsp-egress";
            enum "combined-mpls-lsp-ingress";
            enum "combined-network-ing-egr-octets";
            enum "combined-queue-group";
            enum "combined-sdp-ingress-egress";
            enum "combined-service-ing-egr-octets";
            enum "combined-service-ingress";
            enum "compact-service-ingress-octets";
            enum "complete-pm";
            enum "complete-sdp-ingress-egress";
            enum "complete-service-ingress-egress";
            enum "complete-subscriber-ingress-egress";
            enum "custom-record-aa-sub";
            enum "custom-record-service";
            enum "custom-record-subscriber";
            enum "network-egress-octets";
            enum "network-egress-packets";
            enum "network-ingress-octets";
            enum "network-ingress-packets";
            enum "queue-group-octets";
            enum "queue-group-packets";
            enum "saa";
            enum "service-egress-octets";
            enum "service-egress-packets";
            enum "service-ingress-octets";
            enum "service-ingress-packets";
            enum "video";
            enum "complete-ethernet-port";
            enum "extended-service-ingress-egress";
            enum "complete-network-ing-egr";
            enum "access-egress-octets";
            enum "access-egress-packets";
            enum "combined-access-egress";
            enum "combined-service-egress";
            enum "network-int";
            enum "combined-network-interface-ingress";
            enum "complete-network-interface-ing-egr";
          }
        }
        leaf default {
          type empty;
        }
        container to {
          tailf:cli-compact-syntax;
          tailf:cli-sequence-commands {
            tailf:cli-reset-siblings;
          }
          leaf destination {
            tailf:cli-drop-node-name;
            type enumeration {
              enum "file";
              enum "no-file";
            }
          }
          leaf log-file-id {
            tailf:cli-drop-node-name;
            type uint32;
          }
        }
        leaf shutdown {
          type boolean;
        }
      }
      list event-control {
        tailf:cli-suppress-mode;
        tailf:cli-compact-syntax;
        tailf:cli-sequence-commands {
          tailf:cli-reset-siblings;
        }
        key "name id";
        leaf name {
          type string;
        }
        leaf id {
          type uint32;
        }
        leaf mode {
          tailf:cli-drop-node-name;
          type enumeration {
            enum "generate";
            enum "suppress";
            enum "repeat";
            enum "no-repeat";
          }
        }
        leaf severity-level {
          tailf:cli-optional-in-sequence;
          tailf:cli-drop-node-name;
          type severity-levels;
        }
        leaf throttle {
          tailf:cli-optional-in-sequence;
          type empty;
        }
        leaf disable-specific-throttle {
          tailf:cli-optional-in-sequence;
          tailf:cli-drop-node-name;
          type enumeration {
            enum "disable-specific-throttle";
          }
        }
        container specific-throttle-rate {
          tailf:cli-flatten-container;
          tailf:cli-compact-syntax;
          leaf event-limit {
            tailf:cli-drop-node-name;
            type uint32;
          }
          leaf interval {
            type uint16;
          }
        }
      }
      container event-trigger {
        tailf:cli-add-mode;
        list event {
          key "application-id event-name-id";
          leaf application-id {
            type enumeration {
              enum "application_assurance";
              enum "bgp";
              enum "cflowd";
              enum "chassis";
              enum "cpmhwfilter";
              enum "cpmhwqueue";
              enum "debug";
              enum "dhcp";
              enum "dhcps";
              enum "diameter";
              enum "dot1x";
              enum "efm_oam";
              enum "elmi";
              enum "ering";
              enum "eth_cfm";
              enum "etun";
              enum "filter";
              enum "gsmp";
              enum "igmp";
              enum "igmp_snooping";
              enum "ip";
              enum "ipsec";
              enum "ipsec_cpm";
              enum "isis";
              enum "l2tp";
              enum "lag";
              enum "ldp";
              enum "li";
              enum "lldp";
              enum "logger";
              enum "mcac";
              enum "mcpath";
              enum "mc_redundancy";
              enum "mirror";
              enum "mld";
              enum "mld_snooping";
              enum "mpls";
              enum "mrp";
              enum "msdp";
              enum "nat";
              enum "ntp";
              enum "oam";
              enum "ospf";
              enum "pim";
              enum "pim_snooping";
              enum "port";
              enum "pppoe";
              enum "ptp";
              enum "qos";
              enum "rip";
              enum "route_policy";
              enum "rsvp";
              enum "security";
              enum "snmp";
              enum "stp";
              enum "subscr_mgmt";
              enum "sub_host_trk";
              enum "svcmgr";
              enum "system";
              enum "tip";
              enum "user";
              enum "user_db";
              enum "video";
              enum "vrrp";
              enum "vrtr";
              enum "ipfix";
              enum "radius";
              enum "wpp";
              enum "wlan_gw";
              enum "dynsvc";
              enum "mpls_tp";
              enum "bfd";
              enum "python";
              enum "rip_ng";
              enum "open_flow";
              enum "route_next_hop";
              enum "sflow";
              enum "rpki";
              enum "pcep";
              enum "calltrace";
              enum "pxc";
              enum "satellite";
              enum "ldap";
              enum "pppoe_clnt";
              enum "tls";
              enum "fpe";
              enum "nge";
              enum "gtp";
              enum "bmp";
              enum "adp";
              enum "mgmt_core";
              enum "profile";
              enum "macsec";
              enum "sr_policy";
              enum "pcap";
              enum "mpls_lmgr";
              enum "auto_prov";
              enum "bier";
              enum "rib_api";
              enum "pfcp";
              enum "tree_sid";
              enum "telemetry";
              enum "srv6";
              enum "sr_mpls";
              enum "maffilter";
              enum "anysec";
              enum "pools";
            }
          }
          leaf event-name-id {
            type string;
          }
          list trigger-entry {
            key "entry-id";
            leaf entry-id {
              type uint32;
            }
            leaf event-handler {
              type string;
            }
            leaf log-filter {
              type uint16;
            }
            leaf shutdown {
              type boolean;
            }
          }
          leaf shutdown {
            type boolean;
          }
        }
      }
      list filter {
        key "filter-id";
        leaf filter-id {
          type uint16;
        }
        leaf default-action {
          type enumeration {
            enum "drop";
            enum "forward";
          }
        }
        leaf name {
          tailf:cli-hide-in-submode;
          type string;
        }
        leaf description {
          type string;
        }
        list entry {
          key "entry-id";
          leaf entry-id {
            type uint16;
          }
          leaf action {
            type enumeration {
              enum "drop";
              enum "forward";
            }
          }
          leaf name {
            tailf:cli-hide-in-submode;
            type string;
          }
          leaf description {
            type string;
          }
          container match {
            tailf:cli-add-mode;
            container application {
              tailf:cli-compact-syntax;
              tailf:cli-sequence-commands;
              leaf rule {
                tailf:cli-drop-node-name;
                type enumeration {
                  enum "eq";
                  enum "neq";
                }
              }
              leaf application-id {
                tailf:cli-drop-node-name;
                type enumeration {
                  enum "application_assurance";
                  enum "aps";
                  enum "atm";
                  enum "bgp";
                  enum "cflowd";
                  enum "chassis";
                  enum "debug";
                  enum "dhcp";
                  enum "dhcps";
                  enum "diameter";
                  enum "dynsvc";
                  enum "efm_oam";
                  enum "elmi";
                  enum "ering";
                  enum "eth_cfm";
                  enum "etun";
                  enum "filter";
                  enum "gsmp";
                  enum "gmpls";
                  enum "igh";
                  enum "igmp";
                  enum "igmp_snooping";
                  enum "ip";
                  enum "ipsec";
                  enum "isis";
                  enum "l2tp";
                  enum "lag";
                  enum "ldp";
                  enum "li";
                  enum "lldp";
                  enum "lmp";
                  enum "logger";
                  enum "mcpath";
                  enum "mc_redundancy";
                  enum "mirror";
                  enum "mld";
                  enum "mld_snooping";
                  enum "mpls";
                  enum "mpls_tp";
                  enum "msdp";
                  enum "nat";
                  enum "ntp";
                  enum "oam";
                  enum "open_flow";
                  enum "ospf";
                  enum "pim";
                  enum "pim_snooping";
                  enum "port";
                  enum "ppp";
                  enum "pppoe";
                  enum "radius";
                  enum "rip";
                  enum "rip_ng";
                  enum "route_policy";
                  enum "rsvp";
                  enum "security";
                  enum "snmp";
                  enum "stp";
                  enum "svcmgr";
                  enum "system";
                  enum "user";
                  enum "video";
                  enum "vrrp";
                  enum "vrtr";
                  enum "wlan_gw";
                  enum "wpp";
                }
              }
            }
            container message {
              tailf:cli-compact-syntax;
              tailf:cli-sequence-commands {
                tailf:cli-reset-all-siblings;
              }
              leaf rule {
                tailf:cli-drop-node-name;
                type enumeration {
                  enum "eq";
                  enum "neq";
                }
              }
              leaf pattern {
                type string;
              }
              leaf regexp {
                type empty;
              }
            }
            container number {
              tailf:cli-compact-syntax;
              tailf:cli-sequence-commands {
                tailf:cli-reset-all-siblings;
              }
              leaf rule {
                tailf:cli-drop-node-name;
                type enumeration {
                  enum "eq";
                  enum "neq";
                  enum "lt";
                  enum "lte";
                  enum "gt";
                  enum "gte";
                }
              }
              leaf event-id {
                tailf:cli-drop-node-name;
                type uint32;
              }
            }
            container router {
              tailf:cli-compact-syntax;
              tailf:cli-sequence-commands {
                tailf:cli-reset-all-siblings;
              }
              leaf rule {
                tailf:cli-drop-node-name;
                type enumeration {
                  enum "eq";
                  enum "neq";
                }
              }
              leaf router-instance {
                tailf:cli-drop-node-name;
                type string;
              }
              leaf regexp {
                type empty;
              }
            }
            container severity {
              tailf:cli-compact-syntax;
              tailf:cli-sequence-commands {
                tailf:cli-reset-all-siblings;
              }
              leaf rule {
                tailf:cli-drop-node-name;
                type enumeration {
                  enum "eq";
                  enum "neq";
                  enum "lt";
                  enum "lte";
                  enum "gt";
                  enum "gte";
                  enum "*";
                }
              }
              leaf severity-level {
                tailf:cli-drop-node-name;
                type severity-levels;
              }
            }
            container subject {
              tailf:cli-compact-syntax;
              tailf:cli-sequence-commands {
                tailf:cli-reset-all-siblings;
              }
              leaf rule {
                tailf:cli-drop-node-name;
                type enumeration {
                  enum "eq";
                  enum "neq";
                }
              }
              leaf subject {
                tailf:cli-drop-node-name;
                type string;
              }
              leaf regexp {
                type empty;
              }
            }
          }
        }
      }
      list snmp-trap-group {
        tailf:cli-diff-create-before "/alu:log/log-id" {
          tailf:xpath-root 3;
        }
        key "id";
        leaf id {
          type uint16;
        }
        leaf name {
          tailf:cli-hide-in-submode;
          type string;
        }
        list trap-target {
          tailf:cli-suppress-mode;
          tailf:cli-compact-syntax;
          key "name";
          leaf name {
            type string;
          }
          leaf address {
            type union {
              type inet:ipv4-address;
              type inet:ipv6-address;
            }
          }
          leaf notify-community {
            type string;
          }
          leaf port {
            type uint16;
          }
          leaf version {
            tailf:cli-drop-node-name;
            type enumeration {
              enum "snmpv1";
              enum "snmpv2c";
              enum "snmpv3";
            }
          }
          leaf security-level {
            type enumeration {
              enum "no-auth-no-privacy";
              enum "auth-no-privacy";
              enum "privacy";
            }
          }
          leaf replay {
            type empty;
          }
          leaf dying-gasp {
            type empty;
          }
        }
        leaf description {
          type string;
        }
      }
      container snmp-dying-gasp {
        tailf:cli-compact-syntax;
        tailf:cli-sequence-commands {
          tailf:cli-reset-siblings;
        }

        grouping trap-target-grouping {
          leaf trap-target-group-num {
            tailf:cli-drop-node-name;
            type uint16;
          }
          leaf trap-target-name {
            tailf:cli-drop-node-name;
            type string;
          }
        }
        container primary {
          tailf:cli-optional-in-sequence;
          tailf:cli-flatten-container;
          tailf:cli-compact-syntax;
          tailf:cli-sequence-commands {
            tailf:cli-reset-siblings;
          }
          uses trap-target-grouping;
        }
        container secondary {
          tailf:cli-flatten-container;
          tailf:cli-compact-syntax;
          tailf:cli-sequence-commands {
            tailf:cli-reset-siblings;
          }
          uses trap-target-grouping;
        }
        container tertiary {
          tailf:cli-flatten-container;
          tailf:cli-compact-syntax;
          tailf:cli-sequence-commands {
            tailf:cli-reset-siblings;
          }
          uses trap-target-grouping;
        }
      }
      list log-id {
        key "id";
        leaf id {
          type uint16;
        }
        leaf name {
          tailf:cli-hide-in-submode;
          type string;
        }
        leaf description {
          type string;
        }
        leaf filter {
          type uint16;
        }
        leaf-list from {
          tailf:cli-flat-list-syntax;
          type enumeration {
            enum "main";
            enum "security";
            enum "change";
            enum "debug-trace";
          }
        }
        leaf time-format {
          type enumeration {
            enum "local";
            enum "utc";
          }
        }
        leaf netconf-stream {
          type string;
        }
        container to {
          choice choice {
            case file {
              leaf file {
                type uint32;
              }
            }
            case syslog {
              leaf syslog {
                type uint32;
              }
            }
            case cli {
              leaf cli {
                type empty;
              }
            }
            case console {
              leaf console {
                type empty;
              }
            }
            case netconf {
              leaf netconf {
                type empty;
              }
            }
            case snmp {
              container snmp {
                presence "true";
                leaf size {
                  tailf:cli-drop-node-name;
                  type uint32;
                }
              }
            }
            case memory {
              container memory {
                presence "true";
                leaf size {
                  tailf:cli-drop-node-name;
                  type uint32;
                }
              }
            }
            case session {
              leaf session {
                type uint32;
              }
            }
          }
        }
        leaf shutdown {
          type boolean;
        }
      }
      container route-preference {
        tailf:cli-compact-syntax;
        tailf:cli-sequence-commands {
          tailf:cli-reset-siblings;
        }
        leaf primary {
          type enumeration {
            enum "inband";
            enum "outband";
          }
        }
        leaf secondary {
          type enumeration {
            enum "inband";
            enum "outband";
            enum "none";
          }
        }
      }
      list syslog {
        key "id";
        leaf id {
          type uint32;
        }
        leaf name {
          tailf:cli-hide-in-submode;
          type string;
        }
        leaf address {
          type union {
            type inet:ipv4-address;
            type inet:ipv6-address;
          }
        }
        leaf description {
          type string;
        }
        leaf facility {
          type string;
        }
        leaf log-prefix {
          type string;
        }
        leaf level {
          type enumeration {
            enum "emergency";
            enum "alert";
            enum "critical";
            enum "error";
            enum "warning";
            enum "notice";
            enum "info";
            enum "debug";
          }
        }
        leaf port {
          type uint16;
        }
      }
      container throttle-rate {
        tailf:cli-compact-syntax;
        tailf:cli-sequence-commands {
          tailf:cli-reset-siblings;
        }
        leaf events {
          tailf:cli-drop-node-name;
          type uint32;
        }
        leaf interval {
          type uint16;
        }
      }
      container services-all-events {
        tailf:cli-add-mode;
        list service {
          tailf:cli-suppress-mode;
          key "service-id";
          leaf service-id {
            type union {
              type uint32;
              type string;
            }
          }
        }
      }
    }
    container service {
      tailf:ncs-device-type "cli-ned";
      tailf:display-when "not(../../ncs:module) or ../../ncs:module[ncs:name='netsim-ned-alu-sr']";
      tailf:cli-add-mode;
      list customer {
        key "customer-id";
        leaf customer-id {
          type uint32;
        }
        leaf name {
          tailf:cli-hide-in-submode;
          type string;
        }
        leaf contact {
          type string;
        }
        leaf description {
          type string;
        }
        list multi-service-site {
          key "customer-site-name";
          leaf customer-site-name {
            type string;
          }
          container assignment {
            choice choice {
              leaf port {
                type string;
              }
              leaf card {
                type string;
              }
            }
          }
          leaf description {
            type string;
          }
          container egress {
            tailf:cli-add-mode;
            container agg-rate-limit {
              presence "present";
              tailf:cli-sequence-commands;
              tailf:cli-compact-syntax;
              leaf agg-rate {
                tailf:cli-drop-node-name;
                mandatory true;
                type string;
              }
              leaf queue-frame-based-accounting {
                tailf:cli-hide-in-submode;
                type empty;
              }
            }
            leaf policer-control-policy {
              type string;
            }
            leaf scheduler-policy {
              type string;
            }
            container scheduler-override {
              tailf:cli-add-mode;
              list scheduler {
                key "scheduler-name";
                leaf scheduler-name {
                  type string;
                }
                container rate {
                  tailf:cli-sequence-commands;
                  tailf:cli-compact-syntax;
                  leaf pir-rate {
                    tailf:cli-drop-node-name;
                    type string;
                  }
                  leaf cir {
                    type string;
                  }
                }
              }
            }
          }
          container ingress {
            tailf:cli-add-mode;
            leaf policer-control-policy {
              type string;
            }
            leaf scheduler-policy {
              type string;
            }
            container scheduler-override {
              tailf:cli-add-mode;
              list scheduler {
                key "scheduler-name";
                leaf scheduler-name {
                  type string;
                }
                container rate {
                  presence "present";
                  tailf:cli-sequence-commands;
                  tailf:cli-compact-syntax;
                  leaf pir-rate {
                    tailf:cli-drop-node-name;
                    mandatory true;
                    type string;
                  }
                  leaf cir {
                    type string;
                  }
                }
              }
            }
          }
          leaf tod-suite {
            type string;
          }
        }
        leaf phone {
          type string;
        }
      }
      list sdp {
        key "sdp-id";
        leaf sdp-id {
          type uint32;
        }
        list sr-te-lsp {
          tailf:cli-suppress-mode;
          key "lsp-id";
          leaf lsp-id {
            type string;
          }
        }
        container class-forwarding {
          tailf:cli-add-mode;
          presence "true";
          leaf default-lsp {
            tailf:cli-hide-in-submode;
            type string;
          }
          leaf enforce-diffserv-lsp-fc {
            type empty;
          }
          list fc {
            tailf:cli-suppress-mode;
            key "class";
            leaf class {
              type fc-name;
            }
            leaf lsp {
              type string;
            }
          }
          leaf multicast-lsp {
            type string;
          }
          leaf shutdown {
            type boolean;
          }
        }
        list lsp {
          tailf:cli-suppress-mode;
          key "lsp-name";
          leaf lsp-name {
            type string;
          }
        }
        leaf far-end {
          type union {
            type inet:ipv4-address;
            type inet:ipv6-address;
          }
        }
        leaf accounting-policy {
          type uint8;
        }
        leaf adv-mtu-override {
          type empty;
        }
        leaf bgp-tunnel {
          type empty;
        }
        container binding {
          tailf:cli-add-mode;
          leaf port {
            type string;
          }
          list pw-port {
            key "pw-port-id";
            leaf pw-port-id {
              type uint32;
            }
            leaf vc-id {
              tailf:cli-hide-in-submode;
              type uint32;
            }
            leaf monitor-oper-group {
              type string;
            }
            container egress {
              container shaping {
                choice choice {
                  leaf vport {
                    type string;
                  }
                  leaf int-dest-id {
                    type string;
                  }
                }
              }
            }
            leaf vc-type {
              type enumeration {
                enum "ether";
                enum "vlan";
              }
            }
            leaf vlan-vc-tag {
              type uint16;
            }
            leaf shutdown {
              type boolean;
            }
          }
        }
        leaf booking-factor {
          type uint16;
        }
        leaf collect-stats {
          type empty;
        }
        leaf delivery-type {
          tailf:cli-hide-in-submode;
          tailf:cli-drop-node-name;
          type enumeration {
            enum "gre";
            enum "mpls";
            enum "l2tpv3";
          }
        }
        leaf description {
          type string;
        }
        container keep-alive {
          tailf:cli-add-mode;
          leaf hello-time {
            type uint16;
          }
          leaf hold-down-time {
            type uint16;
          }
          leaf max-drop-count {
            type uint8;
          }
          leaf message-length {
            type uint16;
          }
          leaf timeout {
            type uint8;
          }
          leaf shutdown {
            type boolean;
          }
        }
        leaf metric {
          type uint16;
        }
        leaf sr-type {
          tailf:cli-drop-node-name;
          type enumeration {
            enum "sr-isis";
            enum "sr-ospf";
            enum "ldp";
          }
        }
        container mixed-lsp-mode {
          tailf:cli-add-mode;
          presence "true";
          tailf:cli-diff-create-before "../bgp-tunnel" {
            tailf:xpath-root 3;
          }
          leaf revert-time {
            type union {
              type uint16;
              type enumeration {
                enum "infinite";
              }
            }
          }
        }
        leaf network-domain {
          type string;
        }
        leaf path-mtu {
          type uint16;
        }
        leaf pbb-etype {
          type uint16;
        }
        leaf signaling {
          type enumeration {
            enum "off";
            enum "tldp";
            enum "bgp";
          }
        }
        leaf local-end {
          type inet:ipv6-address;
        }
        leaf tunnel-far-end {
          type inet:ipv4-address;
        }
        leaf vlan-vc-etype {
          type uint32;
        }
        leaf shutdown {
          type boolean;
        }
      }
      container sdp-group {
        tailf:cli-add-mode;
        list group-name {
          tailf:cli-suppress-mode;
          key "name";
          leaf name {
            type string;
          }
          leaf value {
            mandatory true;
            type uint32;
          }
        }
      }

      grouping service-epipe-cpipe-common-grouping {
        uses service-id-grouping;
        leaf customer {
          tailf:cli-hide-in-submode;
          type uint32;
        }
        leaf name {
          tailf:cli-hide-in-submode;
          type string;
        }
        leaf vc-switching {
          tailf:cli-hide-in-submode;
          type empty;
        }
        leaf vpn {
          tailf:cli-hide-in-submode;
          type uint32;
        }
        leaf description {
          type string;
        }
        leaf service-name {
          type string;
        }
        leaf service-mtu {
          type uint16;
        }
        list spoke-sdp {
          key "sdp-id vc-id";
          leaf description {
            type string;
          }
          container egress {
            tailf:cli-add-mode;
            container l2tpv3 {
              tailf:cli-add-mode;
              leaf cookie {
                type string;
              }
            }
            leaf vc-label {
              type uint32;
            }
          }
          container eth-cfm {
            tailf:cli-add-mode;
            uses eth-cfm;
          }
          leaf force-vlan-vc-forwarding {
            type empty;
          }
          leaf standby-signaling-slave {
            type empty;
          }
          container ingress {
            tailf:cli-add-mode;
            container l2tpv3 {
              tailf:cli-add-mode;
              leaf cookie {
                type string;
              }
            }
            leaf vc-label {
              type uint32;
            }
          }
          leaf pw-status-signaling {
            type empty;
          }
          leaf control-word {
            type empty;
          }
          leaf collect-stats {
            type empty;
          }
          container hash-label {
            presence "true";
            leaf signal-capability {
              type empty;
            }
          }
          leaf precedence {
            type union {
              type enumeration {
                enum "primary";
              }
              type uint8;
            }
          }
          leaf vlan-vc-tag {
            type uint32;
          }
          leaf entropy-label {
            type empty;
          }
          leaf sdp-id {
            type uint32;
          }
          uses sdp-common;
        }
        list sap {
          key "sap-id";
          leaf sap-id {
            type string;
          }
          leaf endpoint {
            tailf:cli-hide-in-submode;
            type string;
          }
          leaf description {
            type string;
          }
          leaf cflowd {
            type empty;
          }
          container cem {
            tailf:cli-add-mode;
            container packet {
              tailf:cli-compact-syntax;
              leaf jitter-buffer {
                type uint8;
              }
              leaf payload-size {
                type uint16;
              }
            }
            leaf-list report-alarm {
              tailf:cli-flat-list-syntax;
              type enumeration {
                enum "stray";
                enum "malformed";
                enum "pktloss";
                enum "overrun";
                enum "underrun";
                enum "rpktloss";
                enum "rfault";
                enum "rrdi";
              }
            }
            leaf rtp-header {
              type empty;
            }
            leaf local-ecid {
              type uint32;
            }
            leaf remote-ecid {
              type uint32;
            }
            leaf remote-mac {
              type string;
            }
          }
          leaf accounting-policy {
            type uint8;
          }

          grouping vlan-manipulation-grouping {
            container vlan-manipulation {
              tailf:cli-add-mode;
              leaf preserve {
                type empty;
              }
              leaf push {
                type string;
              }
              container translate {
                tailf:cli-compact-syntax;
                tailf:cli-sequence-commands {
                  tailf:cli-reset-all-siblings;
                }
                leaf type {
                  tailf:cli-drop-node-name;
                  type enumeration {
                    enum "1-to-1";
                    enum "2-to-1";
                    enum "2-to-2";
                  }
                }
                leaf qtag {
                  tailf:cli-drop-node-name;
                  tailf:cli-optional-in-sequence;
                  type string;
                }
              }
            }
          }
          container egress {
            tailf:cli-add-mode;
            leaf egress-remark-policy {
              type string;
            }
            leaf qos {
              type uint16;
            }
            container agg-rate {
              tailf:cli-add-mode;
              container rate {
                tailf:cli-compact-syntax;
                leaf rate {
                  tailf:cli-drop-node-name;
                  type union {
                    type uint32;
                    type enumeration {
                      enum "max";
                    }
                  }
                }
                leaf cir {
                  type union {
                    type uint32;
                    type enumeration {
                      enum "max";
                    }
                  }
                }
              }
            }
            container agg-rate-limit {
              tailf:cli-compact-syntax;
              tailf:cli-sequence-commands {
                tailf:cli-reset-siblings;
              }
              choice pir-choice {
                leaf pir-less {
                  tailf:cli-drop-node-name;
                  tailf:cli-optional-in-sequence;
                  type uint32;
                }
                leaf pir {
                  tailf:cli-optional-in-sequence;
                  type uint32;
                }
              }
              leaf cir {
                type uint32;
              }
            }
            container filter {
              tailf:cli-compact-syntax;
              uses filter-choice;
            }
            uses sap-queue-override-grouping;
            leaf scheduler-policy {
              type string;
            }
            uses sap-scheduler-override-grouping;
            container vlan-qos-policy {
              tailf:cli-compact-syntax;
              tailf:cli-sequence-commands {
                tailf:cli-reset-all-siblings;
              }
              leaf vlan-qos-policy-name {
                tailf:cli-drop-node-name;
                type string;
              }
              leaf port-redirect {
                type empty;
              }
            }
            uses vlan-manipulation-grouping;
            container qtag-manipulation {
              tailf:cli-add-mode;
              leaf preserve {
                type empty;
              }
            }
          }
          container ingress {
            tailf:cli-add-mode;
            container aggregate-meter-rate {
              tailf:cli-compact-syntax;
              tailf:cli-sequence-commands {
                tailf:cli-reset-all-siblings;
              }
              leaf value {
                tailf:cli-drop-node-name;
                type uint32;
              }
              leaf burst {
                type uint32;
              }
            }
            container aggregate-policer-rate {
              tailf:cli-compact-syntax;
              leaf rate {
                tailf:cli-drop-node-name;
                type union {
                  type string;
                  type uint32;
                }
              }
              leaf burst {
                type union {
                  type uint32;
                  type string;
                }
              }
            }
            container filter {
              tailf:cli-compact-syntax;
              uses filter-choice;
            }
            leaf match-qinq-dot1p {
              type enumeration {
                enum "top";
                enum "bottom";
              }
            }
            container qos {
              tailf:cli-compact-syntax;
              tailf:cli-sequence-commands {
                tailf:cli-reset-siblings;
              }
              leaf policy-id {
                tailf:cli-drop-node-name;
                type uint16;
              }
              leaf shared-queuing {
                type empty;
              }
            }
            uses sap-queue-override-grouping;
            leaf scheduler-policy {
              type string;
            }
            uses vlan-manipulation-grouping;
            leaf vlan-translation {
              type union {
                type enumeration {
                  enum "copy-outer";
                }
                type uint16;
              }
            }
            container agg-rate-limit {
              tailf:cli-compact-syntax;
              tailf:cli-sequence-commands {
                tailf:cli-reset-siblings;
              }
              leaf agg-rate {
                tailf:cli-drop-node-name;
                type uint32;
              }
              leaf cir {
                type uint32;
              }
            }
            leaf scheduler-mode {
              type scheduler-mode;
            }
            uses sap-scheduler-override-grouping;
            container qtag-manipulation {
              tailf:cli-add-mode;
              leaf preserve {
                type empty;
              }
            }
          }
          leaf collect-stats {
            type empty;
          }
          container eth-cfm {
            tailf:cli-add-mode;
            uses eth-cfm;
            container mip {
              presence "true";
              leaf mac {
                type ieee-mac;
              }
            }
          }
          leaf multi-service-site {
            type string;
          }
          leaf oper-group {
            type string;
          }
          leaf dist-cpu-protection {
            type string;
          }
          leaf shutdown {
            type boolean;
          }
          container ethernet {
            tailf:cli-add-mode;
            leaf llf {
              type empty;
            }
          }
        }
        list endpoint {
          key "endpoint-name";
          leaf endpoint-name {
            type string;
          }
          leaf active-hold-delay {
            type uint8;
          }
          leaf description {
            type string;
          }
          leaf revert-time {
            type union {
              type enumeration {
                enum "infinite";
              }
              type uint16;
            }
          }
          leaf standby-signaling-master {
            type empty;
          }
          leaf standby-signaling-slave {
            type empty;
          }
        }
      }
      list cpipe {
        key "service-id";
        uses service-epipe-cpipe-common-grouping;
        leaf vc-type {
          tailf:cli-hide-in-submode;
          type enumeration {
            enum "satop-e1";
            enum "satop-t1";
            enum "cesopsn";
            enum "cesopsn-cas";
          }
        }
        leaf test {
          tailf:cli-hide-in-submode;
          type empty;
        }
        leaf shutdown {
          type boolean;
        }
      }
      list epipe {
        key "service-id";
        uses service-epipe-cpipe-common-grouping {
          augment "sap" {
            container statistics {
              tailf:cli-add-mode;
              container ingress {
                tailf:cli-add-mode;
                leaf counter-mode {
                  type enumeration {
                    enum "in-out-profile-count";
                    enum "forward-drop-count";
                  }
                }
              }
            }
          }
          refine "spoke-sdp/endpoint";
        }
        container load-balancing {
          tailf:cli-add-mode;
          leaf per-service-hashing {
            type empty;
          }
        }
        leaf svc-sap-type {
          tailf:cli-hide-in-submode;
          type enumeration {
            enum "null-star";
            enum "dot1q-preserve";
            enum "any";
            enum "dot1q-range";
          }
        }
        leaf customer-vid {
          tailf:cli-hide-in-submode;
          type uint16;
        }
        list pw-port {
          key "pw-port-id fpe";
          leaf pw-port-id {
            type string;
          }
          leaf fpe {
            type uint8;
          }
          leaf shutdown {
            type boolean;
          }
        }
        list site {
          key "name";
          leaf name {
            type string;
          }
          leaf boot-timer {
            type uint16;
          }
          leaf sap {
            type string;
          }
          leaf site-activation-timer {
            type uint16;
          }
          leaf site-id {
            type uint16;
          }
          leaf shutdown {
            type boolean;
          }
        }
        container bgp {
          tailf:cli-add-mode;
          leaf route-distinguisher {
            type string;
          }
          container route-target {
            tailf:cli-compact-syntax;
            tailf:cli-sequence-commands {
              tailf:cli-reset-all-siblings;
            }
            leaf export {
              type string;
            }
            leaf import {
              type string;
            }
          }
          leaf-list vsi-import {
            tailf:cli-flat-list-syntax;
            type string;
          }
          leaf-list vsi-export {
            tailf:cli-flat-list-syntax;
            type string;
          }
        }
        container bgp-evpn {
          tailf:cli-add-mode;
          presence "true";
          container local-ac-name {
            tailf:cli-add-mode;
            presence "true";
            leaf ac-name {
              tailf:cli-drop-node-name;
              tailf:cli-hide-in-submode;
              type string;
            }
            leaf eth-tag {
              type uint32;
            }
          }
          container remote-ac-name {
            tailf:cli-add-mode;
            presence "true";
            leaf ac-name {
              tailf:cli-drop-node-name;
              tailf:cli-hide-in-submode;
              type string;
            }
            leaf eth-tag {
              type uint32;
            }
          }
          list local-attachment-circuit {
            key "ac-name";
            leaf ac-name {
              type string;
            }
            leaf endpoint {
              tailf:cli-hide-in-submode;
              type string;
            }
            leaf eth-tag {
              type uint32;
            }
          }
          list remote-attachment-circuit {
            key "ac-name";
            leaf ac-name {
              type string;
            }
            leaf endpoint {
              tailf:cli-hide-in-submode;
              type string;
            }
            leaf eth-tag {
              type uint32;
            }
          }
          leaf evi {
            type uint32;
          }
          container mpls {
            tailf:cli-add-mode;
            presence "true";
            leaf control-word {
              type empty;
            }
            leaf bgp {
              tailf:cli-hide-in-submode;
              type uint8;
            }
            leaf force-vlan-vc-forwarding {
              type empty;
            }
            leaf route-next-hop {
              type union {
                type inet:ipv4-address;
                type inet:ipv6-address;
                type enumeration {
                  enum "system-ipv4";
                  enum "system-ipv6";
                }
              }
            }
            leaf default-route-tag {
              type uint32;
            }
            container auto-bind-tunnel {
              tailf:cli-add-mode;
              leaf enforce-strict-tunnel-tagging {
                type empty;
              }
              uses resolution-filter-grouping;
            }
            leaf ecmp {
              type uint32;
            }
            leaf entropy-label {
              type empty;
            }
            leaf shutdown {
              type boolean;
            }
          }
        }
        leaf shutdown {
          type boolean;
        }
      }
      list oper-group {
        key "group-name";
        leaf group-name {
          type string;
        }
        container hold-time {
          tailf:cli-add-mode;
          container group {
            presence "true";
            leaf up {
              type uint32;
            }
            leaf down {
              type uint32;
            }
          }
        }
      }
      list ies {
        key "service-id";
        leaf service-id {
          type uint32;
        }
        leaf customer {
          tailf:cli-hide-in-submode;
          type uint32;
        }
        leaf name {
          tailf:cli-hide-in-submode;
          type string;
        }
        leaf description {
          type string;
        }
        list redundant-interface {
          key "id";
          leaf id {
            type string;
          }
          leaf description {
            type string;
          }
          leaf address {
            type tailf:ipv4-address-and-prefix-length;
          }
          list spoke-sdp {
            key "sdp-id";
            leaf sdp-id {
              type string;
            }
            leaf shutdown {
              type boolean;
            }
          }
          leaf shutdown {
            type boolean;
          }
        }
        list subscriber-interface {
          key "id";
          uses subscriber-interface-grouping {
            refine "group-interface/tos-marking-state";
            augment "group-interface/sap" {
              leaf cpu-protection {
                type uint16;
              }
              list static-host {
                key "ip";
                leaf ip {
                  type inet:ipv4-address;
                }
                leaf shutdown {
                  type boolean;
                }
              }
            }
            augment "group-interface/dhcp" {
              leaf shutdown {
                type boolean;
              }
            }
          }
          container hold-time {
            tailf:cli-add-mode;
            list down {
              tailf:cli-suppress-mode;
              tailf:cli-compact-syntax;
              key "type";
              leaf type {
                type enumeration {
                  enum "ip";
                  enum "ipv6";
                }
              }
              leaf time {
                tailf:cli-drop-node-name;
                type uint32;
              }
              leaf init-only {
                type empty;
              }
            }
          }
          container ipv6 {
            tailf:cli-add-mode;
            presence "true";
            list address {
              tailf:cli-compact-syntax;
              tailf:cli-suppress-mode;
              key "ipv6-address";
              leaf ipv6-address {
                type tailf:ipv6-address-and-prefix-length;
              }
              choice adr {
                leaf pd {
                  type empty;
                }
                leaf wan-host {
                  type empty;
                }
              }
            }
            container default-dns {
              tailf:cli-compact-syntax;
              tailf:cli-sequence-commands {
                tailf:cli-reset-all-siblings;
              }
              leaf address {
                tailf:cli-drop-node-name;
                type inet:ipv6-address;
              }
              leaf secondary {
                type inet:ipv6-address;
              }
            }
            leaf delegated-prefix-length {
              type union {
                type uint8;
                type enumeration {
                  enum "variable";
                }
              }
            }
            leaf link-local-address {
              type inet:ipv6-address;
            }
            leaf allow-unmatching-prefixes {
              type empty;
            }
            container subscriber-prefixes {
              tailf:cli-add-mode;
              list prefix {
                tailf:cli-sequence-commands {
                  tailf:cli-reset-siblings;
                }
                tailf:cli-compact-syntax;
                tailf:cli-suppress-mode;
                key "ipv6-prefix";
                leaf ipv6-prefix {
                  type tailf:ipv6-address-and-prefix-length;
                }
                leaf pd {
                  tailf:cli-optional-in-sequence;
                  type empty;
                }
                leaf wan-host {
                  tailf:cli-optional-in-sequence;
                  type empty;
                }
                leaf track-srrp {
                  tailf:cli-optional-in-sequence;
                  type uint32;
                }
              }
            }
          }
          container dhcp {
            tailf:cli-add-mode;
            container gi-address {
              tailf:cli-compact-syntax;
              tailf:cli-sequence-commands {
                tailf:cli-reset-all-siblings;
              }
              leaf gi-address-value {
                tailf:cli-drop-node-name;
                type inet:ipv4-address;
              }
              leaf src-ip-addr {
                type empty;
              }
            }
            leaf virtual-subnet {
              type empty;
            }
          }
          leaf shutdown {
            type boolean;
          }
        }
        list interface {
          key "ip-int-name";
          leaf ip-int-name {
            type string;
          }
          leaf tunnel {
            tailf:cli-hide-in-submode;
            type empty;
          }
          leaf monitor-oper-group {
            type string;
          }
          leaf allow-directed-broadcasts {
            type empty;
          }
          leaf arp-learn-unsolicited {
            type empty;
          }
          leaf arp-populate {
            type empty;
          }
          leaf arp-timeout {
            type uint16;
          }
          leaf authentication-policy {
            type string;
          }
          container bfd {
            tailf:cli-compact-syntax;
            uses bfd-grouping;
          }
          uses cflowd-params-grouping;
          container cflowd {
            tailf:cli-compact-syntax;
            tailf:cli-sequence-commands {
              tailf:cli-reset-siblings;
            }
            leaf id {
              tailf:cli-drop-node-name;
              type enumeration {
                enum "acl";
                enum "interface";
              }
            }
            leaf direction {
              tailf:cli-drop-node-name;
              type enumeration {
                enum "ingress-only";
                enum "egress-only";
                enum "both";
              }
            }
          }
          leaf cpu-protection {
            type uint8;
          }
          leaf delayed-enable {
            type uint16;
          }
          leaf description {
            type string;
          }
          container dhcp {
            tailf:cli-add-mode;
            leaf-list server {
              tailf:cli-flat-list-syntax;
              type inet:ip-address;
            }
            container gi-address {
              tailf:cli-compact-syntax;
              tailf:cli-sequence-commands {
                tailf:cli-reset-all-siblings;
              }
              leaf gi-address-value {
                tailf:cli-drop-node-name;
                type inet:ipv4-address;
              }
              leaf src-ip-addr {
                type empty;
              }
            }
            leaf lease-populate {
              type uint16;
            }
            leaf trusted {
              type empty;
            }
            leaf shutdown {
              type boolean;
            }
          }
          leaf dynamic-tunnel-redundant-next-hop {
            type inet:ipv4-address;
          }
          leaf enable-ingress-stats {
            type empty;
          }
          leaf enable-mac-accounting {
            type empty;
          }
          container host-connectivity {
            tailf:cli-compact-syntax;
            tailf:cli-sequence-commands;
            leaf source {
              type enumeration {
                enum "vrrp";
                enum "interface";
              }
            }
            leaf interval {
              type uint16;
            }
            leaf action {
              type enumeration {
                enum "remove";
                enum "alarm";
              }
            }
            leaf timeout {
              type uint8;
            }
            leaf count {
              type uint8;
            }
          }
          uses interface-icmp-grouping;
          leaf ip-mtu {
            type uint16;
          }
          container ipv6 {
            tailf:cli-add-mode;
            presence "true";
            leaf local-dhcp-server {
              type string;
            }
            uses ipv6-grouping;
            uses dhcp6-grouping;
          }
          leaf local-dhcp-server {
            type string;
          }
          leaf loopback {
            type empty;
          }
          leaf mac {
            type ieee-mac;
          }
          list sap {
            key "sap-id";
            leaf sap-id {
              type string;
            }
            leaf accounting-policy {
              type uint8;
            }
            leaf description {
              type string;
            }
            leaf dist-cpu-protection {
              type string;
            }
            leaf collect-stats {
              type empty;
            }
            container egress {
              tailf:cli-add-mode;
              choice agg {
                case new {
                  uses agg-rate-grouping;
                }
                case old {
                  container agg-rate-limit {
                    tailf:cli-compact-syntax;
                    tailf:cli-sequence-commands;
                    leaf agg-rate {
                      tailf:cli-drop-node-name;
                      type union {
                        type uint32;
                        type enumeration {
                          enum "max";
                        }
                      }
                    }
                    leaf queue-frame-based-accounting {
                      type empty;
                    }
                  }
                }
              }
              container filter {
                leaf ip {
                  type filter-id;
                }
                leaf ipv6 {
                  type filter-id;
                }
              }
              leaf policer-control-policy {
                type string;
              }
              leaf qinq-mark-top-only {
                type empty;
              }
              leaf qos {
                type uint16;
              }
              uses sap-queue-override-grouping;
              leaf scheduler-mode {
                type scheduler-mode;
              }
              leaf scheduler-policy {
                type string;
              }
              uses sap-scheduler-override-grouping;
            }
            container ingress {
              tailf:cli-add-mode;
              leaf qos {
                type uint16;
              }
              container filter {
                uses filter-choice;
              }
              leaf flowspec {
                type boolean;
              }
              leaf flowspec-ipv6 {
                type boolean;
              }
              leaf match-qinq-dot1p {
                type enumeration {
                  enum "top";
                  enum "bottom";
                }
              }
              leaf policer-control-policy {
                type string;
              }
              container policer-control-override {
                presence "true";
                tailf:cli-add-mode;
                leaf max-rate {
                  type union {
                    type enumeration {
                      enum "max";
                    }
                    type uint32;
                  }
                }
                container priority-mbs-thresholds {
                  tailf:cli-add-mode;
                  container min-thresh-separation {
                    tailf:cli-compact-syntax;
                    tailf:cli-sequence-commands {
                      tailf:cli-reset-siblings;
                    }
                    uses mbs-rate-grouping;
                  }
                  list priority {
                    key "level";
                    leaf level {
                      type uint8;
                    }
                    container mbs-contribution {
                      tailf:cli-compact-syntax;
                      tailf:cli-sequence-commands {
                        tailf:cli-reset-siblings;
                      }
                      uses mbs-rate-grouping;
                    }
                  }
                }
              }
              uses sap-policer-override-grouping-ingress;
              uses sap-queue-override-grouping;
              leaf scheduler-policy {
                type string;
              }
              uses sap-scheduler-override-grouping;
            }
            leaf anti-spoof {
              type enumeration {
                enum "nh-mac";
                enum "ip";
                enum "mac";
                enum "ip-mac";
              }
            }
            leaf multi-service-site {
              type string;
            }
            container sub-sla-mgmt {
              presence "present";
              tailf:cli-add-mode;
              leaf def-sub-id {
                type enumeration {
                  enum "use-sap-id";
                }
              }
              leaf def-sub-profile {
                type string;
              }
              container single-sub-parameters {
                presence "present";
                tailf:cli-add-mode;
                leaf profiled-traffic-only {
                  type empty;
                }
              }
              leaf shutdown {
                type boolean;
              }
            }
            leaf calling-station-id {
              type string;
            }
            list ip-tunnel {
              key "name";
              leaf name {
                type string;
              }
              leaf description {
                type string;
              }
              leaf dest-ip {
                type inet:ipv4-address;
              }
              container gre-header {
                tailf:cli-compact-syntax;
                presence "true";
              }
              leaf source {
                type inet:ipv4-address;
              }
              leaf remote-ip {
                type inet:ipv4-address;
              }
              leaf delivery-service {
                type union {
                  type uint32;
                  type string;
                }
              }
              leaf shutdown {
                type boolean;
              }
            }
            leaf shutdown {
              type empty;
            }
          }
          list spoke-sdp {
            key "sdp-id vc-id";
            leaf sdp-id {
              type uint32;
            }
            leaf vc-id {
              type uint32;
            }
            leaf vc-type {
              tailf:cli-hide-in-submode;
              type enumeration {
                enum "ether";
                enum "ipipe";
              }
            }
            container egress {
              tailf:cli-add-mode;
              container filter {
                uses filter-choice;
              }
            }
            container ingress {
              tailf:cli-add-mode;
              container filter {
                uses filter-choice;
              }
            }
            leaf shutdown {
              type boolean;
            }
          }
          leaf tos-marking-state {
            type enumeration {
              enum "trusted";
              enum "untrusted";
            }
          }
          container urpf-check {
            tailf:cli-add-mode;
            leaf mode {
              type enumeration {
                enum "strict";
                enum "loose";
                enum "strict-no-ecmp";
              }
            }
          }
          leaf vas-if-type {
            type enumeration {
              enum "to-from-access";
              enum "to-from-network";
              enum "to-from-both";
            }
          }
          list vrrp {
            key "virtual-router-id";
            leaf virtual-router-id {
              type uint8;
            }
            leaf owner {
              tailf:cli-hide-in-submode;
              type empty;
            }
            leaf passive {
              tailf:cli-hide-in-submode;
              type empty;
            }
            uses authentication-key-grouping;
            leaf init-delay {
              type uint16;
            }
            leaf mac {
              type ieee-mac;
            }
            leaf master-int-inherit {
              type empty;
            }
            container message-interval {
              tailf:cli-compact-syntax;
              tailf:cli-sequence-commands {
                tailf:cli-reset-siblings;
              }
              leaf seconds {
                tailf:cli-drop-node-name;
                tailf:cli-optional-in-sequence;
                type uint8;
              }
              leaf milliseconds {
                type uint16;
              }
            }
            leaf ping-reply {
              type empty;
            }
            leaf policy {
              type uint16;
            }
            leaf preempt {
              type empty;
            }
            leaf priority {
              type uint8;
            }
            leaf ssh-reply {
              type empty;
            }
            leaf standby-forwarding {
              type empty;
            }
            leaf telnet-reply {
              type empty;
            }
            leaf traceroute-reply {
              type empty;
            }
            list backup {
              tailf:cli-suppress-mode;
              key "address";
              leaf address {
                type inet:ipv4-address;
              }
            }
            leaf shutdown {
              type boolean;
            }
          }
          list secondary {
            tailf:cli-suppress-mode;
            tailf:cli-sequence-commands {
              tailf:cli-reset-all-siblings;
            }
            key "address";
            leaf address {
              type tailf:ipv4-address-and-prefix-length;
            }
            leaf broadcast {
              type enumeration {
                enum "all-ones";
                enum "host-ones";
              }
            }
          }
          container address {
            tailf:cli-compact-syntax;
            tailf:cli-sequence-commands {
              tailf:cli-reset-all-siblings;
            }
            leaf ip-address {
              tailf:cli-drop-node-name;
              tailf:cli-break-sequence-commands;
              tailf:cli-diff-create-before "../../static-arp" {
                tailf:xpath-root 3;
              }
              type tailf:ipv4-address-and-prefix-length;
            }
            leaf broadcast {
              type enumeration {
                enum "all-ones";
                enum "host-ones";
              }
            }
            leaf track-srrp {
              type uint32;
            }
          }
          list static-arp {
            tailf:cli-suppress-mode;
            key "ip-address";
            leaf ip-address {
              type inet:ipv4-address;
            }
            leaf ieee-address {
              tailf:cli-drop-node-name;
              type ieee-mac;
            }
          }
          leaf qos-route-lookup {
            type enumeration {
              enum "destination";
              enum "source";
            }
          }
          container vpls {
            tailf:cli-add-mode;
            presence "true";
            leaf service-name {
              tailf:cli-drop-node-name;
              tailf:cli-hide-in-submode;
              mandatory true;
              type string;
            }
            container egress {
              tailf:cli-add-mode;
              leaf reclassify-using-qos {
                type uint16;
              }
              leaf v4-routed-override-filter {
                type filter-id;
              }
            }
            container ingress {
              tailf:cli-add-mode;
              leaf v4-routed-override-filter {
                type filter-id;
              }
              leaf v6-routed-override-filter {
                type filter-id;
              }
            }
          }
          leaf shutdown {
            type empty;
          }
        }
        leaf service-name {
          type string;
        }
        leaf shutdown {
          type boolean;
        }
      }
      container proxy-arp-nd {
        tailf:cli-add-mode;
        list mac-list {
          key "name";
          leaf name {
            type string;
          }
          list mac {
            tailf:cli-suppress-mode;
            key "mac-id";
            leaf mac-id {
              type ieee-mac;
            }
          }
        }
      }
      container nat {
        tailf:cli-add-mode;
        list nat-policy {
          key "name";
          leaf name {
            type string;
          }
          container pool {
            tailf:cli-compact-syntax;
            tailf:cli-sequence-commands;
            leaf name {
              tailf:cli-drop-node-name;
              type string;
            }
            leaf router {
              type string;
            }
          }
          container timeouts {
            tailf:cli-add-mode;
            tailf:cli-compact-syntax;
            tailf:cli-sequence-commands;
            list timeouts {
              tailf:cli-drop-node-name;
              tailf:cli-suppress-mode;
              key "name";
              leaf name {
                type enumeration {
                  enum "icmp-query";
                  enum "sip";
                  enum "subscriber-retention";
                  enum "tcp-established";
                  enum "tcp-syn";
                  enum "tcp-time-wait";
                  enum "tcp-transitory";
                  enum "udp";
                  enum "udp-dns";
                  enum "udp-initial";
                }
              }
              leaf hrs {
                tailf:cli-optional-in-sequence;
                type uint8;
              }
              leaf min {
                tailf:cli-optional-in-sequence;
                type uint8;
              }
              leaf sec {
                tailf:cli-optional-in-sequence;
                type uint8;
              }
            }
          }
        }
      }
      list vpls {
        key "service-id";
        // NCS expand uses statement
        leaf service-id {
          type service-id;
        }
        leaf customer {
          tailf:cli-hide-in-submode;
          type uint32;
        }
        leaf name {
          tailf:cli-hide-in-submode;
          type string;
        }
        leaf etree {
          tailf:cli-hide-in-submode;
          type empty;
        }
        leaf vpn {
          tailf:cli-hide-in-submode;
          type uint32;
        }
        leaf m-vpls {
          tailf:cli-hide-in-submode;
          type empty;
        }
        choice a {
          leaf b-vpls {
            tailf:cli-hide-in-submode;
            type empty;
          }
          leaf i-vpls {
            tailf:cli-hide-in-submode;
            type empty;
          }
          leaf r-vpls {
            tailf:cli-hide-in-submode;
            type empty;
          }
        }
        leaf svc-sap-type {
          tailf:cli-hide-in-submode;
          type enumeration {
            enum "any";
            enum "dot1q-range";
          }
        }
        leaf description {
          type string;
        }
        leaf disable-learning {
          type empty;
        }
        leaf disable-aging {
          type empty;
        }
        leaf discard-unknown {
          type empty;
        }
        container allow-ip-int-bind {
          tailf:cli-add-mode;
          presence "true";
          leaf evpn-mpls-ecmp {
            type empty;
          }
          leaf forward-ipv4-multicast-to-ip-int {
            type empty;
          }
          leaf vxlan-ipv4-tep-ecmp {
            type empty;
          }
          container igmp-snooping {
            tailf:cli-add-mode;
            leaf mrouter-port {
              type empty;
            }
          }
        }
        leaf allow-ip-int-binding {
          type empty;
        }
        leaf service-name {
          type string;
        }
        list endpoint {
          key "endpoint-name";
          leaf endpoint-name {
            type string;
          }
          leaf description {
            type string;
          }
          leaf revert-time {
            type union {
              type enumeration {
                enum "infinite";
              }
              type uint16;
            }
          }
          leaf suppress-standby-signaling {
            type enable-disable;
          }
          container restrict-protected-src {
            tailf:cli-compact-syntax;
            presence "present";
            leaf restrict-protected-src-value {
              tailf:cli-drop-node-name;
              type enumeration {
                enum "alarm-only";
                enum "discard-frame";
              }
            }
          }
        }
        container eth-cfm {
          tailf:cli-add-mode;
          uses eth-cfm;
          leaf vmep-extensions {
            type empty;
          }
          leaf tunnel-fault {
            type enumeration {
              enum "accept";
              enum "ignore";
            }
          }
        }
        leaf fdb-table-high-wmark {
          type uint8;
        }
        leaf fdb-table-low-wmark {
          type uint8;
        }
        leaf fdb-table-size {
          type uint32;
        }
        container igmp-snooping {
          tailf:cli-add-mode;
          leaf query-interval {
            type uint16;
          }
          leaf report-src-ip {
            type inet:ipv4-address;
          }
          leaf robust-count {
            type uint32;
          }
          leaf shutdown {
            type boolean;
          }
        }
        list site {
          key "name";
          leaf name {
            type string;
          }
          leaf site-id {
            type uint32;
          }
          leaf sap {
            type string;
          }
          leaf spoke-sdp {
            type string;
          }
          leaf shutdown {
            type boolean;
          }
        }
        list interface {
          key "ip-int-name";
          leaf ip-int-name {
            type string;
          }
          container address {
            tailf:cli-sequence-commands;
            tailf:cli-compact-syntax;
            choice a {
              leaf addr-and-prefix {
                tailf:cli-drop-node-name;
                type tailf:ipv4-address-and-prefix-length;
              }
              case addr-and-netmask {
                leaf addr {
                  tailf:cli-drop-node-name;
                  type inet:ipv4-address;
                }
                leaf mask {
                  tailf:cli-drop-node-name;
                  type inet:ipv4-address;
                }
              }
            }
          }
          leaf arp-timeout {
            type uint16;
          }
          leaf description {
            type string;
          }
          leaf mac {
            type ieee-mac;
          }
          list static-arp {
            tailf:cli-suppress-mode;
            tailf:cli-sequence-commands;
            tailf:cli-compact-syntax;
            key "address";
            leaf address {
              type inet:ipv4-address;
            }
            leaf ieee-address {
              tailf:cli-drop-node-name;
              type ieee-mac;
            }
            leaf unnumbered {
              type empty;
            }
          }
          leaf unnumbered {
            type union {
              type inet:ipv4-address;
              type string;
            }
          }
          leaf shutdown {
            type boolean;
          }
        }
        leaf local-age {
          type uint32;
        }
        container load-balancing {
          tailf:cli-add-mode;
          leaf per-service-hashing {
            type empty;
          }
          leaf spi-load-balancing {
            type empty;
          }
          leaf teid-load-balancing {
            type empty;
          }
        }
        container mac-move {
          tailf:cli-add-mode;
          leaf move-frequency {
            type uint8;
          }
          leaf number-retries {
            type uint8;
          }
          leaf retry-timeout {
            type uint8;
          }

          grouping vpls-mac-move-ports-grouping {
            leaf cumulative-factor {
              type uint8;
            }
            list sap {
              tailf:cli-suppress-mode;
              tailf:cli-delete-when-empty;
              key "id";
              leaf id {
                type string;
              }
            }
            list spoke-sdp {
              tailf:cli-suppress-mode;
              tailf:cli-delete-when-empty;
              key "id";
              leaf id {
                type string;
              }
            }
          }
          container primary-ports {
            tailf:cli-add-mode;
            uses vpls-mac-move-ports-grouping;
          }
          container secondary-ports {
            tailf:cli-add-mode;
            uses vpls-mac-move-ports-grouping;
          }
          leaf shutdown {
            type boolean;
          }
        }
        leaf mfib-table-high-wmark {
          type uint8;
        }
        leaf mfib-table-low-wmark {
          type uint8;
        }
        leaf mfib-table-size {
          type uint32;
        }
        container pbb {
          tailf:cli-add-mode;
          list backbone-vpls {
            key "service-id";
            leaf service-id {
              type service-id;
            }
            leaf isid {
              tailf:cli-hide-in-submode;
              type uint32;
            }

            grouping service-vpls-mld-snooping-grouping {
              container mld-snooping {
                tailf:cli-add-mode;
                leaf mrouter-port {
                  type empty;
                }
              }
            }

            grouping service-vpls-igmp-snooping-grouping {
              container igmp-snooping {
                tailf:cli-add-mode;
                leaf mrouter-port {
                  type empty;
                }
              }
            }
            container igmp-snooping {
              tailf:cli-add-mode;
              leaf mrouter-dest {
                type string;
              }
            }
            container mld-snooping {
              tailf:cli-add-mode;
              leaf mrouter-dest {
                type string;
              }
            }
            list sap {
              key "sap-id";
              leaf sap-id {
                type string;
              }
              uses service-vpls-igmp-snooping-grouping;
              uses service-vpls-mld-snooping-grouping;
            }
            list sdp {
              key "sdp-id";
              leaf sdp-id {
                type string;
              }
              uses service-vpls-igmp-snooping-grouping;
              uses service-vpls-mld-snooping-grouping;
            }
            leaf stp {
              type empty;
            }
          }
          leaf force-qtag-forwarding {
            type empty;
          }
          leaf propagate-mac-flush-from-bvpls {
            type empty;
          }
          leaf-list send-bvpls-flush {
            tailf:cli-flat-list-syntax;
            type enumeration {
              enum "all-but-mine";
              enum "all-from-me";
            }
          }
          leaf send-flush-on-bvpls-failure {
            type empty;
          }
          leaf source-bmac {
            type ieee-mac;
          }
          leaf use-sap-bmac {
            type empty;
          }
        }
        container proxy-arp {
          tailf:cli-add-mode;
          presence "true";
          list static {
            tailf:cli-suppress-mode;
            key "address";
            leaf address {
              type inet:ipv4-address;
            }
            leaf ieee-addr {
              mandatory true;
              tailf:cli-drop-node-name;
              type ieee-mac;
            }
          }
          leaf age-time {
            type uint32;
          }
          container dup-detect {
            tailf:cli-compact-syntax;
            leaf anti-spoof-mac {
              type ieee-mac;
            }
            leaf window {
              type uint32;
            }
            leaf num-moves {
              type uint32;
            }
            leaf hold-down {
              type uint32;
            }
          }
          list dynamic {
            key "address";
            leaf address {
              type inet:ipv4-address;
            }
            leaf mac-list {
              type string;
            }
            leaf resolve {
              type uint32;
            }
          }
          leaf dynamic-arp-populate {
            type empty;
          }
          leaf evpn-route-tag {
            type uint32;
          }
          leaf garp-flood-evpn {
            type boolean;
          }
          leaf send-refresh {
            type uint32;
          }
          leaf table-size {
            type uint32;
          }
          leaf unknown-arp-request-flood-evpn {
            type boolean;
          }
          leaf shutdown {
            type boolean;
          }
        }
        leaf propagate-mac-flush {
          type empty;
        }
        leaf remote-age {
          type uint32;
        }
        leaf send-flush-on-failure {
          type empty;
        }
        leaf service-mtu {
          type uint16;
        }
        list spb {
          key "isis-instance";
          leaf isis-instance {
            type uint16;
          }
          leaf fid {
            tailf:cli-hide-in-submode;
            type uint16;
          }
          list level {
            key "level";
            leaf level {
              type uint32;
            }
            leaf bridge-priority {
              type uint8;
            }
            container ect-algorithm {
              leaf fid-range {
                type string;
              }
              leaf path-id {
                tailf:cli-drop-node-name;
                type enumeration {
                  enum "low-path-id";
                  enum "high-path-id";
                }
              }
            }
            container forwarding-tree-topology {
              leaf unicast {
                type enumeration {
                  enum "spf";
                  enum "st";
                }
              }
            }
            leaf hello-interval {
              type uint16;
            }
            leaf hello-multiplier {
              type uint8;
            }
            leaf metric {
              type uint16;
            }
          }
          leaf lsp-pacing-interval {
            type uint32;
          }
          leaf retransmit-interval {
            type uint32;
          }
          leaf shutdown {
            type boolean;
          }
        }
        container stp {
          tailf:cli-add-mode;
          leaf forward-delay {
            type uint8;
          }
          leaf hello-time {
            type uint8;
          }
          leaf hold-count {
            type uint8;
          }
          leaf max-age {
            type uint8;
          }
          leaf mode {
            type enumeration {
              enum "rstp";
              enum "comp-dot1w";
              enum "dot1w";
              enum "mstp";
              enum "pmstp";
            }
          }
          list mst-instance {
            key "mst-inst-number";
            leaf mst-inst-number {
              type uint16;
            }
            leaf mst-priority {
              type uint16;
            }
            list vlan-range {
              tailf:cli-suppress-mode;
              key "vlan";
              leaf vlan {
                tailf:cli-allow-range;
                type string;
              }
            }
          }
          leaf mst-max-hops {
            type uint8;
          }
          leaf mst-name {
            type string;
          }
          leaf mst-revision {
            type uint16;
          }
          leaf priority {
            type uint16;
          }
          leaf shutdown {
            type boolean;
          }
        }
        leaf def-mesh-vc-id {
          type uint32;
        }
        list mesh-sdp {
          key "sdp-id vc-id";
          uses sdp-spoke-mesh-common;
        }
        container pim-snooping {
          tailf:cli-add-mode;
          leaf shutdown {
            type boolean;
          }
        }
        list spoke-sdp {
          key "sdp-id vc-id";
          uses sdp-spoke-mesh-common;
          leaf leaf-ac {
            tailf:cli-hide-in-submode;
            type empty;
          }
          leaf split-horizon-group {
            tailf:cli-hide-in-submode;
            type string;
          }
          container dhcp {
            tailf:cli-add-mode;
            leaf description {
              type string;
            }
            leaf snoop {
              type empty;
            }
          }
          leaf bpdu-translation {
            type enumeration {
              enum "auto";
              enum "pvst";
              enum "stp";
            }
          }
          leaf diable-aging {
            type empty;
          }
          leaf disable-learning {
            type empty;
          }
          leaf discard-unknown-source {
            type empty;
          }
          leaf l2pt-termination {
            type empty;
          }
          leaf entropy-label {
            type empty;
          }
          leaf limit-mac-move {
            type limit-mac-move;
          }
          leaf max-nbr-mac-addr {
            type uint32;
          }
          container stp {
            tailf:cli-add-mode;
            uses stp-common;
          }
          container oper-group-choice {
            tailf:cli-drop-node-name;
            leaf monitor-oper-group {
              type string;
            }
            leaf oper-group {
              type string;
            }
          }
          container transit-policy {
            leaf prefix {
              type uint16;
            }
          }
          leaf pw-status-signaling {
            type boolean;
          }
        }
        list sap {
          key "sap-id";
          leaf sap-id {
            type string;
          }
          leaf dist-cpu-protection {
            type string;
          }
          leaf leaf-ac {
            tailf:cli-hide-in-submode;
            type empty;
          }
          list static-mac {
            tailf:cli-suppress-mode;
            tailf:cli-delete-when-empty;
            key "mac";
            leaf mac {
              type ieee-mac;
            }
          }
          leaf eth-ring {
            tailf:cli-hide-in-submode;
            type uint32;
          }
          container sub-sla-mgmt {
            tailf:cli-add-mode;
            container single-sub-parameters {
              tailf:cli-add-mode;
              leaf profiled-traffic-only {
                type empty;
              }
              container non-sub-traffic {
                tailf:cli-compact-syntax;
                leaf sub-profile {
                  type string;
                }
                leaf sla-profile {
                  type string;
                }
                leaf subscriber {
                  type string;
                }
              }
            }
            leaf shutdown {
              type boolean;
            }
          }
          leaf allow-dot1q-msaps {
            type empty;
          }
          leaf arp-reply-agent {
            tailf:cli-drop-node-name;
            type enumeration {
              enum "no arp-reply-agent";
              enum "arp-reply-agent";
              enum "arp-reply-agent sub-ident";
            }
          }
          leaf cflowd {
            type empty;
          }
          leaf split-horizon-group {
            tailf:cli-hide-in-submode;
            type string;
          }
          leaf capture-sap {
            tailf:cli-hide-in-submode;
            type empty;
          }
          leaf dhcp-python-policy {
            type string32;
          }
          leaf dhcp6-python-policy {
            type string32;
          }
          leaf-list trigger-packet {
            tailf:cli-flat-list-syntax;
            type enumeration {
              enum "dhcp";
              enum "pppoe";
              enum "arp";
              enum "dhcp6";
              enum "ppp";
              enum "rtr-solicit";
              enum "data";
            }
          }
          leaf authentication-policy {
            type string;
          }
          leaf accounting-policy {
            type uint8;
          }
          leaf anti-spoof {
            type enumeration {
              enum "ip";
              enum "ip-mac";
              enum "mac";
            }
          }
          leaf app-profile {
            type string;
          }
          leaf auto-learn-mac-protect {
            type empty;
          }
          leaf bpdu-translation {
            type enumeration {
              enum "auto";
              enum "pvst";
              enum "stp";
            }
          }
          leaf collect-stats {
            type empty;
          }
          leaf description {
            type string;
          }
          leaf disable-aging {
            type empty;
          }
          leaf disable-learning {
            type empty;
          }
          leaf discard-unknown-source {
            type empty;
          }
          container eth-cfm {
            tailf:cli-add-mode;
            uses eth-cfm;
            container mip {
              presence "true";
              leaf mac {
                type string;
              }
            }
          }
          leaf host-lockout-policy {
            type string32;
          }
          container igmp-snooping {
            tailf:cli-add-mode;
            uses igmp-snooping-grouping;
          }
          container ingress {
            tailf:cli-add-mode;
            // NCS expand uses statement
            container filter {
              // NCS expand uses statement
              leaf ip {
                type filter-id;
              }
              leaf ipv6 {
                type filter-id;
              }
              leaf mac {
                type filter-id;
              }
            }
            container aggregate-meter-rate {
              tailf:cli-compact-syntax;
              tailf:cli-sequence-commands {
                tailf:cli-reset-siblings;
              }
              leaf value {
                tailf:cli-drop-node-name;
                type uint32;
              }
              leaf burst {
                type uint32;
              }
            }
            leaf match-qinq-dot1p {
              type enumeration {
                enum "top";
                enum "bottom";
              }
            }
            container qos {
              tailf:cli-compact-syntax;
              tailf:cli-sequence-commands {
                tailf:cli-reset-all-siblings;
              }
              leaf policy-id {
                tailf:cli-drop-node-name;
                type uint16;
              }
              leaf shared-queuing {
                tailf:cli-optional-in-sequence;
                type empty;
              }
              leaf enable-table-classification {
                type empty;
              }
            }
            // NCS expand uses statement
            container queue-override {
              tailf:cli-add-mode;
              list queue {
                key "queue-id";
                leaf queue-id {
                  type uint32;
                }
                // NCS expand uses statement
                container adaptation-rule {
                  tailf:cli-compact-syntax;
                  leaf pir {
                    type enumeration {
                      enum "max";
                      enum "min";
                      enum "closest";
                    }
                  }
                  leaf cir {
                    type enumeration {
                      enum "max";
                      enum "min";
                      enum "closest";
                    }
                  }
                }
                leaf avg-frame-overhead {
                  type decimal64 {
                    fraction-digits 2;
                  }
                }
                container mbs {
                  tailf:cli-compact-syntax;
                  tailf:cli-sequence-commands {
                    tailf:cli-reset-siblings;
                  }
                  leaf val {
                    tailf:cli-drop-node-name;
                    type union {
                      type enumeration {
                        enum "default";
                      }
                      type uint32;
                    }
                  }
                  leaf unit {
                    tailf:cli-drop-node-name;
                    type enumeration {
                      enum "bytes";
                      enum "kilobytes";
                    }
                  }
                }
                leaf cbs {
                  type union {
                    type enumeration {
                      enum "default";
                    }
                    type uint32;
                  }
                }
                leaf high-prio-only {
                  type union {
                    type enumeration {
                      enum "default";
                    }
                    type uint8;
                  }
                }
                container rate {
                  tailf:cli-compact-syntax;
                  tailf:cli-sequence-commands {
                    tailf:cli-reset-siblings;
                  }
                  leaf pir {
                    tailf:cli-drop-node-name;
                    type union {
                      type enumeration {
                        enum "max";
                      }
                      type uint32;
                    }
                  }
                  leaf cir {
                    type union {
                      type enumeration {
                        enum "max";
                      }
                      type uint32;
                    }
                  }
                }
                container parent {
                  tailf:cli-compact-syntax;
                  tailf:cli-sequence-commands {
                    tailf:cli-reset-siblings;
                  }
                  leaf weight {
                    type uint8;
                  }
                  leaf cir-weight {
                    type uint8;
                  }
                }
                // NCS expand uses statement
                container percent-rate {
                  tailf:cli-compact-syntax;
                  tailf:cli-sequence-commands {
                    tailf:cli-reset-all-siblings;
                  }
                  leaf pir {
                    tailf:cli-drop-node-name;
                    type decimal64 {
                      fraction-digits 2;
                    }
                  }
                  leaf cir {
                    tailf:cli-optional-in-sequence;
                    type decimal64 {
                      fraction-digits 2;
                    }
                  }
                }
              }
            }
            leaf agg-shaper-rate {
              type union {
                type uint32;
                type enumeration {
                  enum "max";
                }
              }
            }
            // NCS expand uses statement
            container policer-override {
              tailf:cli-add-mode;
              list policer {
                key "policer-id";
                leaf policer-id {
                  type uint8;
                }
                // NCS expand uses statement
                // NCS expand uses statement
                container cbs {
                  tailf:cli-compact-syntax;
                  tailf:cli-sequence-commands {
                    tailf:cli-reset-siblings;
                  }
                  // NCS expand uses statement
                  leaf size {
                    tailf:cli-drop-node-name;
                    type union {
                      type uint32;
                      type enumeration {
                        enum "default";
                      }
                    }
                  }
                  leaf unit {
                    tailf:cli-drop-node-name;
                    type enumeration {
                      enum "bytes";
                      enum "kilobytes";
                    }
                  }
                }
                container mbs {
                  tailf:cli-compact-syntax;
                  tailf:cli-sequence-commands {
                    tailf:cli-reset-siblings;
                  }
                  // NCS expand uses statement
                  leaf size {
                    tailf:cli-drop-node-name;
                    type union {
                      type uint32;
                      type enumeration {
                        enum "default";
                      }
                    }
                  }
                  leaf unit {
                    tailf:cli-drop-node-name;
                    type enumeration {
                      enum "bytes";
                      enum "kilobytes";
                    }
                  }
                }
                container rate {
                  tailf:cli-compact-syntax;
                  tailf:cli-sequence-commands {
                    tailf:cli-reset-siblings;
                  }
                  leaf pir {
                    tailf:cli-drop-node-name;
                    type rate-type;
                  }
                  leaf cir {
                    type rate-type;
                  }
                }
                leaf stat-mode {
                  type policer-stat-mode;
                }
                container packet-byte-offset {
                  tailf:cli-compact-syntax;
                  choice add-delete {
                    leaf add {
                      type uint8;
                    }
                    leaf subtract {
                      type uint8;
                    }
                  }
                }
              }
            }
            leaf policer-control-policy {
              type string;
            }
            leaf scheduler-policy {
              type string;
            }
            // NCS expand uses statement
            container scheduler-override {
              tailf:cli-add-mode;
              list scheduler {
                key "scheduler-policy-name";
                leaf scheduler-policy-name {
                  type string;
                }
                container parent {
                  tailf:cli-compact-syntax;
                  leaf weight {
                    type uint32;
                  }
                  leaf cir-weight {
                    type uint32;
                  }
                }
                container rate {
                  tailf:cli-compact-syntax;
                  tailf:cli-sequence-commands {
                    tailf:cli-reset-siblings;
                  }
                  leaf rate {
                    tailf:cli-drop-node-name;
                    type union {
                      type uint32;
                      type enumeration {
                        enum "max";
                      }
                    }
                  }
                  leaf cir {
                    type union {
                      type uint32;
                      type enumeration {
                        enum "sum";
                        enum "max";
                      }
                    }
                  }
                }
              }
            }
            leaf vlan-translation {
              type union {
                type enumeration {
                  enum "copy-outer";
                }
                type uint16;
              }
            }
            container aggregate-policer-rate {
              tailf:cli-compact-syntax;
              leaf rate {
                tailf:cli-drop-node-name;
                type uint32;
              }
              leaf burst {
                type union {
                  type uint32;
                  type enumeration {
                    enum "default";
                  }
                }
              }
            }
            container qtag-manipulation {
              tailf:cli-add-mode;
              leaf preserve {
                type empty;
              }
            }
          }
          leaf lag-link-map-profile {
            type uint8;
          }
          leaf l2pt-termination {
            type empty;
          }
          leaf limit-mac-move {
            type limit-mac-move;
          }
          leaf mac-pinning {
            type empty;
          }
          container managed-vlan-list {
            tailf:cli-add-mode;
            leaf default-sap {
              type empty;
            }
            leaf range {
              type string;
            }
          }
          leaf max-nbr-mac-addr {
            type uint32;
          }
          leaf monitor-oper-group {
            type string;
          }
          container msap-defaults {
            tailf:cli-add-mode;
            leaf group-interface {
              type string;
            }
            leaf policy {
              type string32;
            }
            leaf service {
              type service-id;
            }
          }
          container ipoe-session {
            tailf:cli-add-mode;
            uses ipoe-session-grouping;
          }
          leaf multi-service-site {
            type string;
          }
          leaf pppoe-policy {
            type string32;
          }
          container restrict-protected-src {
            tailf:cli-compact-syntax;
            presence "present";
            leaf restrict-protected-src-value {
              tailf:cli-drop-node-name;
              type enumeration {
                enum "alarm-only";
                enum "discard-frame";
              }
            }
          }
          leaf restrict-unprotected-dst {
            type empty;
          }
          leaf ring-node {
            type empty;
          }
          container egress {
            tailf:cli-add-mode;
            uses sap-egress-grouping;
          }
          container stp {
            tailf:cli-add-mode;
            uses stp-common;
            list mst-instance {
              key "mst-inst-number";
              leaf mst-inst-number {
                type uint16;
              }
              leaf mst-path-cost {
                type uint32;
              }
              leaf mst-priority {
                type uint32;
              }
            }
          }
          container statistics {
            tailf:cli-add-mode;
            container ingress {
              tailf:cli-add-mode;
              leaf counter-mode {
                type string;
              }
            }
          }
          leaf tod-suite {
            type string;
          }
          leaf track-srrp {
            type uint32;
          }
          leaf shutdown {
            type empty;
          }
        }
        list split-horizon-group {
          key "group-name";
          leaf group-name {
            type string;
          }
          leaf residential-group {
            tailf:cli-hide-in-submode;
            type empty;
          }
          leaf auto-learn-mac-protect {
            type empty;
          }
          leaf description {
            type string;
          }
          container restrict-protected-src {
            tailf:cli-compact-syntax;
            presence "present";
            leaf restrict-protected-src-value {
              tailf:cli-drop-node-name;
              type enumeration {
                enum "alarm-only";
                enum "discard-frame";
              }
            }
          }
          leaf restrict-unprotected-dst {
            type empty;
          }
        }
        list bgp {
          key "bgp-id";
          leaf bgp-id {
            type string;
          }

          grouping pw-template-binding-grouping {
            leaf policy-id {
              type uint16;
            }
            leaf split-horizon-group {
              tailf:cli-hide-in-submode;
              type string;
            }
          }
          list pw-template-bind {
            key "policy-id";
            uses pw-template-binding-grouping;
            leaf import-rt {
              tailf:cli-hide-in-submode;
              type string32;
            }
          }
          list pw-template-binding {
            key "policy-id";
            uses pw-template-binding-grouping;
            leaf monitor-oper-group {
              type string;
            }
            container import-rt {
              tailf:cli-hide-in-submode;
              tailf:cli-flatten-container;
              tailf:cli-compact-syntax;
              tailf:cli-sequence-commands {
                tailf:cli-reset-siblings;
              }
              leaf rt1 {
                tailf:cli-drop-node-name;
                type string32;
              }
              leaf rt2 {
                tailf:cli-drop-node-name;
                type string32;
              }
              leaf rt3 {
                tailf:cli-drop-node-name;
                type string32;
              }
              leaf rt4 {
                tailf:cli-drop-node-name;
                type string32;
              }
              leaf rt5 {
                tailf:cli-drop-node-name;
                type string32;
              }
            }
          }
          leaf route-distinguisher {
            type string;
          }
          container route-target {
            tailf:cli-compact-syntax;
            tailf:cli-sequence-commands {
              tailf:cli-reset-all-siblings;
            }
            leaf export {
              type string;
            }
            leaf import {
              type string;
            }
          }
          leaf-list vsi-import {
            tailf:cli-flat-list-syntax;
            type string;
          }
          leaf-list vsi-export {
            tailf:cli-flat-list-syntax;
            type string;
          }
        }
        container bgp-ad {
          tailf:cli-add-mode;
          presence "true";
          leaf vpls-id {
            type service-id;
          }
          container vsi-id {
            tailf:cli-add-mode;
            tailf:cli-delete-when-empty;
            leaf prefix {
              type inet:ipv4-address;
            }
          }
          leaf shutdown {
            type boolean;
          }
        }
        container bgp-evpn {
          tailf:cli-add-mode;
          presence "true";
          leaf unknown-mac-route {
            type empty;
          }
          leaf evi {
            type uint32;
          }
          container mac-duplication {
            tailf:cli-add-mode;
            container detect {
              tailf:cli-compact-syntax;
              leaf num-moves {
                type uint8;
              }
              leaf window {
                type uint8;
              }
            }
            leaf retry {
              type uint8;
            }
          }
          container ip-route-advertisement {
            tailf:cli-compact-syntax;
            presence "true";
            leaf incl-host {
              type empty;
            }
          }
          container mpls {
            tailf:cli-add-mode;
            presence "true";
            leaf bgp {
              tailf:cli-hide-in-submode;
              type uint8;
            }
            leaf entropy-label {
              type empty;
            }
            leaf route-next-hop {
              type union {
                type inet:ipv4-address;
                type inet:ipv6-address;
                type enumeration {
                  enum "system-ipv4";
                  enum "system-ipv6";
                }
              }
            }
            leaf default-route-tag {
              type uint32;
            }
            leaf split-horizon-group {
              type string;
            }
            leaf control-word {
              type empty;
            }
            leaf restrict-protected-src {
              type enumeration {
                enum "discard-frame";
              }
            }
            leaf force-vlan-vc-forwarding {
              type empty;
            }
            container auto-bind-tunnel {
              tailf:cli-add-mode;
              uses resolution-filter-grouping;
              leaf enforce-strict-tunnel-tagging {
                type empty;
              }
            }
            leaf ingress-replication-bum-label {
              type empty;
            }
            leaf ecmp {
              type uint32;
            }
            leaf oper-group {
              type string;
            }
            leaf shutdown {
              type boolean;
            }
          }
          container vxlan {
            tailf:cli-add-mode;
            presence "true";
            leaf shutdown {
              type boolean;
            }
            leaf bgp {
              tailf:cli-hide-in-submode;
              type uint32;
            }
            leaf vxlan-instance {
              tailf:cli-hide-in-submode;
              type uint32;
            }
          }
        }
        container static-mac {
          tailf:cli-add-mode;
          list mac {
            tailf:cli-suppress-mode;
            tailf:cli-compact-syntax;
            tailf:cli-delete-when-empty;
            key "mac";
            leaf mac {
              type ieee-mac;
            }
            leaf create {
              type empty;
            }
            leaf black-hole {
              type empty;
            }
            leaf sap {
              type string;
            }
            leaf monitor {
              type enumeration {
                enum "fwd-status";
              }
            }
          }
        }
        container bgp-vpls {
          tailf:cli-add-mode;
          leaf max-ve-id {
            type uint16;
          }
          container ve-name {
            tailf:cli-add-mode;
            leaf ve-name {
              tailf:cli-drop-node-name;
              tailf:cli-hide-in-submode;
              type string;
            }
            leaf ve-id {
              type uint16;
            }
          }
          leaf shutdown {
            type boolean;
          }
        }
        list vxlan {
          key "vni";
          leaf instance {
            tailf:cli-hide-in-submode;
            type uint32;
          }
          leaf vni {
            type uint32;
          }
          container assisted-replication {
            tailf:cli-compact-syntax;
            tailf:cli-sequence-commands {
              tailf:cli-reset-all-siblings;
            }
            leaf role {
              tailf:cli-drop-node-name;
              type enumeration {
                enum "leaf";
                enum "replicator";
              }
            }
            leaf replicator-activation-time {
              type uint8;
            }
          }
          container network {
            tailf:cli-add-mode;
            container ingress {
              tailf:cli-add-mode;
              container qos {
                tailf:cli-compact-syntax;
                tailf:cli-sequence-commands {
                  tailf:cli-reset-all-siblings;
                }
                leaf network-policy-id {
                  tailf:cli-drop-node-name;
                  type uint16;
                }
                leaf fp-redirect-group {
                  type string;
                }
                leaf instance {
                  type uint16;
                }
              }
            }
          }
          leaf restrict-protected-src {
            type enumeration {
              enum "discard-frame";
            }
          }
          leaf rx-discard-on-ndf {
            type enumeration {
              enum "bm";
              enum "bum";
              enum "none";
            }
          }
        }
        leaf shutdown {
          type boolean;
        }
      }
      list vprn {
        key "service-id";
        uses service-id-grouping;
        leaf customer {
          tailf:cli-hide-in-submode;
          type uint32;
        }
        leaf entropy-label {
          type empty;
        }
        container ntp {
          tailf:cli-add-mode;
          presence "true";
          leaf shutdown {
            type boolean;
          }
        }
        container management {
          tailf:cli-add-mode;
          presence "true";
          leaf allow-ftp {
            type empty;
          }
          leaf allow-grpc {
            type empty;
          }
          leaf allow-netconf {
            type empty;
          }
          leaf allow-ssh {
            type empty;
          }
          leaf allow-telnet {
            type empty;
          }
          leaf allow-telnet6 {
            type empty;
          }
        }
        container aaa {
          tailf:cli-add-mode;
          container remote-servers {
            tailf:cli-add-mode;

            grouping remote-servers-grouping {
              container accounting {
                presence "true";
                leaf record-type {
                  type enumeration {
                    enum "start-stop";
                    enum "stop-only";
                  }
                }
              }
              container authorization {
                presence "true";
                leaf use-priv-lvl {
                  type empty;
                }
              }
              list server {
                tailf:cli-suppress-mode;
                tailf:cli-delete-when-empty;
                tailf:cli-sequence-commands {
                  tailf:cli-reset-all-siblings;
                }
                tailf:cli-compact-syntax;
                unique "address";
                key "server-index";
                leaf server-index {
                  type uint32;
                }
                leaf address {
                  type union {
                    type inet:ipv4-address;
                    type inet:ipv6-address;
                  }
                }
                leaf secret {
                  type string;
                }
                leaf key-type {
                  tailf:cli-drop-node-name;
                  tailf:cli-optional-in-sequence;
                  type enumeration {
                    enum "hash";
                    enum "hash2";
                    enum "custom";
                  }
                }
                leaf port {
                  type uint32;
                }
              }
              container priv-lvl-map {
                tailf:cli-add-mode;
                list priv-lvl {
                  tailf:cli-suppress-mode;
                  key "priv-lvl";
                  leaf priv-lvl {
                    type uint8;
                  }
                  leaf user-profile {
                    tailf:cli-drop-node-name;
                    type string;
                  }
                }
              }
              leaf shutdown {
                type boolean;
              }
            }
            container tacplus {
              tailf:cli-add-mode;
              presence "true";
              uses remote-servers-grouping;
              leaf timeout {
                type uint32;
              }
            }
          }
        }
        leaf name {
          tailf:cli-hide-in-submode;
          type string;
        }
        container maximum-ipv6-routes {
          tailf:cli-compact-syntax;
          leaf number {
            tailf:cli-drop-node-name;
            type uint32;
          }
          leaf threshold {
            type uint32;
          }
          leaf log-only {
            type empty;
          }
        }
        leaf multicast-info-policy {
          type string32;
        }
        leaf ecmp {
          type uint8;
        }
        leaf ignore-nh-metric {
          type empty;
        }
        leaf auto-bind {
          type enumeration {
            enum "ldp";
            enum "gre";
            enum "rsvp-te";
            enum "mpls";
            enum "mpls-gre";
          }
        }
        container auto-bind-tunnel {
          tailf:cli-add-mode;
          uses resolution-filter-grouping;
          leaf ecmp {
            type uint8;
          }
          leaf weighted-ecmp {
            type empty;
          }
        }
        container bgp {
          tailf:cli-add-mode;
          presence "true";
          leaf advertise-inactive {
            type empty;
          }
          leaf enable-peer-tracking {
            type empty;
          }
          leaf-list backup-path {
            tailf:cli-flat-list-syntax;
            type enumeration {
              enum "ipv4";
              enum "ipv6";
              enum "label-ipv4";
              enum "label-ipv6";
            }
          }
          leaf loop-detect {
            type enumeration {
              enum "drop-peer";
              enum "discard-route";
            }
          }
          leaf rapid-withdrawal {
            type empty;
          }
          leaf damping {
            type empty;
          }
          leaf-list family {
            tailf:cli-flat-list-syntax;
            type family-names-type;
          }
          uses authentication-key-grouping;
          uses bgp-common-grouping;
          uses bgp-best-path-selection-grouping;
          uses bgp-local-as-grouping;
          leaf router-id {
            type inet:ipv4-address;
          }
          container error-handling {
            tailf:cli-add-mode;
            leaf update-fault-tolerance {
              type empty;
            }
          }
          uses bgp-import-export-grouping;
          uses bgp-graceful-restart-grouping;
          container monitor {
            tailf:cli-add-mode;
            leaf shutdown {
              type boolean;
            }
            leaf-list station {
              tailf:cli-flat-list-syntax;
              type string;
            }
          }
          container rib-management {
            tailf:cli-add-mode;
            container ipv4 {
              tailf:cli-add-mode;
              leaf-list leak-import {
                tailf:cli-flat-list-syntax;
                ordered-by user;
                type string;
              }
            }
            container ipv6 {
              tailf:cli-add-mode;
              leaf-list leak-import {
                tailf:cli-flat-list-syntax;
                ordered-by user;
                type string;
              }
            }
          }
          list group {
            key "name";
            leaf name {
              type string;
            }
            leaf damping {
              type empty;
            }
            leaf multihop {
              type uint32;
            }
            leaf passive {
              type empty;
            }
            uses enable-origin-validation-grouping;
            leaf enable-peer-tracking {
              type empty;
            }
            leaf loop-detect-threshold {
              type uint32;
            }
            leaf auth-keychain {
              type string;
            }
            container error-handling {
              tailf:cli-add-mode;
              leaf update-fault-tolerance {
                type empty;
              }
            }
            leaf as-override {
              type empty;
            }
            uses bgp-local-as-grouping;
            uses authentication-key-grouping;
            leaf bfd-enable {
              type empty;
            }
            leaf description {
              type string;
            }
            leaf keepalive {
              type uint32;
            }
            leaf hold-time {
              type uint32;
            }
            leaf med-out {
              type union {
                type uint32;
                type string;
              }
            }
            leaf loop-detect {
              type enumeration {
                enum "drop-peer";
                enum "discard-route";
                enum "ignore-loop";
                enum "off";
              }
            }
            leaf-list disable-communities {
              tailf:cli-flat-list-syntax;
              type enumeration {
                enum "standard";
                enum "extended";
                enum "large";
              }
            }
            leaf-list family {
              tailf:cli-flat-list-syntax;
              type enumeration {
                enum "ipv4";
                enum "ipv6";
                enum "mcast-ipv4";
                enum "label-ipv4";
                enum "label-ipv6";
              }
            }
            uses bgp-import-export-grouping;
            uses bgp-graceful-restart-grouping;
            leaf local-address {
              type union {
                type inet:ipv4-address;
                type inet:ipv6-address;
                type string;
              }
            }
            leaf min-route-advertisement {
              type uint8;
            }
            list neighbor {
              key "address";
              leaf address {
                type union {
                  type inet:ipv4-address;
                  type inet:ipv6-address;
                }
              }
              uses enable-origin-validation-grouping;
              leaf local-preference {
                type uint32;
              }
              leaf advertise-inactive {
                type empty;
              }
              leaf as-override {
                type empty;
              }
              leaf bfd-enable {
                type empty;
              }
              leaf description {
                type string;
              }
              leaf-list family {
                tailf:cli-flat-list-syntax;
                type enumeration {
                  enum "ipv4";
                  enum "ipv6";
                }
              }
              uses bgp-graceful-restart-grouping;
              uses bgp-import-export-grouping;
              leaf local-address {
                type union {
                  type inet:ipv4-address;
                  type inet:ipv6-address;
                }
              }
              uses bgp-local-as-grouping;
              leaf loop-detect {
                type enumeration {
                  enum "drop-peer";
                  enum "discard-route";
                  enum "ignore-loop";
                  enum "off";
                }
              }
              leaf med-out {
                type union {
                  type uint32;
                  type enumeration {
                    enum "igp-cost";
                  }
                }
              }
              leaf multihop {
                type uint8;
              }
              leaf peer-as {
                type uint32;
              }
              uses bgp-prefix-limit-grouping;
              leaf passive {
                type empty;
              }
              leaf ttl-security {
                type uint8;
              }
              container remove-private {
                presence "true";
                leaf-list options {
                  tailf:cli-drop-node-name;
                  tailf:cli-flat-list-syntax;
                  type enumeration {
                    enum "limited";
                    enum "skip-peer-as";
                  }
                }
              }
              leaf split-horizon {
                type empty;
              }
              leaf type {
                type enumeration {
                  enum "internal";
                  enum "external";
                }
              }
              uses authentication-key-grouping;
              leaf keepalive {
                type uint32;
              }
              leaf hold-time {
                type uint32;
              }
              leaf shutdown {
                type boolean;
              }
            }
            uses bgp-prefix-limit-grouping;
            leaf split-horizon {
              type empty;
            }
            leaf peer-as {
              type uint32;
            }
            container remove-private {
              presence "true";
              leaf-list options {
                tailf:cli-drop-node-name;
                tailf:cli-flat-list-syntax;
                type enumeration {
                  enum "limited";
                  enum "skip-peer-as";
                  enum "replace";
                }
              }
            }
            leaf type {
              type enumeration {
                enum "internal";
                enum "external";
              }
            }
            leaf next-hop-self {
              type empty;
            }
            leaf preference {
              type uint8;
            }
            leaf local-preference {
              type uint32;
            }
            leaf shutdown {
              type boolean;
            }
          }
          leaf ibgp-multipath {
            type empty;
          }
          leaf med-out {
            type union {
              type uint32;
              type enumeration {
                enum "igp-cost";
              }
            }
          }
          leaf min-route-advertisement {
            type uint8;
          }
          uses bgp-multipath-grouping;
          uses bgp-multi-path-grouping;
          container next-hop-resolution {
            tailf:cli-add-mode;
            leaf policy {
              type string;
            }
          }
          leaf split-horizon {
            type empty;
          }
          leaf shutdown {
            type boolean;
          }
        }
        container bgp-ipvpn {
          tailf:cli-add-mode;
          container mpls {
            tailf:cli-add-mode;
            container auto-bind-tunnel {
              tailf:cli-add-mode;
              leaf resolution {
                type enumeration {
                  enum "disabled";
                  enum "any";
                  enum "filter";
                }
              }
              container resolution-filter {
                tailf:cli-add-mode;
                leaf bgp {
                  type boolean;
                }
                leaf ldp {
                  type empty;
                }
                leaf rsvp {
                  type empty;
                }
                leaf sr-isis {
                  type empty;
                }
                leaf sr-ospf {
                  type empty;
                }
                leaf sr-ospf3 {
                  type empty;
                }
                leaf sr-policy {
                  type empty;
                }
                leaf sr-te {
                  type empty;
                }
              }
              leaf ecmp {
                type uint32;
              }
              leaf weighted-ecmp {
                type empty;
              }
            }
            leaf route-distinguisher {
              type string;
            }
            leaf-list vrf-import {
              tailf:cli-flat-list-syntax;
              ordered-by user;
              type string;
            }
            leaf-list vrf-export {
              tailf:cli-flat-list-syntax;
              ordered-by user;
              type string;
            }
            container vrf-target {
              tailf:cli-compact-syntax;
              leaf ext-community {
                tailf:cli-drop-node-name;
                type string;
              }
              leaf export {
                type string;
              }
              leaf import {
                type string;
              }
            }
            leaf shutdown {
              type boolean;
            }
          }
        }
        container bgp-evpn {
          tailf:cli-add-mode;
          container mpls {
            tailf:cli-add-mode;
            container auto-bind-tunnel {
              tailf:cli-add-mode;
              leaf resolution {
                type enumeration {
                  enum "disabled";
                  enum "any";
                  enum "filter";
                }
              }
              container resolution-filter {
                tailf:cli-add-mode;
                leaf bgp {
                  type empty;
                }
                leaf ldp {
                  type empty;
                }
                leaf rsvp {
                  type empty;
                }
                leaf sr-isis {
                  type empty;
                }
                leaf sr-ospf {
                  type empty;
                }
                leaf sr-ospf3 {
                  type empty;
                }
                leaf sr-policy {
                  type empty;
                }
                leaf sr-te {
                  type empty;
                }
              }
            }
            leaf route-distinguisher {
              type string;
            }
            leaf-list vrf-import {
              tailf:cli-flat-list-syntax;
              ordered-by user;
              type string;
            }
            leaf-list vrf-export {
              tailf:cli-flat-list-syntax;
              ordered-by user;
              type string;
            }
            container vrf-target {
              tailf:cli-compact-syntax;
              leaf ext-community {
                tailf:cli-drop-node-name;
                type string;
              }
              leaf export {
                type string;
              }
              leaf import {
                type string;
              }
            }
            leaf shutdown {
              type boolean;
            }
          }
        }
        container bgp-shared-queue {
          tailf:cli-compact-syntax;
          presence "true";
          leaf cir {
            type rate-type;
          }
          leaf pir {
            type rate-type;
          }
        }
        leaf-list enable-bgp-vpn-backup {
          tailf:cli-flat-list-syntax;
          type enumeration {
            enum "ipv4";
            enum "ipv6";
          }
        }
        leaf export-inactive-bgp {
          type empty;
        }
        container grt-lookup {
          tailf:cli-add-mode;
          container enable-grt {
            tailf:cli-add-mode;
            presence "true";
            leaf allow-local-management {
              type empty;
            }
          }
          leaf-list export-grt {
            tailf:cli-flat-list-syntax;
            ordered-by user;
            type string;
          }
          leaf export-limit {
            type uint16;
          }
          leaf-list import-grt {
            tailf:cli-flat-list-syntax;
            ordered-by user;
            type string;
          }
          leaf export-v6-limit {
            type uint16;
          }
        }
        leaf label-mode {
          type enumeration {
            enum "vrf";
            enum "next-hop";
          }
        }
        container mc-maximum-routes {
          tailf:cli-compact-syntax;
          tailf:cli-sequence-commands {
            tailf:cli-reset-all-siblings;
          }
          leaf number {
            tailf:cli-drop-node-name;
            type uint32;
          }
          leaf log-only {
            tailf:cli-optional-in-sequence;
            type empty;
          }
          leaf threshold {
            type uint8;
          }
        }
        container rip {
          presence "true";
          tailf:cli-add-mode;
          uses authentication-key-grouping;
          leaf export {
            type string;
          }
          list group {
            key "name";
            leaf name {
              type string;
            }
            container timers {
              tailf:cli-compact-syntax;
              tailf:cli-sequence-commands;
              leaf update {
                tailf:cli-drop-node-name;
                type uint32;
              }
              leaf timeout {
                tailf:cli-drop-node-name;
                type uint32;
              }
              leaf flush {
                tailf:cli-drop-node-name;
                type uint32;
              }
            }
            uses authentication-key-grouping;
            list neighbor {
              key "intf-id";
              leaf intf-id {
                type string32;
              }
              uses authentication-key-grouping;
              leaf bfd-enable {
                type empty;
              }
              leaf receive {
                type enumeration {
                  enum "both";
                  enum "none";
                  enum "version-1";
                  enum "version-2";
                }
              }
              leaf split-horizon {
                type enumeration {
                  enum "enable";
                  enum "disable";
                }
              }
              container timers {
                tailf:cli-compact-syntax;
                leaf update {
                  tailf:cli-drop-node-name;
                  type uint16;
                }
                leaf timeout {
                  tailf:cli-drop-node-name;
                  type uint16;
                }
                leaf flush {
                  tailf:cli-drop-node-name;
                  type uint16;
                }
              }
              leaf shutdown {
                type boolean;
              }
            }
            leaf-list export {
              tailf:cli-flat-list-syntax;
              ordered-by user;
              type string;
            }
            leaf shutdown {
              type boolean;
            }
          }
          leaf shutdown {
            type boolean;
          }
        }
        container ospf {
          tailf:cli-add-mode;
          presence "true";
          leaf router-id {
            tailf:cli-hide-in-submode;
            tailf:cli-drop-node-name;
            type inet:ipv4-address;
          }
          leaf super-backbone {
            type empty;
          }
          container vpn-domain {
            tailf:cli-compact-syntax;
            leaf domain-type {
              tailf:cli-drop-node-name;
              type string;
            }
            leaf id {
              tailf:cli-drop-node-name;
              type string;
            }
          }
          leaf vpn-tag {
            type uint32;
          }
          list area {
            key "area-id";
            uses ospf-area-id-grouping;
            list interface {
              key "ip-int-name";
              leaf ip-int-name {
                type string32;
              }
              leaf mtu {
                type uint16;
              }
              leaf metric {
                type uint16;
              }
              container bfd-enable {
                presence "true";
              }
              leaf authentication-type {
                type enumeration {
                  enum "password";
                  enum "message-digest";
                }
              }
              leaf interface-type {
                type enumeration {
                  enum "broadcast";
                  enum "point-to-point";
                }
              }
              leaf hello-interval {
                type uint16;
              }
              leaf dead-interval {
                type uint16;
              }
              list message-digest-key {
                tailf:cli-suppress-mode;
                tailf:cli-compact-syntax;
                tailf:cli-sequence-commands {
                  tailf:cli-reset-all-siblings;
                }
                key "key-id";
                leaf key-id {
                  type uint32;
                }
                leaf md5 {
                  type empty;
                }
                leaf hash-value {
                  tailf:cli-drop-node-name;
                  type string;
                }
                leaf scheme {
                  tailf:cli-drop-node-name;
                  type hash-method;
                }
              }
              leaf shutdown {
                type boolean;
              }
            }
            list sham-link {
              key "ip-int-name ip-address";
              leaf ip-int-name {
                type string32;
              }
              leaf ip-address {
                type inet:ipv4-address;
              }
              leaf metric {
                type uint32;
              }
            }
          }
          leaf-list export {
            tailf:cli-flat-list-syntax;
            ordered-by user;
            type string;
          }
          leaf shutdown {
            type boolean;
          }
        }
        list ospf3 {
          key "ospf-instance";
          leaf ospf-instance {
            type uint32;
          }
          leaf export {
            type string;
          }
          list area {
            key "area-id";
            uses ospf-area-id-grouping;
            list interface {
              key "ip-int-name";
              leaf ip-int-name {
                type string32;
              }
              leaf mtu {
                type uint16;
              }
              leaf metric {
                type uint16;
              }
              container bfd-enable {
                presence "true";
              }
              leaf authentication-type {
                type enumeration {
                  enum "password";
                  enum "message-digest";
                }
              }
              leaf interface-type {
                type enumeration {
                  enum "broadcast";
                  enum "point-to-point";
                }
              }
              leaf hello-interval {
                type uint16;
              }
              leaf dead-interval {
                type uint16;
              }
              list message-digest-key {
                tailf:cli-suppress-mode;
                tailf:cli-compact-syntax;
                tailf:cli-sequence-commands {
                  tailf:cli-reset-all-siblings;
                }
                key "key-id";
                leaf key-id {
                  type uint32;
                }
                leaf md5 {
                  type empty;
                }
                leaf hash-value {
                  tailf:cli-drop-node-name;
                  type string;
                }
                leaf scheme {
                  tailf:cli-drop-node-name;
                  type hash-method;
                }
              }
              leaf shutdown {
                type boolean;
              }
            }
          }
          leaf shutdown {
            type boolean;
          }
        }
        leaf description {
          type string;
        }
        container dhcp {
          tailf:cli-add-mode;
          uses local-dhcp-server-grouping;
        }
        container dhcp6 {
          tailf:cli-add-mode;
          list local-dhcp-server {
            key "server-name";
            leaf server-name {
              type string32;
            }
            leaf description {
              type string;
            }
            container use-link-address {
              presence "true";
              leaf scope {
                type enumeration {
                  enum "subnet";
                  enum "pool";
                }
              }
            }
            list pool {
              key "pool-name";
              leaf pool-name {
                type string32;
              }
              container delegated-prefix-length {
                tailf:cli-compact-syntax;
                tailf:cli-sequence-commands {
                  tailf:cli-reset-all-siblings;
                }
                leaf prefix-length {
                  tailf:cli-drop-node-name;
                  type uint8;
                }
                leaf minimum {
                  tailf:cli-optional-in-sequence;
                  type uint8;
                }
                leaf maximum {
                  type uint8;
                }
              }
              list prefix {
                key "ipv6-prefix";
                leaf ipv6-prefix {
                  type tailf:ipv6-address-and-prefix-length;
                }
                leaf failover {
                  tailf:cli-hide-in-submode;
                  type enumeration {
                    enum "local";
                    enum "remote";
                    enum "access-driven";
                  }
                }
                leaf pd {
                  tailf:cli-hide-in-submode;
                  type empty;
                }
                leaf wan-host {
                  tailf:cli-hide-in-submode;
                  type empty;
                }
                uses dhcp6-lease-timers-grouping;
              }
            }
            leaf shutdown {
              type boolean;
            }
          }
        }
        container igmp {
          tailf:cli-add-mode;

          grouping vprn-igmp-interface-grouping {
            leaf ip-int-name {
              type string32;
            }
            leaf disable-router-alert-check {
              type empty;
            }
            leaf import {
              type string;
            }
            leaf max-groups {
              type uint16;
            }
            leaf max-grp-sources {
              type uint32;
            }
            leaf max-sources {
              type uint16;
            }
            uses mcac-grouping;
            leaf sub-hosts-only {
              type empty;
            }
            leaf subnet-check {
              type empty;
            }
            leaf version {
              type uint8;
            }
            leaf shutdown {
              type boolean;
            }
          }

          grouping vrpn-igmp-grp-range-grouping {
            list grp-range {
              key "start end";
              leaf start {
                type inet:ipv4-address;
              }
              leaf end {
                type inet:ipv4-address;
              }
              list source {
                tailf:cli-suppress-mode;
                key "address";
                leaf address {
                  type inet:ipv4-address;
                }
              }
            }
          }

          grouping vprn-igmp-query-grouping {
            leaf query-response-interval {
              type uint16;
            }
            leaf query-last-member-interval {
              type uint16;
            }
            leaf query-last-listener-interval {
              type uint32;
            }
            leaf query-interval {
              type uint16;
            }
            leaf redundant-multicast {
              type empty;
            }
          }
          list group-interface {
            key "ip-int-name";
            leaf fwd-service {
              tailf:cli-prefix-key;
              type union {
                type uint32;
                type string;
              }
            }
            uses vprn-igmp-interface-grouping;
            leaf query-src-ip {
              type inet:ipv4-address;
            }
          }
          leaf grp-if-query-src-ip {
            type inet:ipv4-address;
          }
          list interface {
            key "ip-int-name";
            uses vprn-igmp-query-grouping;
            uses vprn-igmp-interface-grouping;
            container ssm-translate {
              tailf:cli-add-mode;
              uses vrpn-igmp-grp-range-grouping;
            }
            uses igmp-static-grouping;
          }
          uses vprn-igmp-query-grouping;
          leaf robust-count {
            type uint8;
          }
          container ssm-translate {
            tailf:cli-add-mode;
            uses vrpn-igmp-grp-range-grouping;
          }
          leaf shutdown {
            type boolean;
          }
        }
        list subscriber-interface {
          key "id";
          uses subscriber-interface-grouping {
            augment "group-interface" {
              leaf arp-timeout {
                type uint16;
              }
            }
            augment "group-interface/dhcp" {
              leaf shutdown {
                type boolean;
              }
            }
            augment "group-interface/sap" {
              list static-host {
                key "ip";
                leaf ip {
                  type inet:ipv4-address;
                }
                leaf shutdown {
                  type boolean;
                }
              }
            }
          }
          container dhcp {
            tailf:cli-add-mode;
            uses subscriber-interface-dhcp-common-grouping;
            leaf lease-populate {
              type uint32;
            }
            container relay-proxy {
              tailf:cli-compact-syntax;
              tailf:cli-sequence-commands {
                tailf:cli-reset-siblings;
              }
              presence "true";
              leaf release-update-src-ip {
                tailf:cli-optional-in-sequence;
                type empty;
              }
              leaf siaddr-override {
                type inet:ipv4-address;
              }
            }
            leaf python-policy {
              type string32;
            }
            container option {
              tailf:cli-add-mode;
              container vendor-specific-option {
                tailf:cli-add-mode;
                leaf client-mac-address {
                  type empty;
                }
                leaf sap-id {
                  type empty;
                }
                leaf service-id {
                  type empty;
                }
                leaf string {
                  type string;
                }
                leaf system-id {
                  type empty;
                }
              }
            }
            leaf shutdown {
              type boolean;
            }
          }
          container ipv6 {
            tailf:cli-add-mode;
            presence "true";
            leaf allow-unmatching-prefixes {
              type empty;
            }
            leaf delegated-prefix-length {
              type union {
                type uint8;
                type enumeration {
                  enum "variable";
                }
              }
            }
            leaf link-local-address {
              type inet:ipv6-address;
            }
            container subscriber-prefixes {
              tailf:cli-add-mode;
              list prefix {
                tailf:cli-sequence-commands {
                  tailf:cli-reset-siblings;
                }
                tailf:cli-compact-syntax;
                tailf:cli-suppress-mode;
                key "ipv6-prefix";
                leaf ipv6-prefix {
                  type tailf:ipv6-address-and-prefix-length;
                }
                leaf pd {
                  tailf:cli-optional-in-sequence;
                  type empty;
                }
                leaf wan-host {
                  tailf:cli-optional-in-sequence;
                  type empty;
                }
                leaf track-srrp {
                  tailf:cli-optional-in-sequence;
                  type uint32;
                }
              }
            }
            container dhcp6 {
              tailf:cli-add-mode;
              container relay {
                tailf:cli-add-mode;
                leaf link-address {
                  type inet:ipv6-address;
                }
                leaf-list server {
                  tailf:cli-flat-list-syntax;
                  type inet:ipv6-address;
                }
                leaf source-address {
                  type inet:ipv6-address;
                }
                leaf shutdown {
                  type boolean;
                }
              }
            }
            container router-advertisements {
              tailf:cli-add-mode;
              leaf managed-configuration {
                type empty;
              }
              leaf other-stateful-configuration {
                type empty;
              }
              leaf max-advertisement {
                type uint32;
              }
              container prefix-options {
                tailf:cli-add-mode;
                leaf autonomous {
                  type empty;
                }
                leaf on-link {
                  type boolean;
                }
                leaf preferred-lifetime {
                  type union {
                    type uint32;
                    type enumeration {
                      enum "infinite";
                    }
                  }
                }
                leaf valid-lifetime {
                  type union {
                    type uint32;
                    type enumeration {
                      enum "infinite";
                    }
                  }
                }
              }
              leaf shutdown {
                type boolean;
              }
            }
          }
          leaf shutdown {
            type boolean;
          }
        }
        list interface {
          key "ip-int-name";
          leaf ip-int-name {
            type string32;
          }
          leaf tunnel {
            tailf:cli-hide-in-submode;
            type empty;
          }
          container arp-host-route {
            tailf:cli-add-mode;
            list populate {
              tailf:cli-suppress-mode;
              key "mode";
              leaf mode {
                type enumeration {
                  enum "static";
                  enum "dynamic";
                  enum "evpn";
                }
              }
            }
          }
          leaf arp-timeout {
            type uint16;
          }
          leaf arp-learn-unsolicited {
            type empty;
          }
          leaf arp-proactive-refresh {
            type empty;
          }
          leaf arp-populate {
            type empty;
          }
          leaf arp-populate-host-route {
            type empty;
          }
          leaf local-proxy-arp {
            type empty;
          }
          container bfd {
            tailf:cli-compact-syntax;
            uses bfd-grouping;
          }
          uses cflowd-params-grouping;
          container dhcp {
            tailf:cli-add-mode;
            leaf description {
              type string;
            }
            container gi-address {
              tailf:cli-compact-syntax;
              leaf gi-address-value {
                tailf:cli-drop-node-name;
                type inet:ipv4-address;
              }
              leaf src-ip-addr {
                type empty;
              }
            }
            leaf lease-populate {
              type uint16;
            }
            uses dhcp-option-grouping {
              augment "option" {
                container circuit-id {
                  presence "true";
                  leaf id {
                    tailf:cli-drop-node-name;
                    type enumeration {
                      enum "ascii-tuple";
                      enum "ifindex";
                      enum "sap-id";
                      enum "vlan-ascii-tuple";
                    }
                  }
                }
              }
              augment "option/vendor-specific-option" {
                leaf sap-id {
                  type empty;
                }
              }
            }
            leaf-list server {
              tailf:cli-flat-list-syntax;
              type inet:ipv4-address;
            }
            leaf trusted {
              type empty;
            }
            leaf use-arp {
              type empty;
            }
            leaf shutdown {
              type boolean;
            }
          }
          leaf dynamic-tunnel-redundant-next-hop {
            type inet:ipv4-address;
          }
          uses interface-icmp-grouping;
          leaf local-dhcp-server {
            type string;
          }
          list secondary {
            tailf:cli-suppress-mode;
            key "address";
            leaf address {
              type tailf:ipv4-address-and-prefix-length;
            }
          }
          list address {
            tailf:cli-suppress-mode;
            key "ip-address";
            leaf ip-address {
              type tailf:ipv4-address-and-prefix-length;
            }
          }
          list static-arp {
            tailf:cli-suppress-mode;
            tailf:cli-sequence-commands;
            tailf:cli-compact-syntax;
            key "address";
            leaf address {
              type inet:ipv4-address;
            }
            leaf ieee-address {
              tailf:cli-drop-node-name;
              type ieee-mac;
            }
            leaf unnumbered {
              type empty;
            }
          }
          leaf description {
            type string;
          }
          leaf enable-ingress-stats {
            type empty;
          }
          leaf ip-mtu {
            type uint16;
          }
          leaf loopback {
            type empty;
          }
          leaf mac {
            type ieee-mac;
          }
          list sap {
            key "sap-id";
            leaf sap-id {
              type string;
            }
            leaf accounting-policy {
              type uint8;
            }
            leaf bandwidth {
              type uint32;
            }
            leaf anti-spoof {
              type enumeration {
                enum "ip";
                enum "ip-mac";
                enum "mac";
              }
            }
            leaf collect-stats {
              type empty;
            }
            leaf description {
              type string;
            }
            leaf multi-service-site {
              type string;
            }
            container egress {
              tailf:cli-add-mode;
              uses sap-egress-grouping;
            }
            container eth-cfm {
              tailf:cli-add-mode;
              uses eth-cfm;
            }
            container ingress {
              tailf:cli-add-mode;
              uses sap-ingress-grouping;
            }
            container ipsec-gw {
              tailf:cli-add-mode;
              leaf name {
                tailf:cli-drop-node-name;
                tailf:cli-hide-in-submode;
                type string;
              }
              container cert {
                tailf:cli-add-mode;
                leaf cert-profile {
                  type string32;
                }
                container status-verify {
                  tailf:cli-add-mode;
                  leaf default-result {
                    type enumeration {
                      enum "good";
                      enum "revoked";
                    }
                  }
                }
                leaf trust-anchor-profile {
                  type string32;
                }
              }
              container default-secure-service {
                tailf:cli-compact-syntax;
                tailf:cli-sequence-commands {
                  tailf:cli-reset-all-siblings;
                }
                choice service {
                  leaf service-id {
                    tailf:cli-drop-node-name;
                    tailf:cli-optional-in-sequence;
                    type service-id;
                  }
                  leaf name {
                    type string;
                  }
                }
                leaf interface {
                  type string32;
                }
              }
              leaf default-tunnel-template {
                type uint16;
              }
              leaf ike-policy {
                type uint16;
              }
              leaf local-gateway-address {
                type union {
                  type inet:ipv4-address;
                  type inet:ipv6-address;
                }
              }
              container local-id {
                tailf:cli-compact-syntax;
                tailf:cli-sequence-commands {
                  tailf:cli-reset-all-siblings;
                }
                leaf type {
                  type enumeration {
                    enum "ipv4";
                    enum "fqdn";
                    enum "ipv6";
                  }
                }
                leaf value {
                  type string;
                }
              }
              leaf shutdown {
                type boolean;
              }
            }
            list ipsec-tunnel {
              key "ipsec-tunnel-name";
              leaf ipsec-tunnel-name {
                type string32;
              }
              leaf shutdown {
                type boolean;
              }
            }
            list ip-tunnel {
              key "ip-tunnel-name";
              leaf ip-tunnel-name {
                type string32;
              }
              leaf clear-df-bit {
                type empty;
              }
              leaf ip-mtu {
                type uint16;
              }
              leaf description {
                type string;
              }
              list dest-ip {
                tailf:cli-suppress-mode;
                key "ip-address";
                leaf ip-address {
                  type union {
                    type inet:ipv4-address;
                    type inet:ipv6-address;
                  }
                }
              }
              leaf gre-header {
                type empty;
              }
              leaf source {
                type union {
                  type inet:ipv4-address;
                  type inet:ipv6-address;
                }
              }
              leaf remote-ip {
                type union {
                  type inet:ipv4-address;
                  type inet:ipv6-address;
                }
              }
              leaf delivery-service {
                type string;
              }
              leaf shutdown {
                type boolean;
              }
            }
            leaf lag-link-map-profile {
              type uint8;
            }
            leaf dist-cpu-protection {
              type string;
            }
            leaf shutdown {
              type boolean;
            }
          }
          list spoke-sdp {
            key "sdp-id vc-id";
            leaf sdp-id {
              type uint32;
            }
            uses sdp-common;
            container egress {
              tailf:cli-add-mode;
              container filter {
                uses filter-choice;
              }
            }
            container ingress {
              tailf:cli-add-mode;
              container filter {
                uses filter-choice;
              }
            }
          }
          leaf tos-marking-state {
            type enumeration {
              enum "trusted";
              enum "untrusted";
            }
          }
          container urpf-check {
            tailf:cli-add-mode;
            leaf mode {
              type enumeration {
                enum "strict";
                enum "loose";
                enum "strict-no-encap";
              }
            }
          }
          container vpls {
            tailf:cli-add-mode;
            leaf service-name {
              tailf:cli-drop-node-name;
              tailf:cli-hide-in-submode;
              type string;
            }
            container egress {
              tailf:cli-add-mode;
              leaf reclassify-using-qos {
                type string;
              }
              leaf v4-routed-override-filter {
                type filter-id;
              }
            }
            container ingress {
              tailf:cli-add-mode;
              leaf v4-routed-override-filter {
                type filter-id;
              }
              leaf v6-routed-override-filter {
                type filter-id;
              }
            }
            container evpn-tunnel {
              tailf:cli-compact-syntax;
              presence "true";
              leaf ipv6-gateway-address {
                type enumeration {
                  enum "ip";
                  enum "mac";
                }
              }
            }
            container evpn {
              tailf:cli-add-mode;
              container arp {
                tailf:cli-add-mode;
                leaf learn-dynamic {
                  type boolean;
                }
                list advertise {
                  tailf:cli-suppress-mode;
                  key "adv-type";
                  leaf adv-type {
                    type enumeration {
                      enum "dynamic";
                      enum "static";
                    }
                  }
                }
              }
              container nd {
                tailf:cli-add-mode;
                leaf learn-dynamic {
                  type boolean;
                }
                list advertise {
                  tailf:cli-suppress-mode;
                  key "type";
                  leaf type {
                    type enumeration {
                      enum "static";
                      enum "dynamic";
                    }
                  }
                  leaf route-tag {
                    type uint32;
                  }
                }
              }
            }
          }
          list vrrp {
            key "virtual-router-id";
            leaf virtual-router-id {
              type uint8;
            }
            leaf owner {
              tailf:cli-hide-in-submode;
              type empty;
            }
            leaf passive {
              tailf:cli-hide-in-submode;
              type empty;
            }
            uses authentication-key-grouping;
            list backup {
              tailf:cli-suppress-mode;
              key "addr";
              leaf addr {
                type inet:ipv4-address;
              }
            }
            container bfd-enable {
              tailf:cli-compact-syntax;
              tailf:cli-sequence-commands {
                tailf:cli-reset-siblings;
              }
              leaf service-id {
                tailf:cli-optional-in-sequence;
                tailf:cli-drop-node-name;
                type union {
                  type uint32;
                  type string;
                }
              }
              leaf interface {
                tailf:cli-optional-in-sequence;
                type string;
              }
              leaf dst-ip {
                type inet:ipv4-address;
              }
            }
            leaf init-delay {
              type uint16;
            }
            leaf mac {
              type ieee-mac;
            }
            leaf master-int-inherit {
              type empty;
            }
            container message-interval {
              tailf:cli-compact-syntax;
              tailf:cli-sequence-commands {
                tailf:cli-reset-siblings;
              }
              leaf seconds {
                tailf:cli-drop-node-name;
                tailf:cli-optional-in-sequence;
                type uint8;
              }
              leaf milliseconds {
                type uint16;
              }
            }
            leaf ping-reply {
              type empty;
            }
            leaf policy {
              type uint16;
            }
            leaf preempt {
              type empty;
            }
            leaf priority {
              type uint8;
            }
            leaf ssh-reply {
              type empty;
            }
            leaf standby-forwarding {
              type empty;
            }
            leaf telnet-reply {
              type empty;
            }
            leaf traceroute-reply {
              type empty;
            }
            leaf shutdown {
              type empty;
            }
          }
          container ipv6 {
            tailf:cli-add-mode;
            presence "true";
            leaf local-dhcp-server {
              type string32;
            }
            uses ipv6-grouping;
            uses dhcp6-grouping;
            leaf nd-populate-host-route {
              type empty;
            }
            container nd-host-route {
              tailf:cli-add-mode;
              list populate {
                tailf:cli-suppress-mode;
                key "mode";
                leaf mode {
                  type enumeration {
                    enum "static";
                    enum "dynamic";
                    enum "evpn";
                  }
                }
              }
            }
            leaf stale-time {
              type uint32;
            }
          }
          leaf qos-route-lookup {
            type enumeration {
              enum "destination";
              enum "source";
            }
          }
          leaf shutdown {
            type boolean;
          }
        }
        container ipsec {
          tailf:cli-add-mode;
          leaf allow-reverse-route-override {
            type enumeration {
              enum "same-idi";
              enum "any-idi";
            }
          }
          list security-policy {
            key "security-policy-id";
            leaf security-policy-id {
              type uint32;
            }
            list entry {
              key "entry-id";
              leaf entry-id {
                type uint8;
              }
              leaf local-ip {
                type union {
                  type enumeration {
                    enum "any";
                  }
                  type tailf:ipv4-address-and-prefix-length;
                }
              }
              leaf local-v6-ip {
                type union {
                  type enumeration {
                    enum "any";
                  }
                  type tailf:ipv6-address-and-prefix-length;
                }
              }
              leaf remote-ip {
                type union {
                  type enumeration {
                    enum "any";
                  }
                  type tailf:ipv4-address-and-prefix-length;
                }
              }
              leaf remote-v6-ip {
                type union {
                  type enumeration {
                    enum "any";
                  }
                  type tailf:ipv6-address-and-prefix-length;
                }
              }
            }
          }
        }
        container maximum-routes {
          tailf:cli-compact-syntax;
          leaf routes {
            tailf:cli-drop-node-name;
            type uint32;
          }
          leaf log-only {
            type empty;
          }
          leaf threshold {
            type uint8;
          }
        }
        uses nat-pool-grouping;
        container radius-server {
          tailf:cli-add-mode;
          uses radius-server-grouping;
        }
        container dns {
          tailf:cli-add-mode;
          presence "true";
          leaf default-domain {
            type string;
          }
          leaf ipv4-source-address {
            type inet:ipv4-address;
          }
          leaf ipv6-source-address {
            type inet:ipv6-address;
          }
          leaf primary-dns {
            type union {
              type inet:ipv4-address;
              type inet:ipv6-address;
            }
          }
          leaf secondary-dns {
            type union {
              type inet:ipv4-address;
              type inet:ipv6-address;
            }
          }
          leaf tertiary-dns {
            type union {
              type inet:ipv4-address;
              type inet:ipv6-address;
            }
          }
          leaf shutdown {
            type boolean;
          }
        }
        container log {
          tailf:cli-add-mode;
          list filter {
            key "filter-id";
            leaf filter-id {
              type union {
                type uint32;
                type string;
              }
            }
            leaf name {
              tailf:cli-hide-in-submode;
              type string;
            }
            leaf default-action {
              type enumeration {
                enum "drop";
                enum "forward";
              }
            }
            leaf description {
              type string;
            }
            list entry {
              key "entry-id";
              leaf entry-id {
                type union {
                  type uint32;
                  type string;
                }
              }
              leaf name {
                tailf:cli-hide-in-submode;
                type string;
              }
              leaf action {
                type enumeration {
                  enum "drop";
                  enum "forward";
                }
              }
              leaf description {
                type string;
              }
              container match {
                tailf:cli-add-mode;
                container application {
                  tailf:cli-compact-syntax;
                  leaf operator {
                    tailf:cli-drop-node-name;
                    type enumeration {
                      enum "eq";
                      enum "neq";
                    }
                  }
                  leaf application-id {
                    tailf:cli-drop-node-name;
                    type string;
                  }
                }
                container message {
                  tailf:cli-compact-syntax;
                  leaf operator {
                    tailf:cli-drop-node-name;
                    type enumeration {
                      enum "eq";
                      enum "neq";
                    }
                  }
                  leaf pattern {
                    type string;
                  }
                  leaf regexp {
                    type empty;
                  }
                }
                container number {
                  tailf:cli-compact-syntax;
                  leaf operator {
                    tailf:cli-drop-node-name;
                    type enumeration {
                      enum "eq";
                      enum "neq";
                      enum "lt";
                      enum "lte";
                      enum "gt";
                      enum "gte";
                    }
                  }
                  leaf event-id {
                    tailf:cli-drop-node-name;
                    type uint32;
                  }
                }
                container severity {
                  tailf:cli-compact-syntax;
                  leaf operator {
                    tailf:cli-drop-node-name;
                    type enumeration {
                      enum "eq";
                      enum "neq";
                      enum "lt";
                      enum "lte";
                      enum "gt";
                      enum "gte";
                    }
                  }
                  leaf severity-level {
                    tailf:cli-drop-node-name;
                    type enumeration {
                      enum "cleared";
                      enum "indeterminate";
                      enum "critical";
                      enum "major";
                      enum "minor";
                      enum "warning";
                    }
                  }
                }
                container subject {
                  tailf:cli-compact-syntax;
                  leaf operator {
                    tailf:cli-drop-node-name;
                    type enumeration {
                      enum "eq";
                      enum "neq";
                    }
                  }
                  leaf subject {
                    tailf:cli-drop-node-name;
                    type string;
                  }
                  leaf regexp {
                    type empty;
                  }
                }
              }
            }
          }
          list syslog {
            key "syslog-id";
            leaf syslog-id {
              type union {
                type uint32;
                type string;
              }
            }
            leaf name {
              tailf:cli-hide-in-submode;
              type string;
            }
            leaf description {
              type string;
            }
            leaf address {
              type union {
                type inet:ipv4-address;
                type inet:ipv6-address;
              }
            }
            leaf facility {
              type enumeration {
                enum "kernel";
                enum "user";
                enum "mail";
                enum "systemd";
                enum "auth";
                enum "syslogd";
                enum "printer";
                enum "netnews";
                enum "uucp";
                enum "cron";
                enum "authpriv";
                enum "ftp";
                enum "ntp";
                enum "logaudit";
                enum "logalert";
                enum "cron2";
                enum "local0";
                enum "local1";
                enum "local2";
                enum "local3";
                enum "local4";
                enum "local5";
                enum "local6";
                enum "local7";
              }
            }
            leaf log-prefix {
              type string;
            }
            leaf port {
              type uint32;
            }
          }
          list snmp-trap-group {
            key "group-id";
            leaf group-id {
              type union {
                type uint32;
                type string;
              }
            }
            leaf name {
              tailf:cli-hide-in-submode;
              type string;
            }
            leaf description {
              type string;
            }
            list trap-target {
              tailf:cli-suppress-mode;
              tailf:cli-compact-syntax;
              tailf:cli-sequence-commands;
              key "name";
              leaf name {
                type string;
              }
              leaf address {
                type union {
                  type inet:ipv4-address;
                  type inet:ipv6-address;
                }
              }
              leaf snmp-type {
                tailf:cli-drop-node-name;
                tailf:cli-optional-in-sequence;
                type enumeration {
                  enum "snmpv1";
                  enum "snmpv2c";
                  enum "snmpv3";
                }
              }
              leaf notify-community {
                type string;
              }
              leaf security-level {
                tailf:cli-optional-in-sequence;
                type enumeration {
                  enum "no-auth-no-privacy";
                  enum "auth-no-privacy";
                  enum "privacy";
                }
              }
            }
          }
          list log-id {
            key "log-id";
            leaf log-id {
              type union {
                type uint32;
                type string;
              }
            }
            leaf name {
              tailf:cli-hide-in-submode;
              type string;
            }
            leaf description {
              type string;
            }
            leaf filter {
              type union {
                type uint32;
                type string;
              }
            }
            leaf-list from {
              tailf:cli-flat-list-syntax;
              type enumeration {
                enum "main";
                enum "security";
                enum "change";
                enum "debug-trace";
              }
            }
            leaf netconf-stream {
              type string;
            }
            leaf shutdown {
              type boolean;
            }
            leaf time-format {
              type enumeration {
                enum "local";
                enum "utc";
              }
            }
            container to {
              tailf:cli-compact-syntax;
              leaf destination {
                tailf:cli-drop-node-name;
                type enumeration {
                  enum "netconf";
                  enum "snmp";
                  enum "syslog";
                }
              }
              leaf size {
                tailf:cli-drop-node-name;
                type uint32;
              }
              leaf syslog-id {
                tailf:cli-drop-node-name;
                type union {
                  type uint32;
                  type string;
                }
              }
            }
          }
        }
        list redundant-interface {
          key "ip-int-name";
          leaf ip-int-name {
            type string32;
          }
          leaf description {
            type string;
          }
          container address {
            tailf:cli-sequence-commands {
              tailf:cli-reset-all-siblings;
            }
            tailf:cli-compact-syntax;
            leaf ip-address {
              tailf:cli-drop-node-name;
              type tailf:ipv4-address-and-prefix-length;
            }
            leaf remote-ip {
              type inet:ipv4-address;
            }
          }
          list spoke-sdp {
            key "sdp-id-vc-id";
            leaf sdp-id-vc-id {
              type string;
            }
            leaf description {
              type string;
            }
            leaf shutdown {
              type boolean;
            }
          }
          leaf shutdown {
            type boolean;
          }
        }
        leaf route-distinguisher {
          type string;
        }
        container source-address {
          tailf:cli-add-mode;
          list application {
            tailf:cli-suppress-mode;
            key "app";
            leaf app {
              type union {
                type enumeration {
                  enum "cflowd";
                  enum "ntp";
                  enum "ping";
                  enum "ptp";
                  enum "ssh";
                  enum "telnet";
                  enum "traceroute";
                  enum "icmp-error";
                }
                type string;
              }
            }
            leaf source {
              tailf:cli-drop-node-name;
              type union {
                type inet:ipv4-address;
                type string;
              }
            }
          }
          list application6 {
            tailf:cli-suppress-mode;
            key "app";
            leaf app {
              type union {
                type enumeration {
                  enum "cflowd";
                  enum "ntp";
                  enum "ping";
                  enum "telnet";
                  enum "traceroute";
                  enum "icmp6-error";
                }
                type string;
              }
            }
            leaf source {
              tailf:cli-drop-node-name;
              type inet:ipv6-address;
            }
          }
        }
        container snmp {
          tailf:cli-add-mode;
          leaf access {
            type empty;
          }
          uses snmp-community-grouping;
        }
        list snmp-community {
          tailf:cli-suppress-mode;
          tailf:cli-compact-syntax;
          tailf:cli-sequence-commands {
            tailf:cli-reset-all-siblings;
          }
          key "name type";
          leaf name {
            type string;
          }
          leaf type {
            tailf:cli-drop-node-name;
            tailf:cli-optional-in-sequence;
            type hash-method;
          }
          leaf access-parameters {
            tailf:cli-drop-node-name;
            tailf:cli-optional-in-sequence;
            type enumeration {
              enum "r";
              enum "rw";
            }
          }
          leaf version {
            tailf:cli-optional-in-sequence;
            type enumeration {
              enum "v2c";
              enum "v1";
              enum "both";
            }
          }
        }
        leaf-list vrf-export {
          tailf:cli-flat-list-syntax;
          ordered-by user;
          type string;
        }
        leaf-list vrf-import {
          tailf:cli-flat-list-syntax;
          ordered-by user;
          type string;
        }
        container vrf-target {
          tailf:cli-compact-syntax;
          leaf export {
            type string;
          }
          leaf import {
            type string;
          }
          leaf ext-community {
            tailf:cli-drop-node-name;
            type string;
          }
        }
        leaf autonomous-system {
          type uint32;
        }
        list spoke-sdp {
          key "sdp-id";
          leaf sdp-id {
            type string;
          }
          leaf description {
            type string;
          }
          leaf shutdown {
            type boolean;
          }
        }
        leaf carrier-carrier-vpn {
          type empty;
        }
        leaf type {
          type enumeration {
            enum "hub";
            enum "spoke";
            enum "subscriber-split-horizon";
          }
        }

        grouping service-vprn-static-route-grouping {
          leaf preference {
            tailf:cli-break-sequence-commands;
            type uint8;
          }
          leaf metric {
            type uint16;
          }
          leaf state {
            tailf:cli-drop-node-name;
            type enable-disable;
          }
          leaf tag {
            type uint32;
          }
          leaf bfd-enable {
            type empty;
          }
          leaf cpe-check {
            type inet:ipv4-address;
          }
          leaf drop-count {
            type uint32;
          }
          leaf interval {
            type uint32;
          }
          leaf log {
            type empty;
          }
          leaf prefix-list-name {
            type string;
          }
          leaf prefix-list-to-use {
            tailf:cli-drop-node-name;
            type enumeration {
              enum "all";
              enum "none";
            }
          }
          leaf community {
            type string;
          }
          leaf description {
            type string;
          }
        }
        list static-route-entry {
          key "route";
          leaf route {
            type union {
              type tailf:ipv4-address-and-prefix-length;
              type tailf:ipv6-address-and-prefix-length;
            }
          }
          leaf-list community {
            tailf:cli-flat-list-syntax;
            type string;
          }
          list next-hop {
            key "next-hop";
            leaf next-hop {
              type union {
                type inet:ipv4-address;
                type inet:ipv6-address;
                type string;
              }
            }
            uses static-route-entry-nh-grouping;
            container prefix-list {
              tailf:cli-compact-syntax;
              tailf:cli-sequence-commands {
                tailf:cli-reset-siblings;
              }
              leaf name {
                tailf:cli-drop-node-name;
                type string;
              }
              leaf modifyer {
                tailf:cli-drop-node-name;
                type enumeration {
                  enum "all";
                  enum "none";
                  enum "any";
                }
              }
            }
          }
          container grt {
            tailf:cli-add-mode;
            presence "true";
            leaf description {
              type string;
            }
            leaf metric {
              type uint32;
            }
            leaf preference {
              type uint32;
            }
            leaf shutdown {
              type boolean;
            }
          }
          list ipsec-tunnel {
            key "name";
            leaf name {
              type string;
            }
            leaf shutdown {
              type boolean;
            }
          }
          container black-hole {
            tailf:cli-add-mode;
            presence "true";
            uses static-route-entry-nh-grouping;
            container prefix-list {
              tailf:cli-compact-syntax;
              tailf:cli-sequence-commands {
                tailf:cli-reset-siblings;
              }
              leaf name {
                tailf:cli-drop-node-name;
                type string;
              }
              leaf modifyer {
                tailf:cli-drop-node-name;
                type enumeration {
                  enum "all";
                  enum "none";
                  enum "any";
                }
              }
            }
          }
          list indirect {
            key "ip-address";
            leaf ip-address {
              type inet:ipv4-address;
            }
            uses static-route-entry-nh-grouping;
          }
          leaf tag {
            type uint32;
          }
        }
        container static-route {
          tailf:cli-compact-syntax;
          list static-route-next-hop {
            tailf:cli-drop-node-name;
            tailf:cli-compact-syntax;
            tailf:cli-sequence-commands {
              tailf:cli-reset-siblings;
            }
            tailf:cli-suppress-mode;
            key "route next-hop";
            leaf route {
              type union {
                type tailf:ipv4-address-and-prefix-length;
                type tailf:ipv6-address-and-prefix-length;
              }
            }
            leaf next-hop {
              type union {
                type inet:ipv4-address;
                type inet:ipv6-address;
                type string;
              }
            }
            uses service-vprn-static-route-grouping;
          }
          list static-route-indirect {
            tailf:cli-drop-node-name;
            tailf:cli-compact-syntax;
            tailf:cli-sequence-commands {
              tailf:cli-reset-siblings;
            }
            tailf:cli-suppress-mode;
            key "route indirect";
            leaf route {
              type union {
                type tailf:ipv4-address-and-prefix-length;
                type tailf:ipv6-address-and-prefix-length;
              }
            }
            leaf indirect {
              type inet:ipv4-address;
            }
            uses service-vprn-static-route-grouping;
          }
          list static-route-ipsec-tunnel {
            tailf:cli-drop-node-name;
            tailf:cli-compact-syntax;
            tailf:cli-sequence-commands {
              tailf:cli-reset-siblings;
            }
            tailf:cli-suppress-mode;
            key "route ipsec-tunnel";
            leaf route {
              type union {
                type tailf:ipv4-address-and-prefix-length;
                type tailf:ipv6-address-and-prefix-length;
              }
            }
            leaf ipsec-tunnel {
              type string;
            }
            uses service-vprn-static-route-grouping;
          }
          list static-route-indirect-blackhole {
            tailf:cli-drop-node-name;
            tailf:cli-compact-syntax;
            tailf:cli-sequence-commands {
              tailf:cli-reset-siblings;
            }
            tailf:cli-suppress-mode;
            key "route";
            leaf route {
              type union {
                type tailf:ipv4-address-and-prefix-length;
                type tailf:ipv6-address-and-prefix-length;
              }
            }
            leaf black-hole {
              type empty;
            }
            uses service-vprn-static-route-grouping;
          }
        }
        uses router-aggregate-grouping;
        container sgt-qos {
          tailf:cli-add-mode;
          list application {
            tailf:cli-suppress-mode;
            key "app-name";
            leaf app-name {
              type enumeration {
                enum "bmp";
                enum "bgp";
                enum "pim";
                enum "ospf";
                enum "rip";
                enum "call-trace";
                enum "dhcp";
                enum "diameter";
                enum "dns";
                enum "ftp";
                enum "grpc";
                enum "gtp";
                enum "http";
                enum "ibcp";
                enum "icmp";
                enum "igmp";
                enum "l2tp";
                enum "ldp";
                enum "mld";
                enum "msdp";
                enum "sdp";
                enum "mtrace2";
                enum "ndis";
                enum "ntp";
                enum "pcep";
                enum "pfcp";
                enum "ptp";
                enum "radius";
                enum "rsvp";
                enum "snmp";
                enum "snmp-notification";
                enum "srrp";
                enum "ssh";
                enum "syslog";
                enum "tacplus";
                enum "telnet";
                enum "tftp";
                enum "traceroute";
                enum "vrrp";
                enum "arp";
                enum "isis";
                enum "pppoe";
              }
            }
            leaf dscp {
              type string;
            }
            leaf dot1p {
              type uint32;
            }
          }
          list dscp {
            tailf:cli-suppress-mode;
            key "dscp-name";
            leaf dscp-name {
              type enumeration {
                enum "be";
                enum "ef";
                enum "cp1";
                enum "cp2";
                enum "cp3";
                enum "cp4";
                enum "cp5";
                enum "cp6";
                enum "cp7";
                enum "cp9";
                enum "cs1";
                enum "cs2";
                enum "cs3";
                enum "cs4";
                enum "cs5";
                enum "nc1";
                enum "nc2";
                enum "af11";
                enum "af12";
                enum "af13";
                enum "af21";
                enum "af22";
                enum "af23";
                enum "af31";
                enum "af32";
                enum "af33";
                enum "af41";
                enum "af42";
                enum "af43";
                enum "cp11";
                enum "cp13";
                enum "cp15";
                enum "cp17";
                enum "cp19";
                enum "cp21";
                enum "cp23";
                enum "cp25";
                enum "cp27";
                enum "cp29";
                enum "cp31";
                enum "cp33";
                enum "cp35";
                enum "cp37";
                enum "cp39";
                enum "cp41";
                enum "cp42";
                enum "cp43";
                enum "cp44";
                enum "cp45";
                enum "cp47";
                enum "cp49";
                enum "cp50";
                enum "cp51";
                enum "cp52";
                enum "cp53";
                enum "cp54";
                enum "cp55";
                enum "cp57";
                enum "cp58";
                enum "cp59";
                enum "cp60";
                enum "cp61";
                enum "cp62";
                enum "cp63";
              }
            }
            leaf fc {
              type enumeration {
                enum "be";
                enum "l2";
                enum "af";
                enum "l1";
                enum "h2";
                enum "ef";
                enum "h1";
                enum "nc";
              }
            }
          }
        }
        container pim {
          tailf:cli-add-mode;
          uses pim-common-grouping;
          leaf ipv4-multicast-disable {
            type boolean;
          }
          leaf ipv6-multicast-disable {
            type boolean;
          }
          list interface {
            key "name";
            leaf name {
              type string;
            }
            leaf priority {
              type uint32;
            }
            leaf max-groups {
              type uint32;
            }
            leaf bfd-enable {
              type empty;
            }
            container sticky-dr {
              presence "true";
              leaf priority {
                type uint32;
              }
            }
            leaf multicast-senders {
              type enumeration {
                enum "auto";
                enum "always";
                enum "never";
              }
            }
            leaf hello-interval {
              type uint32;
            }
            leaf shutdown {
              type boolean;
            }
          }
          container rp {
            tailf:cli-add-mode;
            list anycast {
              key "rp-ip-address";
              leaf rp-ip-address {
                type inet:ipv4-address;
              }
              list rp-set-peer {
                tailf:cli-suppress-mode;
                key "ip-address";
                leaf ip-address {
                  type inet:ipv4-address;
                }
              }
            }
            leaf auto-rp-discovery {
              type empty;
            }
            container static {
              tailf:cli-add-mode;
              list address {
                key "address";
                leaf address {
                  type union {
                    type inet:ipv4-address;
                    type inet:ipv6-address;
                  }
                }
                list group-prefix {
                  tailf:cli-suppress-mode;
                  key "address";
                  leaf address {
                    type tailf:ipv4-address-and-prefix-length;
                  }
                }
                leaf override {
                  type empty;
                }
              }
            }
            container bsr-candidate {
              tailf:cli-add-mode;
              leaf shutdown {
                type boolean;
              }
            }
            container rp-candidate {
              tailf:cli-add-mode;
              leaf shutdown {
                type boolean;
              }
            }
          }
          leaf shutdown {
            type boolean;
          }
        }
        container mvpn {
          tailf:cli-add-mode;
          container auto-discovery {
            tailf:cli-compact-syntax;
            tailf:cli-sequence-commands {
              tailf:cli-reset-siblings;
            }
            leaf mode {
              tailf:cli-drop-node-name;
              tailf:cli-diff-create-before "../../provider-tunnel/inclusive/pim/options/multicast-type" {
                tailf:xpath-root 3;
                tailf:cli-when-target-create;
              }
              tailf:cli-diff-create-before "../../provider-tunnel/selective/pim/pim-ssm" {
                tailf:xpath-root 3;
                tailf:cli-when-target-create;
              }
              tailf:cli-diff-create-before "../../provider-tunnel/inclusive/rsvp" {
                tailf:xpath-root 3;
                tailf:cli-when-target-create;
              }
              type enumeration {
                enum "default";
                enum "mdt-safi";
              }
            }
            leaf source-address {
              type inet:ipv4-address;
            }
          }
          leaf c-mcast-signaling {
            type enumeration {
              enum "bgp";
              enum "pim";
            }
          }
          container intersite-shared {
            choice intersite-shared {
              leaf-list arg {
                tailf:cli-drop-node-name;
                tailf:cli-flat-list-syntax;
                type enumeration {
                  enum "persistent-type5-adv";
                  enum "kat-type5-adv-withdraw";
                }
              }
              leaf disable {
                type empty;
              }
            }
          }
          leaf umh-selection {
            type enumeration {
              enum "highest-ip";
              enum "hash-based";
              enum "tunnel-status";
              enum "unicast-rt-pref";
            }
          }
          leaf mdt-type {
            type enumeration {
              enum "sender-only";
              enum "receiver-only";
              enum "sender-receiver";
            }
          }
          container provider-tunnel {
            tailf:cli-add-mode;

            grouping inclusive-selective-common-grouping {
              container mldp {
                tailf:cli-add-mode;
                leaf shutdown {
                  type boolean;
                }
              }
            }
            container inclusive {
              tailf:cli-add-mode;
              uses inclusive-selective-common-grouping;
              container pim {
                tailf:cli-add-mode;
                presence "true";
                container options {
                  tailf:cli-hide-in-submode;
                  tailf:cli-flatten-container;
                  tailf:cli-drop-node-name;
                  tailf:cli-compact-syntax;
                  tailf:cli-sequence-commands {
                    tailf:cli-reset-siblings;
                  }
                  leaf multicast-type {
                    tailf:cli-drop-node-name;
                    tailf:cli-optional-in-sequence;
                    type enumeration {
                      enum "asm";
                      enum "ssm";
                    }
                  }
                  leaf grp-ip-address {
                    tailf:cli-drop-node-name;
                    type inet:ipv4-address;
                  }
                }
                leaf shutdown {
                  type boolean;
                }
              }
              container rsvp {
                tailf:cli-add-mode;
                presence "true";
                leaf lsp-template {
                  type string;
                }
                leaf shutdown {
                  type boolean;
                }
              }
            }
            container selective {
              tailf:cli-add-mode;
              uses inclusive-selective-common-grouping;
              leaf maximum-p2mp-spmsi {
                type uint16;
              }
              container pim {
                tailf:cli-compact-syntax;
                tailf:cli-drop-node-name;
                tailf:cli-sequence-commands {
                  tailf:cli-reset-siblings;
                }
                choice pim-choice {
                  leaf pim-asm {
                    type empty;
                  }
                  leaf pim-ssm {
                    type empty;
                  }
                }
                choice addr {
                  leaf address1 {
                    tailf:cli-drop-node-name;
                    type tailf:ipv4-address-and-prefix-length;
                  }
                  leaf address2 {
                    tailf:cli-drop-node-name;
                    type inet:ipv4-address;
                  }
                }
                leaf netmask {
                  tailf:cli-drop-node-name;
                  type inet:ipv4-address;
                }
              }
              list data-threshold {
                tailf:cli-suppress-mode;
                tailf:cli-compact-syntax;
                tailf:cli-sequence-commands {
                  tailf:cli-reset-all-siblings;
                }
                key "c-grp-ip-addr-mask";
                leaf c-grp-ip-addr-mask {
                  tailf:cli-drop-node-name;
                  type tailf:ipv4-address-and-prefix-length;
                }
                leaf s-pmsi-threshold {
                  tailf:cli-drop-node-name;
                  type uint32;
                }
              }
            }
          }
          list vrf-target {
            key "id";
            leaf id {
              type string;
            }
            leaf export {
              type string;
            }
            leaf import {
              type string;
            }
          }
        }
        container router-advertisement {
          tailf:cli-add-mode;
          list interface {
            key "ip-int-name";
            leaf ip-int-name {
              type string32;
            }
            leaf use-virtual-mac {
              type empty;
            }
            leaf shutdown {
              type boolean;
            }
          }
        }
        leaf router-id {
          type inet:ipv4-address;
        }
        list isis {
          key "id";
          leaf id {
            type uint32;
          }
          leaf area-id {
            type string;
          }
          leaf ipv6-routing {
            type enumeration {
              enum "native";
              enum "mt";
            }
          }
          container multi-topology {
            tailf:cli-add-mode;
            leaf ipv6-unicast {
              type empty;
            }
          }
          list interface {
            key "name";
            leaf name {
              type string;
            }
            leaf passive {
              type empty;
            }
            leaf interface-type {
              type enumeration {
                enum "point-to-point";
              }
            }
            leaf shutdown {
              type boolean;
            }
          }
          leaf router-id {
            type inet:ipv4-address;
          }
          leaf shutdown {
            type boolean;
          }
        }
        leaf service-name {
          type string;
        }
        leaf weighted-ecmp {
          type empty;
        }
        leaf shutdown {
          type boolean;
        }
      }
      list pw-template {
        key "policy-id";
        leaf policy-id {
          type uint16;
        }
        leaf use-provisioned-sdp {
          tailf:cli-hide-in-submode;
          type empty;
        }
        leaf name {
          tailf:cli-hide-in-submode;
          type string;
        }
        leaf auto-learn-mac-protect {
          type empty;
        }
        leaf disable-learning {
          type empty;
        }
        container egress {
          tailf:cli-add-mode;
          choice filter-name-choice {
            container filter {
              uses filter-choice;
            }
            container filter-name {
              tailf:cli-add-mode;
              uses filter-choice;
            }
          }
        }
        container ingress {
          tailf:cli-add-mode;
          choice filter-name-choice {
            container filter {
              uses filter-choice;
            }
            container filter-name {
              tailf:cli-add-mode;
              uses filter-choice;
            }
          }
        }
        container restrict-protected-src {
          presence "true";
          leaf value {
            tailf:cli-drop-node-name;
            type enumeration {
              enum "alarm-only";
              enum "discard-frame";
            }
          }
        }
        leaf mac-pinning {
          type empty;
        }
        leaf force-vlan-vc-forwarding {
          type empty;
        }
        container split-horizon-group {
          tailf:cli-add-mode;
          tailf:cli-delete-when-empty;
          presence "true";
          leaf group-name {
            tailf:cli-drop-node-name;
            tailf:cli-hide-in-submode;
            type string;
          }
          leaf auto-learn-mac-protect {
            type empty;
          }
          leaf description {
            type string;
          }
          container restrict-protected-src {
            presence "true";
            leaf option {
              tailf:cli-drop-node-name;
              type enumeration {
                enum "alarm-only";
                enum "discard-frame";
              }
            }
          }
          leaf restrict-unprotected-dst {
            type empty;
          }
        }
        leaf vc-type {
          type enumeration {
            enum "ether";
            enum "vlan";
          }
        }
        leaf limit-mac-move {
          type enumeration {
            enum "non-blockable";
          }
        }
      }
      container system {
        tailf:cli-add-mode;
        container bgp-evpn {
          tailf:cli-add-mode;
          container evpn-etree-leaf-label {
            presence "true";
            leaf label {
              tailf:cli-drop-node-name;
              type uint32;
            }
          }
          container ip-prefix-routes {
            tailf:cli-add-mode;
            leaf iff-attribute-uniform-propagation {
              type empty;
            }
            leaf iff-bgp-path-selection {
              type empty;
            }
          }
          leaf ingress-replication-bum-label-block {
            type string;
          }
          leaf route-distinguisher {
            type string;
          }
          list ethernet-segment {
            key "name";
            leaf name {
              type string32;
            }
            leaf ac-df-capability {
              type enumeration {
                enum "include";
                enum "exclude";
              }
            }
            container dot1q {
              tailf:cli-add-mode;
              list q-tag-range {
                tailf:cli-suppress-mode;
                key "start";
                leaf start {
                  type uint32;
                }
                leaf to {
                  tailf:cli-optional-in-sequence;
                  type uint32;
                }
              }
            }
            leaf oper-group {
              type string;
            }
            leaf virtual {
              tailf:cli-hide-in-submode;
              type empty;
            }
            leaf esi {
              type string;
            }
            leaf es-orig-ip {
              type inet:ipv4-address;
            }
            leaf route-next-hop {
              type inet:ipv4-address;
            }
            leaf es-activation-timer {
              type uint8;
            }
            leaf sdp {
              type uint32;
            }
            container service-carving {
              tailf:cli-add-mode;
              leaf mode {
                type enumeration {
                  enum "auto";
                  enum "manual";
                  enum "off";
                }
              }
              container manual {
                tailf:cli-add-mode;
                container preference {
                  tailf:cli-add-mode;
                  presence "true";
                  leaf non-revertive {
                    tailf:cli-hide-in-submode;
                    type empty;
                  }
                  leaf value {
                    type uint32;
                  }
                }
              }
            }
            container multi-homing {
              tailf:cli-compact-syntax;
              tailf:cli-sequence-commands {
                tailf:cli-reset-all-siblings;
              }
              leaf value {
                tailf:cli-drop-node-name;
                type enumeration {
                  enum "single-active";
                  enum "all-active";
                }
              }
              leaf no-esi-label {
                type empty;
              }
            }
            leaf lag {
              type uint32;
            }
            container qinq {
              tailf:cli-add-mode;
              container s-tag {
                tailf:cli-sequence-commands;
                tailf:cli-compact-syntax;
                leaf s-tag {
                  tailf:cli-drop-node-name;
                  type string;
                }
                leaf c-tag-range {
                  type string;
                }
                leaf to {
                  type string;
                }
              }
              list s-tag-range {
                tailf:cli-suppress-mode;
                key "start";
                leaf start {
                  type union {
                    type uint32;
                    type string;
                  }
                }
                leaf to {
                  type union {
                    type uint32;
                    type string;
                  }
                }
              }
            }
            leaf port {
              type string;
            }
            list vc-id-range {
              tailf:cli-suppress-mode;
              key "start";
              leaf start {
                type uint32;
              }
              leaf to {
                tailf:cli-optional-in-sequence;
                type uint32;
              }
            }
            leaf shutdown {
              type boolean;
            }
          }
        }
      }
      container template {
        tailf:cli-add-mode;
        list vpls-sap-template {
          key "name";
          leaf name {
            type string32;
          }
          container ingress {
            tailf:cli-add-mode;
            container qos {
              tailf:cli-compact-syntax;
              tailf:cli-sequence-commands {
                tailf:cli-reset-all-siblings;
              }
              leaf policy-id {
                tailf:cli-drop-node-name;
                type uint16;
              }
              leaf shared-queuing {
                type empty;
              }
            }
          }
        }
      }
    }
    list router {
      tailf:ncs-device-type "cli-ned";
      tailf:display-when "not(../ncs:module) or ../ncs:module[ncs:name='netsim-ned-alu-sr']";
      key "router-name";
      leaf router-name {
        type router-type;
      }
      container flowspec {
        tailf:cli-add-mode;
        leaf ip-filter-max-size {
          type uint32;
        }
        leaf ipv6-filter-max-size {
          type uint32;
        }
      }
      container bfd {
        tailf:cli-add-mode;
        list bfd-template {
          key "template";
          leaf template {
            type string;
          }
          leaf echo-receive {
            type uint32;
          }
          leaf multiplier {
            type uint32;
          }
          leaf receive-interval {
            type uint32;
          }
          leaf transmit-interval {
            type uint32;
          }
          leaf type {
            type enumeration {
              enum "cpm-np";
            }
          }
        }
        container seamless-bfd {
          tailf:cli-add-mode;
          list peer {
            key "address";
            leaf address {
              type union {
                type inet:ipv4-address;
                type inet:ipv6-address;
                type string;
              }
            }
            leaf discriminator {
              type uint32;
            }
          }
        }
      }
      leaf class-forwarding {
        type empty;
      }
      leaf ecmp {
        type uint32;
      }
      leaf-list leak-export {
        tailf:cli-flat-list-syntax;
        ordered-by user;
        type string;
      }
      leaf leak-export-limit {
        type uint32;
      }
      leaf single-sfm-overload {
        type empty;
      }
      container segment-routing {
        tailf:cli-add-mode;
        container sr-policies {
          tailf:cli-add-mode;
          list static-policy {
            key "policy-id";
            leaf policy-id {
              type string;
            }
            leaf binding-sid {
              type uint32;
            }
            leaf color {
              type uint32;
            }
            leaf distinguisher {
              type uint32;
            }
            leaf endpoint {
              type inet:ipv4-address;
            }
            leaf head-end {
              type inet:ipv4-address;
            }
            list segment-list {
              key "id";
              leaf id {
                type uint32;
              }
              leaf weight {
                type uint32;
              }
              list segment {
                key "id";
                leaf id {
                  type uint32;
                }
                leaf mpls-label {
                  type uint32;
                }
              }
              leaf shutdown {
                type boolean;
              }
            }
            leaf shutdown {
              type boolean;
            }
          }
          leaf shutdown {
            type boolean;
          }
        }
      }
      container admin-tags {
        tailf:cli-add-mode;
        list admin-tag {
          tailf:cli-suppress-mode;
          key "tag";
          leaf tag {
            type string32;
          }
        }
        list route-admin-tag-policy {
          key "policy-name";
          leaf policy-name {
            type string;
          }
          list exclude {
            tailf:cli-suppress-mode;
            key "tag";
            leaf tag {
              type string32;
            }
          }
          list include {
            tailf:cli-suppress-mode;
            key "tag";
            leaf tag {
              type string32;
            }
          }
        }
      }
      leaf autonomous-system {
        type uint32;
      }
      leaf entropy-label {
        type empty;
      }
      leaf icmp-tunneling {
        type empty;
      }
      list interface {
        key "interface-name";
        leaf interface-name {
          type string;
        }
        leaf address {
          type tailf:ipv4-address-and-prefix-length;
        }
        leaf description {
          type string;
        }
        leaf collect-stats {
          type empty;
        }
        container dhcp {
          tailf:cli-add-mode;
          leaf description {
            type string;
          }
          container gi-address {
            tailf:cli-compact-syntax;
            tailf:cli-sequence-commands {
              tailf:cli-reset-all-siblings;
            }
            leaf gi-address-value {
              tailf:cli-drop-node-name;
              type inet:ipv4-address;
            }
            leaf src-ip-addr {
              type empty;
            }
          }
          uses dhcp-option-grouping {
            augment "option" {
              leaf circuit-id {
                type enumeration {
                  enum "ascii-tuple";
                  enum "ifindex";
                  enum "vlan-ascii-tuple";
                  enum "if-name";
                  enum "port-id";
                  enum "none";
                }
              }
            }
            augment "option/vendor-specific-option" {
              leaf port-id {
                type empty;
              }
              leaf system-id {
                type empty;
              }
            }
          }
          leaf python-policy {
            type string32;
          }
          leaf relay-plain-bootp {
            type empty;
          }
          leaf-list server {
            tailf:cli-flat-list-syntax;
            type inet:ipv4-address;
          }
          leaf trusted {
            type empty;
          }
          leaf shutdown {
            type boolean;
          }
        }
        leaf dist-cpu-protection {
          type string;
        }
        container ldp-sync-timer {
          tailf:cli-compact-syntax;
          leaf ldp-sync-timer {
            tailf:cli-drop-node-name;
            type uint32;
          }
          leaf end-of-lib {
            type empty;
          }
        }
        container load-balancing {
          tailf:cli-add-mode;
          leaf lsr-load-balancing {
            type enumeration {
              enum "lbl-only";
              enum "lbl-ip";
              enum "ip-only";
              enum "eth-encap-ip";
              enum "lbl-ip-l4-teid";
            }
          }
        }
        leaf local-dhcp-server {
          type string;
        }
        leaf cpu-protection {
          type uint16;
        }
        leaf loopback {
          type empty;
        }
        leaf enable-ingress-stats {
          type empty;
        }
        leaf unnumbered-mpls-tp {
          tailf:cli-hide-in-submode;
          type empty;
        }
        leaf port {
          type string;
        }
        container egress {
          tailf:cli-add-mode;
          container filter {
            leaf ip {
              type filter-id;
            }
            leaf ipv6 {
              type filter-id;
            }
          }
          leaf queue-policy {
            type string;
          }
          container agg-rate-limit {
            tailf:cli-compact-syntax;
            tailf:cli-sequence-commands {
              tailf:cli-reset-all-siblings;
            }
            leaf agg-rate {
              tailf:cli-drop-node-name;
              type uint32;
            }
            leaf cir {
              type uint32;
            }
          }
          leaf vlan-qos-policy {
            type string;
          }
          container agg-rate {
            tailf:cli-add-mode;
            container rate {
              tailf:cli-compact-syntax;
              leaf val {
                tailf:cli-drop-node-name;
                type union {
                  type uint32;
                  type enumeration {
                    enum "max";
                  }
                }
              }
              leaf cir {
                type union {
                  type uint32;
                  type enumeration {
                    enum "max";
                  }
                }
              }
            }
          }
          leaf egress-remark-policy {
            type string;
          }
        }
        container if-attribute {
          tailf:cli-add-mode;
          list admin-group {
            tailf:cli-suppress-mode;
            key "group-name";
            leaf group-name {
              type string;
            }
          }
          container delay {
            tailf:cli-add-mode;
            leaf static {
              type uint32;
            }
            leaf delay-selection {
              type enumeration {
                enum "static";
                enum "dynamic";
                enum "static-preferred";
                enum "dynamic-preferred";
              }
            }
            container dynamic {
              tailf:cli-add-mode;
              leaf measurement-template {
                type string;
              }
              container twamp-light {
                tailf:cli-add-mode;
                container ipv4 {
                  tailf:cli-add-mode;
                  leaf source {
                    type inet:ipv4-address;
                  }
                  leaf destination {
                    type inet:ipv4-address;
                  }
                  leaf shutdown {
                    type boolean;
                  }
                }
                container ipv6 {
                  tailf:cli-add-mode;
                  leaf source {
                    type inet:ipv6-address;
                  }
                  leaf destination {
                    type inet:ipv6-address;
                  }
                  leaf shutdown {
                    type boolean;
                  }
                }
              }
            }
          }
        }
        container ingress {
          tailf:cli-add-mode;
          container filter {
            leaf ip {
              type filter-id;
            }
            leaf ipv6 {
              type filter-id;
            }
          }
          leaf qos {
            type string;
          }
        }
        leaf lsr-load-balancing {
          type enumeration {
            enum "lbl-only";
            enum "lbl-ip";
            enum "ip-only";
            enum "eth-encap-ip";
          }
        }
        uses interface-icmp-grouping;
        leaf ptp-hw-assist {
          type empty;
        }
        container urpf-check {
          tailf:cli-add-mode;
          leaf mode {
            type enumeration {
              enum "strict";
              enum "loose";
              enum "strict-no-ecmp";
            }
          }
        }
        container ipv6 {
          tailf:cli-add-mode;
          leaf local-dhcp-server {
            type string32;
          }
          uses ipv6-grouping;
        }
        container bfd {
          tailf:cli-compact-syntax;
          uses bfd-grouping;
        }
        leaf autonomous-system {
          type uint16;
        }
        uses cflowd-params-grouping;
        container cflowd {
          tailf:cli-compact-syntax;
          tailf:cli-sequence-commands {
            tailf:cli-reset-all-siblings;
          }
          leaf id {
            tailf:cli-drop-node-name;
            type enumeration {
              enum "acl";
              enum "interface";
            }
          }
          leaf direction {
            tailf:cli-drop-node-name;
            type enumeration {
              enum "ingress-only";
              enum "egress-only";
              enum "both";
            }
          }
        }
        container static-arp {
          tailf:cli-compact-syntax;
          tailf:cli-sequence-commands {
            tailf:cli-reset-siblings;
          }
          leaf ip-address {
            tailf:cli-drop-node-name;
            type inet:ipv4-address;
          }
          leaf ieee-address {
            tailf:cli-drop-node-name;
            type ieee-mac;
          }
        }
        leaf tos-marking-state {
          type enumeration {
            enum "trusted";
            enum "untrusted";
          }
        }
        container qos {
          tailf:cli-compact-syntax;
          tailf:cli-sequence-commands {
            tailf:cli-reset-siblings;
          }
          leaf network-policy-id {
            tailf:cli-drop-node-name;
            type uint16;
          }
          leaf egress-port-redirect-group {
            tailf:cli-optional-in-sequence;
            type string;
          }
          leaf egress-instance {
            tailf:cli-optional-in-sequence;
            type uint16;
          }
          leaf ingress-fp-redirect-group {
            tailf:cli-optional-in-sequence;
            type string;
          }
          leaf ingress-instance {
            tailf:cli-optional-in-sequence;
            type uint16;
          }
        }
        leaf tcp-mss {
          type uint32;
        }
        leaf shutdown {
          type boolean;
        }
      }
      container tunnel-interface {
        list rsvp-p2mp {
          key "lsp-name";
          leaf lsp-name {
            type string;
          }
        }
      }
      container bgp {
        tailf:cli-add-mode;
        presence "present";
        uses router-bgp-add-paths-grouping;
        leaf initial-send-delay-zero {
          type empty;
        }
        container monitor {
          tailf:cli-add-mode;
          presence "true";
          leaf-list route-monitoring {
            tailf:cli-flat-list-syntax;
            type enumeration {
              enum "pre-policy";
              enum "post-policy";
            }
          }
          leaf-list station {
            tailf:cli-flat-list-syntax;
            type string;
          }
          leaf shutdown {
            type boolean;
          }
        }
        leaf override-tunnel-elc {
          type empty;
        }
        leaf loop-detect-threshold {
          type uint32;
        }
        leaf-list advertise-external {
          tailf:cli-flat-list-syntax;
          type enumeration {
            enum "ipv4";
            enum "ipv6";
            enum "label-ipv4";
            enum "label-ipv6";
          }
        }
        leaf advertise-inactive {
          type empty;
        }
        leaf aggregator-id-zero {
          type empty;
        }
        leaf auth-keychain {
          type string;
        }
        uses prompted-authentication-key-grouping;
        leaf-list backup-path {
          tailf:cli-flat-list-syntax;
          type enumeration {
            enum "ipv4";
            enum "ipv6";
            enum "label-ipv4";
            enum "label-ipv6";
          }
        }
        uses bgp-best-path-selection-grouping;
        leaf bfd-enable {
          type empty;
        }
        container bgp-tunnel-metric {
          tailf:cli-compact-syntax;
          leaf metric {
            tailf:cli-drop-node-name;
            type uint32;
          }
          leaf prefer-aigp {
            type empty;
          }
        }
        leaf cluster {
          type inet:ipv4-address;
        }
        leaf connect-retry {
          type uint16;
        }
        leaf damping {
          type empty;
        }
        leaf description {
          type string;
        }
        leaf disable-4byte-asn {
          type empty;
        }
        leaf disable-client-reflect {
          type empty;
        }
        leaf-list disable-communities {
          tailf:cli-flat-list-syntax;
          type enumeration {
            enum "standard";
            enum "extended";
          }
        }
        leaf disable-fast-external-failover {
          type empty;
        }
        leaf disable-route-table-install {
          type empty;
        }
        leaf enable-inter-as-vpn {
          type empty;
        }
        leaf enable-peer-tracking {
          type empty;
        }
        leaf enable-rr-vpn-forwarding {
          type empty;
        }
        container error-handling {
          tailf:cli-add-mode;
          leaf update-fault-tolerance {
            type empty;
          }
        }
        leaf-list family {
          tailf:cli-flat-list-syntax;
          type family-names-type;
        }
        leaf flowspec-validate {
          type empty;
        }
        container flowspec {
          tailf:cli-add-mode;
          leaf validate-dest-prefix {
            type empty;
          }
        }
        leaf link-state-import-enable {
          type empty;
        }
        leaf link-state-export-enable {
          type empty;
        }
        uses bgp-graceful-restart-grouping;
        list group {
          key "id";
          leaf id {
            type string;
          }
          uses router-bgp-grouping;
          uses bgp-import-export-grouping;
          uses enable-origin-validation-grouping;
          container error-handling {
            tailf:cli-add-mode;
            leaf update-fault-tolerance {
              type empty;
            }
          }
          list neighbor {
            key "address";
            leaf address {
              type union {
                type inet:ipv4-address;
                type inet:ipv6-address;
              }
            }
            uses router-bgp-grouping;
            uses enable-origin-validation-grouping;
            leaf-list advertise-label {
              tailf:cli-flat-list-syntax;
              type enumeration {
                enum "ipv4";
                enum "include-ldp-prefix";
                enum "ipv6";
              }
            }
            uses bgp-import-export-grouping;
          }
          leaf-list next-hop-unchanged {
            tailf:cli-flat-list-syntax;
            type enumeration {
              enum "label-ipv4";
              enum "label-ipv6";
            }
          }
        }
        leaf ibgp-multipath {
          type empty;
        }
        container igp-shortcut {
          tailf:cli-compact-syntax;
          tailf:cli-sequence-commands;
          leaf value {
            tailf:cli-drop-node-name;
            type enumeration {
              enum "ldp";
              enum "rsvp-te";
              enum "mpls";
            }
          }
          leaf disallow-igp {
            type empty;
          }
        }
        uses bgp-import-export-grouping;
        uses bgp-common-grouping;
        uses bgp-local-as-grouping;
        leaf local-preference {
          type uint32;
        }
        leaf loop-detect {
          type enumeration {
            enum "drop-peer";
            enum "discard-route";
            enum "ignore-loop";
            enum "off";
          }
        }
        leaf med-out {
          type union {
            type uint32;
            type enumeration {
              enum "igp-cost";
            }
          }
        }
        leaf min-as-origination {
          type uint8;
        }
        leaf min-route-advertisement {
          type uint8;
        }
        leaf mp-bgp-keep {
          type empty;
        }
        leaf multihop {
          type uint8;
        }
        uses bgp-multipath-grouping;
        uses bgp-multi-path-grouping {
          augment "multi-path" {
            container label-ipv6 {
              tailf:cli-sequence-commands {
                tailf:cli-reset-all-siblings;
              }
              tailf:cli-compact-syntax;
              uses max-paths-uneqcosts-grouping;
            }
          }
        }
        leaf mvpn-vrf-import-subtype-new {
          type empty;
        }
        uses bgp-next-hop-resolution-grouping;
        container outbound-route-filtering {
          tailf:cli-add-mode;
          container extended-community {
            tailf:cli-add-mode;
            leaf accept-orf {
              type empty;
            }
            container send-orf {
              presence "true";
              leaf-list send-orf {
                tailf:cli-drop-node-name;
                tailf:cli-flat-list-syntax;
                type string;
              }
            }
          }
        }
        container rib-management {
          tailf:cli-add-mode;
          container ipv4 {
            tailf:cli-add-mode;
            leaf-list leak-import {
              tailf:cli-flat-list-syntax;
              ordered-by user;
              type string;
            }
          }
          container ipv6 {
            tailf:cli-add-mode;
            leaf-list leak-import {
              tailf:cli-flat-list-syntax;
              ordered-by user;
              type string;
            }
            leaf route-table-import {
              type string;
            }
          }
          container label-ipv4 {
            tailf:cli-add-mode;
            leaf route-table-import {
              type string;
            }
          }
          container label-ipv6 {
            tailf:cli-add-mode;
            leaf route-table-import {
              type string;
            }
          }
        }
        leaf path-mtu-discovery {
          type empty;
        }
        leaf peer-tracking-policy {
          type string;
        }
        leaf purge-timer {
          type uint8;
        }
        leaf-list rapid-update {
          tailf:cli-flat-list-syntax;
          type enumeration {
            enum "evpn";
            enum "l2-vpn";
            enum "mvpn-ipv4";
            enum "mdt-safi";
            enum "mvpn-ipv6";
            enum "label-ipv4";
            enum "label-ipv6";
            enum "vpn-ipv4";
            enum "vpn-ipv6";
            enum "mcast-vpn-ipv4";
            enum "mcast-vpn-ipv6";
          }
        }
        leaf rapid-withdrawal {
          type empty;
        }
        leaf-list remove-private {
          tailf:cli-flat-list-syntax;
          type enumeration {
            enum "limited";
            enum "skip-peer-as";
          }
        }
        leaf-list route-target-list {
          tailf:cli-flat-list-syntax;
          type union {
            type uint32;
            type inet:ipv4-address;
          }
        }
        leaf router-id {
          type union {
            type inet:ipv4-address;
            type inet:ipv6-address;
          }
        }
        leaf selective-label-ipv4-install {
          type empty;
        }
        container segment-routing {
          tailf:cli-add-mode;
          presence "true";
          container prefix-sid-range {
            tailf:cli-compact-syntax;
            leaf global {
              type empty;
            }
          }
          leaf shutdown {
            type boolean;
          }
        }
        leaf split-horizon {
          type empty;
        }
        leaf transport-tunnel {
          type enumeration {
            enum "ldp";
            enum "rsvp-te";
            enum "mpls";
          }
        }
        leaf vpn-apply-export {
          type empty;
        }
        leaf vpn-apply-import {
          type empty;
        }
        leaf shutdown {
          type boolean;
        }
      }
      leaf ip-fast-reroute {
        type empty;
      }
      leaf fib-priority {
        type enumeration {
          enum "high";
          enum "standard";
        }
      }
      container if-attribute {
        tailf:cli-add-mode;
        list admin-group {
          tailf:cli-suppress-mode;
          key "group-name";
          leaf group-name {
            type string;
          }
          leaf value {
            type uint8;
          }
        }
        list srlg-group {
          tailf:cli-suppress-mode;
          tailf:cli-compact-syntax;
          tailf:cli-sequence-commands {
            tailf:cli-reset-all-siblings;
          }
          key "group-name";
          leaf group-name {
            type string32;
          }
          leaf value {
            type uint32;
          }
          leaf penalty-weight {
            type uint32;
          }
        }
      }
      container igmp {
        tailf:cli-add-mode;
        presence "present";

        grouping iface-grouping {
          leaf disable-router-alert-check {
            type empty;
          }
          leaf import {
            type string;
          }
          leaf max-groups {
            type uint32;
          }
          leaf max-grp-sources {
            type uint32;
          }
          leaf max-sources {
            type uint32;
          }
          uses mcac-grouping;
          leaf subnet-check {
            type boolean;
          }
          leaf version {
            type uint32;
          }
        }

        grouping igmp-common-grouping {
          leaf query-interval {
            type uint32;
          }
          leaf query-response-interval {
            type uint32;
          }
          container ssm-translate {
            tailf:cli-add-mode;
            list grp-range {
              key "start end";
              leaf start {
                type inet:ipv4-address;
              }
              leaf end {
                type inet:ipv4-address;
              }
              list source {
                tailf:cli-suppress-mode;
                tailf:cli-delete-when-empty;
                key "ip-address";
                leaf ip-address {
                  type inet:ipv4-address;
                }
              }
            }
          }
        }
        list group-interface {
          key "ip-int-name";
          leaf ip-int-name {
            type string;
          }
          uses iface-grouping;
          leaf query-src-ip {
            type inet:ipv4-address;
          }
          leaf sub-hosts-only {
            type empty;
          }
          leaf shutdown {
            type boolean;
          }
        }
        leaf grp-if-query-src-ip {
          type inet:ipv4-address;
        }
        list interface {
          key "ip-int-name";
          leaf ip-int-name {
            type string;
          }
          uses iface-grouping;
          leaf query-last-listener-interval {
            type uint32;
          }
          leaf redundant-multicast {
            type empty;
          }
          uses igmp-common-grouping;
          uses igmp-static-grouping;
          leaf shutdown {
            type boolean;
          }
        }
        uses igmp-common-grouping;
        leaf query-last-member-interval {
          type uint32;
        }
        leaf robust-count {
          type uint32;
        }
        container tunnel-interface {
          list rsvp-p2mp {
            key "lsp-name";
            leaf lsp-name {
              type string;
            }
            uses igmp-static-grouping;
            leaf shutdown {
              type boolean;
            }
          }
        }
        leaf shutdown {
          type boolean;
        }
      }
      leaf router-id {
        type inet:ipv4-address;
      }
      list static-route {
        tailf:cli-compact-syntax;
        tailf:cli-sequence-commands {
          tailf:cli-reset-all-siblings;
        }
        tailf:cli-delete-when-empty;
        tailf:cli-suppress-mode;
        key "route";
        leaf route {
          type union {
            type tailf:ipv4-address-and-prefix-length;
            type tailf:ipv6-address-and-prefix-length;
          }
        }
        choice nh {
          list next-hop {
            tailf:cli-compact-syntax;
            tailf:cli-sequence-commands {
              tailf:cli-reset-all-siblings;
            }
            tailf:cli-delete-when-empty;
            tailf:cli-suppress-mode;
            key "address";
            leaf address {
              type union {
                type inet:ipv4-address;
                type inet:ipv6-address;
                type string;
              }
            }
            uses static-route-extras-grouping;
          }
          leaf indirect {
            tailf:cli-break-sequence-commands;
            type union {
              type inet:ipv4-address;
              type inet:ipv6-address;
              type string;
            }
          }
          leaf black-hole {
            tailf:cli-break-sequence-commands;
            type empty;
          }
        }
        uses static-route-extras-grouping;
        choice rsvp-ldp {
          leaf rsvp-te {
            type empty;
          }
          leaf ldp {
            type empty;
          }
        }
        leaf disallow-igp {
          type empty;
        }
      }
      list static-route-entry {
        key "route";
        leaf route {
          type union {
            type tailf:ipv4-address-and-prefix-length;
            type tailf:ipv6-address-and-prefix-length;
            type string;
          }
        }
        list next-hop {
          key "address";
          leaf address {
            type union {
              type inet:ipv4-address;
              type inet:ipv6-address;
              type string;
            }
          }
          uses static-route-entry-nh-grouping;
        }
        list indirect {
          key "address";
          leaf address {
            type union {
              type inet:ipv4-address;
              type inet:ipv6-address;
              type string;
            }
          }
          uses static-route-entry-nh-grouping;
        }
        container black-hole {
          tailf:cli-add-mode;
          presence "true";
          uses static-route-entry-nh-grouping;
          container prefix-list {
            tailf:cli-compact-syntax;
            tailf:cli-sequence-commands {
              tailf:cli-reset-siblings;
            }
            leaf name {
              tailf:cli-drop-node-name;
              type string;
            }
            leaf modifyer {
              tailf:cli-drop-node-name;
              type enumeration {
                enum "all";
                enum "none";
                enum "any";
              }
            }
          }
        }
        leaf tag {
          type uint32;
        }
      }
      uses router-aggregate-grouping;

      grouping router-isis-grouping {
        leaf advertise-passive-only {
          type empty;
        }
        leaf prefix-attributes-tlv {
          type empty;
        }
        container entropy-label {
          tailf:cli-add-mode;
          leaf override-tunnel-elc {
            type empty;
          }
        }
        container database-export {
          tailf:cli-compact-syntax;
          tailf:cli-sequence-commands;
          leaf identifier {
            type uint64;
          }
          leaf bgp-ls-identifier {
            tailf:cli-optional-in-sequence;
            type uint64;
          }
        }
        leaf advertise-router-capability {
          type enumeration {
            enum "area";
            enum "as";
          }
        }
        container igp-shortcut {
          tailf:cli-add-mode;

          grouping res-filter-grouping {
            leaf resolution {
              type enumeration {
                enum "any";
                enum "disabled";
                enum "filter";
                enum "match-family-ip";
              }
            }
            container resolution-filter {
              tailf:cli-add-mode;
              list filter {
                tailf:cli-suppress-mode;
                tailf:cli-drop-node-name;
                key "filter";
                leaf filter {
                  type enumeration {
                    enum "rsvp";
                    enum "sr-te";
                  }
                }
              }
            }
          }
          container tunnel-next-hop {
            tailf:cli-add-mode;
            // NCS drop config false container family
            container family-ipv4 {
              tailf:cli-add-mode;
              uses res-filter-grouping;
            }
            container family-ipv6 {
              tailf:cli-add-mode;
              uses res-filter-grouping;
            }
            container family-srv4 {
              tailf:cli-add-mode;
              uses res-filter-grouping;
            }
            container family-srv6 {
              tailf:cli-add-mode;
              uses res-filter-grouping;
            }
          }
          leaf shutdown {
            type boolean;
          }
        }
        leaf advertise-tunnel-link {
          type empty;
        }
        leaf all-l1isis {
          type string;
        }
        leaf all-l2isis {
          type string;
        }
        list area-id {
          tailf:cli-suppress-mode;
          key "id";
          leaf id {
            type string;
          }
        }
        leaf auth-keychain {
          type string;
        }
        leaf authentication-check {
          type boolean;
        }
        uses prompted-authentication-key-grouping;
        leaf authentication-type {
          type enumeration {
            enum "password";
            enum "message-digest";
          }
        }
        leaf csnp-authentication {
          type boolean;
        }
        leaf default-route-tag {
          type uint32;
        }
        leaf disable-ldp-sync {
          type empty;
        }
        leaf-list export {
          tailf:cli-flat-list-syntax;
          ordered-by user;
          type string;
        }
        container export-limit {
          tailf:cli-compact-syntax;
          tailf:cli-sequence-commands {
            tailf:cli-reset-siblings;
          }
          leaf number {
            tailf:cli-drop-node-name;
            type uint32;
          }
          leaf log {
            type uint8;
          }
        }
        container graceful-restart {
          tailf:cli-add-mode;
          presence "true";
          leaf helper-disable {
            type empty;
          }
        }
        leaf hello-authentication {
          type boolean;
        }
        leaf hello-padding {
          type enumeration {
            enum "adaptive";
            enum "loose";
            enum "strict";
          }
        }
        leaf ignore-attached-bit {
          type empty;
        }
        leaf ignore-lsp-errors {
          type empty;
        }
        leaf iid-tlv-enable {
          type empty;
        }
        leaf standard-multi-instance {
          type empty;
        }
        list interface {
          key "name";
          leaf name {
            type string;
          }
          list bfd-enable {
            tailf:cli-suppress-mode;
            key "bfd-enable";
            leaf bfd-enable {
              type enumeration {
                enum "ipv4";
                enum "ipv6";
              }
            }
            leaf include-bfd-tlv {
              type empty;
            }
          }
          container ipv4-adjacency-sid {
            leaf label {
              type uint32;
            }
          }
          container ipv6-adjacency-sid {
            leaf label {
              type uint32;
            }
          }
          container ipv6-node-sid {
            leaf index {
              type uint32;
            }
          }
          leaf csnp-interval {
            type uint16;
          }
          leaf hello-authentication {
            type boolean;
          }
          uses prompted-hello-authentication-key-grouping;
          leaf hello-authentication-type {
            type enumeration {
              enum "password";
              enum "message-digest";
            }
          }
          leaf interface-type {
            type enumeration {
              enum "broadcast";
              enum "point-to-point";
            }
          }
          leaf ipv4-multicast-disable {
            type empty;
          }
          leaf ipv6-multicast-disable {
            type empty;
          }
          leaf ipv6-unicast-disable {
            type empty;
          }
          list level {
            key "id";
            leaf id {
              type uint8;
            }
            uses prompted-hello-authentication-key-grouping;
            leaf hello-authentication-type {
              type enumeration {
                enum "password";
                enum "message-digest";
              }
            }
            leaf hello-interval {
              type uint16;
            }
            leaf hello-multiplier {
              type uint8;
            }
            leaf ipv4-multicast-metric {
              type uint32;
            }
            leaf ipv6-multicast-metric {
              type uint32;
            }
            leaf ipv6-unicast-metric {
              type uint32;
            }
            leaf metric {
              type uint32;
            }
            leaf passive {
              type empty;
            }
            leaf priority {
              type uint8;
            }
            leaf sd-offset {
              type uint32;
            }
            leaf sf-offset {
              type uint32;
            }
          }
          leaf level-capability {
            type enumeration {
              enum "level-1";
              enum "level-2";
              enum "level-1/2";
            }
          }
          leaf loopfree-alternate-exclude {
            type empty;
          }
          leaf lsp-pacing-interval {
            type uint16;
          }
          leaf mesh-group {
            type union {
              type uint32;
              type enumeration {
                enum "blocked";
              }
            }
          }
          leaf passive {
            type empty;
          }
          leaf retransmit-interval {
            type uint16;
          }
          leaf tag {
            type uint32;
          }
          leaf shutdown {
            type boolean;
          }
        }
        leaf ipv4-multicast-routing {
          type enumeration {
            enum "native";
            enum "mt";
          }
        }
        leaf ipv4-routing {
          type boolean;
        }
        leaf ipv6-routing {
          type enumeration {
            enum "native";
            enum "mt";
          }
        }
        leaf ipv6-multicast-routing {
          type enumeration {
            enum "native";
            enum "mt";
          }
        }
        leaf ldp-over-rsvp {
          type empty;
        }
        list level {
          key "id";
          leaf id {
            type uint8;
          }
          uses prompted-authentication-key-grouping;
          leaf authentication-type {
            type enumeration {
              enum "password";
              enum "message-digest";
            }
          }
          leaf csnp-authentication {
            type boolean;
          }
          leaf default-ipv4-multicast-metric {
            type uint32;
          }
          leaf default-ipv6-multicast-metric {
            type uint32;
          }
          leaf default-ipv6-unicast-metric {
            type uint32;
          }
          leaf default-metric {
            type uint32;
          }
          leaf external-preference {
            type uint8;
          }
          leaf hello-authentication {
            type boolean;
          }
          leaf loopfree-alternate-exclude {
            type empty;
          }
          leaf preference {
            type uint8;
          }
          leaf psnp-authentication {
            type boolean;
          }
          leaf wide-metrics-only {
            type empty;
          }
        }
        leaf level-capability {
          type enumeration {
            enum "level-1";
            enum "level-2";
            enum "level-1/2";
          }
        }
        list link-group {
          key "name";
          leaf name {
            type string;
          }
          list level {
            key "id";
            leaf id {
              type enumeration {
                enum "1";
                enum "2";
              }
            }
            leaf ipv6-unicast-metric-offset {
              type uint64;
            }
            leaf ipv4-unicast-metric-offset {
              type uint64;
            }
            leaf ipv6-multicast-metric-offset {
              type uint64;
            }
            leaf ipv4-multicast-metric-offset {
              type uint64;
            }
            list member {
              tailf:cli-suppress-mode;
              key "name";
              leaf name {
                type string;
              }
            }
            leaf revert-members {
              type uint32;
            }
            leaf oper-members {
              type uint32;
            }
          }
        }
        container loopfree-alternate {
          tailf:cli-compact-syntax;
          tailf:cli-sequence-commands {
            tailf:cli-reset-siblings;
          }
          presence "true";
          leaf remote-lfa {
            type empty;
          }
          leaf max-pq-cost {
            type uint32;
          }
        }
        container loopfree-alternate-exclude {
          tailf:cli-compact-syntax;
          leaf-list prefix-policy {
            tailf:cli-flat-list-syntax;
            type string;
          }
        }
        leaf lsp-lifetime {
          type uint16;
        }
        leaf lsp-mtu-size {
          type uint16;
        }
        leaf lsp-refresh-interval {
          type uint32;
        }
        container multi-topology {
          tailf:cli-add-mode;
          leaf ipv6-unicast {
            type empty;
          }
        }
        leaf multicast-import {
          type enumeration {
            enum "ipv4";
            enum "ipv6";
            enum "both";
          }
        }
        container overload {
          tailf:cli-compact-syntax;
          presence "true";
          leaf timeout {
            type uint16;
          }
          leaf max-metric {
            type empty;
          }
        }
        container overload-on-boot {
          tailf:cli-compact-syntax;
          presence "true";
          leaf timeout {
            type uint16;
          }
          leaf max-metric {
            type empty;
          }
        }
        leaf psnp-authentication {
          type boolean;
        }
        container reference-bandwidth {
          tailf:cli-compact-syntax;
          choice bandwidth {
            leaf bandwidth-in-kbps {
              tailf:cli-drop-node-name;
              type uint32;
            }
            leaf tbps {
              type uint8;
            }
            leaf gbps {
              type uint16;
            }
            leaf mbps {
              type uint16;
            }
            leaf kbps {
              type uint16;
            }
          }
        }
        leaf router-id {
          type inet:ipv4-address;
        }
        leaf rsvp-shortcut {
          type empty;
        }
        uses router-segment-routing-grouping;
        leaf strict-adjacency-check {
          type empty;
        }
        leaf suppress-attached-bit {
          type empty;
        }
        container timers {
          tailf:cli-add-mode;
          container spf-wait {
            tailf:cli-compact-syntax;
            tailf:cli-sequence-commands {
              tailf:cli-reset-siblings;
            }
            leaf wait {
              tailf:cli-drop-node-name;
              type uint32;
            }
            leaf spf-initial-wait {
              type uint32;
            }
            leaf spf-second-wait {
              type uint32;
            }
          }
          container lsp-wait {
            tailf:cli-compact-syntax;
            tailf:cli-sequence-commands {
              tailf:cli-reset-siblings;
            }
            leaf wait {
              tailf:cli-drop-node-name;
              type uint32;
            }
            leaf lsp-initial-wait {
              type uint32;
            }
            leaf lsp-second-wait {
              type uint32;
            }
          }
        }
        container spf-wait {
          tailf:cli-compact-syntax;
          tailf:cli-sequence-commands {
            tailf:cli-reset-siblings;
          }
          leaf wait {
            tailf:cli-drop-node-name;
            type uint8;
          }
          leaf initial-wait {
            tailf:cli-drop-node-name;
            type uint32;
          }
          leaf second-wait {
            tailf:cli-drop-node-name;
            type uint32;
          }
        }
        container lsp-wait {
          tailf:cli-compact-syntax;
          tailf:cli-sequence-commands {
            tailf:cli-reset-siblings;
          }
          leaf wait {
            tailf:cli-drop-node-name;
            type uint8;
          }
          leaf initial-wait {
            tailf:cli-drop-node-name;
            type uint8;
          }
          leaf second-wait {
            tailf:cli-drop-node-name;
            type uint8;
          }
        }
        leaf traffic-engineering {
          type empty;
        }
        container traffic-engineering-options {
          tailf:cli-add-mode;
          leaf advertise-delay {
            type empty;
          }
          container application-link-attributes {
            tailf:cli-add-mode;
            presence "true";
            leaf legacy {
              type empty;
            }
          }
          leaf ipv6 {
            type empty;
          }
        }
        leaf unicast-import-disable {
          type enumeration {
            enum "ipv4";
            enum "ipv6";
            enum "both";
          }
        }
        leaf shutdown {
          type boolean;
        }
      }
      list isis-list {
        tailf:alt-name "isis";
        key "id";
        leaf id {
          type uint32;
        }
        leaf-list import {
          tailf:cli-flat-list-syntax;
          type string;
        }
        leaf system-id {
          type string;
        }
        uses router-isis-grouping {
          augment "interface" {
            container ipv4-node-sid {
              choice ipv4-node-sid {
                leaf index {
                  type uint32;
                }
                leaf label {
                  type uint32;
                }
              }
            }
          }
        }
        container alt-lsp-refresh-interval {
          tailf:cli-compact-syntax;
          tailf:alt-name "lsp-refresh-interval";
          leaf seconds {
            tailf:cli-drop-node-name;
            type uint16;
          }
          leaf half-lifetime {
            type enable-disable;
          }
        }
        container loopfree-alternates {
          tailf:cli-add-mode;
          container exclude {
            tailf:cli-add-mode;
            leaf-list prefix-policy {
              tailf:cli-flat-list-syntax;
              type string;
            }
          }
          container remote-lfa {
            tailf:cli-add-mode;
            presence "true";
            leaf max-pq-cost {
              tailf:cli-hide-in-submode;
              type uint32;
            }
            container node-protect {
              presence "true";
              leaf max-pq-nodes {
                type uint8;
              }
            }
          }
          container ti-lfa {
            tailf:cli-add-mode;
            presence "true";
            leaf max-sr-frr-labels {
              tailf:cli-hide-in-submode;
              type uint8;
            }
            leaf node-protect {
              type empty;
            }
          }
        }
        container rib-priority {
          container high {
            choice high-options {
              leaf prefix-list-name {
                tailf:cli-drop-node-name;
                type string;
              }
              leaf tag {
                type uint32;
              }
            }
          }
        }
      }
      container isis-container {
        tailf:cli-add-mode;
        tailf:alt-name "isis";
        presence "true";
        uses router-isis-grouping;
      }

      grouping router-ospf-grouping {
        leaf advertise-tunnel-link {
          type empty;
        }
        leaf advertise-router-capability {
          type enumeration {
            enum "link";
            enum "area";
            enum "as";
          }
        }
        uses router-segment-routing-grouping;
        container loopfree-alternates {
          tailf:cli-add-mode;
          presence "true";
          container remote-lfa {
            tailf:cli-add-mode;
            presence "true";
          }
        }
        list area {
          key "area-id";
          uses ospf-area-id-grouping;

          grouping area-range-grouping {
            list area-range {
              tailf:cli-suppress-mode;
              tailf:cli-compact-syntax;
              key "ip-prefix-mask";
              leaf ip-prefix-mask {
                type tailf:ipv4-address-and-prefix-length;
              }
              leaf adv-or-not {
                tailf:cli-drop-node-name;
                type enumeration {
                  enum "advertise";
                  enum "not-advertise";
                }
              }
            }
          }
          uses area-range-grouping;
          container nssa {
            tailf:cli-add-mode;
            uses area-range-grouping;
            leaf redistribute-external {
              type empty;
            }
            container originate-default-route {
              tailf:cli-compact-syntax;
              tailf:cli-sequence-commands {
                tailf:cli-reset-siblings;
              }
              presence "true";
              leaf type-7 {
                type empty;
              }
              leaf no-adjancency {
                type empty;
              }
            }
            leaf summaries {
              type empty;
            }
          }
          list interface {
            key "name";
            leaf name {
              type string;
            }
            leaf secondary {
              tailf:cli-hide-in-submode;
              type empty;
            }
            leaf bfd-enable {
              type empty;
            }
            leaf hello-interval {
              type uint16;
            }
            leaf dead-interval {
              type uint16;
            }
            leaf passive {
              type boolean;
            }
            list message-digest-key {
              tailf:cli-suppress-mode;
              tailf:cli-compact-syntax;
              tailf:cli-sequence-commands {
                tailf:cli-reset-siblings;
              }
              key "key-id";
              leaf key-id {
                type uint32;
              }
              leaf md5 {
                type empty;
              }
              leaf hash-value {
                tailf:cli-drop-node-name;
                type string;
              }
              leaf scheme {
                tailf:cli-drop-node-name;
                type hash-method;
              }
            }
            leaf interface-type {
              type enumeration {
                enum "broadcast";
                enum "point-to-point";
              }
            }
            leaf authentication-type {
              type enumeration {
                enum "password";
                enum "message-digest";
              }
            }
            leaf metric {
              type uint16;
            }
            leaf mtu {
              type uint16;
            }
            container node-sid {
              leaf label {
                type uint32;
              }
            }
            leaf sid-protection {
              type boolean;
            }
            leaf shutdown {
              type boolean;
            }
          }
          container stub {
            tailf:cli-add-mode;
            leaf default-metric {
              type uint32;
            }
            leaf summaries {
              type boolean;
            }
          }
        }
        leaf asbr {
          type empty;
        }
        leaf compatible-rfc1583 {
          type empty;
        }
        leaf disable-ldp-sync {
          type empty;
        }
        leaf-list export {
          tailf:cli-flat-list-syntax;
          ordered-by user;
          type string;
        }
        container export-limit {
          tailf:cli-compact-syntax;
          tailf:cli-sequence-commands;
          leaf limit {
            tailf:cli-drop-node-name;
            type uint32;
          }
          leaf log {
            type uint8;
          }
        }
        container external-db-overflow {
          tailf:cli-compact-syntax;
          tailf:cli-sequence-commands;
          leaf limit {
            tailf:cli-drop-node-name;
            type int32;
          }
          leaf seconds {
            tailf:cli-drop-node-name;
            type uint32;
          }
        }
        leaf external-preference {
          type uint8;
        }
        container graceful-restart {
          tailf:cli-add-mode;
          leaf helper-disable {
            type empty;
          }
        }
        leaf ldp-over-rsvp {
          type empty;
        }
        leaf multicast-import {
          type empty;
        }
        leaf overload {
          type uint16;
        }
        container overload-alt {
          presence "true";
          tailf:alt-name "overload";
          tailf:cli-delete-when-empty;
          leaf timeout {
            type uint16;
          }
        }
        leaf overload-include-stub {
          type empty;
        }
        container overload-on-boot {
          tailf:cli-compact-syntax;
          presence "true";
          leaf timeout {
            type uint16;
          }
        }
        leaf preference {
          type uint8;
        }
        leaf reference-bandwidth {
          type uint32;
        }
        leaf rsvp-shortcut {
          type empty;
        }
        container timers {
          tailf:cli-add-mode;
          leaf lsa-arrival {
            type uint16;
          }
        }
        leaf traffic-engineering {
          type empty;
        }
        leaf unicast-import-disable {
          type empty;
        }
        leaf shutdown {
          type boolean;
        }
      }
      list ospf-list {
        tailf:alt-name "ospf";
        key "ospf-instance";
        leaf ospf-instance {
          type uint8;
        }
        leaf router-id {
          tailf:cli-drop-node-name;
          tailf:cli-hide-in-submode;
          type inet:ipv4-address;
        }
        uses router-ospf-grouping {
          augment "timers" {
            leaf lsa-accumulate {
              type uint16;
            }
            container lsa-generate {
              tailf:cli-compact-syntax;
              tailf:cli-sequence-commands {
                tailf:cli-reset-all-siblings;
              }
              leaf max-lsa-wait {
                tailf:cli-drop-node-name;
                type uint32;
              }
              leaf lsa-initial-wait {
                tailf:cli-drop-node-name;
                type uint32;
              }
              leaf lsa-second-wait {
                tailf:cli-drop-node-name;
                type uint32;
              }
            }
            leaf redistribute-delay {
              type uint16;
            }
            container spf-wait {
              tailf:cli-compact-syntax;
              tailf:cli-sequence-commands {
                tailf:cli-reset-all-siblings;
              }
              leaf max-spf-wait {
                tailf:cli-drop-node-name;
                type uint32;
              }
              leaf spf-initial-wait {
                tailf:cli-drop-node-name;
                type uint32;
              }
              leaf spf-second-wait {
                tailf:cli-drop-node-name;
                type uint32;
              }
            }
            container alt-lsa-generate {
              tailf:alt-name "lsa-generate";
              tailf:cli-compact-syntax;
              tailf:cli-sequence-commands {
                tailf:cli-reset-all-siblings;
              }
              leaf max-lsa-wait {
                tailf:cli-drop-node-name;
                type uint32;
              }
              leaf lsa-initial-wait {
                type uint32;
              }
              leaf lsa-second-wait {
                type uint32;
              }
            }
            container alt-spf-wait {
              tailf:alt-name "spf-wait";
              tailf:cli-compact-syntax;
              tailf:cli-sequence-commands {
                tailf:cli-reset-all-siblings;
              }
              leaf max-spf-wait {
                tailf:cli-drop-node-name;
                type uint32;
              }
              leaf spf-initial-wait {
                type uint32;
              }
              leaf spf-second-wait {
                type uint32;
              }
            }
            leaf incremental-spf-wait {
              type uint16;
            }
          }
        }
      }
      container ospf-container {
        tailf:alt-name "ospf";
        tailf:cli-add-mode;
        presence "true";
        leaf router-id {
          type inet:ipv4-address;
        }
        leaf router-id1 {
          tailf:cli-drop-node-name;
          tailf:cli-hide-in-submode;
          type inet:ipv4-address;
        }
        uses router-ospf-grouping {
          augment "timers" {
            container lsa-generate {
              tailf:cli-compact-syntax;
              tailf:cli-sequence-commands {
                tailf:cli-reset-all-siblings;
              }
              leaf max-lsa-wait {
                tailf:cli-drop-node-name;
                type uint32;
              }
              leaf lsa-initial-wait {
                tailf:cli-drop-node-name;
                type uint32;
              }
              leaf lsa-second-wait {
                tailf:cli-drop-node-name;
                type uint32;
              }
            }
            container spf-wait {
              tailf:cli-compact-syntax;
              tailf:cli-sequence-commands {
                tailf:cli-reset-all-siblings;
              }
              leaf max-spf-wait {
                tailf:cli-drop-node-name;
                type uint32;
              }
              leaf spf-initial-wait {
                tailf:cli-drop-node-name;
                type uint32;
              }
              leaf spf-second-wait {
                tailf:cli-drop-node-name;
                type uint32;
              }
            }
          }
        }
      }

      grouping router-ospf3-grouping {
        list area {
          key "area-id";
          leaf area-id {
            type union {
              type uint32;
              type inet:ipv4-address;
            }
          }
          list interface {
            key "interface-name";
            leaf interface-name {
              type string;
            }
            leaf interface-type {
              type enumeration {
                enum "broadcast";
                enum "point-to-point";
              }
            }
            leaf passive {
              type empty;
            }
            leaf mtu {
              type uint16;
            }
            leaf metric {
              type uint16;
            }
            leaf shutdown {
              type boolean;
            }
          }
        }
        leaf shutdown {
          type boolean;
        }
      }
      list ospf3-list {
        tailf:alt-name "ospf3";
        key "ospf3-instance";
        leaf ospf3-instance {
          type uint8;
        }
        leaf router-id {
          tailf:cli-drop-node-name;
          tailf:cli-hide-in-submode;
          type union {
            type inet:ipv4-address;
            type inet:ipv6-address;
          }
        }
        uses router-ospf3-grouping;
      }
      container ospf3-container {
        tailf:cli-add-mode;
        tailf:alt-name "ospf3";
        presence "true";
        leaf router-id {
          type union {
            type inet:ipv4-address;
            type inet:ipv6-address;
          }
        }
        uses router-ospf3-grouping;
      }
      container mcac {
        tailf:cli-add-mode;
        list policy {
          key "policy-name";
          leaf policy-name {
            type string32;
          }
          list bundle {
            key "bundle-name";
            leaf bundle-name {
              type string32;
            }
            leaf bandwidth {
              type uint32;
            }
            list channel {
              tailf:cli-suppress-mode;
              tailf:cli-compact-syntax;
              tailf:cli-sequence-commands {
                tailf:cli-reset-siblings;
              }
              key "start-address end-address";
              leaf start-address {
                type union {
                  type inet:ipv4-address;
                  type inet:ipv6-address;
                }
              }
              leaf end-address {
                type union {
                  type inet:ipv4-address;
                  type inet:ipv6-address;
                }
              }
              leaf source {
                tailf:cli-optional-in-sequence;
                type union {
                  type tailf:ipv4-address-and-prefix-length;
                  type tailf:ipv6-address-and-prefix-length;
                }
              }
              leaf bw {
                type uint32;
              }
              leaf class {
                tailf:cli-optional-in-sequence;
                type enumeration {
                  enum "high";
                  enum "low";
                }
              }
              leaf type {
                tailf:cli-optional-in-sequence;
                type enumeration {
                  enum "mandatory";
                  enum "optional";
                }
              }
            }
            leaf description {
              type string;
            }
            container mc-constraints {
              tailf:cli-add-mode;
              list lag-port-down {
                tailf:cli-suppress-mode;
                tailf:cli-compact-syntax;
                tailf:cli-sequence-commands;
                key "lag-id number-down";
                leaf lag-id {
                  type uint16;
                }
                leaf number-down {
                  type uint8;
                }
                leaf level {
                  type uint8;
                }
              }
              list level {
                tailf:cli-suppress-mode;
                tailf:cli-compact-syntax;
                tailf:cli-sequence-commands;
                key "level";
                leaf level {
                  type uint8;
                }
                leaf bw {
                  type uint32;
                }
              }
              leaf use-lag-port-weight {
                type empty;
              }
            }
            leaf shutdown {
              type boolean;
            }
          }
          leaf default-action {
            type enumeration {
              enum "accept";
              enum "discard";
            }
          }
          leaf description {
            type string;
          }
        }
      }
      container msdp {
        tailf:cli-add-mode;
        presence "present";
        leaf local-address {
          type inet:ipv4-address;
        }
        list group {
          key "group-name";
          leaf group-name {
            type string;
          }
          leaf mode {
            type string;
          }
          list peer {
            key "ip-address";
            leaf ip-address {
              type inet:ipv4-address;
            }
            leaf shutdown {
              type boolean;
            }
          }
          leaf shutdown {
            type boolean;
          }
        }
      }
      uses nat-pool-grouping;
      container l2tp {
        tailf:cli-add-mode;
        leaf local-address {
          type inet:ipv4-address;
        }
        leaf shutdown {
          type boolean;
        }
        list group {
          key "group-id";
          leaf group-id {
            type string;
          }
          leaf protocol {
            tailf:cli-hide-in-submode;
            type enumeration {
              enum "v2";
              enum "v3";
              enum "v3draft";
            }
          }
          leaf local-address {
            type inet:ipv4-address;
          }
          list tunnel {
            key "tunnel-id";
            leaf tunnel-id {
              type string;
            }
            leaf local-name {
              type string;
            }
            leaf peer {
              type inet:ipv4-address;
            }
            leaf preference {
              type uint32;
            }
            container password {
              tailf:cli-compact-syntax;
              tailf:cli-sequence-commands {
                tailf:cli-reset-siblings;
              }
              leaf id {
                tailf:cli-drop-node-name;
                type string;
              }
              leaf method {
                tailf:cli-drop-node-name;
                type hash-method;
              }
            }
            leaf remote-name {
              type string;
            }
            leaf load-balance-method {
              type enumeration {
                enum "per-session";
                enum "per-tunnel";
              }
            }
            leaf shutdown {
              type boolean;
            }
          }
          leaf shutdown {
            type boolean;
          }
        }
      }
      container ldp {
        tailf:cli-add-mode;
        presence "present";
        container fast-reroute {
          presence "true";
          leaf backup-sr-tunnel {
            type empty;
          }
        }

        grouping router-ldp-hello-keepalive-grouping {
          container hello {
            tailf:cli-compact-syntax;
            tailf:cli-sequence-commands {
              tailf:cli-reset-siblings;
            }
            leaf timeout {
              tailf:cli-drop-node-name;
              type uint16;
            }
            leaf factor {
              tailf:cli-drop-node-name;
              type uint8;
            }
          }
          container keepalive {
            tailf:cli-compact-syntax;
            tailf:cli-sequence-commands {
              tailf:cli-reset-siblings;
            }
            leaf timeout {
              tailf:cli-drop-node-name;
              type uint16;
            }
            leaf factor {
              tailf:cli-drop-node-name;
              type uint8;
            }
          }
        }
        container aggregate-prefix-match {
          tailf:cli-add-mode;
          presence "present";
          leaf shutdown {
            type boolean;
          }
        }
        container egress-statistics {
          tailf:cli-add-mode;
          list fec-prefix {
            key "prefix";
            leaf prefix {
              type union {
                type inet:ipv4-address;
                type tailf:ipv4-address-and-prefix-length;
              }
            }
            leaf accounting-policy {
              type uint8;
            }
            leaf collect-stats {
              type empty;
            }
            leaf shutdown {
              type boolean;
            }
          }
        }
        leaf entropy-label-capability {
          type empty;
        }
        leaf-list export {
          tailf:cli-flat-list-syntax;
          ordered-by user;
          type string;
        }
        list fec-originate {
          tailf:cli-suppress-mode;
          tailf:cli-compact-syntax;
          tailf:cli-sequence-commands {
            tailf:cli-reset-siblings;
          }
          key "ip-prefix";
          leaf ip-prefix {
            type tailf:ipv4-address-and-prefix-length;
          }
          leaf advertised-label {
            tailf:cli-optional-in-sequence;
            type uint16;
          }
          leaf pop {
            tailf:cli-optional-in-sequence;
            type empty;
          }
          leaf next-hop {
            tailf:cli-optional-in-sequence;
            type inet:ipv4-address;
          }
          leaf swap-label {
            tailf:cli-break-sequence-commands;
            type uint32;
          }
          leaf interface {
            type string;
          }
        }
        container graceful-restart {
          tailf:cli-add-mode;
          presence "true";
          leaf maximum-recovery-time {
            type uint32;
          }
        }
        container interface-parameters {
          tailf:cli-add-mode;
          list interface {
            key "name";
            leaf name {
              type string;
            }
            leaf dual-stack {
              tailf:cli-hide-in-submode;
              type empty;
            }
            leaf bfd-enable {
              type empty;
            }
            leaf-list alt-bfd-enable {
              tailf:cli-flat-list-syntax;
              tailf:alt-name "bfd-enable";
              type enumeration {
                enum "ipv4";
                enum "ipv6";
              }
            }
            container ipv4 {
              tailf:cli-add-mode;
              uses router-ldp-hello-keepalive-grouping;
              container local-lsr-id {
                tailf:cli-compact-syntax;
                choice local-lsr-id-choice {
                  leaf local-lsr-id {
                    tailf:cli-drop-node-name;
                    type enumeration {
                      enum "system";
                      enum "interface";
                    }
                  }
                  leaf interface-name {
                    type string;
                  }
                }
              }
              container fec-type-capability {
                tailf:cli-add-mode;
                leaf p2mp-ipv4 {
                  type enable-disable;
                }
                leaf p2mp-ipv6 {
                  type enable-disable;
                }
                leaf prefix-ipv4 {
                  type enable-disable;
                }
                leaf prefix-ipv6 {
                  type enable-disable;
                }
              }
              leaf transport-address {
                type enumeration {
                  enum "system";
                  enum "interface";
                }
              }
              leaf shutdown {
                type boolean;
              }
            }
            container ipv6 {
              tailf:cli-add-mode;
              uses router-ldp-hello-keepalive-grouping;
              leaf local-lsr-id {
                type union {
                  type enumeration {
                    enum "system";
                    enum "interface";
                  }
                  type string;
                }
              }
              leaf transport-address {
                type enumeration {
                  enum "system";
                  enum "interface";
                }
              }
              leaf shutdown {
                type boolean;
              }
            }
            leaf local-lsr-id {
              type enumeration {
                enum "system";
                enum "interface";
              }
            }
            leaf multicast-traffic {
              type enable-disable;
            }
            leaf transport-address {
              type enumeration {
                enum "system";
                enum "interface";
              }
            }
            leaf shutdown {
              type boolean;
            }
          }
          container ipv4 {
            tailf:cli-add-mode;
            uses router-ldp-hello-keepalive-grouping;
            leaf transport-address {
              type enumeration {
                enum "system";
                enum "interface";
              }
            }
          }
          container ipv6 {
            tailf:cli-add-mode;
            leaf transport-address {
              type enumeration {
                enum "system";
                enum "interface";
              }
            }
            uses router-ldp-hello-keepalive-grouping;
          }
          uses router-ldp-hello-keepalive-grouping;
        }
        container peer-parameters {
          tailf:cli-add-mode;
          list peer {
            key "addr";
            leaf addr {
              type inet:ipv4-address;
            }
            container authentication-key {
              tailf:cli-compact-syntax;
              tailf:cli-sequence-commands {
                tailf:cli-reset-all-siblings;
              }
              leaf authentication-key {
                tailf:cli-drop-node-name;
                type string;
              }
              leaf scheme {
                tailf:cli-drop-node-name;
                type hash-method;
              }
            }
            leaf adv-adj-addr-only {
              type empty;
            }
            leaf export-prefixes {
              type string;
            }
          }
        }
        leaf prefer-tunnel-in-tunnel {
          type empty;
        }
        leaf shortcut-local-ttl-propagate {
          type boolean;
        }
        leaf shortcut-transit-ttl-propagate {
          type boolean;
        }
        container targeted-session {
          tailf:cli-add-mode;
          uses router-ldp-hello-keepalive-grouping;
          container ipv4 {
            tailf:cli-add-mode;
            uses router-ldp-hello-keepalive-grouping;
          }
          container ipv6 {
            tailf:cli-add-mode;
            uses router-ldp-hello-keepalive-grouping;
          }
          list peer {
            key "peer-address";
            leaf peer-address {
              type union {
                type inet:ipv4-address;
                type inet:ipv6-address;
              }
            }
            leaf bfd-enable {
              type empty;
            }
            uses router-ldp-hello-keepalive-grouping;
            leaf local-lsr-id {
              type string;
            }
            container tunneling {
              tailf:cli-add-mode;
              presence "true";
              leaf lsp {
                type string;
              }
            }
            leaf shutdown {
              type boolean;
            }
          }
        }
        leaf-list export-tunnel-table {
          ordered-by user;
          tailf:cli-flat-list-syntax;
          type string;
        }
        leaf implicit-null-label {
          type empty;
        }
        leaf label-withdrawal-delay {
          type uint32;
        }
        container session-parameters {
          tailf:cli-add-mode;
          list peer {
            key "ip-address";
            leaf ip-address {
              type union {
                type inet:ipv4-address;
                type inet:ipv6-address;
              }
            }
            leaf adv-adj-addr-only {
              type empty;
            }
            leaf-list export-prefixes {
              tailf:cli-flat-list-syntax;
              type string;
            }
            container fec-type-capability {
              tailf:cli-add-mode;
              leaf prefix-ipv4 {
                type enumeration {
                  enum "enable";
                  enum "disable";
                }
              }
              leaf prefix-ipv6 {
                type enumeration {
                  enum "enable";
                  enum "disable";
                }
              }
            }
          }
        }
        container tcp-session-parameters {
          tailf:cli-add-mode;
          list peer-transport {
            key "ip-address";
            leaf ip-address {
              type union {
                type inet:ipv4-address;
                type inet:ipv6-address;
              }
            }
            uses prompted-authentication-key-grouping;
            leaf path-mtu-discovery {
              type empty;
            }
            leaf ttl-security {
              type uint8;
            }
          }
        }
        container import-pmsi-routes {
          tailf:cli-add-mode;
          leaf mvpn {
            type empty;
          }
          leaf mvpn-no-export-community {
            type empty;
          }
        }
        leaf tunnel-table-pref {
          type uint32;
        }
        leaf shutdown {
          type boolean;
        }
      }
      container ldp-shortcut {
        tailf:cli-compact-syntax;
        presence "true";
        leaf value {
          tailf:cli-drop-node-name;
          type enumeration {
            enum "ipv4";
            enum "ipv6";
          }
        }
      }
      container dhcp {
        tailf:cli-add-mode;
        uses local-dhcp-server-grouping;
      }
      container dhcp6 {
        tailf:cli-add-mode;
        list local-dhcp-server {
          key "server-name";
          leaf server-name {
            type string;
          }
          leaf description {
            type string;
          }
          leaf user-ident {
            type enumeration {
              enum "duid";
              enum "interface-id";
              enum "interface-id-link-local";
            }
          }
          container use-link-address {
            presence "true";
            leaf scope {
              type enumeration {
                enum "subnet";
                enum "pool";
              }
            }
          }
          container lease-hold-time {
            tailf:cli-compact-syntax;
            leaf days {
              type uint32;
            }
            leaf hrs {
              type uint32;
            }
            leaf min {
              type uint32;
            }
            leaf sec {
              type uint32;
            }
          }
          container lease-hold-time-for {
            tailf:cli-add-mode;
            leaf solicited-release {
              type empty;
            }
          }
          list pool {
            key "name";
            leaf name {
              type string;
            }
            leaf description {
              type string;
            }
            container delegated-prefix-length {
              tailf:cli-compact-syntax;
              leaf prefix-lenght {
                tailf:cli-drop-node-name;
                type uint32;
              }
              leaf minimum {
                type uint32;
              }
              leaf maximum {
                type uint32;
              }
            }
            container options {
              tailf:cli-add-mode;
              leaf-list dns-server {
                tailf:cli-flat-list-syntax;
                type inet:ipv6-address;
              }
              list custom-option {
                tailf:cli-suppress-mode;
                key "option-number";
                leaf option-number {
                  type uint16;
                }
                choice val {
                  leaf hex {
                    type string;
                  }
                  leaf string {
                    type string;
                  }
                }
              }
            }
            list prefix {
              key "address";
              leaf address {
                type tailf:ipv6-address-and-prefix-length;
              }
              leaf pd {
                tailf:cli-hide-in-submode;
                type empty;
              }
              leaf wan-host {
                tailf:cli-hide-in-submode;
                type empty;
              }
              container preferred-lifetime {
                tailf:cli-compact-syntax;
                leaf days {
                  type uint32;
                }
                leaf hrs {
                  type uint32;
                }
                leaf min {
                  type uint32;
                }
                leaf sec {
                  type uint32;
                }
              }
              container rebind-timer {
                tailf:cli-compact-syntax;
                leaf days {
                  type uint32;
                }
                leaf hrs {
                  type uint32;
                }
                leaf min {
                  type uint32;
                }
                leaf sec {
                  type uint32;
                }
              }
              container renew-timer {
                tailf:cli-compact-syntax;
                leaf days {
                  type uint32;
                }
                leaf hrs {
                  type uint32;
                }
                leaf min {
                  type uint32;
                }
                leaf sec {
                  type uint32;
                }
              }
              container valid-lifetime {
                tailf:cli-compact-syntax;
                leaf days {
                  type uint32;
                }
                leaf hrs {
                  type uint32;
                }
                leaf min {
                  type uint32;
                }
                leaf sec {
                  type uint32;
                }
              }
            }
          }
          leaf use-pool-from-client {
            type empty;
          }
          leaf shutdown {
            type boolean;
          }
        }
      }
      container radius-server {
        tailf:cli-add-mode;
        uses radius-server-grouping;
      }
      container rip {
        tailf:cli-add-mode;
        list group {
          key "name";
          leaf name {
            type string32;
          }
          leaf description {
            type string;
          }
          leaf export {
            type string;
          }
          leaf metric-out {
            type uint8;
          }
          list neighbor {
            key "intf-id";
            leaf intf-id {
              type string;
            }
            container authentication-key {
              tailf:cli-compact-syntax;
              leaf key {
                tailf:cli-drop-node-name;
                type string;
              }
              leaf hash {
                tailf:cli-drop-node-name;
                type enumeration {
                  enum "hash";
                  enum "hash2";
                }
              }
            }
            container timers {
              tailf:cli-compact-syntax;
              leaf update {
                tailf:cli-drop-node-name;
                type uint16;
              }
              leaf timeout {
                tailf:cli-drop-node-name;
                type uint16;
              }
              leaf flush {
                tailf:cli-drop-node-name;
                type uint16;
              }
            }
            leaf shutdown {
              type boolean;
            }
          }
          leaf shutdown {
            type boolean;
          }
        }
        leaf shutdown {
          type boolean;
        }
      }
      container mpls {
        tailf:cli-add-mode;
        presence "true";
        container auto-bandwidth-multipliers {
          tailf:cli-compact-syntax;
          tailf:cli-sequence-commands {
            tailf:cli-reset-siblings;
          }
          leaf sample-multiplier {
            type uint16;
          }
          leaf adjust-multiplier {
            type uint16;
          }
        }
        leaf bypass-resignal-timer {
          type uint32;
        }
        leaf hold-timer {
          type uint8;
        }
        leaf cspf-on-loose-hop {
          type empty;
        }
        leaf p2mp-resignal-timer {
          type uint16;
        }
        leaf least-fill-reoptim-thd {
          type uint16;
        }
        leaf static-lsp-fast-retry {
          type uint8;
        }
        list path {
          key "name";
          leaf name {
            type string;
          }
          list hop {
            tailf:cli-suppress-mode;
            tailf:cli-compact-syntax;
            tailf:cli-sequence-commands {
              tailf:cli-reset-siblings;
            }
            key "hop-number";
            leaf hop-number {
              type uint16;
            }
            leaf ip-address {
              tailf:cli-drop-node-name;
              type inet:ipv4-address;
            }
            leaf mode {
              tailf:cli-drop-node-name;
              type enumeration {
                enum "loose";
                enum "strict";
              }
            }
          }
          leaf shutdown {
            type boolean;
          }
        }
        container pce-report {
          leaf rsvp-te {
            type enumeration {
              enum "disable";
              enum "enable";
            }
          }
          leaf sr-te {
            type enumeration {
              enum "disable";
              enum "enable";
            }
          }
        }
        container sr-te-resignal {
          tailf:cli-add-mode;
          leaf resignal-timer {
            type uint32;
          }
          leaf resignal-on-igp-event {
            type empty;
          }
        }
        list admin-group {
          tailf:cli-suppress-mode;
          key "name";
          leaf name {
            type string;
          }
          leaf value {
            tailf:cli-drop-node-name;
            type uint32;
          }
        }
        leaf admin-group-frr {
          type empty;
        }
        leaf resignal-timer {
          type uint16;
        }
        container srlg-database {
          tailf:cli-add-mode;
          list router-id {
            key "ip-address";
            leaf ip-address {
              type inet:ipv4-address;
            }
            list interface {
              tailf:cli-suppress-mode;
              key "ip-address srlg-group";
              leaf ip-address {
                type inet:ipv4-address;
              }
              leaf srlg-group {
                type string32;
              }
            }
            leaf shutdown {
              type boolean;
            }
          }
        }
        container srlg-frr {
          tailf:cli-compact-syntax;
          presence "present";
          leaf strict {
            type empty;
          }
        }
        list srlg-group {
          key "name";
          leaf name {
            type string;
          }
          leaf value {
            type uint32;
          }
        }
        list interface {
          key "name";
          leaf name {
            type string;
          }
          leaf-list admin-group {
            tailf:cli-flat-list-syntax;
            type string;
          }
          list label-map {
            key "in-label";
            leaf in-label {
              type uint32;
            }
            leaf pop {
              type empty;
            }
            leaf shutdown {
              type boolean;
            }
          }
          leaf te-metric {
            type uint32;
          }
          list srlg-group {
            tailf:cli-suppress-mode;
            key "group-name";
            leaf group-name {
              type string32;
            }
          }
          leaf shutdown {
            type boolean;
          }
        }
        container pce-initiated-lsp {
          tailf:cli-add-mode;
          presence "true";
          container sr-te {
            tailf:cli-add-mode;
            leaf shutdown {
              type boolean;
            }
          }
        }
        list lsp-template {
          key "template";
          leaf template {
            type string;
          }
          leaf mode {
            tailf:cli-hide-in-submode;
            tailf:cli-drop-node-name;
            type enumeration {
              enum "p2mp";
              enum "mesh-p2p";
              enum "one-hop-p2p";
              enum "mesh-p2p-srte";
              enum "pce-init-p2p-srte";
              enum "one-hop-p2p-srte";
            }
          }
          leaf default-path {
            type string;
          }
          leaf path-computation-method {
            type enumeration {
              enum "local-cspf";
            }
          }
          leaf label-stack-reduction {
            type empty;
          }
          container fast-reroute {
            tailf:cli-add-mode;
            leaf frr-method {
              tailf:cli-hide-in-submode;
              tailf:cli-drop-node-name;
              type enumeration {
                enum "facility";
                enum "one-to-one";
              }
            }
            leaf hop-limit {
              type uint16;
            }
          }
          leaf cspf {
            type empty;
          }
          container egress-statistics {
            tailf:cli-add-mode;
            leaf collect-stats {
              type empty;
            }
            leaf accounting-policy {
              type uint8;
            }
          }
          leaf template-id {
            tailf:cli-hide-in-submode;
            type union {
              type string;
              type uint32;
            }
          }
          container max-sr-labels {
            tailf:cli-compact-syntax;
            leaf label-stack-size {
              tailf:cli-drop-node-name;
              type uint8;
            }
            leaf additional-frr-labels {
              type uint8;
            }
          }
          leaf pce-report {
            type enumeration {
              enum "enable";
              enum "inherit";
              enum "disable";
            }
          }
          leaf shutdown {
            type boolean;
          }
        }
        container auto-lsp {
          tailf:cli-compact-syntax;
          tailf:cli-sequence-commands;
          list lsp-template {
            tailf:cli-suppress-mode;
            key "template";
            leaf template {
              type string;
            }
            leaf-list policy {
              tailf:cli-flat-list-syntax;
              type string;
            }
          }
        }
        list lsp {
          key "name";
          leaf name {
            type string;
          }
          leaf label-stack-reduction {
            type empty;
          }
          leaf vprn-auto-bind {
            type enumeration {
              enum "include";
              enum "exclude";
            }
          }
          leaf bgp-transport-tunnel {
            type enumeration {
              enum "include";
              enum "exclude";
            }
          }
          leaf bgp-shortcut {
            type boolean;
          }
          leaf entropy-label {
            type enumeration {
              enum "force-disable";
              enum "inherit";
              enum "enable";
            }
          }
          leaf metric {
            type uint32;
          }
          leaf metric-type {
            type enumeration {
              enum "igp";
              enum "te";
            }
          }
          leaf bypass-only {
            tailf:cli-hide-in-submode;
            type empty;
          }
          leaf p2mp-lsp {
            tailf:cli-hide-in-submode;
            type empty;
          }
          leaf mpls-tp {
            tailf:cli-hide-in-submode;
            type uint16;
          }
          leaf sr-te {
            tailf:cli-hide-in-submode;
            type empty;
          }
          list admin-tag {
            tailf:cli-suppress-mode;
            key "tag";
            leaf tag {
              type string32;
            }
          }
          leaf to {
            type inet:ipv4-address;
          }
          leaf from {
            type inet:ipv4-address;
          }
          leaf-list exclude {
            tailf:cli-flat-list-syntax;
            type string;
          }
          container auto-bandwidth {
            tailf:cli-add-mode;
            container adjust-down {
              tailf:cli-compact-syntax;
              tailf:cli-sequence-commands;
              leaf percent {
                tailf:cli-drop-node-name;
                type uint8;
              }
              leaf bw {
                type uint32;
              }
            }
            container adjust-up {
              tailf:cli-compact-syntax;
              tailf:cli-sequence-commands;
              leaf percent {
                tailf:cli-drop-node-name;
                type uint8;
              }
              leaf bw {
                type uint32;
              }
            }
            list fc {
              tailf:cli-suppress-mode;
              key "fc-name";
              leaf fc-name {
                type fc-name;
              }
              leaf sampling-weight {
                type uint8;
              }
            }
            leaf max-bandwidth {
              type uint32;
            }
            leaf min-bandwidth {
              type uint32;
            }
            leaf monitor-bandwidth {
              type empty;
            }
            container multipliers {
              tailf:cli-compact-syntax;
              tailf:cli-sequence-commands {
                tailf:cli-reset-siblings;
              }
              leaf sample-multiplier {
                type uint16;
              }
              leaf adjust-multiplier {
                type uint16;
              }
            }
            container overflow-limit {
              tailf:cli-compact-syntax;
              tailf:cli-sequence-commands {
                tailf:cli-reset-siblings;
              }
              leaf number {
                tailf:cli-drop-node-name;
                type uint8;
              }
              leaf threshold {
                type uint8;
              }
              leaf bw {
                type uint32;
              }
            }
            container underflow-limit {
              tailf:cli-compact-syntax;
              tailf:cli-sequence-commands {
                tailf:cli-reset-siblings;
              }
              leaf number {
                tailf:cli-drop-node-name;
                type uint8;
              }
              leaf threshold {
                type uint8;
              }
              leaf bw {
                type uint32;
              }
            }
          }
          container cspf {
            presence "true";
            leaf use-te-metric {
              type empty;
            }
          }
          container egress-statistics {
            tailf:cli-add-mode;
            leaf collect-stats {
              type empty;
            }
            leaf accounting-policy {
              type uint8;
            }
            leaf shutdown {
              type boolean;
            }
          }
          leaf adspec {
            type empty;
          }
          container fast-reroute {
            tailf:cli-add-mode;
            leaf frr-method {
              tailf:cli-hide-in-submode;
              tailf:cli-drop-node-name;
              type enumeration {
                enum "facility";
                enum "one-to-one";
              }
            }
            leaf hop-limit {
              type uint8;
            }
            leaf node-protect {
              type boolean;
            }
          }
          container igp-shortcut {
            tailf:cli-compact-syntax;
            tailf:cli-sequence-commands {
              tailf:cli-reset-all-siblings;
            }
            leaf lfa {
              tailf:cli-drop-node-name;
              tailf:cli-optional-in-sequence;
              type enumeration {
                enum "lfa-protect";
                enum "lfa-only";
              }
            }
            container relative-metric {
              tailf:cli-flatten-container;
              tailf:cli-optional-in-sequence;
              presence "true";
              leaf offset {
                tailf:cli-drop-node-name;
                type int8;
              }
            }
            leaf igp-shortcut {
              tailf:cli-drop-node-name;
              tailf:cli-optional-in-sequence;
              type enumeration {
                enum "igp-shortcut";
                enum "no";
              }
            }
          }
          list include {
            tailf:cli-suppress-mode;
            key "group";
            leaf group {
              type string;
            }
          }
          leaf least-fill {
            type empty;
          }
          container max-sr-labels {
            tailf:cli-compact-syntax;
            tailf:cli-sequence-commands {
              tailf:cli-reset-all-siblings;
            }
            leaf label-stack-size {
              tailf:cli-drop-node-name;
              type uint8;
            }
            leaf additional-frr-labels {
              type uint8;
            }
          }
          leaf path-computation-method {
            type enumeration {
              enum "local-cspf";
              enum "pce";
            }
          }
          leaf pce-control {
            type empty;
          }
          leaf pce-computation {
            type empty;
          }
          leaf pce-report {
            type enumeration {
              enum "enable";
              enum "disable";
              enum "inherit";
            }
          }
          leaf propagate-admin-group {
            type empty;
          }

          grouping router-mpls-lsp-prim-sec-grouping {
            container bfd {
              tailf:cli-add-mode;
              leaf bfd-template {
                type string;
              }
              leaf bfd-enable {
                type empty;
              }
            }
            leaf path {
              type string;
            }
            leaf-list include {
              tailf:cli-flat-list-syntax;
              type string;
            }
            leaf-list exclude {
              tailf:cli-flat-list-syntax;
              type string;
            }
            leaf adaptive {
              type empty;
            }
            leaf bandwidth {
              type uint32;
            }
            leaf hop-limit {
              type uint8;
            }
            container priority {
              tailf:cli-compact-syntax;
              tailf:cli-sequence-commands {
                tailf:cli-reset-siblings;
              }
              leaf setup-priority {
                tailf:cli-drop-node-name;
                type uint8;
              }
              leaf hold-priority {
                tailf:cli-drop-node-name;
                type uint8;
              }
            }
            leaf shutdown {
              type boolean;
            }
          }
          list primary {
            key "path";
            uses router-mpls-lsp-prim-sec-grouping;
          }
          list secondary {
            key "path";
            uses router-mpls-lsp-prim-sec-grouping;
            leaf standby {
              type empty;
            }
          }
          leaf retry-limit {
            type uint16;
          }
          leaf retry-timer {
            type uint16;
          }
          leaf shutdown {
            type boolean;
          }
        }
        list static-lsp {
          key "name";
          leaf name {
            type string;
          }
          container push {
            tailf:cli-compact-syntax;
            tailf:cli-sequence-commands {
              tailf:cli-reset-siblings;
            }
            leaf label {
              tailf:cli-drop-node-name;
              type union {
                type uint32;
                type enumeration {
                  enum "implicit-null-label";
                }
              }
            }
            leaf nexthop {
              type inet:ipv4-address;
            }
          }
          leaf to {
            type inet:ipv4-address;
          }
          leaf metric {
            type uint32;
          }
          leaf shutdown {
            type boolean;
          }
        }
        container ingress-statistics {
          tailf:cli-add-mode;
          list lsp {
            tailf:cli-compact-syntax;
            key "name";
            leaf name {
              type string;
            }
            leaf sender {
              tailf:cli-hide-in-submode;
              type inet:ipv4-address;
            }
            leaf collect-stats {
              type empty;
            }
            leaf shutdown {
              type empty;
            }
          }
        }
        leaf p2p-active-path-fast-retry {
          type uint8;
        }
        leaf user-srlg-db {
          type enable-disable;
        }

        grouping entropy-label-grouping {
          container entropy-label {
            leaf rsvp-te {
              type enumeration {
                enum "force-disable";
                enum "enable";
              }
            }
            leaf sr-te {
              type enumeration {
                enum "force-disable";
                enum "enable";
              }
            }
          }
        }
        uses entropy-label-grouping;
        container tunnel-table-pref {
          tailf:cli-add-mode;
          leaf rsvp-te {
            type uint32;
          }
          leaf sr-te {
            type uint32;
          }
        }
        leaf shutdown {
          type boolean;
        }
      }
      container mpls-labels {
        tailf:cli-add-mode;
        leaf bgp-labels-hold-timer {
          type uint8;
        }
        container sr-labels {
          tailf:cli-compact-syntax;
          tailf:cli-sequence-commands {
            tailf:cli-reset-all-siblings;
          }
          leaf start {
            type uint32;
          }
          leaf end {
            type uint32;
          }
        }
        leaf static-label-range {
          type uint32;
        }
        list reserved-label-block {
          key "name";
          leaf name {
            type string;
          }
          container start-label {
            tailf:cli-compact-syntax;
            tailf:cli-sequence-commands {
              tailf:cli-reset-all-siblings;
            }
            leaf label {
              tailf:cli-drop-node-name;
              type uint32;
            }
            leaf end-label {
              type uint32;
            }
          }
        }
      }
      container origin-validation {
        tailf:cli-add-mode;
        list rpki-session {
          key "ip-address";
          leaf ip-address {
            type union {
              type inet:ipv4-address;
              type inet:ipv6-address;
              type string;
            }
          }
          leaf description {
            type string;
          }
          leaf port {
            type uint32;
          }
          leaf local-address {
            type union {
              type inet:ipv4-address;
              type inet:ipv6-address;
              type string;
            }
          }
          leaf shutdown {
            type boolean;
          }
        }
      }
      container rsvp {
        tailf:cli-add-mode;
        presence "present";
        leaf implicit-null-label {
          type empty;
        }
        list interface {
          key "name";
          leaf name {
            type string;
          }
          leaf bfd-enable {
            type empty;
          }
          leaf hello-interval {
            type uint16;
          }
          container refresh-reduction {
            tailf:cli-add-mode;
            leaf reliable-delivery {
              type empty;
            }
          }
          uses prompted-authentication-key-grouping;
          leaf subscription {
            type uint16;
          }
          leaf shutdown {
            type boolean;
          }
        }
        leaf node-id-in-rro {
          type enumeration {
            enum "include";
            enum "exclude";
          }
        }
        leaf refresh-reduction-over-bypass {
          type enable-disable;
        }
        leaf refresh-time {
          type uint16;
        }
        leaf shutdown {
          type boolean;
        }
      }
      container router-advertisement {
        tailf:cli-add-mode;
        list interface {
          key "ip-int-name";
          leaf ip-int-name {
            type string;
          }
          leaf current-hop-limit {
            type uint8;
          }
          leaf max-advertisement-interval {
            type uint16;
          }
          leaf min-advertisement-interval {
            type uint16;
          }
          leaf mtu {
            type uint16;
          }
          leaf managed-configuration {
            type empty;
          }
          leaf other-stateful-configuration {
            type empty;
          }
          list prefix {
            key "ipv6-prefix";
            leaf ipv6-prefix {
              type inet:ipv6-prefix;
            }
            leaf preferred-lifetime {
              type uint32;
            }
            leaf valid-lifetime {
              type uint32;
            }
          }
          leaf reachable-time {
            type uint32;
          }
          leaf retransmit-time {
            type uint32;
          }
          leaf router-lifetime {
            type uint16;
          }
          leaf use-virtual-mac {
            type empty;
          }
          leaf shutdown {
            type boolean;
          }
        }
      }
      container mld {
        tailf:cli-add-mode;
        list interface {
          key "ip-int-name";
          leaf ip-int-name {
            type string;
          }
          leaf shutdown {
            type boolean;
          }
        }
        leaf shutdown {
          type boolean;
        }
      }
      container pcep {
        tailf:cli-add-mode;
        container pcc {
          tailf:cli-add-mode;
          leaf keepalive {
            type uint32;
          }
          leaf dead-timer {
            type uint32;
          }
          leaf max-srte-pce-init-lsps {
            type uint32;
          }
          leaf redelegation-timer {
            type uint32;
          }
          container state-timer {
            tailf:cli-compact-syntax;
            tailf:cli-sequence-commands {
              tailf:cli-reset-all-siblings;
            }
            leaf seconds {
              tailf:cli-drop-node-name;
              type uint32;
            }
            leaf action {
              tailf:cli-optional-in-sequence;
              type enumeration {
                enum "remove";
                enum "none";
              }
            }
          }
          leaf local-address {
            type inet:ipv4-address;
          }
          list peer {
            key "address";
            leaf address {
              type inet:ipv4-address;
            }
            leaf preference {
              tailf:cli-hide-in-submode;
              type uint8;
            }
            leaf route-preference {
              type enumeration {
                enum "both";
                enum "inband";
                enum "outband";
              }
            }
            leaf shutdown {
              type boolean;
            }
          }
          leaf shutdown {
            type boolean;
          }
        }
      }
      container route-next-hop-policy {
        tailf:cli-add-mode;
        list template {
          key "template-name";
          leaf template-name {
            type string;
          }
          leaf protection-type {
            type enumeration {
              enum "link";
              enum "node";
            }
          }
          leaf nh-type {
            type enumeration {
              enum "ip";
              enum "tunnel";
            }
          }
          leaf srlg-enable {
            type empty;
          }
        }
      }
      container policy-options {
        tailf:cli-add-mode;
        list prefix-list {
          key "name";
          leaf name {
            type string;
          }
          list prefix {
            tailf:cli-suppress-mode;
            tailf:cli-delete-when-empty;
            key "ip-prefix";
            leaf ip-prefix {
              type union {
                type tailf:ipv4-address-and-prefix-length;
                type tailf:ipv6-address-and-prefix-length;
              }
            }
            leaf exact {
              type empty;
            }
            leaf longer {
              type empty;
            }
            leaf through {
              type uint8;
            }
            leaf prefix-length-range {
              type string;
            }
          }
        }
        list community {
          key "name";
          leaf name {
            type string;
          }
          leaf-list members {
            tailf:cli-flat-list-syntax;
            type string;
          }
          container expression {
            tailf:cli-compact-syntax;
            tailf:cli-sequence-commands {
              tailf:cli-reset-all-siblings;
            }
            leaf expression {
              tailf:cli-drop-node-name;
              type string;
            }
            leaf exact {
              type empty;
            }
          }
        }
        list alt-community {
          tailf:cli-suppress-mode;
          tailf:cli-compact-syntax;
          tailf:cli-delete-when-empty;
          tailf:alt-name "community";
          key "name";
          leaf name {
            type string;
          }
          leaf-list members {
            tailf:cli-flat-list-syntax;
            type string;
          }
          container expression {
            tailf:cli-compact-syntax;
            tailf:cli-sequence-commands {
              tailf:cli-reset-all-siblings;
            }
            leaf expression {
              tailf:cli-drop-node-name;
              type string;
            }
            leaf exact {
              type empty;
            }
          }
        }
        list damping {
          key "name";
          leaf name {
            type string;
          }
          leaf half-life {
            type uint8;
          }
          leaf max-suppress {
            type uint16;
          }
          leaf reuse {
            type uint32;
          }
          leaf suppress {
            type uint32;
          }
        }
        list policy-statement {
          key "name";
          leaf name {
            type string;
          }
          leaf description {
            type string;
          }
          container default-action {
            uses policy-options-default-action-grouping;
          }
          list entry {
            key "id";
            leaf id {
              type uint32;
            }
            leaf description {
              type string;
            }
            container conditional-expression {
              presence "true";
              tailf:cli-add-mode;
              leaf route-exists {
                type string;
              }
            }
            container action {
              tailf:cli-add-mode;
              presence "true";
              leaf mode {
                tailf:cli-drop-node-name;
                tailf:cli-hide-in-submode;
                type enumeration {
                  enum "drop";
                  enum "accept";
                  enum "next-entry";
                  enum "next-policy";
                }
              }
              uses policy-option-action-params-grouping;
              uses policy-options-action-fc-grouping;
            }
            leaf action-reject {
              type empty;
            }
            container from {
              tailf:cli-add-mode;
              presence "true";
              leaf area {
                type union {
                  type uint32;
                  type inet:ipv4-address;
                }
              }
              leaf as-path {
                type string;
              }
              container as-path-length {
                tailf:cli-compact-syntax;
                leaf length {
                  tailf:cli-drop-node-name;
                  type uint32;
                }
                leaf operator {
                  tailf:cli-drop-node-name;
                  type enumeration {
                    enum "equal";
                    enum "or-higher";
                    enum "or-lower";
                  }
                }
              }
              leaf as-path-group {
                type string;
              }
              container community {
                tailf:cli-compact-syntax;
                tailf:cli-sequence-commands {
                  tailf:cli-reset-siblings;
                }
                leaf expression {
                  tailf:cli-optional-in-sequence;
                  type empty;
                }
                leaf community {
                  tailf:cli-drop-node-name;
                  type string;
                }
              }
              container community-count {
                tailf:cli-sequence-commands {
                  tailf:cli-reset-all-siblings;
                }
                tailf:cli-compact-syntax;
                leaf count {
                  tailf:cli-drop-node-name;
                  type uint32;
                }
                leaf op {
                  tailf:cli-drop-node-name;
                  type enumeration {
                    enum "equal";
                    enum "or-higher";
                    enum "or-lower";
                  }
                }
                leaf val {
                  tailf:cli-drop-node-name;
                  type enumeration {
                    enum "standard";
                    enum "extended";
                    enum "large";
                  }
                }
              }
              leaf external {
                type empty;
              }
              leaf evpn-type {
                type uint8;
              }
              container metric {
                tailf:cli-compact-syntax;
                leaf value {
                  tailf:cli-drop-node-name;
                  type uint32;
                }
                leaf comparator {
                  tailf:cli-drop-node-name;
                  type enumeration {
                    enum "equal";
                    enum "or-higher";
                    enum "or-lower";
                  }
                }
              }
              leaf next-hop {
                type union {
                  type inet:ipv4-address;
                  type inet:ipv6-address;
                  type string;
                }
              }
              leaf-list family {
                tailf:cli-flat-list-syntax;
                type family-names-type;
              }
              leaf group-address {
                type string;
              }
              leaf host-ip {
                type string;
              }
              leaf interface {
                type string;
              }
              leaf level {
                type uint8;
              }
              container neighbor {
                choice a {
                  leaf ip-address {
                    tailf:cli-drop-node-name;
                    type inet:ipv4-address;
                  }
                  leaf prefix-list {
                    type string;
                  }
                }
              }
              leaf origin {
                type enumeration {
                  enum "igp";
                  enum "egp";
                  enum "incomplete";
                  enum "any";
                  enum "aaa";
                  enum "dhcp";
                  enum "ludb";
                }
              }
              leaf origin-validation-state {
                type enumeration {
                  enum "valid";
                  enum "notFound";
                  enum "invalid";
                }
              }
              leaf path-type {
                type enumeration {
                  enum "ibgp";
                  enum "ebgp";
                }
              }
              leaf policy {
                type string;
              }
              leaf-list prefix-list {
                tailf:cli-flat-list-syntax;
                ordered-by user;
                type string;
              }
              container protocol {
                tailf:cli-compact-syntax;
                tailf:cli-sequence-commands {
                  tailf:cli-reset-all-siblings;
                }
                leaf-list protocol {
                  tailf:cli-drop-node-name;
                  tailf:cli-flat-list-syntax;
                  type policy-protocol;
                }
                choice instance-all {
                  leaf instance {
                    type uint8;
                  }
                  leaf all {
                    type empty;
                  }
                }
              }
              leaf source-address {
                type union {
                  type inet:ipv4-address;
                  type inet:ipv6-address;
                }
              }
              leaf state {
                type enumeration {
                  enum "srrp-master";
                  enum "srrp-non-master";
                  enum "ipsec-master-with-peer";
                  enum "ipsec-non-master";
                  enum "ipsec-master-without-peer";
                }
              }
              leaf tag {
                type policy-options-tag;
              }
              leaf type {
                type uint8;
              }
            }
            container to {
              tailf:cli-add-mode;
              presence "true";
              leaf level {
                type uint8;
              }
              leaf neighbor {
                type union {
                  type inet:ipv4-address;
                  type inet:ipv6-address;
                  type string;
                }
              }
              leaf-list prefix-list {
                tailf:cli-flat-list-syntax;
                type string;
              }
              leaf-list protocol {
                tailf:cli-flat-list-syntax;
                type enumeration {
                  enum "all";
                  enum "direct";
                  enum "static";
                  enum "bgp";
                  enum "bgp-label";
                  enum "isis";
                  enum "ospf";
                  enum "rip";
                  enum "aggregate";
                  enum "bgp-vpn";
                  enum "igmp";
                  enum "pim";
                  enum "ospf3";
                  enum "ldp";
                  enum "sub-mgmt";
                  enum "mld";
                  enum "managed";
                  enum "vpn-leak";
                  enum "tms";
                  enum "nat";
                  enum "periodic";
                  enum "ipsec";
                  enum "mpls";
                  enum "dhcpv6-pd";
                  enum "dhcpv6-na";
                  enum "dhcpv6-ta";
                  enum "dhcpv6-pd-excl";
                }
              }
            }
          }
        }
        list as-path {
          key "name";
          leaf name {
            type string;
          }
          leaf expression {
            type string;
          }
        }
        list alt-as-path {
          tailf:cli-compact-syntax;
          tailf:cli-suppress-mode;
          tailf:cli-sequence-commands {
            tailf:cli-reset-all-siblings;
          }
          tailf:alt-name "as-path";
          key "name";
          leaf name {
            type string;
          }
          leaf expression {
            tailf:cli-optional-in-sequence;
            type string;
          }
          leaf regexp {
            tailf:cli-drop-node-name;
            type string;
          }
        }
        list as-path-group {
          key "name";
          leaf name {
            type string;
          }
          list entry {
            tailf:cli-suppress-mode;
            key "entry-id";
            leaf entry-id {
              type uint8;
            }
            leaf expression {
              type union {
                type enumeration {
                  enum "null";
                }
                type string;
              }
            }
          }
        }
      }
      container pim {
        tailf:cli-add-mode;
        list interface {
          key "ip-int-name";
          leaf ip-int-name {
            type string;
          }
          leaf assert-period {
            type uint16;
          }
          container bfd-enable {
            presence "true";
            leaf bfd-enable {
              tailf:cli-drop-node-name;
              type enumeration {
                enum "ipv4";
                enum "ipv6";
              }
            }
          }
          leaf bsm-check-rtr-alert {
            type empty;
          }
          leaf hello-interval {
            type uint8;
          }
          leaf hello-multiplier {
            type uint8;
          }
          leaf improved-assert {
            type boolean;
          }
          leaf instant-prune-echo {
            type empty;
          }
          leaf ipv4-multicast-disable {
            type boolean;
          }
          leaf ipv6-multicast-disable {
            type boolean;
          }
          leaf max-groups {
            type uint16;
          }
          uses mcac-grouping;
          leaf multicast-senders {
            type enumeration {
              enum "auto";
              enum "always";
              enum "never";
            }
          }
          leaf-list p2mp-ldp-tree-join {
            tailf:cli-flat-list-syntax;
            type enumeration {
              enum "ipv4";
              enum "ipv6";
            }
          }
          leaf priority {
            type uint32;
          }
          container sticky-dr {
            leaf priority {
              type uint32;
            }
            leaf three-way-hello {
              type empty;
            }
            leaf tracking-support {
              type empty;
            }
          }
          leaf shutdown {
            type boolean;
          }
        }
        leaf enable-mdt-spt {
          type empty;
        }
        leaf ipv4-multicast-disable {
          type boolean;
        }
        leaf ipv6-multicast-disable {
          type boolean;
        }
        leaf lag-usage-optimization {
          type empty;
        }
        leaf multicast-fast-failover {
          type empty;
        }
        leaf multicast6-fast-failover {
          type empty;
        }
        container rp {
          tailf:cli-add-mode;
          list anycast {
            key "rp-ip-address";
            leaf rp-ip-address {
              type inet:ipv4-address;
            }
            list rp-set-peer {
              tailf:cli-suppress-mode;
              key "ip-address";
              leaf ip-address {
                tailf:cli-drop-node-name;
                type inet:ipv4-address;
              }
            }
          }
          leaf-list bootstrap-import {
            tailf:cli-flat-list-syntax;
            type string;
          }
          leaf-list bootstrap-export {
            tailf:cli-flat-list-syntax;
            type string;
          }
          container static {
            tailf:cli-add-mode;
            list address {
              key "ip-address";
              leaf ip-address {
                type union {
                  type inet:ipv4-address;
                  type inet:ipv6-address;
                }
              }
              list group-prefix {
                tailf:cli-suppress-mode;
                key "grp-ip-addr";
                leaf grp-ip-addr {
                  tailf:cli-drop-node-name;
                  type tailf:ipv4-address-and-prefix-length;
                }
              }
              leaf override {
                type empty;
              }
            }
          }
          container bsr-candidate {
            tailf:cli-add-mode;
            leaf address {
              type inet:ipv4-address;
            }
            leaf hash-mask-len {
              type uint8;
            }
            leaf priority {
              type uint8;
            }
            leaf shutdown {
              type boolean;
            }
          }
          container rp-candidate {
            tailf:cli-add-mode;
            leaf address {
              type inet:ipv4-address;
            }
            list group-range {
              tailf:cli-suppress-mode;
              key "grp-ip-addr";
              leaf grp-ip-addr {
                type tailf:ipv4-address-and-prefix-length;
              }
            }
            leaf holdtime {
              type uint8;
            }
            leaf priority {
              type uint8;
            }
            leaf shutdown {
              type boolean;
            }
          }
        }
        leaf rpf-table {
          type enumeration {
            enum "rtable-m";
            enum "rtable-u";
            enum "both";
          }
        }
        uses pim-common-grouping;
        container ssm-groups {
          tailf:cli-add-mode;
          list group-range {
            tailf:cli-suppress-mode;
            key "prefix";
            leaf prefix {
              type union {
                type tailf:ipv4-address-and-prefix-length;
                type tailf:ipv6-address-and-prefix-length;
              }
            }
          }
        }
        leaf shutdown {
          type boolean;
        }
      }
      container sgt-qos {
        tailf:cli-add-mode;
        list application {
          tailf:cli-suppress-mode;
          key "app-name";
          leaf app-name {
            type enumeration {
              enum "bgp";
              enum "bfd";
              enum "bmp";
              enum "call-trace";
              enum "cflowd";
              enum "dhcp";
              enum "diameter";
              enum "dns";
              enum "ftp";
              enum "grpc";
              enum "gtp";
              enum "http";
              enum "ibcp";
              enum "icmp";
              enum "igmp";
              enum "igmp-reporter";
              enum "l2tp";
              enum "ldp";
              enum "mld";
              enum "mpls-udp-return";
              enum "msdp";
              enum "mtrace2";
              enum "ndis";
              enum "ntp";
              enum "ospf";
              enum "pcep";
              enum "pfcp";
              enum "pim";
              enum "ptp";
              enum "radius";
              enum "rip";
              enum "rsvp";
              enum "sflow";
              enum "snmp";
              enum "snmp-notification";
              enum "srrp";
              enum "ssh";
              enum "syslog";
              enum "tacplus";
              enum "telnet";
              enum "tftp";
              enum "traceroute";
              enum "vrrp";
              enum "arp";
              enum "isis";
              enum "pppoe";
            }
          }
          choice choice {
            leaf dscp {
              type string;
            }
            leaf dot1p {
              type union {
                type uint8;
                type enumeration {
                  enum "none";
                }
              }
            }
          }
        }
        list dscp {
          tailf:cli-suppress-mode;
          key "dscp-name";
          leaf dscp-name {
            type dscp-type;
          }
          leaf fc {
            type fc-name;
          }
        }
      }
      container ttl-propagate {
        tailf:cli-add-mode;
        leaf vprn-local {
          type enumeration {
            enum "none";
            enum "all";
            enum "vc-only";
          }
        }
        leaf vprn-transit {
          type enumeration {
            enum "none";
            enum "all";
            enum "vc-only";
          }
        }
      }
      container twamp-light {
        tailf:cli-add-mode;
        container reflector {
          tailf:cli-add-mode;
          presence "true";
          leaf description {
            type string;
          }
          leaf udp-port {
            tailf:cli-hide-in-submode;
            type uint32;
          }
          leaf shutdown {
            type boolean;
          }
          list prefix {
            leaf description {
              type string;
            }
            key "ip-prefix";
            leaf ip-prefix {
              type union {
                type tailf:ipv6-address-and-prefix-length;
                type tailf:ipv4-address-and-prefix-length;
              }
            }
          }
        }
      }
      container weighted-ecmp {
        presence "true";
        leaf strict {
          type empty;
        }
      }
    }
    container aaa {
      tailf:ncs-device-type "cli-ned";
      tailf:display-when "not(../../ncs:module) or ../../ncs:module[ncs:name='netsim-ned-alu-sr']";
      tailf:cli-add-mode;
      leaf radius-coa-port {
        type enumeration {
          enum "1647";
          enum "1700";
          enum "1812";
          enum "3799";
        }
      }
      list radius-script-policy {
        key "policy-name";
        leaf policy-name {
          type string32;
        }
        leaf description {
          type string;
        }
        container primary {
          tailf:cli-add-mode;
          leaf script-url {
            type string;
          }
          leaf shutdown {
            type boolean;
          }
        }
      }
      list radius-server-policy {
        key "policy-name";
        leaf policy-name {
          type string32;
        }
        leaf description {
          type string;
        }
        leaf acct-on-off {
          type empty;
        }
        leaf acct-request-script-policy {
          type string32;
        }
        leaf python-policy {
          type string32;
        }
        leaf accept-script-policy {
          type string32;
        }
        leaf auth-request-script-policy {
          type string32;
        }
        container servers {
          tailf:cli-add-mode;
          leaf access-algorithm {
            type enumeration {
              enum "direct";
              enum "round-robin";
              enum "hash-based";
            }
          }
          container buffering {
            tailf:cli-add-mode;

            grouping acct-grouping {
              leaf min {
                type uint16;
              }
              leaf max {
                type uint16;
              }
              leaf lifetime {
                type uint8;
              }
            }
            container acct-interim {
              tailf:cli-compact-syntax;
              tailf:cli-sequence-commands;
              uses acct-grouping;
            }
            container acct-start {
              tailf:cli-compact-syntax;
              tailf:cli-sequence-commands;
              uses acct-grouping;
            }
            container acct-stop {
              tailf:cli-compact-syntax;
              tailf:cli-sequence-commands;
              uses acct-grouping;
            }
          }
          container health-check {
            tailf:cli-add-mode;
            container down-timeout {
              tailf:cli-compact-syntax;
              leaf min {
                type uint8;
              }
              leaf sec {
                type uint8;
              }
            }
          }
          container hold-down-time {
            tailf:cli-compact-syntax;
            leaf sec {
              type uint8;
            }
            leaf min {
              type uint8;
            }
            leaf hrs {
              type uint8;
            }
            leaf days {
              type uint8;
            }
          }
          leaf retry {
            type uint16;
          }
          container timeout {
            tailf:cli-compact-syntax;
            tailf:cli-sequence-commands {
              tailf:cli-reset-all-siblings;
            }
            leaf min {
              tailf:cli-optional-in-sequence;
              type uint8;
            }
            leaf sec {
              type uint8;
            }
          }
          leaf router {
            type union {
              type enumeration {
                enum "Base";
                enum "management";
              }
              type uint32;
            }
          }
          list server {
            tailf:cli-suppress-mode;
            key "server-index";
            leaf server-index {
              type uint8;
            }
            leaf name {
              type string32;
            }
          }
          leaf source-address {
            type inet:ipv4-address;
          }
        }
      }
      list diameter-peer-policy {
        key "peer-policy-name";
        leaf peer-policy-name {
          type string32;
        }
        leaf-list applications {
          tailf:cli-flat-list-syntax;
          type enumeration {
            enum "gx";
            enum "gy";
            enum "nasreq";
          }
        }
        leaf origin-host {
          type string;
        }
        leaf origin-realm {
          type string;
        }
        leaf source-address {
          type inet:ipv4-address;
        }
        list peer {
          key "name";
          leaf name {
            type string32;
          }
          leaf destination-host {
            type string;
          }
          leaf destination-realm {
            type string;
          }
          leaf address {
            type inet:ipv4-address;
          }
          container transport {
            tailf:cli-compact-syntax;
            leaf tcp {
              type empty;
            }
            leaf port {
              type uint32;
            }
          }
          leaf shutdown {
            type boolean;
          }
        }
      }
    }
    container system {
      tailf:ncs-device-type "cli-ned";
      tailf:display-when "not(../../ncs:module) or ../../ncs:module[ncs:name='netsim-ned-alu-sr']";
      tailf:cli-add-mode;
      container alarms {
        tailf:cli-add-mode;
        leaf max-cleared {
          type string;
        }
        leaf shutdown {
          type boolean;
        }
      }
      list alarm-contact-input {
        key "id";
        leaf id {
          type uint8;
        }
        leaf description {
          type string;
        }
        leaf alarm-output-severity {
          type enumeration {
            enum "critical";
            enum "major";
            enum "minor";
            enum "none";
          }
        }
        leaf trigger-alarm-msg {
          type string;
        }
        leaf shutdown {
          type boolean;
        }
      }
      container alarm-contact-output {
        tailf:cli-add-mode;
        presence "true";
        leaf shutdown {
          type boolean;
        }
      }
      container bluetooth {
        tailf:cli-add-mode;
        list module {
          key "name";
          leaf name {
            type string;
          }
        }
        leaf power {
          type enumeration {
            enum "off";
            enum "enabled-manual";
            enum "enabled-automatic";
          }
        }
        leaf advertising-timeout {
          type uint32;
        }
      }
      container fp {
        tailf:cli-add-mode;
        container options {
          tailf:cli-add-mode;
          container mpls {
            tailf:cli-add-mode;
            container entropy-label {
              tailf:cli-add-mode;
              leaf shutdown {
                type boolean;
              }
            }
          }
          container services {
            tailf:cli-add-mode;
            container vpls-evpn-mpls {
              tailf:cli-add-mode;
              leaf shutdown {
                type boolean;
              }
            }
          }
          container qos {
            tailf:cli-add-mode;
            container bum-policers {
              tailf:cli-add-mode;
              leaf shutdown {
                type boolean;
              }
            }
            container dscp-transparency {
              tailf:cli-add-mode;
              leaf shutdown {
                type boolean;
              }
            }
            container fc-4-profile {
              tailf:cli-add-mode;
              leaf shutdown {
                type boolean;
              }
            }
          }
          container router {
            tailf:cli-add-mode;
            container ecmp {
              tailf:cli-add-mode;
              leaf shutdown {
                type boolean;
              }
            }
          }
        }
      }
      container grpc {
        tailf:cli-add-mode;
        leaf allow-unsecure-connection {
          type empty;
        }
        container gnmi {
          tailf:cli-add-mode;
          leaf auto-config-save {
            type empty;
          }
          leaf shutdown {
            type boolean;
          }
        }
        container rib-api {
          tailf:cli-add-mode;
          leaf shutdown {
            type boolean;
          }
        }
        container md-cli {
          tailf:cli-add-mode;
          leaf shutdown {
            type boolean;
          }
        }
        container tcp-keepalive {
          tailf:cli-add-mode;
          leaf shutdown {
            type boolean;
          }
        }
        leaf tls-server-profile {
          type string;
        }
        leaf shutdown {
          type boolean;
        }
      }
      container satellite {
        tailf:cli-add-mode;
        list port-template {
          key "name";
          leaf name {
            type string;
          }
          leaf sat-type {
            tailf:cli-hide-in-submode;
            mandatory true;
            type enumeration {
              enum "es48-1gb-sfp";
              enum "es24-1gb-tx";
              enum "es48-sass-1gb-sfp";
              enum "es24-1gb-sfp";
              enum "es64-10gb-sfpp+4-100gb-cfp4";
              enum "es24-sasmxp-1gb-sfp";
              enum "es48-1gb-tx";
              enum "es24-sass-1gb-sfp";
              enum "es64-10gb-sfpp+4-100gb-qsfp28";
            }
          }
          list port {
            key "port-id";
            leaf port-id {
              type string;
            }
            leaf role {
              type enumeration {
                enum "client";
                enum "none";
                enum "uplink";
                enum "system-default";
              }
            }
          }
          leaf shutdown {
            type boolean;
          }
        }
        list eth-sat {
          key "id";
          leaf id {
            type uint32;
          }
          leaf description {
            type string;
          }
          leaf mac-address {
            type ieee-mac;
          }
          container sat-type {
            tailf:cli-compact-syntax;
            tailf:cli-sequence-commands {
              tailf:cli-reset-all-siblings;
            }
            leaf type {
              tailf:cli-drop-node-name;
              type enumeration {
                enum "es24-1gb-sfp";
                enum "es24-1gb-tx";
                enum "es24-sasmxp-1gb-sfp";
                enum "es24-sass-1gb-sfp";
                enum "es48-1gb-sfp";
                enum "es48-1gb-tx";
                enum "es48-sass-1gb-sfp";
                enum "es64-10gb-sfpp+4-100gb-cfp4";
                enum "es64-10gb-sfpp+4-100gb-qsfp28";
              }
            }
            container dynamic-uplink {
              tailf:cli-flatten-container;
              leaf uplink-distribution {
                type enumeration {
                  enum "single-complex";
                  enum "dual-complex";
                }
              }
            }
          }
          leaf client-down-delay {
            type uint32;
          }
          leaf feature {
            type enumeration {
              enum "local-forward";
              enum "ptp-tc";
            }
          }
          leaf enable-console-access {
            type boolean;
          }
          leaf software-repository {
            type string;
          }
          leaf sync-e {
            type empty;
          }
          leaf ptp-tc {
            type empty;
          }
          list port-map {
            tailf:cli-suppress-mode;
            tailf:cli-compact-syntax;
            key "client-port-id";
            leaf client-port-id {
              type string;
            }
            leaf primary {
              type string;
            }
            leaf secondary {
              type string;
            }
          }
          leaf shutdown {
            type boolean;
          }
        }
      }
      container port-topology {
        tailf:cli-add-mode;
        list port {
          tailf:cli-suppress-mode;
          tailf:cli-diff-create-before "/alu:port[port-id=current()/port-id]/ethernet/mode" {
            tailf:xpath-root 3;
            tailf:cli-when-target-set;
          }
          key "port-id";
          leaf port-id {
            type string;
          }
          leaf to {
            type string;
          }
        }
      }
      list power-shelf {
        key "power-shelf-id";
        leaf power-shelf-id {
          type uint32;
        }
        leaf description {
          type string;
        }
        leaf power-shelf-type {
          type string;
        }
        list power-module {
          key "power-module-id";
          leaf power-module-id {
            type uint32;
          }
          leaf power-module-type {
            type enumeration {
              enum "ps-a-dc-6000";
              enum "ps-b-ac/hv-6000";
              enum "ixr-ac-hvdc-3000";
              enum "ixr-dc-3000";
            }
          }
          leaf shutdown {
            type boolean;
          }
        }
        leaf shutdown {
          type boolean;
        }
      }
      container ip {
        tailf:cli-add-mode;
        leaf enforce-unique-if-index {
          type empty;
        }
      }
      list file-transmission-profile {
        key "name";
        leaf name {
          type string32;
        }
        leaf ipv4-source-address {
          type inet:ipv4-address;
        }
        container router {
          choice router {
            leaf router-name {
              tailf:cli-drop-node-name;
              type router-type;
            }
            leaf service {
              type string;
            }
          }
        }
      }
      container ptp {
        tailf:cli-add-mode;
        list alternate-profile {
          key "alternate-profile-name";
          leaf alternate-profile-name {
            type string;
          }
          leaf shutdown {
            type boolean;
          }
        }
        list clock {
          key "clock-id";
          leaf clock-id {
            type uint8;
          }
          leaf clock-mda {
            type string;
          }
          container clock-type {
            choice clock-type {
              leaf ordinary {
                type enumeration {
                  enum "master";
                  enum "slave";
                }
              }
              leaf boundary {
                type empty;
              }
              leaf transparent-e2e {
                type empty;
              }
            }
          }
          leaf domain {
            type uint32;
          }
          leaf dynamic-peers {
            type empty;
          }
          leaf priority1 {
            type uint8;
          }
          leaf priority2 {
            type uint8;
          }
          leaf profile {
            type enumeration {
              enum "ieee1588-2008";
              enum "itu-telecom-freq";
            }
          }
          leaf source-interface {
            type string;
          }
          list ptp-port {
            key "port-id";
            leaf port-id {
              type uint8;
            }
            leaf anno-rx-timeout {
              type uint8;
            }
            leaf log-anno-interval {
              type uint8;
            }
            leaf log-sync-interval {
              type int8;
            }
            list peer {
              key "peer-id";
              leaf peer-id {
                type uint8;
              }
              leaf description {
                type string;
              }
              leaf ip-address {
                type inet:ipv4-address;
              }
            }
            leaf unicast-negotiate {
              type boolean;
            }
            leaf shutdown {
              type boolean;
            }
          }
          leaf shutdown {
            type boolean;
          }
        }
        container clock-type {
          tailf:cli-compact-syntax;
          tailf:cli-sequence-commands {
            tailf:cli-reset-siblings;
          }
          leaf type {
            tailf:cli-drop-node-name;
            type enumeration {
              enum "boundary";
              enum "ordinary";
            }
          }
          leaf role {
            tailf:cli-drop-node-name;
            type enumeration {
              enum "master";
              enum "slave";
            }
          }
        }
        leaf domain {
          type uint32;
        }
        leaf domain-alt1 {
          tailf:alt-name "domain";
          type uint32;
        }
        leaf domain-alt2 {
          tailf:alt-name "domain";
          type uint32;
        }
        leaf domain-alt3 {
          tailf:alt-name "domain";
          type uint32;
        }
        leaf profile {
          type enumeration {
            enum "g8265dot1-2010";
            enum "ieee1588-2008";
            enum "g8275dot1-2014";
            enum "g8275dot2-2016";
          }
        }
        list peer {
          key "ip-address";
          leaf ip-address {
            type inet:ipv4-address;
          }
          leaf local-priority {
            type uint32;
          }
          leaf shutdown {
            type boolean;
          }
        }
        list port {
          key "port-id";
          leaf port-id {
            type string;
          }
          leaf alternate-profile {
            type string;
          }
          leaf master-only {
            type boolean;
          }
          leaf address {
            type string;
          }
          leaf local-priority {
            type uint8;
          }
          leaf shutdown {
            type boolean;
          }
        }
        leaf shutdown {
          type boolean;
        }
      }
      container resource-profile {
        tailf:cli-add-mode;
        container ingress-internal-tcam {
          tailf:cli-add-mode;
          presence "true";
          list eth-cfm {
            key "id";
            leaf id {
              type uint8;
            }
            leaf down-mep {
              type uint8;
            }
          }
          leaf qos-sap-egress-resource {
            type uint32;
          }
          list qos-sap-ingress-resource {
            key "id";
            leaf id {
              type uint32;
            }
          }
          leaf qos-network-ingress-resource {
            type uint32;
          }
          list acl-sap-ingress {
            key "id";
            leaf id {
              type uint32;
            }
          }
          container qos {
            tailf:cli-add-mode;
            presence "true";
          }
        }
        container egress-internal-tcam {
          tailf:cli-add-mode;
          presence "true";
          list qos-sap-egress-resource {
            key "id";
            leaf id {
              type uint32;
            }
          }
          list qos-sap-ingress-resource {
            key "id";
            leaf id {
              type uint32;
            }
          }
          list acl-sap-egress {
            key "id";
            leaf id {
              type uint32;
            }
          }
        }
        leaf g8032-control-sap-tags {
          type string;
        }
        container router {
          tailf:cli-add-mode;
          presence "true";
        }
        container decommission {
          tailf:cli-add-mode;
          presence "true";
        }
      }
      container resource {
        tailf:cli-add-mode;
        list ecmp-profile {
          tailf:cli-suppress-mode;
          tailf:cli-compact-syntax;
          key "id";
          leaf id {
            type uint32;
          }
          leaf type {
            tailf:cli-drop-node-name;
            type enumeration {
              enum "ip";
              enum "mpls";
            }
          }
          leaf links {
            type uint32;
          }
          leaf groups {
            type uint32;
          }
        }
      }
      container atm {
        leaf atm-location-id {
          type string;
        }
        container oam {
          leaf loopback-period {
            type string;
          }
          leaf retry-down {
            type string;
          }
          leaf retry-up {
            type string;
          }
        }
      }
      leaf boot-bad-exec {
        type string;
      }
      leaf boot-good-exec {
        type string;
      }
      list chassis-mode {
        key "chassis-mode";
        leaf chassis-mode {
          type string;
        }
        leaf force {
          tailf:cli-hide-in-submode;
          type empty;
        }
        list power-supply {
          tailf:cli-suppress-mode;
          key "power-supply-id power-supply-type";
          leaf power-supply-id {
            type string;
          }
          leaf power-supply-type {
            type enumeration {
              enum "dc";
            }
          }
        }
      }
      leaf clli-code {
        type string;
      }
      leaf config-backup {
        type string;
      }
      leaf contact {
        type string;
      }
      leaf coordinates {
        type string;
      }
      container cron {
        tailf:cli-add-mode;
        uses cron-schedule-grouping;
      }
      container dns {
        tailf:cli-add-mode;
        container address-pref {
          choice choice {
            leaf ipv4-only {
              type empty;
            }
            leaf ipv6-first {
              type empty;
            }
          }
        }
      }
      leaf enable-icmp-vse {
        type empty;
      }
      container ethernet {
        tailf:cli-add-mode;
        container efm-oam {
          leaf grace-tx-enable {
            type empty;
          }
        }
        leaf new-qinq-untagged-sap {
          type empty;
        }
      }
      leaf l4-load-balancing {
        type empty;
      }
      leaf lacp-system-priority {
        type string;
      }
      container lldp {
        tailf:cli-add-mode;
        leaf message-fast-tx {
          type string;
        }
        leaf message-fast-tx-init {
          type string;
        }
        leaf reinit-delay {
          type string;
        }
        leaf tx-credit-max {
          type string;
        }
        leaf tx-hold-multiplier {
          type string;
        }
        leaf tx-interval {
          type string;
        }
        leaf notification-interval {
          type string;
        }
        leaf shutdown {
          type boolean;
        }
      }
      container load-balancing {
        tailf:cli-add-mode;
        leaf l4-load-balancing {
          type empty;
        }
        container hash-poly {
          tailf:cli-compact-syntax;
          tailf:cli-sequence-commands;
          leaf ecmp {
            type enumeration {
              enum "poly1";
              enum "poly2";
              enum "poly3";
              enum "poly4";
              enum "poly5";
              enum "poly6";
            }
          }
          leaf lag {
            type enumeration {
              enum "poly1";
              enum "poly2";
              enum "poly3";
              enum "poly4";
              enum "poly5";
              enum "poly6";
            }
          }
        }
        leaf lsr-load-balancing {
          type enumeration {
            enum "lbl-only";
            enum "lbl-ip";
            enum "lbl-ip-l4-teid";
            enum "ip-only";
            enum "eth-encap-ip";
          }
        }
        leaf mc-enh-load-balancing {
          type empty;
        }
        leaf service-id-lag-hashing {
          type empty;
        }
        leaf system-ip-load-balancing {
          type empty;
        }
        container hash-algorithm {
          tailf:cli-add-mode;
          list polynomial {
            tailf:cli-suppress-mode;
            tailf:cli-compact-syntax;
            key "ptype";
            leaf ptype {
              type enumeration {
                enum "ecmp";
                enum "lag";
              }
            }
            leaf pval {
              tailf:cli-drop-node-name;
              type enumeration {
                enum "poly1";
                enum "poly2";
                enum "poly3";
                enum "poly4";
                enum "poly5";
                enum "poly6";
              }
            }
          }
        }
      }
      leaf location {
        type string;
      }
      container login-control {
        tailf:cli-add-mode;
        leaf exponential-backoff {
          type empty;
        }
        container ftp {
          tailf:cli-add-mode;
          leaf inbound-max-sessions {
            type uint8;
          }
        }
        leaf idle-timeout {
          type union {
            type uint16;
            type enumeration {
              enum "disable";
            }
          }
        }
        leaf login-banner {
          type empty;
        }
        container motd {
          choice choice {
            leaf url {
              type string;
            }
            leaf text {
              type string;
            }
          }
        }
        container pre-login-message {
          presence "present";
          tailf:cli-sequence-commands;
          tailf:cli-compact-syntax;
          leaf login-text-string {
            tailf:cli-drop-node-name;
            type string;
          }
          leaf name {
            type empty;
          }
        }
        container ssh {
          tailf:cli-add-mode;
          leaf disable-graceful-shutdown {
            type empty;
          }
          leaf inbound-max-sessions {
            type uint8;
          }
          leaf outbound-max-sessions {
            type uint8;
          }
          leaf ttl-security {
            type uint8;
          }
        }
        container telnet {
          tailf:cli-add-mode;
          leaf enable-graceful-shutdown {
            type empty;
          }
          leaf inbound-max-sessions {
            type uint8;
          }
          leaf outbound-max-sessions {
            type uint8;
          }
          leaf ttl-security {
            type string;
          }
        }
      }
      container loopback-no-svc-port {
        tailf:cli-compact-syntax;
        tailf:cli-sequence-commands {
          tailf:cli-reset-siblings;
        }
        leaf mac-swap {
          tailf:cli-optional-in-sequence;
          type empty;
        }
        leaf port-id {
          tailf:cli-drop-node-name;
          type string;
        }
      }
      container lsr-load-balancing {
        choice choice {
          leaf lbl-only {
            type empty;
          }
          leaf lbl-ip {
            type empty;
          }
          leaf ip-only {
            type empty;
          }
        }
      }
      container management-interface {
        tailf:cli-add-mode;
        container remote-management {
          tailf:cli-add-mode;
          leaf shutdown {
            type boolean;
          }
        }
        container cli {
          tailf:cli-add-mode;
          container classic-cli {
            tailf:cli-add-mode;
            leaf allow-immediate {
              type boolean;
            }
          }
          leaf-list cli-engine {
            tailf:cli-flat-list-syntax;
            type enumeration {
              enum "classic-cli";
              enum "md-cli";
            }
          }
          container md-cli {
            tailf:cli-add-mode;
            leaf auto-config-save {
              type empty;
            }
            container environment {
              tailf:cli-add-mode;
              container command-completion {
                tailf:cli-add-mode;
                leaf enter {
                  type boolean;
                }
                leaf space {
                  type boolean;
                }
                leaf tab {
                  type boolean;
                }
              }
              container console {
                tailf:cli-add-mode;
                leaf length {
                  type uint16;
                }
                leaf width {
                  type uint16;
                }
              }
              container message-severity-level {
                tailf:cli-add-mode;
                leaf cli {
                  type enumeration {
                    enum "warning";
                    enum "info";
                  }
                }
              }
              leaf more {
                type boolean;
              }
              container progress-indicator {
                tailf:cli-add-mode;
                leaf delay {
                  type uint32;
                }
                leaf shutdown {
                  type boolean;
                }
              }
              container prompt {
                tailf:cli-add-mode;
                leaf context {
                  type boolean;
                }
                leaf newline {
                  type boolean;
                }
                leaf timestamp {
                  type empty;
                }
                leaf uncommitted-changes-indicator {
                  type boolean;
                }
              }
              leaf time-display {
                type enumeration {
                  enum "local";
                  enum "utc";
                }
              }
            }
          }
        }
        leaf configuration-mode {
          type enumeration {
            enum "classic";
            enum "mixed";
            enum "model-driven";
          }
        }
        leaf schema-path {
          type string;
        }
        container yang-modules {
          tailf:cli-add-mode;
          leaf base-r13-modules {
            type boolean;
          }
          leaf nokia-modules {
            type boolean;
          }
          leaf nokia-submodules {
            type boolean;
          }
          leaf nokia-combined-modules {
            type boolean;
          }
        }
      }
      leaf mc-enh-load-balancing {
        type empty;
      }
      leaf mixed-mode {
        type empty;
      }
      leaf name {
        type string;
      }
      container netconf {
        tailf:cli-add-mode;
        leaf auto-config-save {
          type empty;
        }
        container capabilities {
          tailf:cli-add-mode;
          leaf candidate {
            type boolean;
          }
          leaf writable-running {
            type empty;
          }
        }
        leaf shutdown {
          type boolean;
        }
      }
      container persistence {
        tailf:cli-add-mode;
        container ancp {
          leaf description {
            type string;
          }
          leaf location {
            type string;
          }
        }
        container application-assurance {
          tailf:cli-add-mode;
          leaf description {
            type string;
          }
          leaf location {
            type string;
          }
        }
        container dhcp-server {
          tailf:cli-add-mode;
          leaf description {
            type string;
          }
          leaf location {
            type string;
          }
        }
        container nat-port-forwarding {
          tailf:cli-add-mode;
          leaf description {
            type string;
          }
          leaf location {
            type string;
          }
        }
        container subscriber-mgmt {
          tailf:cli-add-mode;
          leaf description {
            type string;
          }
          leaf location {
            type string;
          }
        }
      }
      list power-module {
        key "power-module-id";
        leaf power-module-id {
          type uint32;
        }
        leaf power-module-type {
          type enumeration {
            enum "ps-a-dc-6000";
            enum "ps-b-ac/hv-6000";
            enum "ixr-ac-hvdc-3000";
            enum "ixr-dc-3000";
          }
        }
        leaf shutdown {
          type boolean;
        }
      }
      container power-management {
        tailf:cli-add-mode;
        list peq {
          key "id";
          leaf id {
            type uint8;
          }
          leaf chassis {
            tailf:cli-hide-in-submode;
            type uint8;
          }
          leaf peq-type {
            type string;
          }
          leaf shutdown {
            type boolean;
          }
        }
        leaf mode {
          type enumeration {
            enum "none";
            enum "basic";
            enum "advanced";
          }
        }
        leaf power-safety-alert {
          type uint32;
        }
        leaf power-safety-level {
          type uint32;
        }
      }
      container script-control {
        tailf:cli-add-mode;
        list script {
          key "script-name";
          leaf script-name {
            type string32;
          }
          leaf owner {
            tailf:cli-hide-in-submode;
            type string32;
          }
          leaf description {
            type string;
          }
          leaf location {
            type string;
          }
          leaf shutdown {
            type boolean;
          }
        }
        list script-policy {
          key "script-name";
          leaf script-name {
            type string32;
          }
          leaf owner {
            tailf:cli-hide-in-submode;
            type string32;
          }
          leaf expire-time {
            type expire-time;
          }
          leaf lifetime {
            type expire-time;
          }
          leaf max-completed {
            type uint16;
          }
          leaf results {
            type string;
          }
          container script {
            tailf:cli-compact-syntax;
            tailf:cli-sequence-commands {
              tailf:cli-reset-siblings;
            }
            leaf script-name {
              tailf:cli-drop-node-name;
              type string32;
            }
            leaf owner {
              type string32;
            }
          }
          leaf shutdown {
            type boolean;
          }
        }
      }
      container snmp {
        tailf:cli-add-mode;
        leaf engineID {
          tailf:cli-case-insensitive;
          type string;
        }
        leaf general-port {
          type uint16;
        }
        leaf packet-size {
          type uint16;
        }
        container streaming {
          tailf:cli-add-mode;
          leaf shutdown {
            type boolean;
          }
        }
        leaf shutdown {
          type boolean;
        }
      }
      container rollback {
        tailf:cli-add-mode;
        leaf local-max-checkpoints {
          type uint8;
        }
        leaf remote-max-checkpoints {
          type uint8;
        }
        leaf rescue-location {
          type string;
        }
        leaf rollback-location {
          type string;
        }
      }
      leaf system-ip-load-balancing {
        type empty;
      }
      container time {
        tailf:cli-add-mode;
        leaf prefer-local-time {
          type empty;
        }
        container ntp {
          tailf:cli-add-mode;
          leaf authentication-check {
            type boolean;
          }
          list authentication-key {
            tailf:cli-suppress-mode;
            tailf:cli-compact-syntax;
            tailf:cli-sequence-commands {
              tailf:cli-reset-all-siblings;
            }
            key "key-id";
            leaf key-id {
              type uint8;
            }
            leaf key {
              type string;
            }
            leaf hash {
              tailf:cli-drop-node-name;
              tailf:cli-optional-in-sequence;
              type hash-method;
            }
            leaf type {
              type enumeration {
                enum "des";
                enum "message-digest";
              }
            }
          }
          container ntp-server {
            presence "true";
            leaf authenticate {
              type empty;
            }
          }
          list server {
            tailf:cli-suppress-mode;
            tailf:cli-compact-syntax;
            tailf:cli-sequence-commands {
              tailf:cli-reset-all-siblings;
            }
            key "address";
            leaf address {
              type union {
                type inet:ipv4-address;
                type inet:ipv6-address;
                type enumeration {
                  enum "ptp";
                }
              }
            }
            leaf key {
              tailf:cli-optional-in-sequence;
              type uint8;
            }
            leaf router {
              tailf:cli-optional-in-sequence;
              type router-type;
            }
            leaf version {
              tailf:cli-optional-in-sequence;
              type uint8;
            }
            leaf prefer {
              type empty;
            }
          }
          leaf shutdown {
            type boolean;
          }
        }
        container sntp {
          tailf:cli-add-mode;
          leaf broadcast-client {
            type empty;
          }
          list server-address {
            tailf:cli-suppress-mode;
            tailf:cli-compact-syntax;
            key "ip";
            leaf ip {
              type inet:ipv4-address;
            }
            leaf version {
              type uint8;
            }
            leaf mode {
              tailf:cli-drop-node-name;
              type enumeration {
                enum "normal";
                enum "preferred";
              }
            }
            leaf interval {
              type uint32;
            }
          }
          leaf shutdown {
            type boolean;
          }
        }
        container zone {
          tailf:cli-compact-syntax;
          tailf:cli-sequence-commands {
            tailf:cli-reset-all-siblings;
          }
          leaf name {
            tailf:cli-drop-node-name;
            type string;
          }
          leaf time {
            tailf:cli-drop-node-name;
            type string;
          }
        }
        list dst-zone {
          key "name";
          leaf name {
            type string;
          }
          container start {
            tailf:cli-sequence-commands;
            tailf:cli-compact-syntax;
            uses time-stamp;
          }
          container end {
            tailf:cli-sequence-commands;
            tailf:cli-compact-syntax;
            uses time-stamp;
          }
          leaf offset {
            type uint8;
          }
        }
      }
      container thresholds {
        tailf:cli-add-mode;
        container rmon {
          tailf:cli-add-mode;
          list alarm {
            tailf:cli-suppress-mode;
            tailf:cli-compact-syntax;
            tailf:cli-sequence-commands {
              tailf:cli-reset-siblings;
            }
            key "rmon-alarm-id";
            leaf rmon-alarm-id {
              type uint16;
            }
            leaf variable-oid {
              type string;
            }
            leaf interval {
              type uint32;
            }
            leaf sample-type {
              tailf:cli-drop-node-name;
              tailf:cli-optional-in-sequence;
              type enumeration {
                enum "absolute";
                enum "delta";
              }
            }
            leaf startup-alarm {
              tailf:cli-optional-in-sequence;
              type enumeration {
                enum "rising";
                enum "falling";
                enum "either";
              }
            }
            leaf rising-event {
              tailf:cli-optional-in-sequence;
              type uint16;
            }
            leaf rising-threshold {
              tailf:cli-optional-in-sequence;
              type int32;
            }
            leaf falling-event {
              tailf:cli-optional-in-sequence;
              type uint16;
            }
            leaf falling-threshold {
              tailf:cli-optional-in-sequence;
              type int32;
            }
            leaf owner {
              tailf:cli-optional-in-sequence;
              type string;
            }
          }
          list event {
            tailf:cli-suppress-mode;
            tailf:cli-compact-syntax;
            tailf:cli-sequence-commands {
              tailf:cli-reset-siblings;
            }
            key "rmon-event-id";
            leaf rmon-event-id {
              type uint16;
            }
            leaf event-type {
              tailf:cli-drop-node-name;
              tailf:cli-optional-in-sequence;
              type enumeration {
                enum "log";
                enum "trap";
                enum "both";
                enum "none";
              }
            }
            leaf description {
              tailf:cli-optional-in-sequence;
              type string;
            }
            leaf owner {
              type string;
            }
          }
        }

        grouping memory-use-grouping {
          leaf rising-threshold {
            type int32;
          }
          leaf falling-threshold {
            tailf:cli-optional-in-sequence;
            type int32;
          }
          leaf interval {
            type uint32;
          }
          leaf rmon-event-type {
            tailf:cli-drop-node-name;
            tailf:cli-optional-in-sequence;
            type enumeration {
              enum "log";
              enum "trap";
              enum "both";
              enum "none";
            }
          }
          leaf startup-alarm {
            tailf:cli-optional-in-sequence;
            type enumeration {
              enum "rising";
              enum "falling";
              enum "either";
            }
          }
        }
        container memory-use-alarm {
          tailf:cli-compact-syntax;
          tailf:cli-sequence-commands {
            tailf:cli-reset-siblings;
          }
          uses memory-use-grouping;
        }
        container memory-use-warn {
          tailf:cli-compact-syntax;
          tailf:cli-sequence-commands {
            tailf:cli-reset-siblings;
          }
          uses memory-use-grouping;
        }

        grouping cflash-cap-grouping {
          leaf cflash-id {
            type enumeration {
              enum "cf1:";
              enum "cf1-A:";
              enum "cf1-B:";
              enum "cf2:";
              enum "cf2-A:";
              enum "cf2-B:";
              enum "cf3:";
              enum "cf3-A:";
              enum "cf3-B:";
            }
          }
          leaf rising-threshold {
            type int32;
          }
          leaf falling-threshold {
            tailf:cli-optional-in-sequence;
            type int32;
          }
          leaf interval {
            type uint32;
          }
          leaf rmon-event-type {
            tailf:cli-drop-node-name;
            tailf:cli-optional-in-sequence;
            type enumeration {
              enum "log";
              enum "trap";
              enum "both";
              enum "none";
            }
          }
          leaf startup-alarm {
            tailf:cli-optional-in-sequence;
            type enumeration {
              enum "rising";
              enum "falling";
              enum "either";
            }
          }
        }
        list cflash-cap-alarm {
          tailf:cli-suppress-mode;
          tailf:cli-compact-syntax;
          tailf:cli-sequence-commands {
            tailf:cli-reset-siblings;
          }
          key "cflash-id";
          uses cflash-cap-grouping;
        }
        list cflash-cap-alarm-pct {
          tailf:cli-suppress-mode;
          tailf:cli-compact-syntax;
          tailf:cli-sequence-commands {
            tailf:cli-reset-siblings;
          }
          key "cflash-id";
          uses cflash-cap-grouping;
        }
        list cflash-cap-warn {
          tailf:cli-suppress-mode;
          tailf:cli-compact-syntax;
          tailf:cli-sequence-commands {
            tailf:cli-reset-siblings;
          }
          key "cflash-id";
          uses cflash-cap-grouping;
        }
        container kb-memory-use-alarm {
          tailf:cli-compact-syntax;
          tailf:cli-sequence-commands {
            tailf:cli-reset-all-siblings;
          }
          leaf rising-threshold {
            type int32;
          }
          leaf falling-threshold {
            tailf:cli-optional-in-sequence;
            type int32;
          }
          leaf interval {
            type uint32;
          }
          leaf rmon-event-type {
            tailf:cli-drop-node-name;
            tailf:cli-optional-in-sequence;
            type enumeration {
              enum "log";
              enum "trap";
              enum "both";
              enum "none";
            }
          }
          leaf startup-alarm {
            tailf:cli-optional-in-sequence;
            type enumeration {
              enum "rising";
              enum "falling";
              enum "either";
            }
          }
        }
      }
      list power-supply {
        tailf:cli-suppress-mode;
        tailf:cli-compact-syntax;
        tailf:cli-sequence-commands;
        key "power-supply-id";
        leaf power-supply-id {
          type string;
        }
        leaf type {
          tailf:cli-drop-node-name;
          type enumeration {
            enum "ac";
            enum "dc";
            enum "default";
            enum "none";
          }
        }
        leaf ac_type {
          tailf:cli-drop-node-name;
          type enumeration {
            enum "single";
            enum "multiple";
          }
        }
      }
      container qos {
        tailf:cli-add-mode;

        grouping access-rate-grouping {
          leaf value {
            tailf:cli-drop-node-name;
            type union {
              type uint32;
              type enumeration {
                enum "default";
              }
            }
          }
          leaf unshaped-sap-cir {
            type union {
              type enumeration {
                enum "max";
              }
              type uint32;
            }
          }
        }
        container access-ingress-aggregate-rate {
          tailf:cli-compact-syntax;
          tailf:cli-sequence-commands {
            tailf:cli-reset-siblings;
          }
          uses access-rate-grouping;
        }
        container network-ingress-aggregate-rate {
          tailf:cli-compact-syntax;
          tailf:cli-sequence-commands {
            tailf:cli-reset-siblings;
          }
          uses access-rate-grouping;
        }
      }
      container vsd {
        tailf:cli-add-mode;
        leaf system-id {
          tailf:cli-diff-create-before "../../xmpp/server" {
            tailf:xpath-root 3;
          }
          type string;
        }
      }
      container xmpp {
        tailf:cli-add-mode;
        list server {
          key "name";
          leaf name {
            type string;
          }
          leaf domain-name {
            tailf:cli-hide-in-submode;
            type string;
          }
          leaf router {
            tailf:cli-hide-in-submode;
            type string;
          }
          leaf shutdown {
            type boolean;
          }
        }
      }
      container security {
        tailf:cli-add-mode;
        container management {
          tailf:cli-add-mode;
          leaf allow-ftp {
            type boolean;
          }
          leaf allow-grpc {
            type boolean;
          }
          leaf allow-netconf {
            type boolean;
          }
          leaf allow-ssh {
            type boolean;
          }
          leaf allow-telnet {
            type boolean;
          }
          leaf allow-telnet6 {
            type boolean;
          }
        }
        container hash-control {
          tailf:cli-compact-syntax;
          tailf:cli-sequence-commands {
            tailf:cli-reset-siblings;
          }
          leaf read-version {
            tailf:cli-optional-in-sequence;
            type enumeration {
              enum "1";
              enum "2";
              enum "all";
            }
          }
          leaf write-version {
            type enumeration {
              enum "1";
              enum "2";
            }
          }
        }
        list keychain {
          key "keychain-name";
          leaf keychain-name {
            type string;
          }
          container direction {
            tailf:cli-add-mode;
            container bi {
              tailf:cli-add-mode;
              list entry {
                key "id";
                leaf id {
                  type uint32;
                }
                leaf key {
                  tailf:cli-hide-in-submode;
                  type string;
                }
                leaf method {
                  tailf:cli-drop-node-name;
                  tailf:cli-hide-in-submode;
                  type hash-method;
                }
                leaf algorithm {
                  tailf:cli-hide-in-submode;
                  type enumeration {
                    enum "aes-128-cmac-96";
                    enum "hmac-sha-1-96";
                    enum "password";
                    enum "message-digest";
                    enum "hmac-sha-1";
                    enum "hmac-sha-256";
                    enum "hmac-md5";
                  }
                }
                leaf begin-time {
                  tailf:cli-multi-value;
                  type string;
                }
                leaf option {
                  type enumeration {
                    enum "basic";
                    enum "isis-enhanced";
                  }
                }
                leaf tolerance {
                  type union {
                    type enumeration {
                      enum "forever";
                    }
                    type uint32;
                  }
                }
                leaf shutdown {
                  type boolean;
                }
              }
            }
          }
          leaf description {
            type string;
          }
          leaf shutdown {
            type boolean;
          }
        }
        container management-interface {
          tailf:cli-add-mode;
          container classic-cli {
            tailf:cli-add-mode;
            leaf read-algorithm {
              type hash-hash2-all-hash;
            }
            leaf write-algorithm {
              type hash-hash2-cleartext;
            }
          }
          container grpc {
            tailf:cli-add-mode;
            leaf hash-algorithm {
              type hash-hash2-cleartext;
            }
          }
          container md-cli {
            tailf:cli-add-mode;
            leaf hash-algorithm {
              type hash-hash2-cleartext;
            }
          }
          container netconf {
            tailf:cli-add-mode;
            leaf hash-algorithm {
              type hash-hash2-cleartext;
            }
          }
        }
        container pki {
          tailf:cli-add-mode;
          container certificate-expiration-warning {
            tailf:cli-compact-syntax;
            tailf:cli-sequence-commands {
              tailf:cli-reset-all-siblings;
            }
            leaf hours {
              tailf:cli-drop-node-name;
              type uint16;
            }
            leaf repeat {
              type uint16;
            }
          }
          container crl-expiration-warning {
            tailf:cli-compact-syntax;
            tailf:cli-sequence-commands {
              tailf:cli-reset-all-siblings;
            }
            leaf hours {
              tailf:cli-drop-node-name;
              type uint16;
            }
            leaf repeat {
              type uint16;
            }
          }
          list ca-profile {
            key "name";
            leaf name {
              type string32;
            }
            leaf description {
              type string;
            }
            leaf cert-file {
              type string;
            }
            container cmpv2 {
              tailf:cli-add-mode;
              leaf accept-unprotected-errormsg {
                type empty;
              }
              leaf accept-unprotected-pkiconf {
                type empty;
              }
              leaf same-recipnonce-for-pollreq {
                type empty;
              }
              leaf always-set-sender-for-ir {
                type empty;
              }
              leaf http-response-timeout {
                type uint32;
              }
              container key-list {
                tailf:cli-add-mode;
                list key {
                  tailf:cli-suppress-mode;
                  key "reference";
                  leaf password {
                    tailf:cli-drop-node-name;
                    tailf:cli-prefix-key;
                    type string;
                  }
                  leaf hashing {
                    tailf:cli-drop-node-name;
                    tailf:cli-prefix-key;
                    type enumeration {
                      enum "hash";
                      enum "hash2";
                      enum "custom";
                    }
                  }
                  leaf reference {
                    type uint32;
                  }
                }
              }
              leaf url {
                type string;
              }
              leaf response-signing-cert {
                type string;
              }
            }
            leaf crl-file {
              type string;
            }
            leaf revocation-check {
              type enumeration {
                enum "crl";
                enum "crl-optional";
              }
            }
            container auto-crl-update {
              tailf:cli-add-mode;
              container pre-update-time {
                tailf:cli-compact-syntax;
                tailf:cli-sequence-commands {
                  tailf:cli-reset-all-siblings;
                }
                leaf days {
                  tailf:cli-optional-in-sequence;
                  type uint32;
                }
                leaf hrs {
                  tailf:cli-optional-in-sequence;
                  type uint32;
                }
              }
              leaf schedule-type {
                type enumeration {
                  enum "periodic";
                  enum "next-update-based";
                }
              }
              container crl-urls {
                tailf:cli-add-mode;
                list url-entry {
                  key "entry-id";
                  leaf entry-id {
                    type uint8;
                  }
                  leaf file-transmission-profile {
                    type string32;
                  }
                  leaf url {
                    type string;
                  }
                }
              }
              leaf shutdown {
                type boolean;
              }
            }
            leaf shutdown {
              type boolean;
            }
          }
        }
        list profile {
          key "name";
          leaf name {
            type string;
          }
          leaf default-action {
            type enumeration {
              enum "deny-all";
              enum "permit-all";
              enum "none";
              enum "read-only-all";
            }
          }
          list entry {
            key "entry-id";
            leaf entry-id {
              type uint16;
            }
            leaf action {
              type enumeration {
                enum "permit";
                enum "deny";
                enum "read-only";
                enum "none";
              }
            }
            leaf description {
              type string;
            }
            leaf match {
              type string;
            }
          }
          leaf li {
            type empty;
          }
          container netconf {
            tailf:cli-add-mode;
            container base-op-authorization {
              tailf:cli-add-mode;
              leaf action {
                type empty;
              }
              leaf cancel-commit {
                type empty;
              }
              leaf close-session {
                type empty;
              }
              leaf commit-op {
                type empty;
              }
              leaf commit {
                type empty;
              }
              leaf copy-config {
                type empty;
              }
              leaf create-subscription {
                type empty;
              }
              leaf delete-config {
                type empty;
              }
              leaf discard-changes {
                type empty;
              }
              leaf edit-config {
                type empty;
              }
              leaf get {
                type empty;
              }
              leaf get-config {
                type empty;
              }
              leaf get-data {
                type empty;
              }
              leaf get-schema {
                type empty;
              }
              leaf kill-session {
                type empty;
              }
              leaf lock {
                type empty;
              }
              leaf validate {
                type empty;
              }
            }
          }
          container grpc {
            tailf:cli-add-mode;
            container rpc-authorization {
              tailf:cli-add-mode;
              leaf gnoi-cert-mgmt-rotate {
                type enumeration {
                  enum "permit";
                  enum "deny";
                }
              }
              leaf gnoi-cert-mgmt-install {
                type enumeration {
                  enum "permit";
                  enum "deny";
                }
              }
              leaf gnoi-cert-mgmt-getcert {
                type enumeration {
                  enum "permit";
                  enum "deny";
                }
              }
              leaf gnoi-cert-mgmt-revoke {
                type enumeration {
                  enum "permit";
                  enum "deny";
                }
              }
              leaf gnoi-cert-mgmt-cangenerate {
                type enumeration {
                  enum "permit";
                  enum "deny";
                }
              }
              leaf gnoi-file-get {
                type enumeration {
                  enum "permit";
                  enum "deny";
                }
              }
              leaf gnoi-file-put {
                type enumeration {
                  enum "permit";
                  enum "deny";
                }
              }
              leaf gnoi-file-stat {
                type enumeration {
                  enum "permit";
                  enum "deny";
                }
              }
              leaf gnoi-file-remove {
                type enumeration {
                  enum "permit";
                  enum "deny";
                }
              }
              leaf gnoi-system-setpackage {
                type enumeration {
                  enum "permit";
                  enum "deny";
                }
              }
              leaf gnoi-system-switchcontrolprocessor {
                type enumeration {
                  enum "permit";
                  enum "deny";
                }
              }
              leaf gnoi-system-reboot {
                type enumeration {
                  enum "permit";
                  enum "deny";
                }
              }
              leaf gnoi-system-rebootstatus {
                type enumeration {
                  enum "permit";
                  enum "deny";
                }
              }
              leaf gnoi-system-cancelreboot {
                type enumeration {
                  enum "permit";
                  enum "deny";
                }
              }
              leaf gnmi-capabilities {
                type enumeration {
                  enum "permit";
                  enum "deny";
                }
              }
              leaf gnmi-get {
                type enumeration {
                  enum "permit";
                  enum "deny";
                }
              }
              leaf gnmi-set {
                type enumeration {
                  enum "permit";
                  enum "deny";
                }
              }
              leaf gnmi-subscribe {
                type enumeration {
                  enum "permit";
                  enum "deny";
                }
              }
              leaf md-cli-session {
                type enumeration {
                  enum "permit";
                  enum "deny";
                }
              }
              leaf rib-api-modify {
                type enumeration {
                  enum "permit";
                  enum "deny";
                }
              }
              leaf rib-api-getversion {
                type enumeration {
                  enum "permit";
                  enum "deny";
                }
              }
            }
          }
          leaf ssh-max-sessions {
            type uint32;
          }
        }
        container password {
          tailf:cli-add-mode;
          container admin-password {
            tailf:cli-compact-syntax;
            tailf:cli-sequence-commands {
              tailf:cli-reset-siblings;
            }
            leaf password {
              tailf:cli-drop-node-name;
              type string;
            }
            leaf scheme {
              tailf:cli-drop-node-name;
              type hash-method;
            }
          }
          leaf aging {
            type uint16;
          }
          container complexity-rules {
            tailf:cli-add-mode;
            leaf minimum-length {
              type uint8;
            }
            container required {
              tailf:cli-compact-syntax;
              leaf lowercase {
                type uint8;
              }
              leaf uppercase {
                type uint8;
              }
              leaf numeric {
                type uint8;
              }
              leaf special-character {
                type uint8;
              }
            }
            leaf allow-user-name {
              type empty;
            }
          }
          container health-check {
            leaf interval {
              type uint16;
            }
            leaf no {
              type empty;
            }
          }
          container health-check-alt {
            tailf:alt-name "health-check";
            leaf interval {
              type uint16;
            }
          }
          leaf-list authentication-order {
            tailf:cli-flat-list-syntax;
            ordered-by user;
            type enumeration {
              enum "local";
              enum "radius";
              enum "tacplus";
              enum "ldap";
              enum "exit-on-reject";
            }
          }
          container attempts {
            tailf:cli-compact-syntax;
            tailf:cli-sequence-commands {
              tailf:cli-reset-all-siblings;
            }
            leaf count {
              tailf:cli-drop-node-name;
              type uint8;
            }
            leaf time {
              tailf:cli-break-sequence-commands;
              type uint8;
            }
            leaf lockout {
              type uint8;
            }
          }
        }
        container radius {
          tailf:cli-add-mode;
          leaf authorization {
            type empty;
          }
          leaf accounting {
            type empty;
          }
          list server {
            tailf:cli-suppress-mode;
            tailf:cli-compact-syntax;
            key "server-index";
            leaf server-index {
              type uint32;
            }
            leaf address {
              mandatory true;
              type inet:ipv4-address;
            }
            leaf secret {
              mandatory true;
              type string;
            }
            leaf type {
              tailf:cli-drop-node-name;
              type hash-method;
            }
          }
          leaf shutdown {
            type boolean;
          }
        }
        container tech-support {
          tailf:cli-add-mode;
          leaf ts-location {
            type string;
          }
        }
        container tls {
          tailf:cli-add-mode;
          list cert-profile {
            key "profile-name";
            leaf profile-name {
              type string;
            }
            list entry {
              tailf:cli-diff-create-before "../shutdown" {
                tailf:xpath-root 3;
              }
              key "entry-id";
              leaf entry-id {
                type uint8;
              }
              leaf cert {
                type string;
              }
              leaf key {
                type string;
              }
              container send-chain {
                tailf:cli-add-mode;
                list ca-profile {
                  tailf:cli-suppress-mode;
                  key "profile";
                  leaf profile {
                    type string32;
                  }
                }
              }
            }
            leaf shutdown {
              type boolean;
            }
          }
          list server-cipher-list {
            key "name";
            leaf name {
              type string;
            }
            list cipher {
              tailf:cli-suppress-mode;
              key "index";
              leaf index {
                type uint32;
              }
              leaf name {
                type enumeration {
                  enum "tls-rsa-with3des-ede-cbc-sha";
                  enum "tls-rsa-with-aes128-cbc-sha";
                  enum "tls-rsa-with-aes256-cbc-sha";
                  enum "tls-rsa-with-aes128-cbc-sha256";
                  enum "tls-rsa-with-aes256-cbc-sha256";
                }
              }
            }
          }
          list server-tls-profile {
            key "name";
            leaf name {
              type string;
            }
            leaf cert-profile {
              type string;
            }
            leaf cipher-list {
              type string;
            }
            leaf shutdown {
              type boolean;
            }
          }
        }
        container tacplus {
          tailf:cli-add-mode;
          container accounting {
            presence "true";
            leaf record-type {
              type enumeration {
                enum "start-stop";
                enum "stop-only";
              }
            }
          }
          container authorization {
            presence "true";
            leaf use-prix-lvl {
              type empty;
            }
          }
          leaf interactive-authentication {
            type empty;
          }
          container priv-lvl-map {
            tailf:cli-add-mode;
            list priv-lvl {
              tailf:cli-suppress-mode;
              key "lvl";
              leaf lvl {
                type uint8;
              }
              leaf user-profile {
                tailf:cli-drop-node-name;
                type union {
                  type enumeration {
                    enum "default";
                  }
                  type string;
                }
              }
            }
          }
          leaf route-preference {
            type enumeration {
              enum "both";
              enum "inband";
              enum "outband";
            }
          }
          list server {
            tailf:cli-suppress-mode;
            tailf:cli-compact-syntax;
            key "server-index";
            leaf server-index {
              type uint8;
            }
            leaf address {
              type union {
                type inet:ipv4-address;
                type inet:ipv6-address;
              }
            }
            leaf secret {
              type string;
            }
            leaf hash {
              tailf:cli-drop-node-name;
              type hash-method;
            }
            leaf port {
              type uint16;
            }
          }
          leaf timeout {
            type uint32;
          }
          leaf use-default-template {
            type empty;
          }
          leaf shutdown {
            type boolean;
          }
        }
        leaf telnet-server {
          type empty;
        }
        leaf telnet6-server {
          type empty;
        }
        leaf ftp-server {
          type empty;
        }
        leaf per-peer-queuing {
          type empty;
        }
        container snmp {
          tailf:cli-add-mode;
          container access {
            list group {
              tailf:cli-suppress-mode;
              tailf:cli-delete-when-empty;
              tailf:cli-compact-syntax;
              tailf:cli-sequence-commands {
                tailf:cli-reset-all-siblings;
              }
              key "name security-model security-level";
              leaf name {
                type string;
              }
              leaf security-model {
                type enumeration {
                  enum "usm";
                  enum "snmpv1";
                  enum "snmpv2c";
                  enum "snmpv2ac";
                }
              }
              leaf security-level {
                type enumeration {
                  enum "auth-no-privacy";
                  enum "no-auth-no-privacy";
                  enum "privacy";
                }
              }
              container context {
                tailf:cli-optional-in-sequence;
                tailf:cli-compact-syntax;
                leaf context-name {
                  tailf:cli-drop-node-name;
                  type string;
                }
                leaf match {
                  tailf:cli-optional-in-sequence;
                  tailf:cli-drop-node-name;
                  type enumeration {
                    enum "prefix";
                    enum "exact";
                  }
                }
                uses read-write-notify;
              }
              container read {
                tailf:cli-drop-node-name;
                tailf:cli-compact-syntax;
                tailf:cli-optional-in-sequence;
                uses read-write-notify;
              }

              grouping read-write-notify {
                leaf read {
                  tailf:cli-break-sequence-commands;
                  type string32;
                }
                leaf write {
                  type string32;
                }
                leaf notify {
                  type string32;
                }
              }
            }
          }
          list src-access-list {
            key "list-name";
            leaf list-name {
              type string32;
            }
            list src-host {
              tailf:cli-suppress-mode;
              key "name";
              leaf name {
                type string;
              }
              leaf address {
                type union {
                  type inet:ipv4-address;
                  type inet:ipv6-address;
                  type string;
                }
              }
            }
          }
          uses snmp-community-grouping;
          list usm-community {
            tailf:cli-suppress-mode;
            tailf:cli-compact-syntax;
            tailf:cli-sequence-commands {
              tailf:cli-reset-siblings;
            }
            key "name type";
            leaf name {
              type string;
            }
            leaf type {
              tailf:cli-drop-node-name;
              tailf:cli-optional-in-sequence;
              type hash-method;
            }
            leaf group {
              type string;
            }
            leaf src-access-list {
              type string32;
            }
          }
          container attempts {
            tailf:cli-compact-syntax;
            tailf:cli-sequence-commands {
              tailf:cli-reset-all-siblings;
            }
            leaf count {
              tailf:cli-drop-node-name;
              type uint8;
            }
            leaf time {
              tailf:cli-optional-in-sequence;
              type uint8;
            }
            leaf lockout {
              type uint8;
            }
          }
          list view {
            key "name subtree";
            leaf name {
              type string32;
            }
            leaf subtree {
              type string;
            }
            container mask {
              tailf:cli-compact-syntax;
              tailf:cli-sequence-commands {
                tailf:cli-reset-siblings;
              }
              leaf mask-value {
                tailf:cli-drop-node-name;
                type string;
              }
              leaf type {
                type enumeration {
                  enum "excluded";
                }
              }
            }
          }
        }
        container source-address {
          tailf:cli-add-mode;
          list application {
            tailf:cli-suppress-mode;
            key "name";
            leaf name {
              type net-application;
            }
            leaf address {
              tailf:cli-drop-node-name;
              type union {
                type inet:ipv4-address;
                type string;
              }
            }
          }
          list application6 {
            tailf:cli-suppress-mode;
            key "name";
            leaf name {
              type net-application;
            }
            leaf address {
              tailf:cli-drop-node-name;
              type union {
                type inet:ipv6-address;
              }
            }
          }
        }
        container ssh {
          tailf:cli-add-mode;
          leaf preserve-key {
            type empty;
          }
          leaf server-shutdown {
            type empty;
          }
          container key-re-exchange {
            tailf:cli-add-mode;
            container server {
              tailf:cli-add-mode;
              leaf mbytes {
                type uint32;
              }
              leaf minutes {
                type uint32;
              }
              leaf shutdown {
                type boolean;
              }
            }
            container client {
              tailf:cli-add-mode;
              leaf mbytes {
                type uint32;
              }
              leaf minutes {
                type uint32;
              }
              leaf shutdown {
                type boolean;
              }
            }
          }
          leaf permit-empty-passwords {
            type boolean;
          }
          leaf version {
            type enumeration {
              enum "1";
              enum "2";
              enum "1-2";
            }
          }

          grouping cipher-list-grouping {
            list cipher {
              tailf:cli-suppress-mode;
              key "index";
              leaf index {
                type uint8;
              }
              leaf name {
                type string;
              }
            }
          }
          list client-cipher-list {
            key "protocol-version";
            uses cipher-list-grouping;
            leaf protocol-version {
              type enumeration {
                enum "1";
                enum "2";
              }
            }
          }
          container client-cipher-list-alt {
            tailf:alt-name "client-cipher-list";
            tailf:cli-add-mode;
            uses cipher-list-grouping;
          }
          list server-cipher-list {
            key "protocol-version";
            leaf protocol-version {
              type enumeration {
                enum "1";
                enum "2";
              }
            }
            uses cipher-list-grouping;
          }
          container server-cipher-list-alt {
            tailf:alt-name "server-cipher-list";
            tailf:cli-add-mode;
            uses cipher-list-grouping;
          }
          container server-kex-list {
            tailf:cli-add-mode;
            list kex {
              tailf:cli-suppress-mode;
              key "kex-id";
              unique "name";
              leaf kex-id {
                type uint32;
              }
              leaf name {
                type enumeration {
                  enum "diffie-hellman-group16-sha512";
                  enum "diffie-hellman-group14-sha256";
                  enum "diffie-hellman-group14-sha1";
                  enum "diffie-hellman-group-exchange-sha1";
                  enum "diffie-hellman-group1-sha1";
                }
              }
            }
          }
          container client-kex-list {
            tailf:cli-add-mode;
            list kex {
              tailf:cli-suppress-mode;
              key "kex-id";
              unique "name";
              leaf kex-id {
                type uint32;
              }
              leaf name {
                type enumeration {
                  enum "diffie-hellman-group16-sha512";
                  enum "diffie-hellman-group14-sha256";
                  enum "diffie-hellman-group14-sha1";
                  enum "diffie-hellman-group-exchange-sha1";
                  enum "diffie-hellman-group1-sha1";
                }
              }
            }
          }
          container server-mac-list {
            tailf:cli-add-mode;
            presence "true";
            list mac {
              tailf:cli-suppress-mode;
              key "index";
              leaf index {
                type uint8;
              }
              leaf name {
                type string;
              }
            }
          }
          container client-mac-list {
            tailf:cli-add-mode;
            presence "true";
            list mac {
              tailf:cli-suppress-mode;
              key "index";
              leaf index {
                type uint8;
              }
              leaf name {
                type string;
              }
            }
          }
        }
        list user-template {
          key "user-template-id";
          leaf user-template-id {
            type enumeration {
              enum "tacplus_default";
              enum "radius_default";
              enum "ldap_default";
            }
          }
          leaf-list access {
            tailf:cli-flat-list-syntax;
            type enumeration {
              enum "console";
              enum "snmp";
              enum "ftp";
              enum "li";
              enum "netconf";
              enum "grpc";
            }
          }
          leaf profile {
            type string;
          }
        }
        list user {
          key "user-id";
          leaf user-id {
            type string;
          }
          leaf-list access {
            tailf:cli-flat-list-syntax;
            type enumeration {
              enum "console";
              enum "snmp";
              enum "ftp";
              enum "li";
              enum "netconf";
              enum "grpc";
            }
          }
          container console {
            tailf:cli-add-mode;
            leaf cannot-change-password {
              type empty;
            }
            leaf login-exec {
              type string;
            }
            container disable {
              leaf member {
                type union {
                  type enumeration {
                    enum "default";
                    enum "administrative";
                  }
                  type string;
                }
              }
            }
            list member {
              tailf:cli-suppress-mode;
              key "name";
              leaf name {
                type string;
              }
            }
            leaf new-password-at-login {
              type empty;
            }
          }
          leaf home-directory {
            type string;
          }
          container password {
            tailf:cli-compact-syntax;
            tailf:cli-sequence-commands {
              tailf:cli-reset-siblings;
            }
            leaf id {
              tailf:cli-drop-node-name;
              type string;
            }
            leaf method {
              tailf:cli-drop-node-name;
              type hash-method;
            }
          }
          leaf restricted-to-home {
            type empty;
          }
          container public-keys {
            tailf:cli-add-mode;
            container rsa {
              tailf:cli-add-mode;
              list rsa-key {
                key "rsa-public-key-id";
                leaf rsa-public-key-id {
                  type uint8;
                }
                leaf description {
                  type string;
                }
                leaf key-value {
                  type string;
                }
              }
            }
            container ecdsa {
              tailf:cli-add-mode;
              list ecdsa-key {
                key "rsa-public-key-id";
                leaf rsa-public-key-id {
                  type uint8;
                }
                leaf description {
                  type string;
                }
                leaf key-value {
                  type string;
                }
              }
            }
          }
          list rsa-key {
            tailf:cli-suppress-mode;
            tailf:cli-compact-syntax;
            tailf:cli-sequence-commands;
            key "key-id";
            leaf key-id {
              type uint8;
            }
            leaf key {
              tailf:cli-drop-node-name;
              type string;
            }
          }
          container snmp {
            tailf:cli-add-mode;
            container authentication {
              tailf:cli-compact-syntax;
              tailf:cli-sequence-commands {
                tailf:cli-reset-siblings;
              }
              leaf none {
                tailf:cli-optional-in-sequence;
                type empty;
              }
              leaf hash {
                tailf:cli-optional-in-sequence;
                type empty;
              }
              leaf hash2 {
                tailf:cli-optional-in-sequence;
                type empty;
              }
              leaf auth-type {
                tailf:cli-drop-node-name;
                type enumeration {
                  enum "md5";
                  enum "sha";
                  enum "hmac-md5-96";
                  enum "hmac-sha2-256";
                }
              }
              leaf key-1 {
                tailf:cli-drop-node-name;
                type string;
              }
              leaf privacy {
                type enumeration {
                  enum "none";
                  enum "des-key";
                  enum "aes-128-cfb-key";
                  enum "cbc-des";
                  enum "cfb128-aes-256";
                }
              }
              leaf key-2 {
                tailf:cli-drop-node-name;
                type string;
              }
              leaf hashval {
                tailf:cli-drop-node-name;
                type string;
              }
            }
            leaf group {
              type string;
            }
          }
        }
        container disable {
          leaf user {
            type enumeration {
              enum "admin";
            }
          }
        }
        container cpu-protection {
          tailf:cli-add-mode;
          leaf link-specific-rate {
            type union {
              type uint32;
              type enumeration {
                enum "max";
              }
            }
          }
          list policy {
            key "policy-id";
            leaf policy-id {
              type uint16;
            }
            leaf overall-rate {
              type union {
                type enumeration {
                  enum "max";
                }
                type uint32;
              }
            }
            leaf out-profile-rate {
              type union {
                type uint32;
                type enumeration {
                  enum "max";
                }
              }
            }
            leaf description {
              type string;
            }
            leaf per-source-rate {
              type union {
                type enumeration {
                  enum "max";
                }
                type uint16;
              }
            }
          }
          container protocol-protection {
            presence "true";
            tailf:cli-compact-syntax;
            leaf allow-sham-links {
              type empty;
            }
            leaf block-pim-tunneled {
              type empty;
            }
          }
          leaf port-overall-rate {
            type union {
              type enumeration {
                enum "max";
              }
              type uint32;
            }
          }
        }
        container dist-cpu-protection {
          tailf:cli-add-mode;
          list policy {
            key "policy-id";
            leaf policy-id {
              type string;
            }
            leaf description {
              type string;
            }
            leaf type {
              tailf:cli-hide-in-submode;
              type enumeration {
                enum "port";
                enum "access-network";
              }
            }
            list static-policer {
              key "policy-name";
              leaf policy-name {
                type string;
              }
              leaf description {
                type string;
              }
              container rate {
                tailf:cli-compact-syntax;
                choice rate {
                  container kbps {
                    tailf:cli-compact-syntax;
                    tailf:cli-sequence-commands {
                      tailf:cli-reset-all-siblings;
                    }
                    leaf kilobits-per-second {
                      tailf:cli-drop-node-name;
                      type union {
                        type enumeration {
                          enum "max";
                        }
                        type uint32;
                      }
                    }
                    leaf mbs {
                      tailf:cli-optional-in-sequence;
                      type union {
                        type uint32;
                        type enumeration {
                          enum "default";
                        }
                      }
                    }
                    leaf unit {
                      tailf:cli-drop-node-name;
                      type enumeration {
                        enum "bytes";
                        enum "kilobytes";
                      }
                    }
                  }
                  container packets {
                    tailf:cli-compact-syntax;
                    tailf:cli-sequence-commands {
                      tailf:cli-reset-all-siblings;
                    }
                    leaf ppi {
                      tailf:cli-drop-node-name;
                      type union {
                        type enumeration {
                          enum "max";
                        }
                        type uint32;
                      }
                    }
                    leaf within {
                      type uint32;
                    }
                    leaf initial-delay {
                      type uint8;
                    }
                  }
                }
              }
              container exceed-action {
                tailf:cli-compact-syntax;

                grouping hold-down-grouping {
                  leaf hold-down {
                    type union {
                      type uint16;
                      type enumeration {
                        enum "none";
                        enum "indefinite";
                      }
                    }
                  }
                }
                choice exceed-action {
                  container discard {
                    presence "true";
                    uses hold-down-grouping;
                  }
                  container low-priority {
                    presence "true";
                    uses hold-down-grouping;
                  }
                }
              }
            }
            list protocol {
              key "name";
              leaf name {
                type union {
                  type enumeration {
                    enum "arp";
                    enum "dhcp";
                    enum "http-redirect";
                    enum "icmp";
                    enum "igmp";
                    enum "mld";
                    enum "ndis";
                    enum "pppoe-pppoa";
                    enum "all-unspecified";
                    enum "mpls-ttl";
                    enum "bfd-cpm";
                    enum "bgp";
                    enum "eth-cfm";
                    enum "isis";
                    enum "ldp";
                    enum "ospf";
                    enum "pim";
                    enum "rsvp";
                  }
                  type string;
                }
              }
              container enforcement {
                tailf:cli-compact-syntax;
                tailf:cli-sequence-commands {
                  tailf:cli-reset-all-siblings;
                }
                leaf policy-type {
                  tailf:cli-drop-node-name;
                  type enumeration {
                    enum "static";
                    enum "dynamic";
                  }
                }
                leaf policy-name {
                  tailf:cli-drop-node-name;
                  type string;
                }
              }
            }
          }
        }
        container cpm-filter {
          tailf:cli-add-mode;
          leaf default-action {
            type enumeration {
              enum "accept";
              enum "drop";
            }
          }
          container ip-filter {
            tailf:cli-add-mode;
            list entry {
              key "entry-id";
              leaf entry-id {
                type uint16;
              }
              container action {
                tailf:cli-compact-syntax;
                choice action-choice {
                  leaf drop {
                    type empty;
                  }
                  leaf accept {
                    type empty;
                  }
                  leaf queue {
                    type uint32;
                  }
                }
              }
              leaf description {
                type string;
              }
              leaf log {
                type uint16;
              }
              container match {
                tailf:cli-add-mode;
                presence "true";
                leaf protocol {
                  tailf:cli-hide-in-submode;
                  type protocol;
                }
                leaf dscp {
                  type dscp-type;
                }
                container dst-ip {
                  tailf:cli-compact-syntax;
                  tailf:cli-sequence-commands;
                  uses filter-match-ip-grouping;
                }
                container dst-port {
                  tailf:cli-compact-syntax;
                  tailf:cli-sequence-commands;
                  uses cpm-filter-match-port-grouping;
                }
                leaf fragment {
                  type boolean;
                }
                leaf icmp-code {
                  type union {
                    type uint32;
                    type enumeration {
                      enum "none";
                      enum "network-unreachable";
                      enum "host-unreachable";
                      enum "protocol-unreachable";
                      enum "port-unreachable";
                      enum "fragmentation-needed";
                      enum "source-route-failed";
                      enum "dest-network-unknown";
                      enum "dest-host-unknown";
                      enum "src-host-isolated";
                      enum "network-unreachable-for-tos";
                      enum "host-unreachable-for-tos";
                    }
                  }
                }
                leaf icmp-type {
                  type icmp-type;
                }
                container ip-option {
                  tailf:cli-compact-syntax;
                  leaf value {
                    tailf:cli-drop-node-name;
                    type uint8;
                  }
                  leaf mask {
                    tailf:cli-drop-node-name;
                    type uint8;
                  }
                }
                leaf multiple-option {
                  type boolean;
                }
                leaf option-present {
                  type boolean;
                }
                container port {
                  tailf:cli-compact-syntax;
                  tailf:cli-sequence-commands;
                  uses cpm-filter-match-port-grouping;
                }
                leaf router {
                  type union {
                    type uint32;
                    type string;
                  }
                }
                container src-ip {
                  tailf:cli-compact-syntax;
                  tailf:cli-sequence-commands;
                  uses filter-match-ip-grouping;
                }
                container src-port {
                  tailf:cli-compact-syntax;
                  tailf:cli-sequence-commands;
                  uses cpm-filter-match-port-grouping;
                }
                leaf tcp-ack {
                  type boolean;
                }
                leaf tcp-syn {
                  type boolean;
                }
              }
            }
            leaf shutdown {
              type boolean;
            }
          }
          container ipv6-filter {
            tailf:cli-add-mode;
            list entry {
              key "entry-id";
              leaf entry-id {
                type uint16;
              }
              container action {
                tailf:cli-compact-syntax;
                choice action-choice {
                  leaf drop {
                    type empty;
                  }
                  leaf accept {
                    type empty;
                  }
                  leaf queue {
                    type uint32;
                  }
                }
              }
              leaf description {
                type string;
              }
              leaf log {
                type uint16;
              }
              container match {
                tailf:cli-add-mode;
                presence "true";
                leaf fragment {
                  type enumeration {
                    enum "true";
                    enum "false";
                  }
                }
                leaf next-header {
                  tailf:cli-hide-in-submode;
                  type protocol;
                }
                leaf dscp {
                  type dscp-type;
                }
                container dst-ip {
                  tailf:cli-compact-syntax;
                  tailf:cli-sequence-commands;
                  uses filter-match-ipv6-grouping;
                }
                container dst-port {
                  tailf:cli-compact-syntax;
                  tailf:cli-sequence-commands;
                  uses cpm-filter-match-port-grouping;
                }
                leaf flow-label {
                  type uint32;
                }
                leaf hop-by-hop-opt {
                  type boolean;
                }
                leaf icmp-code {
                  type uint32;
                }
                leaf icmp-type {
                  type icmpv6-type;
                }
                container port {
                  tailf:cli-compact-syntax;
                  tailf:cli-sequence-commands;
                  uses cpm-filter-match-port-grouping;
                }
                leaf router {
                  type union {
                    type uint32;
                    type string;
                  }
                }
                container src-ip {
                  tailf:cli-compact-syntax;
                  tailf:cli-sequence-commands;
                  uses filter-match-ipv6-grouping;
                }
                container src-port {
                  tailf:cli-compact-syntax;
                  tailf:cli-sequence-commands;
                  uses cpm-filter-match-port-grouping;
                }
                leaf tcp-ack {
                  type boolean;
                }
                leaf tcp-syn {
                  type boolean;
                }
              }
            }
            leaf shutdown {
              type boolean;
            }
          }
        }
        container cpm-queue {
          tailf:cli-add-mode;
          list queue {
            key "queue-id";
            leaf queue-id {
              type uint32;
            }
            leaf cbs {
              type union {
                type uint32;
                type enumeration {
                  enum "max";
                }
              }
            }
            leaf mbs {
              type union {
                type uint32;
                type enumeration {
                  enum "max";
                }
              }
            }
            container rate {
              tailf:cli-compact-syntax;
              tailf:cli-sequence-commands;
              leaf value {
                tailf:cli-drop-node-name;
                type union {
                  type enumeration {
                    enum "max";
                  }
                  type uint32;
                }
              }
              leaf cir {
                type union {
                  type enumeration {
                    enum "max";
                  }
                  type uint32;
                }
              }
            }
          }
        }
        container management-access-filter {
          tailf:cli-add-mode;
          container ip-filter {
            tailf:cli-add-mode;
            tailf:cli-delete-when-empty;
            presence "true";
            leaf default-action {
              type filter-action;
            }
            list entry {
              key "entry-name";
              leaf entry-name {
                type uint32;
              }
              leaf action {
                type filter-action;
              }
              leaf description {
                type string;
              }
              leaf log {
                type empty;
              }
              container src-ip {
                tailf:cli-compact-syntax;
                choice format-choice {
                  container address-netmask {
                    tailf:cli-drop-node-name;
                    tailf:cli-compact-syntax;
                    leaf address {
                      tailf:cli-drop-node-name;
                      type union {
                        type tailf:ipv4-address-and-prefix-length;
                        type inet:ipv4-address;
                      }
                    }
                    leaf netmask {
                      tailf:cli-drop-node-name;
                      type inet:ipv4-address;
                    }
                  }
                  leaf ip-prefix-list {
                    type string;
                  }
                }
              }
              container dst-port {
                tailf:cli-compact-syntax;
                tailf:cli-sequence-commands {
                  tailf:cli-reset-siblings;
                }
                leaf port {
                  tailf:cli-drop-node-name;
                  type uint16;
                }
                leaf mask {
                  tailf:cli-drop-node-name;
                  tailf:cli-optional-in-sequence;
                  type uint16;
                }
              }
              leaf src-port {
                type string;
              }
              container l4-src-port {
                tailf:cli-compact-syntax;
                tailf:cli-sequence-commands {
                  tailf:cli-reset-all-siblings;
                }
                leaf port {
                  tailf:cli-drop-node-name;
                  type uint32;
                }
                leaf mask {
                  tailf:cli-drop-node-name;
                  tailf:cli-optional-in-sequence;
                  type uint32;
                }
              }
              leaf router {
                type router-type;
              }
              leaf protocol {
                type union {
                  type enumeration {
                    enum "none";
                    enum "icmp";
                    enum "igmp";
                    enum "ip";
                    enum "tcp";
                    enum "egp";
                    enum "igp";
                    enum "udp";
                    enum "rdp";
                    enum "ipv6";
                    enum "ipv6-route";
                    enum "ipv6-frag";
                    enum "idrp";
                    enum "rsvp";
                    enum "gre";
                    enum "ipv6-icmp";
                    enum "ipv6-no-nxt";
                    enum "ipv6-opts";
                    enum "iso-ip";
                    enum "eigrp";
                    enum "ospf-igp";
                    enum "ether-ip";
                    enum "encap";
                    enum "pnni";
                    enum "pim";
                    enum "vrrp";
                    enum "l2tp";
                    enum "stp";
                    enum "ptp";
                    enum "isis";
                    enum "crtp";
                    enum "crudp";
                    enum "sctp";
                    enum "*";
                  }
                  type uint8;
                }
              }
            }
            leaf shutdown {
              type boolean;
            }
          }
          container ipv6-filter {
            tailf:cli-add-mode;
            tailf:cli-delete-when-empty;
            presence "true";
            leaf default-action {
              type filter-action;
            }
            list entry {
              key "entry-name";
              leaf entry-name {
                type string;
              }
              leaf action {
                type filter-action;
              }
              leaf description {
                type string;
              }
              container src-ip {
                tailf:cli-compact-syntax;
                choice format-choice {
                  leaf address {
                    tailf:cli-drop-node-name;
                    type union {
                      type tailf:ipv6-address-and-prefix-length;
                      type inet:ipv6-address;
                    }
                  }
                  leaf ipv6-prefix-list {
                    type string;
                  }
                }
              }
              leaf src-port {
                type string;
              }
              container dst-port {
                tailf:cli-compact-syntax;
                tailf:cli-sequence-commands {
                  tailf:cli-reset-siblings;
                }
                leaf port {
                  tailf:cli-drop-node-name;
                  type uint16;
                }
                leaf mask {
                  tailf:cli-drop-node-name;
                  tailf:cli-optional-in-sequence;
                  type uint16;
                }
              }
              leaf next-header {
                type union {
                  type enumeration {
                    enum "udp";
                    enum "tcp";
                    enum "ipv6-icmp";
                  }
                  type string;
                }
              }
              leaf log {
                type empty;
              }
              container l4-src-port {
                tailf:cli-compact-syntax;
                tailf:cli-sequence-commands {
                  tailf:cli-reset-all-siblings;
                }
                leaf port {
                  tailf:cli-drop-node-name;
                  type uint32;
                }
                leaf mask {
                  tailf:cli-drop-node-name;
                  tailf:cli-optional-in-sequence;
                  type uint32;
                }
              }
              leaf router {
                type string;
              }
            }
            leaf shutdown {
              type boolean;
            }
          }
        }
        container vprn-aaa-server {
          tailf:cli-add-mode;
          leaf inband {
            type service-id;
          }
          leaf outband {
            type service-id;
          }
          leaf vprn {
            type service-id;
          }
        }
        container vprn-network-exceptions {
          tailf:cli-compact-syntax;
          presence "true";
          tailf:cli-delete-when-empty;
          leaf number {
            tailf:cli-drop-node-name;
            type uint32;
          }
          leaf seconds {
            tailf:cli-drop-node-name;
            type uint32;
          }
        }
        container usb-port {
          tailf:cli-add-mode;
          tailf:cli-delete-when-empty;
          presence "true";
          leaf shutdown {
            type boolean;
          }
        }
      }
      container sync-if-timing {
        tailf:cli-add-mode;
        leaf description {
          type string;
        }
        container gnss {
          tailf:cli-add-mode;
          leaf shutdown {
            type boolean;
          }
        }
        container ptp {
          tailf:cli-add-mode;
          leaf ql-override {
            type enumeration {
              enum "prs";
              enum "stu";
              enum "st2";
              enum "tnc";
              enum "st3e";
              enum "st3";
              enum "prc";
              enum "ssua";
              enum "ssub";
              enum "sec";
            }
          }
          leaf shutdown {
            type boolean;
          }
        }
        container bits {
          tailf:cli-add-mode;
          container input {
            tailf:cli-add-mode;
            leaf shutdown {
              type boolean;
            }
          }
        }
        container external {
          tailf:cli-add-mode;
          container input-interface {
            tailf:cli-add-mode;
            leaf type {
              type enumeration {
                enum "2048Khz-G703";
                enum "5Mhz";
                enum "10Mhz";
              }
            }
            leaf shutdown {
              type boolean;
            }
          }
        }
        leaf ql-selection {
          type empty;
        }
        container ref-order {
          tailf:cli-compact-syntax;
          tailf:cli-sequence-commands {
            tailf:cli-reset-siblings;
          }

          typedef ref-order-type {
            type enumeration {
              enum "bits";
              enum "ptp";
              enum "ref1";
              enum "ref2";
              enum "synce";
              enum "external";
              enum "gnss";
            }
          }
          leaf first {
            tailf:cli-drop-node-name;
            type ref-order-type;
          }
          leaf second {
            tailf:cli-drop-node-name;
            type ref-order-type;
          }
          leaf third {
            tailf:cli-drop-node-name;
            type ref-order-type;
          }
          leaf fourth {
            tailf:cli-drop-node-name;
            type ref-order-type;
          }
          leaf fifth {
            tailf:cli-drop-node-name;
            type ref-order-type;
          }
        }

        grouping ref-grouping {
          leaf ql-override {
            type enumeration {
              enum "prs";
              enum "stu";
              enum "st2";
              enum "tnc";
              enum "st3e";
              enum "st3";
              enum "prc";
              enum "ssua";
              enum "ssub";
              enum "sec";
              enum "eec1";
              enum "eec2";
            }
          }
          leaf source-port {
            type string;
          }
          leaf source-ptp-clock {
            type uint8;
          }
          leaf shutdown {
            type boolean;
          }
        }
        container ref1 {
          tailf:cli-add-mode;
          uses ref-grouping;
        }
        container ref2 {
          tailf:cli-add-mode;
          uses ref-grouping;
        }
        leaf revert {
          type empty;
        }
      }
      list software-repository {
        key "name";
        leaf name {
          type string;
        }
        leaf description {
          type string;
        }
        leaf primary-location {
          type string;
        }
        leaf secondary-location {
          type string;
        }
        leaf tertiary-location {
          type string;
        }
      }
      container telemetry {
        tailf:cli-add-mode;
        list destination-group {
          key "name";
          leaf name {
            type string;
          }
          leaf allow-unsecure-connection {
            type empty;
          }
          leaf description {
            type string;
          }
          list destination {
            key "address port";
            leaf address {
              type union {
                type inet:ipv4-address;
                type string;
              }
            }
            leaf port {
              type uint32;
            }
            container router-instance {
              leaf router-id {
                tailf:cli-drop-node-name;
                type router-type;
              }
            }
          }
          container tcp-keepalive {
            tailf:cli-add-mode;
            leaf shutdown {
              type boolean;
            }
          }
        }
        container sensor-groups {
          tailf:cli-add-mode;
          list sensor-group {
            key "name";
            leaf name {
              type string;
            }
            leaf description {
              type string;
            }
            list path {
              key "path-string";
              leaf path-string {
                type string;
              }
            }
          }
        }
        container persistent-subscriptions {
          tailf:cli-add-mode;
          list subscription {
            key "name";
            leaf name {
              type string;
            }
            leaf description {
              type string;
            }
            leaf encoding {
              type enumeration {
                enum "json";
                enum "bytes";
                enum "proto";
                enum "json-ietf";
              }
            }
            leaf sample-interval {
              type uint32;
            }
            leaf local-source-address {
              type string;
            }
            leaf destination-group {
              type string;
            }
            leaf mode {
              type enumeration {
                enum "target-defined";
                enum "on-change";
                enum "sample";
              }
            }
            leaf sensor-group {
              type string;
            }
            leaf shutdown {
              type boolean;
            }
          }
        }
      }
    }
    container redundancy {
      tailf:ncs-device-type "cli-ned";
      tailf:display-when "not(../../ncs:module) or ../../ncs:module[ncs:name='netsim-ned-alu-sr']";
      tailf:cli-add-mode;
      container bgp-evpn-multi-homing {
        tailf:cli-add-mode;
        leaf boot-timer {
          type uint32;
        }
        leaf es-activation-timer {
          type uint32;
        }
      }
      container mgmt-ethernet {
        leaf revert {
          type uint16;
        }
      }
      container multi-chassis {
        tailf:cli-add-mode;
        list peer {
          key "address";
          leaf address {
            type inet:ipv4-address;
          }
          leaf description {
            type string;
          }
          leaf peer-name {
            type string;
          }
          container mc-lag {
            tailf:cli-add-mode;
            presence "true";
            leaf hold-on-neighbor-failure {
              type uint8;
            }
            leaf keep-alive-interval {
              type uint16;
            }
            list lag {
              tailf:cli-compact-syntax;
              tailf:cli-suppress-mode;
              key "lag-id";
              leaf lag-id {
                type uint32;
              }
              leaf lacp-key {
                type uint16;
              }
              leaf system-id {
                type ieee-mac;
              }
              leaf remote-lag {
                type uint16;
              }
              leaf system-priority {
                type uint16;
              }
              leaf source-bmac-lsb {
                type union {
                  type enumeration {
                    enum "use-lacp-key";
                  }
                  type uint16;
                  type ieee-mac;
                }
              }
            }
            leaf shutdown {
              type boolean;
            }
          }
          leaf source-address {
            type inet:ipv4-address;
          }
          container sync {
            tailf:cli-add-mode;
            presence "true";
            list port {
              key "port-id";
              leaf port-id {
                type string;
              }
              list range {
                tailf:cli-suppress-mode;
                key "range-val";
                leaf range-val {
                  type string;
                }
                leaf sync-tag {
                  type string;
                }
              }
              leaf sync-tag {
                tailf:cli-hide-in-submode;
                type string;
              }
            }
            leaf local-dhcp-server {
              type empty;
            }
            leaf python {
              type empty;
            }
            leaf srrp {
              type empty;
            }
            leaf-list sub-mgmt {
              tailf:cli-flat-list-syntax;
              type enumeration {
                enum "ipoe";
                enum "pppoe";
              }
            }
            leaf igmp {
              type empty;
            }
            leaf igmp-snooping {
              type empty;
            }
            leaf shutdown {
              type boolean;
            }
          }
          leaf shutdown {
            type boolean;
          }
        }
      }
      leaf rollback-sync {
        type empty;
      }
      leaf synchronize {
        type enumeration {
          enum "boot-env";
          enum "config";
        }
      }
    }
    list connection-profile-vlan {
      tailf:ncs-device-type "cli-ned";
      tailf:display-when "not(../ncs:module) or ../ncs:module[ncs:name='netsim-ned-alu-sr']";
      tailf:cli-diff-create-before "/alu:service/vpls/sap" {
        tailf:xpath-root 3;
      }
      tailf:cli-diff-create-before "/alu:service/epipe/sap" {
        tailf:xpath-root 3;
      }
      tailf:cli-diff-create-before "/alu:service/cpipe/sap" {
        tailf:xpath-root 3;
      }
      key "conn-prof-id";
      leaf conn-prof-id {
        type uint32;
      }
      leaf description {
        type string;
      }
      list vlan-range {
        key "from to";
        tailf:cli-suppress-mode;
        unique "from";
        leaf from {
          type uint32;
        }
        leaf to {
          type uint32;
        }
      }
    }
    list eth-ring {
      tailf:ncs-device-type "cli-ned";
      tailf:display-when "not(../ncs:module) or ../ncs:module[ncs:name='netsim-ned-alu-sr']";
      key "index";
      leaf index {
        type uint32;
      }
      leaf description {
        type string;
      }
      leaf revert-time {
        type uint32;
      }
      leaf rpl-node {
        type enumeration {
          enum "owner";
          enum "nbr";
        }
      }
      list path {
        key "path-id";
        leaf path-id {
          type enumeration {
            enum "a";
            enum "b";
          }
        }
        leaf port {
          tailf:cli-drop-node-name;
          tailf:cli-hide-in-submode;
          type string;
        }
        leaf raps-tag {
          tailf:cli-hide-in-submode;
          type string;
        }
        leaf rpl-end {
          type empty;
        }
        container eth-cfm {
          tailf:cli-add-mode;
          uses eth-cfm {
            augment "mep" {
              leaf control-mep {
                type empty;
              }
            }
          }
        }
        leaf shutdown {
          type boolean;
        }
      }
      leaf shutdown {
        type boolean;
      }
    }
    container filter {
      tailf:ncs-device-type "cli-ned";
      tailf:display-when "not(../../ncs:module) or ../../ncs:module[ncs:name='netsim-ned-alu-sr']";
      tailf:cli-add-mode;
      list ip-filter {
        key "ip-filter-name";
        leaf ip-filter-name {
          type filter-id;
        }
        leaf name {
          tailf:cli-hide-in-submode;
          type string;
        }
        leaf chain-to-system-filter {
          type empty;
        }
        list embed-filter {
          tailf:cli-compact-syntax;
          tailf:cli-suppress-mode;
          tailf:cli-sequence-commands {
            tailf:cli-reset-siblings;
          }
          key "embed-filter-name";
          leaf embed-filter-name {
            type filter-id;
          }
          leaf router {
            tailf:cli-optional-in-sequence;
            type router-type;
          }
          leaf offset {
            type uint32;
          }
          leaf status {
            tailf:cli-drop-node-name;
            type enumeration {
              enum "active";
              enum "inactive";
            }
          }
        }
        leaf default-action {
          type enumeration {
            enum "drop";
            enum "forward";
          }
        }
        leaf filter-name {
          type string;
        }
        leaf scope {
          type enumeration {
            enum "template";
            enum "exclusive";
            enum "embedded";
            enum "system";
          }
        }
        leaf description {
          type string;
        }
        list entry {
          uses ip-filter-entry-grouping;
          key "entry-name";
          leaf pbr-down-action-override {
            type enumeration {
              enum "drop";
              enum "forward";
              enum "filter-default-action";
            }
          }

          grouping ip-filter-entry-action-grouping-old {
            choice action-choice {
              container drop {
                presence "true";
                tailf:cli-compact-syntax;
                tailf:cli-sequence-commands {
                  tailf:cli-reset-all-siblings;
                }
                container packet-length {
                  tailf:cli-flatten-container;
                  tailf:cli-compact-syntax;
                  tailf:cli-sequence-commands {
                    tailf:cli-reset-siblings;
                  }
                  leaf rule {
                    tailf:cli-drop-node-name;
                    type enumeration {
                      enum "eq";
                      enum "gt";
                      enum "lt";
                    }
                  }
                  leaf length {
                    tailf:cli-drop-node-name;
                    type uint32;
                  }
                }
              }
              leaf nat {
                type empty;
              }
              leaf http-redirect {
                type string;
              }
              container forward {
                presence "true";
                container next-hop {
                  choice next-hop-choice {
                    case na {
                      leaf ip-address {
                        tailf:cli-drop-node-name;
                        type inet:ipv4-address;
                      }
                    }
                    case nb {
                      leaf indirect {
                        type inet:ipv4-address;
                      }
                    }
                    case nc {
                      leaf interface {
                        type string;
                      }
                    }
                  }
                }
                leaf router {
                  type router-type;
                }
                leaf sap {
                  type string;
                }
                leaf sdp {
                  type string;
                }
                leaf redirect-policy {
                  type string;
                }
              }
            }
          }

          grouping ip-filter-entry-action-grouping-new {
            choice action-choice {
              container drop {
                tailf:cli-compact-syntax;
                presence "true";
                container packet-length {
                  tailf:cli-flatten-container;
                  tailf:cli-compact-syntax;
                  choice rule-range {
                    container rule {
                      tailf:cli-drop-node-name;
                      tailf:cli-compact-syntax;
                      leaf rule {
                        tailf:cli-drop-node-name;
                        type enumeration {
                          enum "eq";
                          enum "gt";
                          enum "lt";
                        }
                      }
                      leaf length {
                        tailf:cli-drop-node-name;
                        type uint32;
                      }
                    }
                    container range {
                      tailf:cli-compact-syntax;
                      leaf start {
                        tailf:cli-drop-node-name;
                        type uint32;
                      }
                      leaf end {
                        tailf:cli-drop-node-name;
                        type uint32;
                      }
                    }
                  }
                }
              }
              leaf nat {
                type empty;
              }
              leaf http-redirect {
                type string;
              }
              container forward {
                tailf:cli-compact-syntax;
                presence "true";
                container vprn-target {
                  tailf:cli-flatten-container;
                  leaf bgp-nh {
                    type inet:ipv4-address;
                  }
                }
                container next-hop {
                  tailf:cli-flatten-container;
                  choice next-hop-choice {
                    case na {
                      leaf ip-address {
                        tailf:cli-drop-node-name;
                        type inet:ipv4-address;
                      }
                    }
                    case nb {
                      leaf indirect {
                        type inet:ipv4-address;
                      }
                    }
                    case nc {
                      leaf interface {
                        type string;
                      }
                    }
                  }
                }
                leaf router {
                  type service-id;
                }
                leaf lsp {
                  type string;
                }
                leaf sap {
                  type string;
                }
                leaf sdp {
                  type string;
                }
                leaf redirect-policy {
                  type string;
                }
              }
              leaf rate-limit {
                type uint32;
              }
            }
          }
          container action-flat {
            tailf:cli-compact-syntax;
            tailf:alt-name "action";
            uses ip-filter-entry-action-grouping-old;
          }
          container action {
            tailf:cli-add-mode;
            presence "true";
            uses ip-filter-entry-action-grouping-new;
          }
          leaf egress-pbr {
            type enumeration {
              enum "default-load-balancing";
              enum "l4-load-balancing";
            }
          }
        }
      }
      list ipv6-filter {
        key "ip-filter-name";
        leaf ip-filter-name {
          type filter-id;
        }
        leaf name {
          tailf:cli-hide-in-submode;
          type string;
        }
        leaf chain-to-system-filter {
          type empty;
        }
        leaf default-action {
          type enumeration {
            enum "forward";
            enum "drop";
          }
        }
        leaf filter-name {
          type string;
        }
        list embed-filter {
          tailf:cli-compact-syntax;
          tailf:cli-suppress-mode;
          tailf:cli-sequence-commands;
          key "embed-filter-name";
          leaf embed-filter-name {
            type filter-id;
          }
          leaf router {
            tailf:cli-optional-in-sequence;
            type router-type;
          }
          leaf offset {
            type uint32;
          }
          leaf status {
            tailf:cli-drop-node-name;
            type enumeration {
              enum "active";
              enum "inactive";
            }
          }
        }
        leaf scope {
          type enumeration {
            enum "embedded";
            enum "exclusive";
            enum "template";
            enum "system";
          }
        }
        leaf description {
          type string;
        }
        list entry {
          uses ipv6-filter-entry-grouping;
          key "entry-name";
          leaf log {
            type uint32;
          }
          leaf action {
            type enumeration {
              enum "drop";
              enum "forward";
            }
          }
          container action-mode {
            tailf:alt-name "action";
            tailf:cli-add-mode;
            presence "true";
            leaf action {
              tailf:cli-drop-node-name;
              type enumeration {
                enum "drop";
                enum "forward";
              }
            }
            container rate-limit {
              tailf:cli-compact-syntax;
              leaf value {
                tailf:cli-drop-node-name;
                type uint32;
              }
            }
          }
        }
      }
      list mac-filter {
        key "mac-filter-name";
        leaf mac-filter-name {
          type filter-id;
        }
        leaf name {
          tailf:cli-hide-in-submode;
          type string;
        }
        leaf default-action {
          type enumeration {
            enum "drop";
            enum "forward";
          }
        }
        leaf scope {
          type enumeration {
            enum "exclusive";
            enum "template";
          }
        }
        leaf description {
          type string;
        }
        leaf filter-name {
          type string;
        }
        list entry {
          key "entry-name";
          leaf entry-name {
            type string;
          }
          leaf description {
            type string;
          }
          container match {
            tailf:cli-add-mode;
            container dot1p {
              tailf:cli-compact-syntax;
              tailf:cli-sequence-commands {
                tailf:cli-reset-siblings;
              }
              leaf dot1p-value {
                tailf:cli-drop-node-name;
                type uint8;
              }
              leaf dot1p-mask {
                tailf:cli-drop-node-name;
                type uint8;
              }
            }
            container dst-mac {
              tailf:cli-compact-syntax;
              tailf:cli-sequence-commands {
                tailf:cli-reset-siblings;
              }
              leaf mac {
                tailf:cli-drop-node-name;
                type string;
              }
              leaf mask {
                tailf:cli-drop-node-name;
                type string;
              }
            }
            container src-mac {
              tailf:cli-compact-syntax;
              leaf mac {
                tailf:cli-drop-node-name;
                type string;
              }
              leaf mask {
                tailf:cli-drop-node-name;
                type string;
              }
            }
            leaf frame-type {
              tailf:cli-hide-in-submode;
              type enumeration {
                enum "802dot3";
                enum "802dot2-llc";
                enum "802dot2-snap";
                enum "ethernet_II";
              }
            }
            leaf etype {
              type string;
            }
          }
          container action-flat {
            tailf:cli-compact-syntax;
            tailf:alt-name "action";
            choice choice {
              case drop {
                leaf drop {
                  type empty;
                }
              }
              case forward {
                leaf forward {
                  type empty;
                }
                leaf sap {
                  type string;
                }
              }
            }
          }
          container action {
            tailf:cli-add-mode;
            tailf:cli-compact-syntax;
            choice choice {
              case drop {
                leaf drop {
                  type empty;
                }
              }
              case forward {
                leaf forward {
                  type empty;
                }
                leaf sap {
                  type string;
                }
              }
            }
          }
          leaf log {
            type uint32;
          }
        }
      }
      container match-list {
        tailf:cli-add-mode;

        grouping apply-path-grouping {
          container apply-path {
            tailf:cli-add-mode;
            list bgp-peers {
              tailf:cli-compact-syntax;
              tailf:cli-suppress-mode;
              key "id";
              leaf id {
                type uint32;
              }
              leaf router {
                type router-type;
              }
              leaf group {
                type string;
              }
              leaf neighbor {
                type string;
              }
            }
          }
        }
        list ip-prefix-list {
          key "name";
          leaf name {
            type string;
          }
          leaf description {
            type string;
          }
          list prefix {
            tailf:cli-suppress-mode;
            key "pfx";
            leaf pfx {
              type tailf:ipv4-address-and-prefix-length;
            }
          }
          list prefix-exclude {
            tailf:cli-suppress-mode;
            key "address";
            leaf address {
              type tailf:ipv4-address-and-prefix-length;
            }
          }
          uses apply-path-grouping;
        }
        list ipv6-prefix-list {
          key "name";
          leaf name {
            type string;
          }
          leaf description {
            type string;
          }
          list prefix {
            tailf:cli-suppress-mode;
            key "pfx";
            leaf pfx {
              type tailf:ipv6-address-and-prefix-length;
            }
          }
          uses apply-path-grouping;
        }
        list port-list {
          key "port-list-name";
          leaf port-list-name {
            type string32;
          }
          leaf description {
            type string;
          }
          container port {
            list port {
              tailf:cli-drop-node-name;
              tailf:cli-suppress-mode;
              tailf:cli-delete-when-empty;
              key "port-number";
              leaf port-number {
                type uint16;
              }
            }
            list range {
              tailf:cli-suppress-mode;
              tailf:cli-delete-when-empty;
              key "start end";
              leaf start {
                type uint16;
              }
              leaf end {
                type uint16;
              }
            }
          }
        }
      }
      list log {
        key "log-id";
        leaf log-id {
          type uint32;
        }
        leaf description {
          type string;
        }
        container destination {
          choice choice {
            leaf memory {
              type uint32;
            }
            leaf syslog {
              type uint32;
            }
          }
        }
        leaf wrap-around {
          type boolean;
        }
        leaf shutdown {
          type boolean;
        }
      }
      list redirect-policy {
        key "redirect-policy-name";
        leaf redirect-policy-name {
          type string;
        }
        leaf description {
          type string;
        }
        list destination {
          key "ip-address";
          leaf ip-address {
            type inet:ipv4-address;
          }
          leaf description {
            type string;
          }
          container ping-test {
            tailf:cli-add-mode;
            presence "true";
            container drop-count {
              tailf:cli-compact-syntax;
              tailf:cli-sequence-commands {
                tailf:cli-reset-siblings;
              }
              leaf consecutive-failures {
                tailf:cli-drop-node-name;
                type uint8;
              }
              leaf hold-down {
                type uint32;
              }
            }
            leaf interval {
              type uint8;
            }
            leaf timeout {
              type uint8;
            }
          }
          leaf priority {
            type uint8;
          }
          leaf shutdown {
            type boolean;
          }
        }
        leaf shutdown {
          type boolean;
        }
      }
      container system-filter {
        tailf:cli-add-mode;
        leaf ip {
          type filter-id;
        }
        leaf ipv6 {
          type filter-id;
        }
      }
    }
    container test-oam {
      tailf:ncs-device-type "cli-ned";
      tailf:display-when "not(../../ncs:module) or ../../ncs:module[ncs:name='netsim-ned-alu-sr']";
      tailf:cli-add-mode;
      container link-measurement {
        tailf:cli-add-mode;
        list measurement-template {
          key "template-name";
          leaf template-name {
            type string;
          }
          container aggregate-sample-window {
            tailf:cli-add-mode;
            leaf multiplier {
              type uint32;
            }
            leaf window-integrity {
              type uint32;
            }
            container threshold {
              tailf:cli-add-mode;
              leaf absolute {
                type uint32;
              }
              leaf relative {
                type uint32;
              }
            }
          }
          leaf delay {
            type enumeration {
              enum "min";
              enum "max";
              enum "avg";
            }
          }
          leaf description {
            type string;
          }
          leaf interval {
            type uint32;
          }
          container twamp-light {
            tailf:cli-add-mode;
            leaf dest-udp-port {
              type uint32;
            }
            leaf dscp {
              type dscp-type;
            }
            leaf fc {
              type fc-name;
            }
          }
          leaf shutdown {
            type boolean;
          }
        }
      }
      container twamp {
        tailf:cli-add-mode;
        container twamp-test-pdu {
          tailf:cli-add-mode;
          leaf ipv4-timestamping {
            type enumeration {
              enum "central";
              enum "fp";
            }
          }
          leaf ipv6-timestamping {
            type enumeration {
              enum "central";
              enum "fp";
            }
          }
        }
        container server {
          tailf:cli-add-mode;
          leaf inactivity-timeout {
            type uint16;
          }
          leaf max-conn-server {
            type uint8;
          }
          leaf max-sess-server {
            type uint8;
          }
          list prefix {
            key "ip-prefix";
            leaf ip-prefix {
              type tailf:ip-address-and-prefix-length;
            }
            leaf description {
              type string;
            }
            leaf max-conn-prefix {
              type uint8;
            }
            leaf max-sess-prefix {
              type uint8;
            }
          }
          leaf shutdown {
            type boolean;
          }
        }
      }
    }
    container mirror {
      tailf:ncs-device-type "cli-ned";
      tailf:display-when "not(../../ncs:module) or ../../ncs:module[ncs:name='netsim-ned-alu-sr']";
      tailf:cli-add-mode;
      list mirror-dest {
        key "service-id";
        uses service-id-grouping;
        leaf name {
          tailf:cli-hide-in-submode;
          type string;
        }
        list pcap {
          key "name";
          leaf name {
            type union {
              type uint32;
              type string;
            }
          }
          leaf file-url {
            type string;
          }
        }
        leaf mirror-type {
          tailf:cli-hide-in-submode;
          type enumeration {
            enum "ether";
            enum "frame-relay";
            enum "ppp";
            enum "ip-only";
            enum "atm-sdu";
            enum "satop-e1";
            enum "satop-t1";
            enum "cesopsn";
            enum "cesopsn-cas";
          }
        }
        leaf type {
          tailf:cli-hide-in-submode;
          type enumeration {
            enum "ether";
            enum "frame-relay";
            enum "ppp";
            enum "ip-only";
            enum "atm-sdu";
            enum "satop-e1";
            enum "satop-t1";
            enum "cesopsn";
            enum "cesopsn-cas";
          }
        }
        leaf description {
          type string;
        }
        leaf enable-port-id {
          type empty;
        }
        container encap {
          tailf:cli-add-mode;
          list layer-3-encap {
            key "encap";
            leaf encap {
              type enumeration {
                enum "ip-udp-shim";
                enum "ip-gre";
              }
            }
            leaf direction-bit {
              type empty;
            }
            container gateway {
              tailf:cli-add-mode;
              container ip {
                tailf:cli-sequence-commands;
                tailf:cli-compact-syntax;
                leaf src {
                  type inet:ipv4-address;
                }
                leaf dest {
                  type inet:ipv4-address;
                }
              }
              container udp {
                tailf:cli-sequence-commands;
                tailf:cli-compact-syntax;
                leaf src {
                  type inet:port-number;
                }
                leaf dest {
                  type inet:port-number;
                }
              }
            }
          }
        }
        list endpoint {
          key "endpoint-name";
          leaf endpoint-name {
            type string32;
          }
          leaf description {
            type string;
          }
          leaf revert-time {
            type union {
              type uint16;
              type enumeration {
                enum "infinite";
              }
            }
          }
        }
        leaf fc {
          type fc-name;
        }
        container isa-aa-group {
          tailf:cli-compact-syntax;
          tailf:cli-sequence-commands {
            tailf:cli-reset-all-siblings;
          }
          leaf aa-group-id {
            tailf:cli-drop-node-name;
            type uint8;
          }
          leaf traffic-direction {
            tailf:cli-drop-node-name;
            type enumeration {
              enum "from-subscriber";
              enum "to-subscriber";
              enum "all";
              enum "unknown";
            }
          }
        }
        container remote-source {
          tailf:cli-add-mode;
          presence "true";
          leaf far-end {
            type inet:ipv4-address;
          }
          list spoke-sdp {
            key "sdp-id vc-id";
            leaf sdp-id {
              type uint32;
            }
            leaf vc-id {
              type uint32;
            }
            leaf endpoint {
              tailf:cli-hide-in-submode;
              type string32;
            }
            leaf vc-type {
              tailf:cli-hide-in-submode;
              type enumeration {
                enum "ether";
                enum "vlan";
              }
            }
            leaf shutdown {
              type boolean;
            }
          }
        }
        list sap {
          key "sap-id";
          leaf sap-id {
            type string;
          }
          container cem {
            tailf:cli-add-mode;
            container packet {
              choice packet {
                leaf jitter-buffer {
                  type uint8;
                }
                leaf bytes {
                  type uint16;
                }
              }
            }
            leaf rtp-header {
              type empty;
            }
          }
          container egress {
            tailf:cli-add-mode;
            container ip-mirror {
              tailf:cli-add-mode;
              container sa-mac {
                tailf:cli-compact-syntax;
                tailf:cli-sequence-commands {
                  tailf:cli-reset-all-siblings;
                }
                leaf sa-mac {
                  tailf:cli-drop-node-name;
                  type ieee-mac;
                }
                leaf da-mac {
                  type ieee-mac;
                }
              }
            }
            leaf qos {
              type uint16;
            }
          }
        }
        leaf service-name {
          type string;
        }
        leaf shutdown {
          type boolean;
        }
        leaf slice-size {
          type uint16;
        }
        list spoke-sdp {
          key "sdp-id vc-id";
          leaf sdp-id {
            type uint32;
          }
          leaf vc-id {
            type uint32;
          }
          leaf endpoint {
            tailf:cli-hide-in-submode;
            type string32;
          }
          leaf vc-type {
            tailf:cli-hide-in-submode;
            type enumeration {
              enum "ether";
              enum "vlan";
            }
          }
          leaf control-word {
            type empty;
          }
          leaf precedence {
            type enumeration {
              enum "1";
              enum "2";
              enum "3";
              enum "4";
              enum "primary";
            }
          }
          container egress {
            tailf:cli-add-mode;
            container l2tpv3 {
              tailf:cli-add-mode;
              leaf cookie {
                type string;
              }
            }
            leaf vc-label {
              type uint32;
            }
          }
          container ingress {
            tailf:cli-add-mode;
            leaf vc-label {
              type uint32;
            }
          }
          leaf shutdown {
            type boolean;
          }
        }
      }
      list mirror-source {
        key "service-id";
        leaf service-id {
          type service-id;
        }
        list port {
          tailf:cli-suppress-mode;
          tailf:cli-compact-syntax;
          tailf:cli-delete-when-empty;
          key "name";
          leaf name {
            type string;
          }
          leaf egress {
            type empty;
          }
          leaf ingress {
            type empty;
          }
        }
        list sap {
          tailf:cli-suppress-mode;
          tailf:cli-compact-syntax;
          key "sap-id";
          leaf sap-id {
            type string;
          }
          leaf egress {
            type empty;
          }
          leaf ingress {
            type empty;
          }
        }
        leaf shutdown {
          type boolean;
        }
      }
    }
    container saa {
      tailf:ncs-device-type "cli-ned";
      tailf:display-when "not(../../ncs:module) or ../../ncs:module[ncs:name='netsim-ned-alu-sr']";
      tailf:cli-add-mode;
      list test {
        key "test-name";
        leaf test-name {
          type string;
        }
        leaf owner {
          tailf:cli-hide-in-submode;
          type string;
        }
        leaf accounting-policy {
          type uint8;
        }
        leaf continuous {
          type empty;
        }
        leaf description {
          type string;
        }

        grouping saa-test-event-grouping {
          leaf rising-threshold {
            tailf:cli-prefix-key;
            type uint32;
          }
          leaf falling-threshold {
            tailf:cli-optional-in-sequence;
            tailf:cli-prefix-key;
            type uint32;
          }
          leaf direction {
            type enumeration {
              enum "inbound";
              enum "outbound";
              enum "roundtrip";
            }
          }
        }
        list jitter-event {
          tailf:cli-suppress-mode;
          tailf:cli-compact-syntax;
          tailf:cli-sequence-commands {
            tailf:cli-reset-siblings;
          }
          key "direction";
          uses saa-test-event-grouping;
        }
        list latency-event {
          tailf:cli-suppress-mode;
          tailf:cli-compact-syntax;
          tailf:cli-sequence-commands {
            tailf:cli-reset-siblings;
          }
          key "direction";
          uses saa-test-event-grouping;
        }
        list loss-event {
          tailf:cli-suppress-mode;
          tailf:cli-compact-syntax;
          tailf:cli-sequence-commands {
            tailf:cli-reset-siblings;
          }
          key "direction";
          uses saa-test-event-grouping;
        }
        container type {
          tailf:cli-add-mode;
          presence "true";
          tailf:cli-delete-when-empty;
          container cpe-ping {
            tailf:cli-compact-syntax;
            leaf service {
              type service-id;
            }
            leaf destination {
              type inet:ipv4-address;
            }
            leaf source {
              type inet:ipv4-address;
            }
            leaf source-mac {
              type ieee-mac;
            }
            leaf fc {
              type fc-name;
            }
            leaf profile {
              type enumeration {
                enum "in";
                enum "out";
              }
            }
            leaf ttl {
              type uint8;
            }
            leaf count {
              type uint8;
            }
            leaf send-control {
              type empty;
            }
            leaf return-control {
              type empty;
            }
            leaf interval {
              type uint8;
            }
          }
          container icmp-ping {
            tailf:cli-compact-syntax;
            tailf:cli-sequence-commands;
            leaf ip-address {
              tailf:cli-drop-node-name;
              type inet:ipv4-address;
            }
            leaf size {
              tailf:cli-optional-in-sequence;
              type uint32;
            }
            leaf source {
              tailf:cli-break-sequence-commands;
              type inet:ipv4-address;
            }
            leaf interval {
              tailf:cli-optional-in-sequence;
              type uint32;
            }
            leaf count {
              type uint8;
            }
            leaf router {
              tailf:cli-optional-in-sequence;
              type string;
            }
            leaf router-instance {
              tailf:cli-optional-in-sequence;
              type string;
            }
          }
          container dns {
            tailf:cli-compact-syntax;
            leaf target-addr {
              type string;
            }
            leaf name-server {
              type union {
                type inet:ipv4-address;
                type inet:ipv6-address;
              }
            }
            leaf source {
              type union {
                type inet:ipv4-address;
                type inet:ipv6-address;
              }
            }
            leaf count {
              type uint8;
            }
            leaf timeout {
              type uint8;
            }
            leaf interval {
              type uint8;
            }
            leaf record-type {
              type enumeration {
                enum "ipv4-a-record";
                enum "ipv6-aaaa-record";
              }
            }
          }
          container eth-cfm-two-way-delay {
            tailf:cli-compact-syntax;
            leaf mac-address {
              tailf:cli-drop-node-name;
              type ieee-mac;
            }
            leaf mep {
              type uint16;
            }
            leaf domain {
              type uint32;
            }
            leaf association {
              type uint32;
            }
            leaf fc {
              type fc-name;
            }
            leaf profile {
              type enumeration {
                enum "in";
                enum "out";
              }
            }
            leaf count {
              type uint16;
            }
            leaf timeout {
              type uint8;
            }
            leaf interval {
              type uint8;
            }
          }
          container lsp-ping {
            tailf:cli-compact-syntax;
            leaf lsp-name {
              tailf:cli-drop-node-name;
              type string;
            }
            leaf path {
              type string;
            }
            leaf fc {
              type fc-name;
            }
            leaf profile {
              type enumeration {
                enum "in";
                enum "out";
              }
            }
            leaf interval {
              type uint8;
            }
            leaf send-count {
              type uint8;
            }
            leaf size {
              type uint16;
            }
            leaf src-ip-address {
              type union {
                type inet:ipv4-address;
                type inet:ipv6-address;
              }
            }
            leaf timeout {
              type uint8;
            }
            leaf ttl {
              type uint8;
            }
          }
          container sdp-ping {
            tailf:cli-compact-syntax;
            leaf orig-sdp-id {
              tailf:cli-drop-node-name;
              type uint32;
            }
            leaf resp-sdp {
              type uint32;
            }
            leaf fc {
              type fc-name;
            }
            leaf profile {
              type enumeration {
                enum "in";
                enum "out";
              }
            }
            leaf size {
              type uint16;
            }
            leaf count {
              type uint8;
            }
            leaf timeout {
              type uint8;
            }
            leaf interval {
              type uint8;
            }
          }
          container vprn-ping {
            tailf:cli-compact-syntax;
            leaf service-id {
              tailf:cli-drop-node-name;
              type service-id;
            }
            leaf source {
              type union {
                type inet:ipv4-address;
                type inet:ipv6-address;
              }
            }
            leaf destination {
              type union {
                type inet:ipv4-address;
                type inet:ipv6-address;
              }
            }
            leaf fc {
              type fc-name;
            }
            leaf profile {
              type enumeration {
                enum "in";
                enum "out";
              }
            }
            leaf size {
              type uint16;
            }
            leaf ttl {
              type uint8;
            }
            leaf count {
              type uint8;
            }
            leaf return-control {
              type empty;
            }
            leaf timeout {
              type uint8;
            }
            leaf interval {
              type uint8;
            }
          }
        }
        container trap-gen {
          tailf:cli-add-mode;
          leaf probe-fail-enable {
            type empty;
          }
          leaf probe-fail-threshold {
            type uint8;
          }
          leaf test-completion-enable {
            type empty;
          }
          leaf test-fail-enable {
            type empty;
          }
          leaf test-fail-threshold {
            type uint8;
          }
        }
        leaf probe-history {
          type enumeration {
            enum "keep";
            enum "drop";
            enum "auto";
          }
        }
        leaf shutdown {
          type boolean;
        }
      }
    }
    container subscriber-mgmt {
      tailf:ncs-device-type "cli-ned";
      tailf:display-when "not(../../ncs:module) or ../../ncs:module[ncs:name='netsim-ned-alu-sr']";
      tailf:cli-add-mode;
      list category-map {
        key "name";
        leaf name {
          type string;
        }
        leaf description {
          type string;
        }
        leaf gx-session-level-usage {
          type boolean;
        }
        list category {
          key "name";
          leaf name {
            type string;
          }
          leaf credit-type-override {
            type enumeration {
              enum "volume";
              enum "time";
            }
          }
          leaf rating-group {
            type uint32;
          }
          list queue {
            tailf:cli-suppress-mode;
            key "id";
            leaf id {
              type uint32;
            }
            leaf type {
              tailf:cli-drop-node-name;
              type enumeration {
                enum "ingress-only";
                enum "egress-only";
                enum "ingress-egress";
              }
            }
          }
          list policer {
            tailf:cli-suppress-mode;
            key "id";
            leaf id {
              type uint32;
            }
            leaf type {
              tailf:cli-drop-node-name;
              type enumeration {
                enum "ingress-only";
                enum "egress-only";
                enum "ingress-egress";
              }
            }
          }
        }
      }
      list credit-control-policy {
        key "policy-name";
        leaf policy-name {
          type string;
        }
        leaf description {
          type string;
        }
        container credit-control-server {
          leaf diameter {
            type string;
          }
        }
        leaf default-category-map {
          type string;
        }
      }
      list diameter-application-policy {
        key "name";
        leaf name {
          type string;
        }
        leaf application {
          type enumeration {
            enum "gx";
            enum "gy";
            enum "nasreq";
          }
        }
        leaf diameter-peer-policy {
          type string32;
        }
        container on-failure {
          tailf:cli-compact-syntax;
          leaf failover {
            type enumeration {
              enum "enabled";
              enum "disabled";
            }
          }
          leaf handling {
            type enumeration {
              enum "continue";
              enum "retry-and-terminate";
              enum "terminate";
            }
          }
        }
        container gy {
          tailf:cli-add-mode;
          container avp-subscription-id {
            tailf:cli-compact-syntax;
            leaf origin {
              tailf:cli-drop-node-name;
              type enumeration {
                enum "circuit-id";
                enum "dual-stack-remote-id";
                enum "imei";
                enum "imsi";
                enum "mac";
                enum "msisdn";
                enum "nas-port-id";
                enum "subscriber-id";
                enum "username";
              }
            }
            leaf type {
              type enumeration {
                enum "e164";
                enum "imsi";
                enum "nai";
                enum "private";
              }
            }
          }
          container extended-failure-handling {
            tailf:cli-add-mode;
            leaf shutdown {
              type boolean;
            }
            container interim-credit {
              tailf:cli-add-mode;
              leaf max-attempts {
                type union {
                  type uint32;
                  type enumeration {
                    enum "infinite";
                  }
                }
              }
              leaf reporting {
                type empty;
              }
            }
          }
        }
      }
      list local-user-db {
        key "name";
        leaf name {
          type string;
        }
        container ipoe {
          tailf:cli-add-mode;
          leaf-list match-list {
            tailf:cli-flat-list-syntax;
            ordered-by user;
            type enumeration {
              enum "circuit-id";
              enum "derived-id";
              enum "dual-stack-remote-id";
              enum "encap-tag-range";
              enum "ip";
              enum "mac";
              enum "option60";
              enum "remote-id";
              enum "sap-id";
              enum "service-id";
              enum "string";
              enum "system-id";
            }
          }
          list host {
            key "host-name";
            leaf host-name {
              type string;
            }
            leaf auth-policy {
              type string;
            }
            list identification-strings {
              key "option-number";
              leaf option-number {
                type uint32;
              }
              leaf sla-profile-string {
                type string;
              }
              leaf sub-profile-string {
                type string;
              }
            }
            container msap-defaults {
              tailf:cli-add-mode;
              leaf group-interface {
                type string;
              }
              leaf policy {
                type string;
              }
              leaf service {
                type union {
                  type uint32;
                  type string;
                }
              }
            }
            leaf ipv6-wan-address-pool {
              type string;
            }
            leaf ipv6-delegated-prefix-pool {
              type string;
            }
            container options {
              tailf:cli-add-mode;
              leaf subnet-mask {
                type inet:ipv4-address;
              }
              leaf default-router {
                type inet:ipv4-address;
              }
            }
            leaf server {
              type inet:ipv4-address;
            }
            container host-identification {
              tailf:cli-add-mode;
              container option60 {
                leaf string {
                  type string;
                }
              }
              container circuit-id {
                tailf:cli-compact-syntax;
                leaf string {
                  type string;
                }
              }
              leaf sap-id {
                type string;
              }
            }
            container address {
              tailf:cli-compact-syntax;
              leaf pool {
                type string;
              }
            }
            leaf shutdown {
              type boolean;
            }
          }
        }
        container ppp {
          tailf:cli-add-mode;
          leaf-list match-list {
            tailf:cli-flat-list-syntax;
            ordered-by user;
            type enumeration {
              enum "circuit-id";
              enum "derived-id";
              enum "encap-tag-range";
              enum "mac";
              enum "remote-id";
              enum "sap-id";
              enum "service-name";
              enum "username";
            }
          }
          list host {
            key "host-name";
            leaf host-name {
              type string;
            }
            leaf auth-policy {
              type string;
            }
            leaf pre-auth-policy {
              type string;
            }
            container host-identification {
              tailf:cli-add-mode;
              container username {
                tailf:cli-compact-syntax;
                leaf name {
                  tailf:cli-drop-node-name;
                  type string;
                }
                leaf domain {
                  tailf:cli-drop-node-name;
                  type enumeration {
                    enum "domain-only";
                    enum "no-domain";
                  }
                }
              }
            }
            container password {
              tailf:cli-compact-syntax;
              leaf ignore {
                type empty;
              }
            }
            container l2tp {
              tailf:cli-add-mode;
              container group {
                tailf:cli-compact-syntax;
                leaf name {
                  tailf:cli-drop-node-name;
                  type string;
                }
              }
            }
            container address {
              tailf:cli-compact-syntax;
              leaf pool {
                type string;
              }
            }
            leaf shutdown {
              type boolean;
            }
          }
        }
        leaf shutdown {
          type boolean;
        }
      }

      grouping radius-attributes-grouping {
        leaf access-loop-options {
          type empty;
        }
        leaf calling-station-id {
          type enumeration {
            enum "llid";
            enum "mac";
            enum "remote-id";
            enum "sap-id";
            enum "sap-string";
          }
        }
        leaf circuit-id {
          type empty;
        }
        leaf dhcp-vendor-class-id {
          type empty;
        }
        leaf mac-address {
          type empty;
        }
        leaf nas-port {
          type string;
        }
        container nas-port-id {
          tailf:cli-compact-syntax;
          presence "true";
          leaf prefix-string {
            type string;
          }
          leaf suffix {
            type enumeration {
              enum "circuit-id";
              enum "remote-id";
            }
          }
        }
        container nas-port-type {
          tailf:cli-compact-syntax;
          presence "true";
          leaf port-type {
            tailf:cli-drop-node-name;
            type uint8;
          }
        }
        leaf nas-identifier {
          type empty;
        }
        leaf remote-id {
          type empty;
        }
        leaf tunnel-server-attrs {
          type empty;
        }
        leaf wifi-num-attached-ues {
          type empty;
        }
        leaf wifi-ssid-vlan {
          type empty;
        }
      }
      container auto-sub-id-key {
        tailf:cli-add-mode;
        leaf-list ppp-sub-id-key {
          tailf:cli-flat-list-syntax;
          type enumeration {
            enum "mac";
            enum "sap-id";
            enum "circuit-id";
            enum "remote-id";
            enum "session-id";
          }
        }
        leaf-list ipoe-sub-id-key {
          tailf:cli-flat-list-syntax;
          type enumeration {
            enum "mac";
            enum "sap-id";
            enum "circuit-id";
            enum "remote-id";
            enum "dual-stack-remote-id";
          }
        }
      }
      list authentication-policy {
        key "name";
        leaf name {
          type string;
        }
        leaf description {
          type string;
        }
        container fallback-action {
          tailf:cli-compact-syntax;
          tailf:cli-sequence-commands {
            tailf:cli-reset-all-siblings;
          }
          leaf accept {
            tailf:cli-optional-in-sequence;
            type empty;
          }
          leaf user-db {
            type string32;
          }
          leaf force-probing {
            type empty;
          }
        }
        container include-radius-attribute {
          tailf:cli-add-mode;
          container acct-session-id {
            presence "true";
            leaf session {
              tailf:cli-drop-node-name;
              type enumeration {
                enum "host";
                enum "session";
              }
            }
          }
          leaf called-station-id {
            type empty;
          }
          leaf dhcp-options {
            type empty;
          }
          leaf dhcp6-options {
            type empty;
          }
          leaf pppoe-service-name {
            type empty;
          }
          uses radius-attributes-grouping;
        }
        leaf re-authentication {
          type empty;
        }
        leaf radius-server-policy {
          type string32;
        }
        leaf-list send-acct-stop-on-fail {
          tailf:cli-flat-list-syntax;
          type enumeration {
            enum "on-request-failure";
            enum "on-reject";
            enum "on-accept-failure";
          }
        }
        container password {
          tailf:cli-compact-syntax;
          tailf:cli-sequence-commands {
            tailf:cli-reset-siblings;
          }
          leaf pw {
            tailf:cli-drop-node-name;
            type string;
          }
          leaf hashing-scheme {
            tailf:cli-drop-node-name;
            type hash-method;
          }
        }
        leaf pppoe-access-method {
          type enumeration {
            enum "none";
            enum "padi";
            enum "pap-chap";
          }
        }
        container user-name-format {
          tailf:cli-compact-syntax;
          tailf:cli-sequence-commands {
            tailf:cli-reset-all-siblings;
          }
          leaf format {
            tailf:cli-drop-node-name;
            type enumeration {
              enum "ascii-converted-circuit-id";
              enum "ascii-converted-tuple";
              enum "circuit-id";
              enum "dhcp-client-vendor-opts";
              enum "mac";
              enum "mac-giaddr";
              enum "ppp-user-name";
              enum "tuple";
            }
          }
        }
      }
      list host-lockout-policy {
        key "policy-name";
        leaf policy-name {
          type string32;
        }
        leaf description {
          type string;
        }
        leaf lockout-reset-time {
          type uint32;
        }
        container lockout-time {
          tailf:cli-compact-syntax;
          leaf min {
            type uint32;
          }
          leaf max {
            type uint32;
          }
        }
        leaf max-lockout-hosts {
          type uint32;
        }
        leaf host-key {
          type enumeration {
            enum "mac";
          }
        }
      }
      list msap-policy {
        key "msap-policy-name";
        leaf msap-policy-name {
          type string32;
        }
        container cpu-protection {
          tailf:cli-compact-syntax;
          tailf:cli-sequence-commands {
            tailf:cli-reset-all-siblings;
          }
          leaf policy-id {
            tailf:cli-drop-node-name;
            type uint16;
          }
          leaf monitoring {
            tailf:cli-drop-node-name;
            type enumeration {
              enum "mac-monitoring";
              enum "ip-src-monitoring";
            }
          }
        }
        leaf dist-cpu-protection {
          type string;
        }
        leaf description {
          type string;
        }
        container sub-sla-mgmt {
          tailf:cli-add-mode;
          container def-sub-id {
            choice def-sub-id {
              leaf use-sap-id {
                type empty;
              }
              leaf use-auto-id {
                type empty;
              }
              leaf string {
                type string;
              }
            }
          }
          container def-inter-dest-id {
            leaf type {
              tailf:cli-drop-node-name;
              type enumeration {
                enum "use-top-q";
                enum "use-vpi";
              }
            }
          }
          leaf def-sub-profile {
            type string;
          }
          leaf def-sla-profile {
            type string;
          }
          leaf sub-ident-policy {
            type string;
          }
          container single-sub-parameters {
            tailf:cli-add-mode;
            leaf profiled-traffic-only {
              type empty;
            }
          }
        }
        container ies-vprn-only-sap-parameters {
          tailf:cli-add-mode;
          leaf anti-spoof {
            type enumeration {
              enum "ip-mac";
              enum "nh-mac";
            }
          }
          container ingress {
            tailf:cli-add-mode;
            container qos {
              tailf:cli-drop-node-name;
              tailf:cli-compact-syntax;
              leaf qos {
                type uint16;
              }
              leaf queueing {
                tailf:cli-drop-node-name;
                type enumeration {
                  enum "shared-queuing";
                  enum "service-queuing";
                }
              }
            }
          }
          container egress {
            tailf:cli-add-mode;
            tailf:cli-compact-syntax;
            leaf qos {
              type uint16;
            }
          }
        }
      }
      list ipoe-session-policy {
        key "policy-name";
        leaf policy-name {
          type string32;
        }
        leaf description {
          type string;
        }
        container session-key {
          tailf:cli-compact-syntax;
          tailf:cli-sequence-commands;
          leaf sap {
            type empty;
          }
          leaf mac {
            type empty;
          }
          leaf cid {
            tailf:cli-optional-in-sequence;
            type empty;
          }
          leaf rid {
            tailf:cli-optional-in-sequence;
            type empty;
          }
        }
      }
      list ppp-policy {
        key "ppp-policy-name";
        leaf ppp-policy-name {
          type string32;
        }
        leaf description {
          type string;
        }
        leaf ppp-mtu {
          type uint32;
        }
        container default-pap-password {
          tailf:cli-compact-syntax;
          tailf:cli-sequence-commands {
            tailf:cli-reset-siblings;
          }
          leaf password {
            tailf:cli-drop-node-name;
            type string;
          }
          leaf method {
            tailf:cli-drop-node-name;
            type hash-method;
          }
        }
        leaf default-user-name {
          type string;
        }
        container keepalive {
          tailf:cli-compact-syntax;
          tailf:cli-sequence-commands {
            tailf:cli-reset-all-siblings;
          }
          leaf seconds {
            tailf:cli-drop-node-name;
            type uint16;
          }
          leaf hold-up-multiplier {
            type uint8;
          }
        }
        container max-sessions-per-mac {
          tailf:cli-compact-syntax;
          tailf:cli-sequence-commands {
            tailf:cli-reset-all-siblings;
          }
          leaf sessions {
            tailf:cli-drop-node-name;
            type uint16;
          }
          leaf allow-same-circuit-id-for-dhcp {
            type empty;
          }
        }
        leaf ppp-authentication {
          type enumeration {
            enum "pap";
            enum "chap";
            enum "pref-chap";
            enum "pref-pap";
          }
        }
        leaf session-timeout {
          type uint32;
        }
      }
      list radius-accounting-policy {
        key "name";
        leaf name {
          type string32;
        }
        leaf delay-start-time {
          type uint8;
        }
        leaf queue-instance-accounting {
          type enumeration {
            enum "enable";
            enum "disable";
            enum "interim-update";
          }
        }
        container session-accounting {
          presence "true";
          leaf-list keywords {
            tailf:cli-drop-node-name;
            tailf:cli-flat-list-syntax;
            type enumeration {
              enum "interim-update";
              enum "host-update";
            }
          }
        }
        leaf description {
          type string;
        }
        container host-accounting {
          presence "true";
          leaf interim-update {
            type empty;
          }
        }
        container include-radius-attribute {
          tailf:cli-add-mode;
          uses radius-attributes-grouping;
          leaf detailed-acct-attributes {
            type boolean;
          }
          leaf acct-authentic {
            type empty;
          }
          leaf acct-delay-time {
            type empty;
          }
          leaf alc-acct-triggered-reason {
            type empty;
          }
          leaf alc-error-code {
            type empty;
          }
          leaf all-authorized-session-addresses {
            type empty;
          }
          leaf brg-num-active-sessions {
            type empty;
          }
          leaf delegated-ipv6-prefix {
            type empty;
          }
          leaf framed-interface-id {
            type empty;
          }
          leaf framed-ip-netmask {
            type empty;
          }
          leaf framed-ipv6-route {
            type empty;
          }
          leaf framed-route {
            type empty;
          }
          leaf framed-ip-addr {
            type empty;
          }
          leaf framed-ipv6-prefix {
            type empty;
          }
          leaf ipv6-address {
            type empty;
          }
          leaf nat-port-range {
            type empty;
          }
          leaf std-acct-attributes {
            type empty;
          }
          leaf tunnel-client-attrs {
            type empty;
          }
          leaf steering-profile {
            type empty;
          }
          leaf sub-profile {
            type empty;
          }
          leaf sla-profile {
            type empty;
          }
          leaf subscriber-id {
            type empty;
          }
          leaf user-name {
            type empty;
          }
          leaf v6-aggregate-stats {
            type empty;
          }
          leaf wifi-rssi {
            type empty;
          }
        }
        leaf radius-server-policy {
          type string32;
        }
        leaf session-id-format {
          type enumeration {
            enum "description";
            enum "number";
          }
        }
        leaf update-interval {
          type uint32;
        }
      }
      list shcv-policy {
        key "shcv-policy-name";
        leaf shcv-policy-name {
          type string;
        }
        leaf description {
          type string;
        }
        container layer-3 {
          tailf:cli-add-mode;
          leaf source-ip-origin {
            type enumeration {
              enum "interface";
              enum "vrrp";
            }
          }
        }
        container periodic {
          tailf:cli-add-mode;
          leaf action {
            type enumeration {
              enum "alarm";
              enum "remove";
            }
          }
          leaf interval {
            type int16;
          }
          leaf retry-count {
            type uint8;
          }
          leaf timeout {
            type int16;
          }
          leaf shutdown {
            type boolean;
          }
        }
        container trigger {

          grouping trigger-grouping {
            leaf shutdown {
              type boolean;
            }
            leaf retry-count {
              type uint8;
            }
            leaf timeout {
              type int16;
            }
          }
          container ip-conflict {
            tailf:cli-add-mode;
            uses trigger-grouping;
          }
          container host-limit-exceeded {
            tailf:cli-add-mode;
            uses trigger-grouping;
          }
          container inactivity {
            tailf:cli-add-mode;
            // NCS expand uses statement
            leaf shutdown {
              type boolean;
            }
            leaf retry-count {
              type uint8;
            }
            leaf timeout {
              type int16;
            }
          }
          container mobility {
            tailf:cli-add-mode;
            uses trigger-grouping;
          }
          container mac-learning {
            tailf:cli-add-mode;
            // NCS expand uses statement
            leaf shutdown {
              type boolean;
            }
            leaf retry-count {
              type uint8;
            }
            leaf timeout {
              type int16;
            }
          }
        }
        container vpls {
          tailf:cli-add-mode;
          leaf source-ip {
            type inet:ipv4-address;
          }
          leaf source-mac {
            type ieee-mac;
          }
        }
      }
      list sla-profile {
        key "sla-profile-name";
        leaf sla-profile-name {
          type string;
        }
        leaf description {
          type string;
        }
        leaf credit-control-policy {
          type string;
        }
        container host-limit {
          tailf:cli-compact-syntax;
          tailf:cli-sequence-commands {
            tailf:cli-reset-all-siblings;
          }
          leaf max-number-of-hosts {
            tailf:cli-drop-node-name;
            type uint8;
          }
          leaf remove-oldest {
            type empty;
          }
        }
        container host-limits {
          tailf:cli-add-mode;
          leaf ipv4-overall {
            type uint32;
          }
          leaf ipv4-dhcp {
            type uint32;
          }
          leaf ipv6-pd-ipoe-dhcp {
            type uint32;
          }
          leaf ipv6-wan-ipoe-dhcp {
            type uint32;
          }
          leaf ipv6-overall {
            type uint32;
          }
          leaf overall {
            type uint32;
          }
        }
        container ingress {
          tailf:cli-add-mode;
          list qos {
            key "id";
            leaf id {
              type uint16;
            }
            leaf queuing {
              tailf:cli-drop-node-name;
              tailf:cli-hide-in-submode;
              type enumeration {
                enum "multipoint-shared";
                enum "service-queuing";
                enum "shared-queuing";
              }
            }
            list queue {
              key "queue-id";
              leaf queue-id {
                type uint8;
              }
              leaf stat-mode {
                type enumeration {
                  enum "v4-v6";
                }
              }
            }
            list policer {
              key "policer-id";
              leaf policer-id {
                type uint8;
              }
              leaf stat-mode {
                type policer-stat-mode;
              }
            }
          }
          leaf ip-filter {
            type filter-id;
          }
          leaf ipv6-filter {
            type filter-id;
          }
        }
        container egress {
          tailf:cli-add-mode;
          list qos {
            key "id";
            leaf id {
              type uint16;
            }
            leaf multipoint-shared {
              tailf:cli-hide-in-submode;
              type empty;
            }
            leaf vport-scheduler {
              tailf:cli-hide-in-submode;
              type empty;
            }
            list queue {
              key "queue-id";
              leaf queue-id {
                type uint8;
              }
              leaf stat-mode {
                type enumeration {
                  enum "v4-v6";
                }
              }
            }
            list policer {
              key "policer-id";
              leaf policer-id {
                type uint8;
              }
              leaf stat-mode {
                type policer-stat-mode;
              }
            }
          }
          leaf ip-filter {
            type filter-id;
          }
          leaf ipv6-filter {
            type filter-id;
          }
          leaf qos-marking-from-sap {
            type boolean;
          }
          list scheduler-policy {
            key "scheduler-policy-name";
            leaf scheduler-policy-name {
              type string;
            }
            list scheduler {
              tailf:cli-suppress-mode;
              tailf:cli-compact-syntax;
              tailf:cli-sequence-commands {
                tailf:cli-reset-all-siblings;
              }
              key "scheduler-name";
              leaf scheduler-name {
                type string;
              }
              leaf rate {
                type rate-type;
              }
              leaf cir {
                type rate-type-with-sum;
              }
            }
          }
        }
      }
      list sub-ident-policy {
        key "sub-ident-policy-name";
        leaf sub-ident-policy-name {
          type string;
        }
        leaf description {
          type string;
        }
        container app-profile-map {
          tailf:cli-add-mode;
          leaf use-direct-map-as-default {
            type empty;
          }
        }
        leaf strings-from-option {
          type uint32;
        }
        container sub-profile-map {
          tailf:cli-add-mode;
          leaf use-direct-map-as-default {
            type empty;
          }
        }
        container sla-profile-map {
          tailf:cli-add-mode;
          leaf use-direct-map-as-default {
            type empty;
          }
        }
      }
      list igmp-policy {
        key "name";
        leaf name {
          type string;
        }
        leaf per-host-replication {
          type empty;
        }
        container static {
          tailf:cli-add-mode;
          list group {
            key "ip-address";
            leaf ip-address {
              type inet:ipv4-address;
            }
            leaf starg {
              type empty;
            }
          }
        }
      }
      list sub-profile {
        key "sub-profile-name";
        leaf sub-profile-name {
          type string;
        }
        leaf description {
          type string;
        }
        leaf igmp-policy {
          type string;
        }
        leaf accounting-policy {
          type uint8;
        }
        leaf nat-policy {
          type string;
        }
        leaf collect-stats {
          type empty;
        }
        container radius-accounting {
          tailf:cli-add-mode;
          leaf-list policy {
            tailf:cli-flat-list-syntax;
            type string32;
          }
        }
        container radius-accounting-policy {
          tailf:cli-compact-syntax;
          tailf:cli-sequence-commands {
            tailf:cli-reset-all-siblings;
          }
          leaf acct-policy-name {
            tailf:cli-drop-node-name;
            type string32;
          }
          leaf duplicate {
            type string32;
          }
        }
        container sla-profile-map {
          tailf:cli-add-mode;
          leaf use-direct-map-as-default {
            type empty;
          }
          list entry {
            tailf:cli-suppress-mode;
            key "key";
            leaf key {
              type string;
            }
            leaf sla-profile {
              type string;
            }
          }
        }
        container egress {
          tailf:cli-add-mode;
          container scheduler-policy {
            tailf:cli-add-mode;
            leaf scheduler-policy-id {
              tailf:cli-drop-node-name;
              tailf:cli-hide-in-submode;
              type string;
            }
            list scheduler {
              tailf:cli-compact-syntax;
              tailf:cli-suppress-mode;
              tailf:cli-sequence-commands;
              key "scheduler-id";
              leaf scheduler-id {
                type string;
              }
              leaf rate {
                type uint32;
              }
              leaf cir {
                type uint32;
              }
            }
          }
          container agg-rate-limit {
            tailf:cli-compact-syntax;
            tailf:cli-sequence-commands {
              tailf:cli-reset-all-siblings;
            }
            leaf agg-rate {
              tailf:cli-drop-node-name;
              type union {
                type enumeration {
                  enum "max";
                }
                type uint32;
              }
            }
            leaf queue-frame-based-accounting {
              type empty;
            }
          }
        }
      }
    }
    container vrrp {
      tailf:ncs-device-type "cli-ned";
      tailf:display-when "not(../../ncs:module) or ../../ncs:module[ncs:name='netsim-ned-alu-sr']";
      tailf:cli-add-mode;
      list policy {
        key "policy-id";
        leaf policy-id {
          type uint16;
        }
        leaf context {
          tailf:cli-hide-in-submode;
          type service-id;
        }
        leaf delta-in-use-limit {
          type uint8;
        }
        leaf description {
          type string;
        }
        container priority-event {
          tailf:cli-add-mode;

          grouping priority-event-grouping {
            leaf hold-set {
              type uint32;
            }
            leaf hold-clear {
              type uint32;
            }
            container priority {
              tailf:cli-compact-syntax;
              tailf:cli-sequence-commands {
                tailf:cli-reset-siblings;
              }
              leaf priority-level {
                tailf:cli-drop-node-name;
                type uint8;
              }
              leaf keyword {
                tailf:cli-drop-node-name;
                type enumeration {
                  enum "delta";
                  enum "explicit";
                }
              }
            }
          }
          list host-unreachable {
            key "address";
            leaf address {
              type union {
                type inet:ipv4-address;
                type inet:ipv6-address;
              }
            }
            uses priority-event-grouping;
            leaf drop-count {
              type uint8;
            }
            leaf interval {
              type uint8;
            }
            leaf padding-size {
              type uint16;
            }
            leaf timeout {
              type uint8;
            }
          }
          list lag-port-down {
            key "lag-id";
            leaf lag-id {
              type uint32;
            }
            uses priority-event-grouping;
            list number-down {
              key "number-of-lag-ports-down";
              leaf number-of-lag-ports-down {
                type uint8;
              }
              container priority {
                tailf:cli-compact-syntax;
                tailf:cli-sequence-commands {
                  tailf:cli-reset-siblings;
                }
                leaf priority-level {
                  tailf:cli-drop-node-name;
                  type uint8;
                }
                leaf keyword {
                  tailf:cli-drop-node-name;
                  type enumeration {
                    enum "delta";
                    enum "explicit";
                  }
                }
              }
            }
          }
          list mc-ipsec-non-forwarding {
            key "tunnel-grp-id";
            leaf tunnel-grp-id {
              type uint8;
            }
            uses priority-event-grouping;
          }
          list port-down {
            key "port-id";
            leaf port-id {
              type string;
            }
            uses priority-event-grouping;
          }
          list route-unknown {
            key "prefix";
            leaf prefix {
              type union {
                type tailf:ipv4-address-and-prefix-length;
                type tailf:ipv6-address-and-prefix-length;
              }
            }
            uses priority-event-grouping;
            container less-specific {
              tailf:cli-compact-syntax;
              presence "true";
              leaf allow-default {
                type empty;
              }
            }
            list next-hop {
              tailf:cli-suppress-mode;
              key "address";
              leaf address {
                type union {
                  type inet:ipv4-address;
                  type inet:ipv6-address;
                }
              }
            }
            list protocol {
              tailf:cli-suppress-mode;
              key "protocol";
              leaf protocol {
                type enumeration {
                  enum "bgp";
                  enum "bgp-vpn";
                  enum "ospf";
                  enum "isis";
                  enum "rip";
                  enum "static";
                }
              }
            }
          }
        }
      }
    }
    container bof {
      tailf:ncs-device-type "cli-ned";
      tailf:display-when "not(../../ncs:module) or ../../ncs:module[ncs:name='netsim-ned-alu-sr']";
      tailf:cli-add-mode;

      grouping bof-address-grouping {
        leaf address {
          type union {
            type tailf:ipv4-address-and-prefix-length;
            type tailf:ipv6-address-and-prefix-length;
          }
        }
        leaf type {
          tailf:cli-drop-node-name;
          type enumeration {
            enum "active";
            enum "standby";
          }
        }
      }
      list address {
        tailf:cli-suppress-mode;
        tailf:cli-delete-when-empty;
        key "address";
        uses bof-address-grouping;
      }
      container auto-discover {
        tailf:cli-compact-syntax;
        tailf:cli-sequence-commands {
          tailf:cli-reset-siblings;
        }
        presence "true";
        leaf id {
          type string;
        }
        leaf vlan {
          type uint16;
        }
      }
      leaf autonegotiate {
        type empty;
      }
      leaf console-speed {
        type enumeration {
          enum "9600";
          enum "19200";
          enum "38400";
          enum "57600";
          enum "115200";
        }
      }
      leaf dns-domain {
        type string;
      }
      leaf duplex {
        type enumeration {
          enum "full";
          enum "half";
        }
      }
      leaf fips-140-2 {
        type boolean;
      }
      leaf ip-mtu {
        type uint32;
      }
      leaf li-local-save {
        type boolean;
      }
      leaf li-separate {
        type boolean;
      }
      leaf persist {
        type enumeration {
          enum "on";
          enum "off";
        }
      }
      leaf primary-config {
        type string;
      }
      leaf primary-dns {
        type union {
          type inet:ipv4-address;
          type inet:ipv6-address;
        }
      }
      leaf primary-image {
        type string;
      }
      leaf secondary-config {
        type string;
      }
      leaf secondary-dns {
        type union {
          type inet:ipv4-address;
          type inet:ipv6-address;
        }
      }
      leaf secondary-image {
        type string;
      }
      leaf speed {
        type enumeration {
          enum "10";
          enum "100";
          enum "1000";
        }
      }

      grouping bof-static-route-grouping {
        leaf prefix {
          type union {
            type tailf:ipv4-address-and-prefix-length;
            type tailf:ipv6-address-and-prefix-length;
          }
        }
        leaf next-hop {
          type union {
            type inet:ipv4-address;
            type inet:ipv6-address;
          }
        }
      }
      list static-route {
        tailf:cli-suppress-mode;
        tailf:cli-delete-when-empty;
        key "prefix";
        uses bof-static-route-grouping;
      }
      leaf tertiary-config {
        type string;
      }
      leaf tertiary-dns {
        type union {
          type inet:ipv4-address;
          type inet:ipv6-address;
        }
      }
      leaf tertiary-image {
        type string;
      }
      leaf wait {
        type uint8;
      }
      leaf console-disabled {
        type boolean;
      }
      list eth-mgmt-address {
        tailf:cli-suppress-mode;
        tailf:cli-delete-when-empty;
        key "address";
        uses bof-address-grouping;
      }
      leaf eth-mgmt-autoneg {
        type boolean;
      }
      leaf eth-mgmt-disabled {
        type boolean;
      }
      leaf eth-mgmt-duplex {
        type enumeration {
          enum "full";
          enum "half";
        }
      }
      list eth-mgmt-route {
        tailf:cli-suppress-mode;
        tailf:cli-delete-when-empty;
        key "prefix";
        uses bof-static-route-grouping;
      }
      leaf eth-mgmt-speed {
        type enumeration {
          enum "10";
          enum "100";
        }
      }
      leaf uplinkA-address {
        type union {
          type enumeration {
            enum "0";
          }
          type tailf:ipv4-address-and-prefix-length;
        }
      }
      leaf uplinkA-port {
        type string;
      }
      list uplinkA-route {
        tailf:cli-suppress-mode;
        tailf:cli-delete-when-empty;
        key "prefix";
        uses bof-static-route-grouping;
      }
      leaf uplinkA-vlan {
        type uint16;
      }
      leaf uplinkA-autoneg {
        type empty;
      }
      leaf uplinkA-duplex {
        type enumeration {
          enum "full";
          enum "half";
        }
      }
      leaf uplinkA-speed {
        type enumeration {
          enum "10";
          enum "100";
          enum "1000";
          enum "10000";
        }
      }
      leaf uplinkB-address {
        type union {
          type enumeration {
            enum "0";
          }
          type tailf:ipv4-address-and-prefix-length;
        }
      }
      leaf uplinkB-port {
        type string;
      }
      list uplinkB-route {
        tailf:cli-suppress-mode;
        tailf:cli-delete-when-empty;
        key "prefix";
        uses bof-static-route-grouping;
      }
      leaf uplinkB-vlan {
        type uint16;
      }
      leaf uplinkB-autoneg {
        type empty;
      }
      leaf uplinkB-duplex {
        type enumeration {
          enum "full";
          enum "half";
        }
      }
      leaf uplinkB-speed {
        type enumeration {
          enum "10";
          enum "100";
          enum "1000";
          enum "10000";
        }
      }
      leaf uplink-mode {
        type enumeration {
          enum "access-uplink";
          enum "network";
        }
      }
      leaf usb-port-key {
        type string;
      }
      leaf license-file {
        type string;
      }
    }
    container debug {
      tailf:ncs-device-type "cli-ned";
      tailf:display-when "not(../../ncs:module) or ../../ncs:module[ncs:name='netsim-ned-alu-sr']";
      tailf:cli-add-mode;
      container lag {
        list lag-id {
          tailf:cli-suppress-mode;
          key "id";
          leaf id {
            type uint32;
          }
          container items {
            tailf:cli-drop-node-name;
            leaf-list debug-item {
              tailf:cli-drop-node-name;
              tailf:cli-flat-list-syntax;
              type enumeration {
                enum "all";
                enum "cfg";
                enum "red";
                enum "iom-upd";
                enum "port-state";
                enum "timers";
                enum "sel-logic";
                enum "mc-pkt";
                enum "bfd";
                enum "pkt";
              }
            }
            leaf-list port {
              tailf:cli-flat-list-syntax;
              type string;
            }
          }
        }
      }
      list mirror-source {
        key "service-id";
        leaf service-id {
          type service-id;
        }
        list ingress-label {
          tailf:cli-compact-syntax;
          tailf:cli-suppress-mode;
          key "label";
          leaf label {
            type uint32;
          }
        }
        list ip-filter {
          tailf:cli-compact-syntax;
          tailf:cli-suppress-mode;
          tailf:cli-delete-when-empty;
          key "ip-filter-name";
          leaf ip-filter-name {
            type filter-id;
          }
          leaf-list entry {
            tailf:cli-flat-list-syntax;
            type uint16;
          }
        }
        list mac-filter {
          tailf:cli-compact-syntax;
          tailf:cli-suppress-mode;
          key "mac-filter-name";
          leaf mac-filter-name {
            type filter-id;
          }
          leaf-list entry {
            tailf:cli-flat-list-syntax;
            type uint16;
          }
        }
        list port {
          tailf:cli-compact-syntax;
          tailf:cli-suppress-mode;
          key "port-id";
          leaf lag {
            type empty;
          }
          leaf port-id {
            type string;
          }
          leaf ingress {
            type empty;
          }
          leaf egress {
            type empty;
          }
        }
        list sap {
          tailf:cli-compact-syntax;
          tailf:cli-suppress-mode;
          key "sap-id";
          leaf sap-id {
            type string;
          }
          leaf ingress {
            type empty;
          }
          leaf egress {
            type empty;
          }
        }
        list subscriber {
          tailf:cli-compact-syntax;
          tailf:cli-suppress-mode;
          key "sub-ident-string";
          leaf sub-ident-string {
            type string;
          }
          leaf sap {
            type string;
          }
          leaf ip {
            type inet:ipv4-address;
          }
          leaf mac {
            type ieee-mac;
          }
          leaf sla-profile-name {
            tailf:alt-name "sla-profile";
            type string;
          }
          leaf fc {
            type fc-name;
          }
          leaf ingress {
            type empty;
          }
          leaf egress {
            type empty;
          }
        }
        leaf shutdown {
          type boolean;
        }
      }

      grouping debug-router-grouping {
        container bgp {
          tailf:cli-add-mode;

          grouping neighbor-grouping {
            choice zzz {
              leaf neighbor {
                type union {
                  type inet:ipv4-address;
                  type inet:ipv6-address;
                }
              }
              leaf group {
                type string;
              }
            }
          }
          container events {
            tailf:cli-compact-syntax;
            uses neighbor-grouping;
          }
          container packets {
            tailf:cli-compact-syntax;
            uses neighbor-grouping;
          }
        }
        container ip {
          tailf:cli-add-mode;
          leaf arp {
            type empty;
          }
          leaf icmp {
            type empty;
          }
          leaf icmp6 {
            type empty;
          }
        }
      }
      container router {
        list router-id {
          tailf:cli-drop-node-name;
          key "router-name";
          leaf router-name {
            type router-type;
          }
          // NCS expand uses statement
          container bgp {
            tailf:cli-add-mode;

            grouping neighbor-grouping {
              choice zzz {
                leaf neighbor {
                  type union {
                    type inet:ipv4-address;
                    type inet:ipv6-address;
                  }
                }
                leaf group {
                  type string;
                }
              }
            }
            container events {
              tailf:cli-compact-syntax;
              // NCS expand uses statement
              choice zzz {
                leaf neighbor {
                  type union {
                    type inet:ipv4-address;
                    type inet:ipv6-address;
                  }
                }
                leaf group {
                  type string;
                }
              }
            }
            container packets {
              tailf:cli-compact-syntax;
              // NCS expand uses statement
              choice zzz {
                leaf neighbor {
                  type union {
                    type inet:ipv4-address;
                    type inet:ipv6-address;
                  }
                }
                leaf group {
                  type string;
                }
              }
            }
          }
          container ip {
            tailf:cli-add-mode;
            leaf arp {
              type empty;
            }
            leaf icmp {
              type empty;
            }
            leaf icmp6 {
              type empty;
            }
          }
        }
        list service-name {
          key "name";
          leaf name {
            type string;
          }
          uses debug-router-grouping;
        }
      }
    }
    container external-alarms {
      tailf:ncs-device-type "cli-ned";
      tailf:display-when "not(../../ncs:module) or ../../ncs:module[ncs:name='netsim-ned-alu-sr']";
      tailf:cli-add-mode;
      list alarm {
        key "alarm-id";
        leaf alarm-id {
          type uint32;
        }
        leaf chassis-alarming {
          type boolean;
        }
        leaf description {
          type string;
        }
        leaf log {
          type boolean;
        }
        container thresholds {
          tailf:cli-add-mode;
          container analog {
            tailf:cli-add-mode;
            container level {
              tailf:cli-compact-syntax;
              tailf:cli-sequence-commands {
                tailf:cli-reset-siblings;
              }
              leaf op {
                tailf:cli-drop-node-name;
                type enumeration {
                  enum "gt";
                  enum "lt";
                }
              }
              leaf millivolts {
                tailf:cli-drop-node-name;
                type uint32;
              }
            }
          }
        }
        container trigger {
          tailf:cli-compact-syntax;
          tailf:cli-sequence-commands {
            tailf:cli-reset-siblings;
          }
          leaf type {
            tailf:cli-drop-node-name;
            tailf:cli-optional-in-sequence;
            type enumeration {
              enum "all";
            }
          }
          leaf-list alarm-input {
            tailf:cli-drop-node-name;
            tailf:cli-flat-list-syntax;
            type string;
          }
        }
        leaf severity {
          type enumeration {
            enum "critical";
            enum "major";
            enum "minor";
            enum "warning";
          }
        }
        leaf shutdown {
          type boolean;
        }
      }
    }
    container python {
      tailf:ncs-device-type "cli-ned";
      tailf:display-when "not(../../ncs:module) or ../../ncs:module[ncs:name='netsim-ned-alu-sr']";
      tailf:cli-add-mode;
      list python-policy {
        key "name";
        leaf name {
          type string32;
        }
        leaf description {
          type string;
        }
        list dhcp {
          tailf:cli-suppress-mode;
          tailf:cli-sequence-commands {
            tailf:cli-reset-all-siblings;
          }
          key "type direction";
          leaf type {
            type enumeration {
              enum "discover";
              enum "offer";
              enum "request";
              enum "decline";
              enum "ack";
              enum "nak";
              enum "release";
              enum "inform";
              enum "force-renew";
              enum "lease-query";
              enum "lease-unassigned";
              enum "lease-unknown";
              enum "lease-active";
            }
          }
          leaf direction {
            type enumeration {
              enum "ingress";
              enum "egress";
            }
          }
          leaf script {
            type string32;
          }
        }
        list dhcp6 {
          tailf:cli-suppress-mode;
          tailf:cli-sequence-commands {
            tailf:cli-reset-all-siblings;
          }
          key "type direction";
          leaf type {
            type enumeration {
              enum "solicit";
              enum "advertise";
              enum "request";
              enum "confirm";
              enum "renew";
              enum "rebind";
              enum "reply";
              enum "release";
              enum "decline";
              enum "reconfigure";
              enum "info-request";
              enum "relay-forward";
              enum "relay-reply";
            }
          }
          leaf direction {
            type enumeration {
              enum "ingress";
              enum "egress";
            }
          }
          leaf script {
            type string32;
          }
        }
        list radius {
          tailf:cli-suppress-mode;
          key "type direction";
          leaf type {
            type enumeration {
              enum "access-request";
              enum "access-accept";
              enum "access-reject";
              enum "accounting-request";
              enum "accounting-response";
              enum "access-challenge";
              enum "disconnect-request";
              enum "change-of-authorization-request";
            }
          }
          leaf direction {
            type enumeration {
              enum "egress";
              enum "ingress";
            }
          }
          leaf script {
            type string32;
          }
        }
      }
      list python-script {
        key "name";
        leaf name {
          type string32;
        }
        leaf action-on-fail {
          type enumeration {
            enum "drop";
            enum "passthrough";
          }
        }
        leaf description {
          type string;
        }
        leaf primary-url {
          type string;
        }
        leaf shutdown {
          type boolean;
        }
      }
    }
    container commands {
      tailf:ncs-device-type "cli-ned";
      tailf:display-when "not(../../ncs:module) or ../../ncs:module[ncs:name='netsim-ned-alu-sr']";
      tailf:cli-drop-node-name;
    }
  }
  augment "/ncs:devices/ncs:template/ncs:ned-id/ncs:config" {
    leaf model {
      tailf:alt-name "nedAluModel";
      type string;
    }
    leaf model-name {
      tailf:alt-name "nedAluModelName";
      type string;
    }
    leaf os-major {
      tailf:alt-name "nedAluOsMajor";
      type string;
    }
    leaf os-minor {
      tailf:alt-name "nedAluOsMinor";
      type string;
    }
    leaf os-patch {
      tailf:alt-name "nedAluOsPatch";
      type string;
    }
    leaf mode {
      tailf:alt-name "nedAluUseMode";
      type string;
    }
    leaf use-extra-get-port-speed {
      tailf:alt-name "nedAluUseExtraGetPortSpeed";
      type string;
    }
    leaf force-no-filter-name {
      tailf:alt-name "nedAluForceNoFilterName";
      type string;
    }
    container bfd {
      container seamless-bfd {
        list reflector {
          // NCS patched for predictable order
          ordered-by user;
          key "reflector-name";
          leaf reflector-name {
            type string;
          }
          leaf description {
            type string;
          }
          leaf local-state {
            type string;
          }
          leaf discriminator {
            type string;
          }
          leaf shutdown {
            type string;
          }
        }
      }
    }
    container bmp {
      list station {
        // NCS patched for predictable order
        ordered-by user;
        key "station-name";
        leaf station-name {
          type string;
        }
        container connection {
          leaf connect-retry {
            type string;
          }
          leaf local-address {
            type string;
          }
          container station-address {
            leaf address {
              tailf:cli-drop-node-name;
              type string;
            }
            leaf port {
              type string;
            }
          }
          leaf router {
            type string;
          }
          container tcp-keepalive {
            leaf keep-count {
              type string;
            }
            leaf keep-idle {
              type string;
            }
            leaf keep-interval {
              type string;
            }
            leaf shutdown {
              type string;
            }
          }
        }
        leaf description {
          type string;
        }
        leaf-list family {
          // NCS patched for predictable order
          ordered-by user;
          type string;
        }
        leaf initiation-message {
          type string;
        }
        leaf report-local-routes {
          type empty;
        }
        leaf stats-report-interval {
          type string;
        }
        leaf shutdown {
          type string;
        }
      }
      leaf shutdown {
        type string;
      }
    }
    container call-trace {
      container location {

        grouping cf-group {
          leaf disable {
            type empty;
          }
          leaf size-limit {
            type string;
          }
        }
        container cf1 {
          uses cf-group;
        }
        container cf2 {
          uses cf-group;
        }
      }
      list trace-profile {
        // NCS patched for predictable order
        ordered-by user;
        key "profile-name";
        leaf profile-name {
          type string;
        }
        leaf description {
          type string;
        }
        leaf debug-output {
          type empty;
        }
        leaf size-limit {
          type string;
        }
      }
    }
    list card {
      // NCS patched for predictable order
      ordered-by user;
      key "slot-number";
      leaf slot-number {
        type string;
      }
      container card-type {
        leaf card-type {
          tailf:cli-drop-node-name;
          type string;
        }
        leaf level {
          type string;
        }
      }
      leaf fail-on-error {
        type empty;
      }
      list mda {
        // NCS patched for predictable order
        ordered-by user;
        key "mda-slot";
        leaf mda-slot {
          type string;
        }
        list event {
          // NCS patched for predictable order
          ordered-by user;
          key "event-name";
          leaf event-name {
            type string;
          }
          leaf action {
            type string;
          }
          leaf action-alt {
            tailf:alt-name "action";
            type string;
          }
        }
        container mda-type {
          presence "true";
          leaf type {
            tailf:cli-drop-node-name;
            type string;
          }
          leaf level {
            type string;
          }
        }
        container access {
          container ingress {
            leaf fabric-policy {
              type string;
            }
          }
        }
        leaf fail-on-error {
          type empty;
        }
        container egress-xpl {
          leaf window {
            type string;
          }
        }
        container ingress {
          container mcast-path-management {
            leaf shutdown {
              type string;
            }
          }
        }
        container ingress-xpl {
          leaf window {
            type string;
          }
        }
        container network {
          container ingress {
            leaf fabric-policy {
              type string;
            }
            container pool {
              leaf slope-policy {
                type string;
              }
            }
            leaf queue-policy {
              type string;
            }
          }
        }
        leaf sync-e {
          type empty;
        }
        list upgrade {
          // NCS patched for predictable order
          ordered-by user;
          tailf:cli-suppress-mode;
          key "number";
          leaf number {
            type string;
          }
          leaf path {
            type string;
          }
        }
        leaf shutdown {
          type string;
        }
      }
      list fp {
        // NCS patched for predictable order
        ordered-by user;
        key "id";
        leaf id {
          type string;
        }
        leaf fp-resource-policy {
          type string;
        }
        leaf init-extract-prio-mode {
          type string;
        }
        container egress {
          container wred-queue-control {

            grouping max-min-grouping {
              leaf min {
                type string;
              }
              leaf max {
                type string;
              }
            }
            container buffer-allocation {
              uses max-min-grouping;
            }
            container resv-cbs {
              uses max-min-grouping;
            }
            leaf slope-policy {
              type string;
            }
            leaf shutdown {
              type string;
            }
          }
        }
        container ingress {
          container mcast-path-management {
            leaf bandwidth-policy {
              type string;
            }
            leaf shutdown {
              type string;
            }
          }
          container network {
            list queue-group {
              // NCS patched for predictable order
              ordered-by user;
              key "name instance";
              leaf name {
                type string;
              }
              leaf instance {
                type string;
              }
            }
            leaf queue-policy {
              type string;
            }
          }
        }
        container hi-bw-mcast-src {
          leaf alarm {
            type empty;
          }
          leaf default-paths-only {
            type empty;
          }
          leaf group {
            type string;
          }
        }
      }
      container xiom {
        container x1 {
          presence "true";
          container xiom-type {
            leaf type {
              tailf:cli-drop-node-name;
              type string;
            }
            leaf level {
              type string;
            }
          }
          list upgrade {
            // NCS patched for predictable order
            ordered-by user;
            tailf:cli-suppress-mode;
            key "id";
            leaf id {
              type string;
            }
            leaf path {
              type string;
            }
          }
          list mda {
            // NCS patched for predictable order
            ordered-by user;
            key "id";
            leaf id {
              type string;
            }
            leaf mda-type {
              type string;
            }
            leaf shutdown {
              type string;
            }
          }
          leaf shutdown {
            type string;
          }
        }
        container x2 {
          presence "true";
          container xiom-type {
            leaf type {
              tailf:cli-drop-node-name;
              type string;
            }
            leaf level {
              type string;
            }
          }
          list upgrade {
            // NCS patched for predictable order
            ordered-by user;
            tailf:cli-suppress-mode;
            key "id";
            leaf id {
              type string;
            }
            leaf path {
              type string;
            }
          }
          list mda {
            // NCS patched for predictable order
            ordered-by user;
            key "id";
            leaf id {
              type string;
            }
            leaf mda-type {
              type string;
            }
            leaf shutdown {
              type string;
            }
          }
          leaf shutdown {
            type string;
          }
        }
      }
      leaf reset-on-recoverable-error {
        type empty;
      }
      leaf shutdown {
        type string;
      }
      container redundancy {
        leaf revertive {
          type empty;
        }
        container takeover {
          leaf delay {
            type string;
          }
        }
      }
    }
    container cflowd {
      presence "present";
      leaf active-timeout {
        type string;
      }
      leaf active-flow-timeout {
        type string;
      }
      leaf cache-size {
        type string;
      }
      list collector {
        // NCS patched for predictable order
        ordered-by user;
        key "collector-id";
        leaf collector-id {
          type string;
        }
        leaf version {
          type string;
        }
        leaf description {
          type string;
        }
        leaf template-set {
          type string;
        }
        leaf router {
          type ncs_template_router-type;
        }
        container export-filter {
          container interface-list {
            list router {
              // NCS patched for predictable order
              ordered-by user;
              tailf:cli-suppress-mode;
              key "router-id interface";
              leaf router-id {
                type ncs_template_router-type;
              }
              leaf interface {
                type string;
              }
            }
            container service {
              list ies {
                // NCS patched for predictable order
                ordered-by user;
                tailf:cli-suppress-mode;
                key "ies-name interface";
                leaf ies-name {
                  type string;
                }
                leaf interface {
                  type string;
                }
              }
              list vprn {
                // NCS patched for predictable order
                ordered-by user;
                tailf:cli-suppress-mode;
                key "vprn-name interface";
                leaf vprn-name {
                  type string;
                }
                leaf interface {
                  type string;
                }
              }
            }
          }
        }
        leaf autonomous-system-type {
          type string;
        }
        leaf shutdown {
          type empty;
        }
      }
      leaf export-mode {
        type string;
      }
      leaf inactive-timeout {
        type string;
      }
      leaf inactive-flow-timeout {
        type string;
      }
      leaf overflow {
        type string;
      }
      leaf rate {
        type string;
      }
      leaf template-retransmit {
        type string;
      }
      list sample-profile {
        // NCS patched for predictable order
        ordered-by user;
        key "profile-id";
        leaf profile-id {
          type string;
        }
        leaf sample-rate {
          type string;
        }
      }
      leaf shutdown {
        type empty;
      }
    }
    list interface-group-handler {
      // NCS patched for predictable order
      ordered-by user;
      key "index";
      leaf index {
        type string;
      }
      leaf shutdown {
        type string;
      }
    }
    container ipsec {
      list ike-policy {
        // NCS patched for predictable order
        ordered-by user;
        key "ike-policy-id";
        leaf ike-policy-id {
          type string;
        }
        leaf auth-algorithm {
          type string;
        }
        leaf auth-method {
          type string;
        }
        leaf auto-eap-method {
          type string;
        }
        leaf auto-eap-own-method {
          type string;
        }
        leaf description {
          type string;
        }
        leaf dh-group {
          type string;
        }
        container dpd {
          presence "present";
          leaf interval {
            type string;
          }
          leaf max-retries {
            type string;
          }
          leaf reply-only {
            type empty;
          }
        }
        leaf encryption-algorithm {
          type string;
        }
        leaf ike-mode {
          type string;
        }
        leaf ike-transform {
          type string;
        }
        leaf ike-version {
          type string;
        }
        leaf ipsec-lifetime {
          type string;
        }
        leaf isakmp-lifetime {
          type string;
        }
        leaf match-peer-id-to-cert {
          type empty;
        }
        container nat-traversal {
          presence "present";
          leaf force {
            type empty;
          }
          leaf keep-alive-interval {
            type string;
          }
          leaf force-keep-alive {
            type empty;
          }
        }
        leaf own-auth-method {
          type string;
        }
        container pfs {
          presence "present";
          leaf dh-group {
            type string;
          }
        }
      }
      list ike-transform {
        // NCS patched for predictable order
        ordered-by user;
        key "ike-transform-id";
        leaf ike-transform-id {
          type string;
        }
        leaf dh-group {
          type string;
        }
        leaf ike-auth-algorithm {
          type string;
        }
        leaf ike-encryption-algorithm {
          type string;
        }
        leaf isakmp-lifetime {
          type string;
        }
      }
      list ipsec-transform {
        // NCS patched for predictable order
        ordered-by user;
        key "transform-id";
        leaf transform-id {
          type string;
        }
        leaf esp-auth-algorithm {
          type string;
        }
        leaf esp-encryption-algorithm {
          type string;
        }
        leaf ipsec-lifetime {
          type string;
        }
        leaf pfs-dh-group {
          type string;
        }
      }
      list cert-profile {
        // NCS patched for predictable order
        ordered-by user;
        key "profile-name";
        leaf profile-name {
          type ncs_template_string32;
        }
        list entry {
          // NCS patched for predictable order
          ordered-by user;
          key "entry-id";
          leaf entry-id {
            type string;
          }
          leaf cert {
            type string;
          }
          leaf key {
            type string;
          }
          container send-chain {
            list ca-profile {
              // NCS patched for predictable order
              ordered-by user;
              tailf:cli-suppress-mode;
              key "name";
              leaf name {
                type ncs_template_string32;
              }
            }
          }
        }
        leaf shutdown {
          type string;
        }
      }
      list static-sa {
        // NCS patched for predictable order
        ordered-by user;
        key "sa-name";
        leaf sa-name {
          type string;
        }
        container authentication {
          leaf auth-algorithm {
            tailf:cli-drop-node-name;
            type string;
          }
          leaf hex-or-ascii {
            tailf:cli-drop-node-name;
            type string;
          }
          leaf key-value {
            tailf:cli-drop-node-name;
            type string;
          }
          leaf hash-type {
            tailf:cli-drop-node-name;
            type ncs_template_hash-method;
          }
        }
        leaf description {
          type string;
        }
        leaf protocol {
          type string;
        }
        leaf spi {
          type string;
        }
      }
      list trust-anchor-profile {
        // NCS patched for predictable order
        ordered-by user;
        key "name";
        leaf name {
          type ncs_template_string32;
        }
        list trust-anchor {
          // NCS patched for predictable order
          ordered-by user;
          tailf:cli-suppress-mode;
          key "ca-profile-name";
          leaf ca-profile-name {
            type ncs_template_string32;
          }
        }
      }
      list tunnel-template {
        // NCS patched for predictable order
        ordered-by user;
        key "tunnel-template-id";
        leaf tunnel-template-id {
          type string;
        }
        leaf description {
          type string;
        }
        leaf clear-df-bit {
          type empty;
        }
        leaf ip-mtu {
          type string;
        }
        leaf encapsulated-ip-mtu {
          type string;
        }
        leaf sp-reverse-route {
          type empty;
        }
        leaf replay-window {
          type string;
        }
        leaf-list transform {
          // NCS patched for predictable order
          ordered-by user;
          type string;
        }
      }
    }
    list pw-port {
      // NCS patched for predictable order
      ordered-by user;
      key "pw-port-id";
      leaf pw-port-id {
        type string;
      }
      leaf description {
        type string;
      }
      leaf encap-type {
        type string;
      }
    }
    list port {
      // NCS patched for predictable order
      ordered-by user;
      key "port-id";
      leaf port-id {
        type string;
      }
      leaf description {
        type string;
      }
      container access {

        grouping port-xgress-grouping {
          container pool {
            leaf amber-alarm-threshold {
              type string;
            }
            leaf red-alarm-threshold {
              type string;
            }
            leaf resv-cbs {
              type string;
            }
            leaf slope-policy {
              type string;
            }
          }
        }
        container egress {
          uses port-xgress-grouping;
        }
        container ingress {
          uses port-xgress-grouping;
        }
      }
      leaf type {
        type string;
      }
      container aps {
        leaf neighbor {
          type string;
        }
        leaf switching-mode {
          type string;
        }
        leaf protect-circuit {
          type string;
        }
        container working-circuit {
          leaf port-id {
            tailf:cli-drop-node-name;
            type string;
          }
          leaf number {
            type string;
          }
        }
      }
      container connector {
        presence "true";
        container breakout {
          presence "true";
          leaf extra {
            tailf:cli-drop-node-name;
            type string;
          }
        }
        leaf rs-fec-mode {
          type string;
        }
      }
      container ethernet {
        leaf eth-bn-egress-rate-changes {
          type empty;
        }
        leaf egress-port-qos-policy {
          type string;
        }
        leaf connection-type {
          type string;
        }
        leaf mode {
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          type string;
        }
        leaf mode-alt {
          tailf:alt-name "mode";
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          type string;
        }
        container dampening {
          container suppress-threshold {
            leaf threshold {
              tailf:cli-drop-node-name;
              type string;
            }
            leaf reuse-threshold {
              type string;
            }
          }
          container half-life {
            leaf time {
              tailf:cli-drop-node-name;
              type string;
            }
            leaf max-suppress-time {
              type string;
            }
          }
          leaf shutdown {
            type string;
          }
        }
        leaf-list report-alarm {
          // NCS patched for predictable order
          ordered-by user;
          type string;
        }
        container disable {
          leaf-list report-alarm {
            // NCS patched for predictable order
            ordered-by user;
            type string;
          }
        }
        container access {
          leaf accounting-policy {
            type string;
          }
          leaf bandwidth {
            type string;
          }
          container egress {
            list vport {
              // NCS patched for predictable order
              ordered-by user;
              key "name";
              leaf name {
                type ncs_template_string32;
              }
              container agg-rate {
                leaf limit-unused-bandwidth {
                  type empty;
                }
                leaf rate {
                  type string;
                }
              }
              leaf description {
                type string;
              }
              leaf egress-rate-modify {
                type empty;
              }
              container host-match {
                list dest {
                  // NCS patched for predictable order
                  ordered-by user;
                  tailf:cli-suppress-mode;
                  key "destination-string";
                  leaf destination-string {
                    type ncs_template_string32;
                  }
                }
              }
              leaf mon-port-sch {
                type empty;
              }
              leaf port-scheduler-policy {
                type string;
              }
              leaf scheduler-policy {
                type string;
              }
            }
            list queue-group {
              // NCS patched for predictable order
              ordered-by user;
              key "queue-group-name";
              leaf queue-group-name {
                type string;
              }
              leaf instance {
                type string;
              }
              leaf description {
                type string;
              }
              container host-match {
                list dest {
                  // NCS patched for predictable order
                  ordered-by user;
                  tailf:cli-suppress-mode;
                  key "destination-string";
                  leaf destination-string {
                    type ncs_template_string32;
                  }
                }
              }
            }
            leaf qos {
              type string;
            }
          }
          container ingress {
            list queue-group {
              // NCS patched for predictable order
              ordered-by user;
              key "id";
              leaf id {
                type string;
              }
            }
          }
        }
        container crc-monitor {
          container sd-threshold {
            leaf treshold {
              tailf:cli-drop-node-name;
              type string;
            }
            leaf multiplier {
              type string;
            }
          }
          container sf-threshold {
            leaf treshold {
              tailf:cli-drop-node-name;
              type string;
            }
            leaf multiplier {
              type string;
            }
          }
          leaf window-size {
            type string;
          }
        }
        leaf collect-stats {
          type empty;
        }
        container autonegotiate {
          choice autonegotiate-choice {
            leaf disable {
              type empty;
            }
            leaf limited {
              type empty;
            }
          }
        }
        leaf dot1q-etype {
          type string;
        }
        container dot1x {
          container macsec {
            leaf rx-must-be-encrypted {
              type empty;
            }
            leaf-list exclude-protocol {
              // NCS patched for predictable order
              ordered-by user;
              type string;
            }
            list sub-port {
              // NCS patched for predictable order
              ordered-by user;
              key "port-id";
              leaf port-id {
                type string;
              }
              unique "ca-name";
              leaf ca-name {
                type string;
              }
              container encap-match {
                leaf encap {
                  tailf:cli-drop-node-name;
                  type string;
                }
                leaf encap-value {
                  tailf:cli-drop-node-name;
                  type string;
                }
              }
              leaf max-peer {
                type string;
              }
              leaf shutdown {
                type string;
              }
            }
          }
          leaf tunneling {
            type empty;
          }
        }
        container down-when-looped {
          leaf use-broadcast-address {
            type empty;
          }
          leaf shutdown {
            type string;
          }
        }
        leaf lacp-tunnel {
          type empty;
        }
        container efm-oam {
          leaf accept-remote-loopback {
            type empty;
          }
          leaf hold-time {
            type string;
          }
          container transmit-interval {
            leaf interval {
              tailf:cli-drop-node-name;
              type string;
            }
            leaf multiplier {
              type string;
            }
          }
          container link-monitoring {
            leaf shutdown {
              type string;
            }
          }
          leaf tunneling {
            type empty;
          }
          leaf shutdown {
            type string;
          }
        }
        container egress {
          list exp-secondary-shaper {
            // NCS patched for predictable order
            ordered-by user;
            key "secondary-shaper-name";
            leaf secondary-shaper-name {
              type string;
            }
            container agg-burst {
              container high-burst-increase {
                leaf size {
                  tailf:cli-drop-node-name;
                  type string;
                }
                leaf rate {
                  tailf:cli-drop-node-name;
                  type string;
                }
              }
              container low-burst-limit {
                leaf size {
                  tailf:cli-drop-node-name;
                  type string;
                }
                leaf rate {
                  tailf:cli-drop-node-name;
                  type string;
                }
              }
            }
            container class {
              leaf class-number {
                tailf:cli-drop-node-name;
                type string;
              }
              leaf rate {
                type string;
              }
            }
            leaf low-burst-max-class {
              type string;
            }
            container rate {
              leaf rate {
                tailf:cli-drop-node-name;
                type string;
              }
              leaf monitor-threshold {
                type string;
              }
            }
          }
          list queue-group {
            // NCS patched for predictable order
            ordered-by user;
            key "name";
            leaf name {
              type string;
            }
          }
          leaf scheduler-policy {
            type string;
          }
        }
        leaf egress-rate {
          type string;
        }
        leaf egress-scheduler-policy {
          // NCS drop tailf-common:cli-diff-create-before statement
          type string;
        }
        container egress-scheduler-override {
          presence "true";
          list level {
            // NCS patched for predictable order
            ordered-by user;
            tailf:cli-suppress-mode;
            key "priority-level";
            leaf priority-level {
              type string;
            }
            leaf rate {
              type string;
            }
            leaf cir {
              type string;
            }
          }
          leaf max-rate {
            type string;
          }
        }
        container hold-time {
          leaf up {
            type string;
          }
          leaf down {
            type string;
          }
          leaf unit {
            tailf:cli-drop-node-name;
            type string;
          }
        }
        leaf ingress-rate {
          type string;
        }
        container alt-ingress-rate {
          tailf:alt-name "ingress-rate";
          presence "true";
          leaf ingress-rate {
            tailf:cli-drop-node-name;
            type string;
          }
          leaf cbs {
            type string;
          }
          choice unit {
            leaf bytes {
              type empty;
            }
            leaf kilobytes {
              type empty;
            }
          }
          leaf src-pause {
            type empty;
          }
        }
        container lldp {
          list dest-mac {
            // NCS patched for predictable order
            ordered-by user;
            key "id";
            leaf id {
              type string;
            }
            leaf tunnel-nearest-bridge {
              type empty;
            }
            leaf notification {
              type empty;
            }
            leaf admin-status {
              type string;
            }
            leaf port-id-subtype {
              type string;
            }
            leaf-list tx-mgmt-address {
              // NCS patched for predictable order
              ordered-by user;
              type string;
            }
            leaf-list tx-tlvs {
              // NCS patched for predictable order
              ordered-by user;
              type string;
            }
          }
        }
        leaf encap-type {
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          type string;
        }
        leaf mac {
          type ncs_template_ieee-mac;
        }
        leaf mtu {
          type string;
        }
        leaf duplex {
          type string;
        }
        leaf speed {
          type ncs_template_port-speed;
        }
        leaf alt-speed {
          tailf:alt-name "speed";
          type ncs_template_port-speed;
        }
        container network {
          leaf accounting-policy {
            type string;
          }
          leaf collect-stats {
            type empty;
          }
          container egress {
            list queue-group {
              // NCS patched for predictable order
              ordered-by user;
              key "id";
              leaf id {
                type string;
              }
              leaf instance {
                type string;
              }
              leaf accounting-policy {
                type string;
              }
              uses ncs_template_agg-rate-grouping;
              leaf collect-stats {
                type empty;
              }
              leaf description {
                type string;
              }
              leaf policer-control-policy {
                type string;
              }
              container queue-overrides {
                list queue {
                  // NCS patched for predictable order
                  ordered-by user;
                  key "queue-id";
                  leaf queue-id {
                    type string;
                  }
                }
              }
              leaf scheduler-policy {
                type string;
              }
            }
          }
          leaf queue-policy {
            type string;
          }
          leaf scheduler-mode {
            type ncs_template_scheduler-mode;
          }
          leaf qos {
            type string;
          }
        }
        leaf qinq-etype {
          type string;
        }
        container ssm {
          leaf code-type {
            type string;
          }
          leaf tx-dus {
            type empty;
          }
          leaf shutdown {
            type string;
          }
        }
        leaf util-stats-interval {
          type string;
        }
        leaf xgig {
          type string;
        }
        leaf xor-mode {
          type string;
        }
        container down-on-internal-error {
          presence "true";
          leaf tx-disable {
            type empty;
          }
        }
        leaf rs-fec-mode {
          type string;
        }
      }
      container hybrid-buffer-allocation {

        grouping xgress-weights {
          leaf access {
            type string;
          }
          leaf network {
            type string;
          }
        }
        container egr-weight {
          uses xgress-weights;
        }
        container ing-weight {
          uses xgress-weights;
        }
      }
      container transceiver {
        leaf digital-coherent-optics {
          type empty;
        }
      }
      container dwdm {
        container amplifier {
          leaf-list report-alarms {
            // NCS patched for predictable order
            ordered-by user;
            type string;
          }
        }
        leaf channel {
          type string;
        }
        container coherent {
          leaf target-power {
            type string;
          }
          leaf compatibility {
            type string;
          }
          container sweep {
            leaf start {
              type string;
            }
            leaf end {
              type string;
            }
          }
          leaf channel {
            type string;
          }
          leaf mode {
            type string;
          }
          leaf rx-los-thresh {
            type string;
          }
        }
        leaf frequency {
          type string;
        }
        leaf rxdtv-adjust {
          type empty;
        }
        container tdcm {
          leaf channel {
            type string;
          }
          leaf dispersion {
            type string;
          }
          leaf mode {
            type string;
          }
          leaf-list report-alarms {
            // NCS patched for predictable order
            ordered-by user;
            type string;
          }
          container sweep {
            leaf start {
              type string;
            }
            leaf end {
              type string;
            }
          }
          leaf shutdown {
            type string;
          }
        }
      }
      container modify-buffer-allocation-rate {
        leaf egr-percentage-of-rate {
          type string;
        }
        leaf ing-percentage-of-rate {
          type string;
        }
      }
      container multilink-bundle {
        leaf fragment-threshold {
          type string;
        }
        list member {
          // NCS patched for predictable order
          ordered-by user;
          tailf:cli-suppress-mode;
          key "id";
          leaf id {
            type string;
          }
        }
      }
      container network {
        container egress {
          container pool {
            leaf slope-policy {
              type string;
            }
          }
        }
      }
      container otu {
        presence "present";
        leaf async-mapping {
          type empty;
        }
        leaf fec {
          type string;
        }
        leaf otu2-lan-data-rate {
          type string;
        }
        leaf-list report-alarm {
          // NCS patched for predictable order
          ordered-by user;
          type string;
        }
        leaf sd-threshold {
          type string;
        }
        leaf sf-sd-method {
          type string;
        }
        leaf sf-threshold {
          type string;
        }
        container sm-tti {
          container expected {
            choice expected {
              leaf string {
                type string;
              }
              leaf bytes {
                type string;
              }
              leaf use-rx {
                type empty;
              }
            }
          }
          container tx {
            choice tx {
              leaf string {
                type string;
              }
              leaf bytes {
                type string;
              }
            }
          }
        }
      }
      container sonet-sdh {
        leaf clock-source {
          type string;
        }
        leaf framing {
          type string;
        }
        list group {
          // NCS patched for predictable order
          ordered-by user;
          tailf:cli-suppress-mode;
          // NCS drop tailf-common:cli-diff-create-before statement
          key "sonet-sdh-index";
          leaf sonet-sdh-index {
            type string;
          }
          leaf payload {
            type string;
          }
        }
        container hold-time {
          leaf up {
            type string;
          }
          leaf down {
            type string;
          }
        }
        leaf loopback {
          type string;
        }

        grouping port-sonet-sdh-path-grouping {
          leaf mode {
            type string;
          }
          leaf encap-type {
            type string;
          }
          leaf egress-scheduler-policy {
            type string;
          }
          leaf crc {
            type string;
          }
          leaf scramble {
            type empty;
          }
          container network {
            leaf queue-policy {
              type string;
            }
          }
          leaf payload {
            type string;
          }
          container frame-relay {
            leaf lmi-type {
              type string;
            }
            leaf mode {
              type string;
            }
          }
          leaf-list report-alarm {
            // NCS patched for predictable order
            ordered-by user;
            type string;
          }
          leaf shutdown {
            type string;
          }
        }
        container path-sts3-wrapper {
          tailf:cli-drop-node-name;
          container path {
            container sts3 {
              presence "true";
              uses port-sonet-sdh-path-grouping;
            }
          }
        }
        list path {
          // NCS patched for predictable order
          ordered-by user;
          key "sonet-sdh-index";
          leaf sonet-sdh-index {
            type string;
          }
          uses port-sonet-sdh-path-grouping;
        }
        leaf-list report-alarm {
          // NCS patched for predictable order
          ordered-by user;
          type string;
        }
        container section-trace {
          choice a {
            leaf increment-z0 {
              type empty;
            }
            leaf byte {
              type string;
            }
            leaf string {
              type string;
            }
          }
        }
        leaf single-fiber {
          type empty;
        }
        leaf speed {
          type string;
        }
        leaf suppress-lo-alarm {
          type empty;
        }
        container threshold {
          leaf value {
            tailf:cli-drop-node-name;
            type string;
          }
          leaf rate {
            type string;
          }
        }
        leaf tx-dus {
          type empty;
        }
      }
      container tdm {
        leaf buildout {
          type string;
        }
        list ds1 {
          // NCS patched for predictable order
          ordered-by user;
          key "ds1-id";
          leaf ds1-id {
            type string;
          }
          container bert {
            leaf value {
              type string;
            }
            leaf duration {
              type string;
            }
          }
          leaf bit-error-insertion {
            type string;
          }
          leaf framing {
            type string;
          }
          list channel-group {
            // NCS patched for predictable order
            ordered-by user;
            key "id";
            leaf id {
              type string;
            }
            leaf clock-source {
              type string;
            }
            leaf encap-type {
              type string;
            }
            container ppp {
              leaf ber-sf-link-down {
                type empty;
              }
            }
            leaf timeslots {
              type string;
            }
            leaf shutdown {
              type string;
            }
          }
          leaf clock-source {
            type string;
          }
          leaf invert-data {
            type empty;
          }
          leaf loopback {
            type string;
          }
          leaf remote-loop-respond {
            type empty;
          }
          leaf-list report-alarm {
            // NCS patched for predictable order
            ordered-by user;
            type string;
          }
          leaf signal-mode {
            type string;
          }
          container threshold {
            leaf value {
              type string;
            }
            leaf rate {
              type string;
            }
          }
          leaf shutdown {
            type string;
          }
        }
        list ds3 {
          // NCS patched for predictable order
          ordered-by user;
          key "ds3-id";
          leaf ds3-id {
            type string;
          }
          container bert {
            leaf value {
              type string;
            }
          }
          leaf channelized {
            type string;
          }
          leaf clock-source {
            type string;
          }
          leaf encap-type {
            type string;
          }
          leaf shutdown {
            type string;
          }
        }
        list e1 {
          // NCS patched for predictable order
          ordered-by user;
          key "e1-id";
          leaf e1-id {
            type string;
          }
          leaf framing {
            type string;
          }
          leaf clock-source {
            type string;
          }
          list channel-group {
            // NCS patched for predictable order
            ordered-by user;
            key "channel-group-id";
            leaf channel-group-id {
              type string;
            }
            leaf encap-type {
              type string;
            }
            leaf-list timeslots {
              // NCS patched for predictable order
              ordered-by user;
              tailf:cli-range-list-syntax;
              type string;
            }
            leaf shutdown {
              type string;
            }
          }
          leaf shutdown {
            type string;
          }
        }
        leaf lbo {
          type string;
        }
        leaf length {
          type string;
        }
      }
      leaf shutdown {
        type string;
      }
    }
    container isa {
      list application-assurance-group {
        // NCS patched for predictable order
        ordered-by user;
        key "aa-group-id";
        leaf aa-group-id {
          type string;
        }
        leaf aa-sub-scale {
          type string;
        }
        leaf shutdown {
          type string;
        }
      }
      list tunnel-group {
        // NCS patched for predictable order
        ordered-by user;
        key "tunnel-group-id";
        leaf tunnel-group-id {
          type string;
        }
        leaf isa-scale-mode {
          type string;
        }
        leaf active-mda-number {
          type string;
        }
        leaf ipsec-responder-only {
          type empty;
        }
        leaf description {
          type string;
        }
        leaf multi-active {
          type empty;
        }
        list mda {
          // NCS patched for predictable order
          ordered-by user;
          tailf:cli-suppress-mode;
          key "mda";
          leaf mda {
            type string;
          }
        }
        leaf primary {
          type string;
        }
        list esa-vm {
          // NCS patched for predictable order
          ordered-by user;
          tailf:cli-suppress-mode;
          key "esa-id vm-id";
          leaf esa-id {
            type string;
          }
          leaf vm-id {
            type string;
          }
        }
        leaf reassembly {
          type string;
        }
        leaf shutdown {
          type string;
        }
      }
      list nat-group {
        // NCS patched for predictable order
        ordered-by user;
        key "nat-group-id";
        leaf nat-group-id {
          type string;
        }
        leaf description {
          type string;
        }
        leaf active-mda-limit {
          type string;
        }
        leaf mda {
          type string;
        }
        leaf shutdown {
          type string;
        }
      }
    }
    container port-xc {
      list pxc {
        // NCS patched for predictable order
        ordered-by user;
        // NCS drop tailf-common:cli-diff-create-before statement
        key "pxc-id";
        leaf pxc-id {
          type string;
        }
        leaf description {
          type string;
        }
        leaf port {
          type string;
        }
        leaf shutdown {
          type string;
        }
      }
    }
    container macsec {
      list connectivity-association {
        // NCS patched for predictable order
        ordered-by user;
        key "name";
        leaf name {
          type string;
        }
        leaf description {
          type string;
        }
        container static-cak {
          list pre-shared-key {
            // NCS patched for predictable order
            ordered-by user;
            key "key-id encryption-type";
            leaf key-id {
              type string;
            }
            leaf encryption-type {
              type string;
            }
            container cak {
              leaf val {
                tailf:cli-drop-node-name;
                type string;
              }
              leaf algo {
                tailf:cli-drop-node-name;
                type string;
              }
            }
            leaf ckn {
              type string;
            }
          }
        }
        leaf shutdown {
          type string;
        }
      }
    }
    list lag {
      // NCS patched for predictable order
      ordered-by user;
      // NCS drop tailf-common:cli-diff-create-before statement
      // NCS drop tailf-common:cli-diff-create-before statement
      // NCS drop tailf-common:cli-diff-create-before statement
      // NCS drop tailf-common:cli-diff-create-before statement
      // NCS drop tailf-common:cli-diff-create-before statement
      // NCS drop tailf-common:cli-diff-create-before statement
      // NCS drop tailf-common:cli-diff-create-before statement
      key "id";
      leaf id {
        type string;
      }
      leaf name {
        type string;
      }
      leaf description {
        type string;
      }
      container hash-weight-threshold {
        leaf weight {
          tailf:cli-drop-node-name;
          type string;
        }
        leaf action {
          type string;
        }
        leaf cost {
          type string;
        }
      }
      leaf port-weight-speed {
        type string;
      }
      container hold-time {
        leaf down {
          type string;
        }
      }
      container bfd {
        list family {
          // NCS patched for predictable order
          ordered-by user;
          key "family";
          leaf family {
            type string;
          }
          leaf bfd-on-distributing-only {
            type empty;
          }
          leaf local-ip-address {
            type string;
          }
          leaf max-admin-down-time {
            type string;
          }
          leaf max-setup-time {
            type string;
          }
          leaf multiplier {
            type string;
          }
          leaf receive-interval {
            type string;
          }
          leaf remote-ip-address {
            type string;
          }
          leaf transmit-interval {
            type string;
          }
          leaf shutdown {
            type string;
          }
        }
      }
      leaf port-type {
        type string;
      }
      list port {
        // NCS patched for predictable order
        ordered-by user;
        tailf:cli-suppress-mode;
        // NCS drop tailf-common:cli-diff-create-before statement
        key "port-id";
        leaf port-id {
          type string;
        }
        leaf sub-group {
          type string;
        }
        container priority {
          leaf priority {
            tailf:cli-drop-node-name;
            type string;
          }
          leaf sub-group {
            type string;
          }
        }
      }
      container per-link-hash {
        tailf:cli-drop-node-name;
        leaf per-link-hash {
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          type empty;
        }
        leaf weighted {
          type empty;
        }
        leaf auto-rebalance {
          type empty;
        }
      }
      container access {
        container adapt-qos {
          leaf adapt {
            tailf:cli-drop-node-name;
            type string;
          }
          leaf include-egr-hash-cfg {
            type empty;
          }
        }
        leaf per-fp-egr-queuing {
          type empty;
        }
        leaf per-fp-ing-queuing {
          type empty;
        }
        leaf per-fp-sap-instance {
          type empty;
        }
      }
      leaf mode {
        // NCS drop tailf-common:cli-diff-create-before statement
        // NCS drop tailf-common:cli-diff-create-before statement
        // NCS drop tailf-common:cli-diff-create-before statement
        // NCS drop tailf-common:cli-diff-create-before statement
        // NCS drop tailf-common:cli-diff-create-before statement
        // NCS drop tailf-common:cli-diff-create-before statement
        // NCS drop tailf-common:cli-diff-create-before statement
        // NCS drop tailf-common:cli-diff-create-before statement
        type string;
      }
      leaf monitor-oper-group {
        type string;
      }
      leaf encap-type {
        // NCS drop tailf-common:cli-diff-create-before statement
        // NCS drop tailf-common:cli-diff-create-before statement
        // NCS drop tailf-common:cli-diff-create-before statement
        // NCS drop tailf-common:cli-diff-create-before statement
        // NCS drop tailf-common:cli-diff-create-before statement
        // NCS drop tailf-common:cli-diff-create-before statement
        // NCS drop tailf-common:cli-diff-create-before statement
        type string;
      }
      leaf dynamic-cost {
        type empty;
      }
      leaf mac {
        type string;
      }
      list link-map-profile {
        // NCS patched for predictable order
        ordered-by user;
        key "link-map-profile-id";
        leaf link-map-profile-id {
          type string;
        }
        leaf description {
          type string;
        }
        leaf failure-mode {
          type string;
        }
        list link {
          // NCS patched for predictable order
          ordered-by user;
          tailf:cli-suppress-mode;
          key "port-id";
          leaf port-id {
            type string;
          }
          leaf role {
            tailf:cli-drop-node-name;
            type string;
          }
        }
      }
      container port-threshold {
        leaf value {
          tailf:cli-drop-node-name;
          type string;
        }
        leaf action {
          type string;
        }
      }
      container scheduler-mode {
        container vlan-qos {
          presence "true";
          list vlan-qos-policy {
            // NCS patched for predictable order
            ordered-by user;
            key "vlan-qos-policy-name";
            leaf vlan-qos-policy-name {
              type string;
            }
            container agg-rate {
              container rate {
                leaf pir {
                  tailf:cli-drop-node-name;
                  type string;
                }
                leaf cir {
                  type string;
                }
              }
            }
          }
        }
      }
      container lacp {
        leaf mode {
          tailf:cli-drop-node-name;
          type string;
        }
        leaf administrative-key {
          type string;
        }
        leaf system-id {
          type string;
        }
        leaf system-priority {
          type string;
        }
      }
      leaf lacp-mux-control {
        type string;
      }
      leaf lacp-xmit-interval {
        type string;
      }
      leaf lacp-xmit-standby {
        type empty;
      }
      container selection-criteria {
        leaf criteria {
          tailf:cli-drop-node-name;
          type string;
        }
        leaf slave-to-partner {
          type empty;
        }
        leaf subgroup-hold-time {
          type string;
        }
      }
      leaf standby-signaling {
        type string;
      }
      container weight-threshold {
        leaf value {
          tailf:cli-drop-node-name;
          type string;
        }
        leaf action {
          type string;
        }
      }
      leaf shutdown {
        type string;
      }
    }
    container fwd-path-ext {
      container sdp-id-range {
        leaf from {
          type string;
        }
        leaf to {
          type string;
        }
      }
      list fpe {
        // NCS patched for predictable order
        ordered-by user;
        key "fpe-id";
        leaf fpe-id {
          type string;
        }
        container path {
          leaf pxc {
            type string;
          }
          leaf xc-a {
            type string;
          }
          leaf xc-b {
            type string;
          }
        }
        leaf pw-port {
          type empty;
        }
      }
    }
    container cron {
      list script {
        // NCS patched for predictable order
        ordered-by user;
        key "id";
        leaf id {
          type string;
        }
        leaf description {
          type string;
        }
        leaf location {
          type string;
        }
        leaf shutdown {
          type string;
        }
      }
      list action {
        // NCS patched for predictable order
        ordered-by user;
        key "id";
        leaf id {
          type string;
        }
        leaf max-completed {
          type string;
        }
        leaf expire-time {
          type ncs_template_expire-time;
        }
        leaf lifetime {
          type ncs_template_expire-time;
        }
        leaf results {
          type string;
        }
        leaf script {
          type string;
        }
        leaf shutdown {
          type string;
        }
      }
      uses ncs_template_cron-schedule-grouping {
        augment "schedule" {
          leaf action {
            type string;
          }
        }
      }
    }
    container mcast-management {
      list bandwidth-policy {
        // NCS patched for predictable order
        ordered-by user;
        key "policy-name";
        leaf policy-name {
          type ncs_template_string32;
        }

        grouping path-grouping {
          leaf path-limit {
            type string;
          }
        }
        container primary-path {
          uses path-grouping;
        }
        container secondary-path {
          uses path-grouping;
        }
      }
      container chassis-level {
        leaf round-robin-inactive-records {
          type empty;
        }
        container per-mcast-plane-capacity {

          grouping capacity-percentage-grouping {
            leaf primary-percentage {
              tailf:cli-drop-node-name;
              type string;
            }
            leaf secondary {
              type string;
            }
          }
          container mcast-capacity {
            uses capacity-percentage-grouping;
          }
          container redundant-mcast-capacity {
            uses capacity-percentage-grouping;
          }
          leaf total-capacity {
            type string;
          }
        }
      }
      list multicast-info-policy {
        // NCS patched for predictable order
        ordered-by user;
        key "policy-name";
        leaf policy-name {
          type ncs_template_string32;
        }
        list bundle {
          // NCS patched for predictable order
          ordered-by user;
          key "bundle-name";
          leaf bundle-name {
            type ncs_template_string32;
          }
          leaf keepalive-override {
            type string;
          }
          list channel {
            // NCS patched for predictable order
            ordered-by user;
            key "ip-address";
            leaf ip-address {
              type string;
            }
            leaf second-ip-address {
              tailf:cli-drop-node-name;
              type string;
            }
            container bw-activity {
              leaf activity {
                tailf:cli-drop-node-name;
                type string;
              }
              leaf falling-delay {
                type string;
              }
              leaf black-hole-rate {
                type string;
              }
            }
          }
          leaf description {
            type string;
          }
        }
      }
    }
    container oam-pm {
      list bin-group {
        // NCS patched for predictable order
        ordered-by user;
        key "bin-group-number";
        leaf bin-group-number {
          type string;
        }
        leaf fd-bin-count {
          type string;
        }
        leaf fdr-bin-count {
          type string;
        }
        leaf ifdv-bin-count {
          type string;
        }
        leaf description {
          type string;
        }
        list bin-type {
          // NCS patched for predictable order
          ordered-by user;
          key "bt";
          leaf bt {
            type string;
          }
          list bin {
            // NCS patched for predictable order
            ordered-by user;
            key "bin-number";
            leaf bin-number {
              type string;
            }
            leaf lower-bound {
              type string;
            }
          }

          typedef bin-group-event-type {
            type string;
          }
          list delay-event {
            // NCS patched for predictable order
            ordered-by user;
            tailf:cli-suppress-mode;
            key "event-type";
            leaf event-type {
              type bin-group-event-type;
            }
            leaf lowest-bin {
              type string;
            }
            leaf threshold {
              type string;
            }
            leaf clear {
              type string;
            }
          }
          list delay-event-exclusion {
            // NCS patched for predictable order
            ordered-by user;
            tailf:cli-suppress-mode;
            key "event-type";
            leaf event-type {
              type bin-group-event-type;
            }
            leaf lowest-bin {
              type string;
            }
          }
        }
        leaf shutdown {
          type string;
        }
      }
      list session {
        // NCS patched for predictable order
        ordered-by user;
        key "session-name";
        leaf session-name {
          type ncs_template_string32;
        }
        leaf test-family {
          type string;
        }
        leaf session-type {
          type string;
        }
        leaf bin-group {
          type string;
        }
        leaf description {
          type string;
        }
        list meas-interval {
          // NCS patched for predictable order
          ordered-by user;
          // NCS drop tailf-common:cli-diff-create-before statement
          key "interval";
          leaf interval {
            type string;
          }
          leaf accounting-policy {
            type string;
          }
          leaf intervals-stored {
            type string;
          }
          container event-mon {
            leaf delay-events {
              type empty;
            }
            leaf loss-events {
              type empty;
            }
            leaf shutdown {
              type string;
            }
          }
        }
        container ip {
          leaf router-instance {
            type string;
          }
          leaf source-udp-port {
            type string;
          }
          leaf destination {
            type string;
          }
          leaf source {
            type string;
          }
          leaf dest-udp-port {
            type string;
          }
          list twamp-light {
            // NCS patched for predictable order
            ordered-by user;
            key "test-id";
            leaf test-id {
              type string;
            }
            leaf record-stats {
              type string;
            }
            leaf shutdown {
              type string;
            }
          }
        }
        container ethernet {
          leaf dest-mac {
            type ncs_template_ieee-mac;
          }
          leaf priority {
            type string;
          }
          container source {
            leaf mep {
              type string;
            }
            leaf domain {
              type string;
            }
            leaf association {
              type string;
            }
          }
          container dmm {
            leaf test-id {
              type string;
            }
            leaf shutdown {
              type string;
            }
          }
        }
      }
    }
    container qos {
      list adv-config-policy {
        // NCS patched for predictable order
        ordered-by user;
        key "adv-config-policy-name";
        leaf adv-config-policy-name {
          type string;
        }
        container child-control {
          container offered-measurement {
            leaf fast-start {
              type empty;
            }
            leaf fast-stop {
              type empty;
            }
          }
        }
        leaf description {
          type string;
        }
      }
      list dot1p-fc-map {
        // NCS patched for predictable order
        ordered-by user;
        key "name";
        leaf name {
          type string;
        }
        container default-action {
          leaf fc {
            type string;
          }
          leaf profile {
            type string;
          }
        }
        list dot1p {
          // NCS patched for predictable order
          ordered-by user;
          tailf:cli-suppress-mode;
          key "priority";
          leaf priority {
            type string;
          }
          leaf fc {
            type string;
          }
          leaf profile {
            type string;
          }
        }
      }
      list egress-remark-policy {
        // NCS patched for predictable order
        ordered-by user;
        key "egress-remark-policy-name";
        leaf egress-remark-policy-name {
          type string;
        }
        leaf description {
          type string;
        }
        list fc {
          // NCS patched for predictable order
          ordered-by user;
          key "fc-name";
          leaf fc-name {
            type ncs_template_fc-name;
          }
          container dscp {
            choice dscp {
              leaf dscp-name {
                tailf:cli-drop-node-name;
                type string;
              }
              case in-out {
                leaf in-profile {
                  type string;
                }
                leaf out-profile {
                  type string;
                }
              }
            }
          }
          container dot1p {
            uses ncs_template_dot1p-params-grouping;
          }
          container lsp-exp {
            choice lsp-exp {
              leaf lsp-exp-value {
                tailf:cli-drop-node-name;
                type string;
              }
              case in-out {
                leaf in-profile {
                  type string;
                }
                leaf out-profile {
                  type string;
                }
              }
            }
          }
        }
      }
      list fp-resource-policy {
        // NCS patched for predictable order
        ordered-by user;
        key "policy-id";
        leaf policy-id {
          type string;
        }
        leaf description {
          type string;
        }
      }
      container packet-byte-offset {
        leaf shutdown {
          type string;
        }
      }
      list ingress-classification-policy {
        // NCS patched for predictable order
        ordered-by user;
        key "name";
        leaf name {
          type string;
        }
        leaf description {
          type string;
        }
        leaf allow-attachment {
          type string;
        }
        container default-action {
          leaf fc {
            type ncs_template_fc-name;
          }
          leaf profile {
            type ncs_template_in-out;
          }
        }
        uses ncs_template_qos-dscp-list-grouping;
        uses ncs_template_qos-lsp-exp-grouping;
        uses ncs_template_qos-dot1p-list-grouping;
      }
      list network-ingress {
        // NCS patched for predictable order
        ordered-by user;
        key "name";
        leaf name {
          type string;
        }
        leaf description {
          type string;
        }
        leaf ingress-classification-policy {
          type string;
        }
        list policer {
          // NCS patched for predictable order
          ordered-by user;
          key "policer-id";
          leaf policer-id {
            type string;
          }
          // NCS expand uses statement
          container cbs {
            // NCS expand uses statement
            leaf size {
              tailf:cli-drop-node-name;
              type string;
            }
            leaf unit {
              tailf:cli-drop-node-name;
              type string;
            }
          }
          container mbs {
            // NCS expand uses statement
            leaf size {
              tailf:cli-drop-node-name;
              type string;
            }
            leaf unit {
              tailf:cli-drop-node-name;
              type string;
            }
          }
          container rate {
            leaf pir {
              tailf:cli-drop-node-name;
              type ncs_template_rate-type;
            }
            leaf cir {
              type ncs_template_rate-type;
            }
          }
          leaf stat-mode {
            type ncs_template_policer-stat-mode;
          }
        }
        list fc {
          // NCS patched for predictable order
          ordered-by user;
          key "fc-name";
          leaf fc-name {
            type ncs_template_fc-name;
          }
          leaf multicast-policer {
            type string;
          }
          leaf policer {
            type string;
          }
        }
      }
      list port-qos-policy {
        // NCS patched for predictable order
        ordered-by user;
        key "port-qos-policy-name";
        leaf port-qos-policy-name {
          type string;
        }
        leaf description {
          type string;
        }
        list queue {
          // NCS patched for predictable order
          ordered-by user;
          key "queue-id";
          leaf queue-id {
            type string;
          }
          leaf queue-mgmt {
            type string;
          }
          container scheduler-mode {
            leaf scheduler-mode {
              tailf:cli-drop-node-name;
              type string;
            }
            leaf pir-weight {
              type string;
            }
            uses ncs_template_qos-queue-percent-rate-grouping;
          }
        }
        container packet-byte-offset {
          leaf add {
            type string;
          }
          leaf subtract {
            type string;
          }
        }
        list wrr-weights {
          // NCS patched for predictable order
          ordered-by user;
          key "wrr-weights-id";
          leaf wrr-weights-id {
            type string;
          }
          leaf mc-weight {
            type string;
          }
          leaf uc-weight {
            type string;
          }
        }
      }
      list queue-mgmt-policy {
        // NCS patched for predictable order
        ordered-by user;
        key "queue-mgmt-name";
        leaf queue-mgmt-name {
          type string;
        }
        leaf description {
          type string;
        }
        container high-slope {
          uses ncs_template_slope-params-grouping;
        }
        container low-slope {
          uses ncs_template_slope-params-grouping;
        }
        container exceed-slope {
          uses ncs_template_slope-params-grouping;
        }
        container highplus-slope {
          uses ncs_template_slope-params-grouping;
        }
        leaf mbs {
          type string;
        }
      }
      list vlan-qos-policy {
        // NCS patched for predictable order
        ordered-by user;
        key "policy-id";
        leaf policy-id {
          type string;
        }
        leaf description {
          type string;
        }
        container packet-byte-offset {
          leaf add {
            type string;
          }
          leaf subtract {
            type string;
          }
        }
        leaf stat-mode {
          type string;
        }
        list cir-weight-profile {
          // NCS patched for predictable order
          ordered-by user;
          key "profile-id";
          leaf profile-id {
            type string;
          }
          leaf weight {
            type string;
          }
        }
        list queue {
          // NCS patched for predictable order
          ordered-by user;
          key "queue-id";
          leaf queue-id {
            type string;
          }
          uses ncs_template_qos-queue-percent-rate-grouping;
          leaf queue-mgmt {
            type string;
          }
          container queue-type {
            leaf queue-type-alt1 {
              tailf:cli-drop-node-name;
              type ncs_template_queue-type;
            }
            leaf queue-type-alt2 {
              tailf:cli-drop-node-name;
              type ncs_template_queue-type;
            }
            leaf queue-type-alt3 {
              tailf:cli-drop-node-name;
              type ncs_template_queue-type;
            }
            uses ncs_template_qos-queue-percent-rate-grouping;
            leaf cir-weight-profile {
              type string;
            }
          }
        }
      }
      leaf ldp-local-fc-enable {
        type string;
      }
      list dscp-classification {
        // NCS patched for predictable order
        ordered-by user;
        key "classification-id";
        leaf classification-id {
          type string;
        }
        leaf description {
          type string;
        }
        uses ncs_template_qos-dscp-list-grouping;
      }
      list fabric-profile {
        // NCS patched for predictable order
        ordered-by user;
        key "policy-id";
        leaf policy-id {
          type string;
        }
        leaf mode {
          tailf:cli-drop-node-name;
          type string;
        }
        container aggregate-rate {
          leaf rate {
            tailf:cli-drop-node-name;
            type string;
          }
          leaf unshaped-sap-cir {
            type string;
          }
        }
        leaf description {
          type string;
        }
        list dest-mda {
          // NCS patched for predictable order
          ordered-by user;
          key "id";
          leaf id {
            type string;
          }
          leaf rate {
            type string;
          }
        }
      }
      container match-list {
        list ip-prefix-list {
          // NCS patched for predictable order
          ordered-by user;
          key "ip-prefix-list-name";
          leaf ip-prefix-list-name {
            type ncs_template_string32;
          }
          leaf description {
            type string;
          }
          list prefix {
            // NCS patched for predictable order
            ordered-by user;
            tailf:cli-suppress-mode;
            key "ip-prefix";
            leaf ip-prefix {
              type string;
            }
          }
        }
        list ipv6-prefix-list {
          // NCS patched for predictable order
          ordered-by user;
          key "name";
          leaf name {
            type ncs_template_string32;
          }
          leaf description {
            type string;
          }
          list prefix {
            // NCS patched for predictable order
            ordered-by user;
            tailf:cli-suppress-mode;
            key "ip-prefix";
            leaf ip-prefix {
              type string;
            }
          }
        }
      }
      container mc-mlppp {
        list sap-egress {
          // NCS patched for predictable order
          ordered-by user;
          key "policy-id";
          uses ncs_template_sap-egress-common-grouping;
          list fc {
            // NCS patched for predictable order
            ordered-by user;
            key "fc-name";
            uses ncs_template_sap-egress-fc-grouping;
          }
          leaf scope {
            type string;
          }
        }
      }
      list network-queue {
        // NCS patched for predictable order
        ordered-by user;
        key "network-queue-name";
        leaf network-queue-name {
          type string;
        }
        leaf description {
          type string;
        }
        list queue {
          // NCS patched for predictable order
          ordered-by user;
          key "id";
          leaf id {
            type string;
          }
          leaf multipoint {
            type empty;
          }
          leaf queue-type {
            tailf:cli-drop-node-name;
            type ncs_template_queue-type;
          }
          leaf mbs {
            type string;
          }
          leaf cbs {
            type string;
          }
          leaf high-prio-only {
            type string;
          }
          container rate {
            leaf percent {
              tailf:cli-drop-node-name;
              type string;
            }
            leaf cir {
              type string;
            }
            leaf pir {
              type string;
            }
          }
          uses ncs_template_port-parent-grouping;
          leaf queue-mgmt {
            type string;
          }
          leaf queue-mode {
            type string;
          }
          uses ncs_template_queue-adaptation-grouping;
          container drop-tail {
            container low {
              leaf percent-reduction-from-mbs {
                type string;
              }
            }
          }
        }
        list fc {
          // NCS patched for predictable order
          ordered-by user;
          key "id";
          leaf id {
            type string;
          }
          leaf multicast-queue {
            type string;
          }
          leaf queue {
            type string;
          }
          container egress-hsmda {
            leaf queue {
              type string;
            }
          }
        }
      }
      container queue-group-templates {
        container egress {
          list queue-group {
            // NCS patched for predictable order
            ordered-by user;
            key "queue-group-name";
            uses ncs_template_queue-group-template-entry {
              augment "queue" {
                uses ncs_template_packet-byte-offset-grouping;
                leaf dynamic-mbs {
                  type empty;
                }
                leaf queue-delay {
                  type string;
                }
              }
            }
            leaf queues-hqos-manageable {
              type string;
            }
          }
        }
        container ingress {
          list queue-group {
            // NCS patched for predictable order
            ordered-by user;
            key "queue-group-name";
            uses ncs_template_queue-group-template-entry;
          }
        }
      }
      list scheduler-policy {
        // NCS patched for predictable order
        ordered-by user;
        key "scheduler-policy-name";
        leaf scheduler-policy-name {
          type string;
        }
        leaf description {
          type string;
        }
        leaf frame-based-accounting {
          type empty;
        }
        list tier {
          // NCS patched for predictable order
          ordered-by user;
          key "tier";
          leaf tier {
            type string;
          }
          list scheduler {
            // NCS patched for predictable order
            ordered-by user;
            key "scheduler-name";
            leaf scheduler-name {
              type string;
            }
            leaf description {
              type string;
            }
            container parent {
              presence "present";
              leaf scheduler-name {
                tailf:cli-drop-node-name;
                type string;
              }
              leaf weight {
                type string;
              }
              leaf level {
                type string;
              }
              leaf cir-weight {
                type string;
              }
              leaf cir-level {
                type string;
              }
            }
            container port-parent {
              presence "present";
              leaf weight {
                type string;
              }
              leaf level {
                type string;
              }
              leaf cir-weight {
                type string;
              }
              leaf cir-level {
                type string;
              }
            }
            container rate {
              presence "present";
              leaf pir-rate {
                tailf:cli-drop-node-name;
                // NCS drop mandatory statement
                type string;
              }
              leaf cir {
                type string;
              }
            }
            container mbs {
              leaf size {
                tailf:cli-drop-node-name;
                type string;
              }
              leaf unit {
                tailf:cli-drop-node-name;
                type string;
              }
            }
          }
        }
      }
      list shared-queue {
        // NCS patched for predictable order
        ordered-by user;
        key "policy-name";
        leaf policy-name {
          type string;
        }
        leaf description {
          type string;
        }
        container fc {
          presence "present";
          leaf fc-name {
            tailf:cli-drop-node-name;
            // NCS drop mandatory statement
            type string;
          }
          leaf broadcast-queue {
            type string;
          }
          leaf multicast-queue {
            type string;
          }
          leaf queue {
            type string;
          }
          leaf unknown-queue {
            type string;
          }
        }
        list queue {
          // NCS patched for predictable order
          ordered-by user;
          key "queue-id";
          leaf queue-id {
            type string;
          }
          leaf queue-type {
            tailf:cli-drop-node-name;
            type ncs_template_queue-type;
          }
          leaf multipoint {
            type empty;
          }
          leaf cbs {
            type string;
          }
          leaf high-prio-only {
            type string;
          }
          leaf mbs {
            type string;
          }
          leaf pool {
            type string;
          }
          container rate {
            leaf percent {
              tailf:cli-drop-node-name;
              type string;
            }
            leaf cir {
              type string;
            }
          }
        }
      }
      list mpls-lsp-exp-profile-map {
        // NCS patched for predictable order
        ordered-by user;
        // NCS drop tailf-common:cli-diff-create-before statement
        key "policy-id";
        leaf policy-id {
          type string;
        }
        leaf description {
          type string;
        }
        list lsp-exp {
          // NCS patched for predictable order
          ordered-by user;
          tailf:cli-suppress-mode;
          key "lsp-exp-value";
          leaf lsp-exp-value {
            type string;
          }
          leaf profile {
            type string;
          }
        }
      }
      list access-egress {
        // NCS patched for predictable order
        ordered-by user;
        key "policy-id";
        leaf policy-id {
          type string;
        }
        leaf remark {
          type string;
        }
        list fc {
          // NCS patched for predictable order
          ordered-by user;
          key "fc-name";
          leaf fc-name {
            type ncs_template_fc-name;
          }
          leaf dscp-in-profile {
            type ncs_template_dscp-type;
          }
          leaf dscp-out-profile {
            type ncs_template_dscp-type;
          }
          leaf dot1p-in-profile {
            type string;
          }
          leaf dot1p-out-profile {
            type string;
          }
        }
        leaf description {
          type string;
        }
        list queue {
          // NCS patched for predictable order
          ordered-by user;
          key "queue-id";
          leaf queue-id {
            type string;
          }
          uses ncs_template_queue-adaptation-grouping;
          leaf queue-mode {
            type string;
          }
          leaf queue-mgmt {
            type string;
          }
          container rate {
            leaf cir {
              type string;
            }
            leaf pir {
              type string;
            }
          }
        }
        container remarking {
          presence "true";
          leaf remarking {
            tailf:cli-drop-node-name;
            type string;
          }
        }
        leaf scope {
          type string;
        }
      }
      list sap-egress {
        // NCS patched for predictable order
        ordered-by user;
        key "policy-id";
        leaf name {
          type string;
        }
        uses ncs_template_qos-dot1p-list-grouping;
        uses ncs_template_sap-egress-common-grouping {
          augment "queue" {
            uses ncs_template_packet-byte-offset-grouping;
            leaf queue-mode {
              type string;
            }
            leaf queue-mgmt {
              type string;
            }
            leaf weight {
              type string;
            }
          }
          augment "queue/percent-rate" {
            leaf limit {
              tailf:cli-drop-node-name;
              type string;
            }
          }
        }
        leaf policers-hqos-manageable {
          type empty;
        }
        list fc {
          // NCS patched for predictable order
          ordered-by user;
          key "fc-name";
          uses ncs_template_sap-egress-fc-grouping;
          container policer {
            uses ncs_template_policer-ref-grouping;
            leaf port-redirect-group-queue {
              type empty;
            }
            leaf queue {
              type string;
            }
          }
        }
        leaf parent-location {
          type string;
        }
        list policer {
          // NCS patched for predictable order
          ordered-by user;
          key "policer-id";
          leaf policer-id {
            type string;
          }
          uses ncs_template_policer-grouping;
          uses ncs_template_port-parent-grouping;
          container percent-rate {
            leaf pir {
              tailf:cli-drop-node-name;
              type string;
            }
            leaf cir {
              type string;
            }
          }
        }
        leaf policy-name {
          type string;
        }
        container ip-criteria {
          uses ncs_template_ip-criteria-grouping;
        }
        container ipv6-criteria {
          uses ncs_template_ipv6-criteria-grouping;
        }
        list dscp {
          // NCS patched for predictable order
          ordered-by user;
          tailf:cli-suppress-mode;
          key "id";
          leaf id {
            type ncs_template_dscp-type;
          }
          leaf fc {
            type string;
          }
          leaf profile {
            type string;
          }
        }
        leaf remarking {
          type empty;
        }
        leaf remark {
          type string;
        }
        leaf scope {
          type string;
        }
      }
      list sap-ingress {
        // NCS patched for predictable order
        ordered-by user;
        key "policy-id";
        leaf policy-id {
          type string;
        }
        leaf name {
          type string;
        }
        leaf policer-allocation {
          type string;
        }
        leaf description {
          type string;
        }
        leaf ingress-classification-policy {
          type string;
        }
        leaf policy-name {
          type string;
        }
        list meter {
          // NCS patched for predictable order
          ordered-by user;
          key "meter-id";
          uses ncs_template_meter-grouping;
        }
        container num-qos-classifiers {
          leaf num-resources {
            tailf:cli-drop-node-name;
            type string;
          }
          leaf keyword {
            tailf:cli-drop-node-name;
            type string;
          }
        }
        list prec {
          // NCS patched for predictable order
          ordered-by user;
          key "ip-prec-value";
          tailf:cli-suppress-mode;
          leaf ip-prec-value {
            tailf:cli-drop-node-name;
            type string;
          }
          leaf fc {
            type ncs_template_fc-name;
          }
          leaf priority {
            type string;
          }
        }
        list queue {
          // NCS patched for predictable order
          ordered-by user;
          key "queue-id";
          leaf queue-id {
            type string;
          }
          uses ncs_template_queue-grouping {
            augment "percent-rate" {
              leaf limit {
                tailf:cli-drop-node-name;
                type string;
              }
            }
          }
          uses ncs_template_packet-byte-offset-grouping;
        }
        list policer {
          // NCS patched for predictable order
          ordered-by user;
          key "policer-id";
          leaf policer-id {
            type string;
          }
          uses ncs_template_policer-grouping;
        }
        list fc {
          // NCS patched for predictable order
          ordered-by user;
          key "fc-name";
          leaf fc-name {
            type string;
          }
          leaf egress-fc {
            type ncs_template_fc-name;
          }
          container queue {
            uses ncs_template_queue-ref-grouping;
          }
          container broadcast-queue {
            uses ncs_template_queue-ref-grouping;
          }
          container multicast-queue {
            uses ncs_template_queue-ref-grouping;
          }
          container unknown-queue {
            uses ncs_template_queue-ref-grouping;
          }
          container policer {
            uses ncs_template_policer-ref-grouping;
            leaf fp-redirect-group {
              type empty;
            }
          }
          container broadcast-policer {
            uses ncs_template_policer-ref-grouping;
            leaf fp-redirect-group {
              type empty;
            }
          }
          container multicast-policer {
            uses ncs_template_policer-ref-grouping;
            leaf fp-redirect-group {
              type empty;
            }
          }
          container unknown-policer {
            uses ncs_template_policer-ref-grouping;
            leaf fp-redirect-group {
              type empty;
            }
          }
          leaf profile {
            type string;
          }
          leaf broadcast-meter {
            type string;
          }
          leaf meter {
            type string;
          }
          leaf multicast-meter {
            type string;
          }
          leaf unknown-meter {
            type string;
          }

          grouping remark-choice-grouping {
            choice remark-choice {
              leaf dscp {
                type ncs_template_dscp-type;
              }
              leaf prec {
                type string;
              }
            }
          }
          container in-remark {
            uses remark-choice-grouping;
          }
          container out-remark {
            uses remark-choice-grouping;
          }
          leaf de-1-out-profile {
            type empty;
          }
        }
        container ip-criteria {
          uses ncs_template_ip-criteria-grouping;
        }
        container ipv6-criteria {
          uses ncs_template_ipv6-criteria-grouping;
        }
        container mac-criteria {
          uses ncs_template_mac-criteria-grouping;
        }
        leaf default-fc {
          type ncs_template_fc-name;
        }
        leaf default-priority {
          type string;
        }
        leaf dscp-classification {
          type string;
        }
        list dot1p {
          // NCS patched for predictable order
          ordered-by user;
          tailf:cli-suppress-mode;
          key "id";
          leaf id {
            type string;
          }
          leaf fc {
            type ncs_template_fc-name;
          }
          leaf priority {
            type string;
          }
        }
        list lsp-exp {
          // NCS patched for predictable order
          ordered-by user;
          tailf:cli-suppress-mode;
          key "id";
          leaf id {
            type string;
          }
          leaf fc {
            type ncs_template_fc-name;
          }
          leaf priority {
            type string;
          }
        }
        list dscp {
          // NCS patched for predictable order
          ordered-by user;
          tailf:cli-suppress-mode;
          key "id";
          leaf id {
            type ncs_template_dscp-type;
          }
          leaf fc {
            type string;
          }
          leaf priority {
            type string;
          }
        }
      }
      list network {
        // NCS patched for predictable order
        ordered-by user;
        key "id";
        leaf id {
          type string;
        }
        leaf network-policy-type {
          type string;
        }
        leaf name {
          type string;
        }
        leaf description {
          type string;
        }
        container ingress {
          list dscp {
            // NCS patched for predictable order
            ordered-by user;
            tailf:cli-suppress-mode;
            key "id";
            leaf id {
              type ncs_template_dscp-type;
            }
            leaf fc {
              type string;
            }
            leaf profile {
              type ncs_template_in-out;
            }
          }
          leaf ler-use-dscp {
            type empty;
          }
          uses ncs_template_qos-lsp-exp-grouping;
          uses ncs_template_qos-dot1p-list-grouping;
          container default-action {
            leaf fc {
              type ncs_template_fc-name;
            }
            leaf profile {
              type string;
            }
          }
          list meter {
            // NCS patched for predictable order
            ordered-by user;
            key "meter-id";
            uses ncs_template_meter-grouping;
          }
          leaf mpls-lsp-exp-profile {
            type string;
          }
          list fc {
            // NCS patched for predictable order
            ordered-by user;
            key "class";
            leaf class {
              type string;
            }
            leaf meter {
              type string;
            }
            leaf multicast-meter {
              type string;
            }
            list fp-redirect-group {
              // NCS patched for predictable order
              ordered-by user;
              tailf:cli-suppress-mode;
              key "policer-type";
              leaf policer-type {
                type string;
              }
              leaf policer-id {
                tailf:cli-drop-node-name;
                type string;
              }
            }
          }
        }
        container egress {

          grouping egress-fc-settings-grouping {
            leaf dscp-in-profile {
              type ncs_template_dscp-type;
            }
            leaf dscp-out-profile {
              type ncs_template_dscp-type;
            }
            leaf lsp-exp-in-profile {
              type string;
            }
            leaf lsp-exp-out-profile {
              type string;
            }
            leaf dot1p-in-profile {
              type string;
            }
            leaf dot1p-out-profile {
              type string;
            }
            leaf de-mark {
              type string;
            }
            container port-redirect-group {
              leaf policer {
                type string;
              }
              leaf queue {
                type string;
              }
            }
          }
          list dscp {
            // NCS patched for predictable order
            ordered-by user;
            tailf:cli-suppress-mode;
            key "id";
            leaf id {
              type ncs_template_dscp-type;
            }
            leaf fc {
              type string;
            }
            leaf profile {
              type ncs_template_in-out;
            }
          }
          container fc {
            container af {
              // NCS expand uses statement
              leaf dscp-in-profile {
                type ncs_template_dscp-type;
              }
              leaf dscp-out-profile {
                type ncs_template_dscp-type;
              }
              leaf lsp-exp-in-profile {
                type string;
              }
              leaf lsp-exp-out-profile {
                type string;
              }
              leaf dot1p-in-profile {
                type string;
              }
              leaf dot1p-out-profile {
                type string;
              }
              leaf de-mark {
                type string;
              }
              container port-redirect-group {
                leaf policer {
                  type string;
                }
                leaf queue {
                  type string;
                }
              }
            }
            container be {
              // NCS expand uses statement
              leaf dscp-in-profile {
                type ncs_template_dscp-type;
              }
              leaf dscp-out-profile {
                type ncs_template_dscp-type;
              }
              leaf lsp-exp-in-profile {
                type string;
              }
              leaf lsp-exp-out-profile {
                type string;
              }
              leaf dot1p-in-profile {
                type string;
              }
              leaf dot1p-out-profile {
                type string;
              }
              leaf de-mark {
                type string;
              }
              container port-redirect-group {
                leaf policer {
                  type string;
                }
                leaf queue {
                  type string;
                }
              }
            }
            container ef {
              // NCS expand uses statement
              leaf dscp-in-profile {
                type ncs_template_dscp-type;
              }
              leaf dscp-out-profile {
                type ncs_template_dscp-type;
              }
              leaf lsp-exp-in-profile {
                type string;
              }
              leaf lsp-exp-out-profile {
                type string;
              }
              leaf dot1p-in-profile {
                type string;
              }
              leaf dot1p-out-profile {
                type string;
              }
              leaf de-mark {
                type string;
              }
              container port-redirect-group {
                leaf policer {
                  type string;
                }
                leaf queue {
                  type string;
                }
              }
            }
            container h1 {
              // NCS expand uses statement
              leaf dscp-in-profile {
                type ncs_template_dscp-type;
              }
              leaf dscp-out-profile {
                type ncs_template_dscp-type;
              }
              leaf lsp-exp-in-profile {
                type string;
              }
              leaf lsp-exp-out-profile {
                type string;
              }
              leaf dot1p-in-profile {
                type string;
              }
              leaf dot1p-out-profile {
                type string;
              }
              leaf de-mark {
                type string;
              }
              container port-redirect-group {
                leaf policer {
                  type string;
                }
                leaf queue {
                  type string;
                }
              }
            }
            container h2 {
              // NCS expand uses statement
              leaf dscp-in-profile {
                type ncs_template_dscp-type;
              }
              leaf dscp-out-profile {
                type ncs_template_dscp-type;
              }
              leaf lsp-exp-in-profile {
                type string;
              }
              leaf lsp-exp-out-profile {
                type string;
              }
              leaf dot1p-in-profile {
                type string;
              }
              leaf dot1p-out-profile {
                type string;
              }
              leaf de-mark {
                type string;
              }
              container port-redirect-group {
                leaf policer {
                  type string;
                }
                leaf queue {
                  type string;
                }
              }
            }
            container l1 {
              // NCS expand uses statement
              leaf dscp-in-profile {
                type ncs_template_dscp-type;
              }
              leaf dscp-out-profile {
                type ncs_template_dscp-type;
              }
              leaf lsp-exp-in-profile {
                type string;
              }
              leaf lsp-exp-out-profile {
                type string;
              }
              leaf dot1p-in-profile {
                type string;
              }
              leaf dot1p-out-profile {
                type string;
              }
              leaf de-mark {
                type string;
              }
              container port-redirect-group {
                leaf policer {
                  type string;
                }
                leaf queue {
                  type string;
                }
              }
            }
            container l2 {
              // NCS expand uses statement
              leaf dscp-in-profile {
                type ncs_template_dscp-type;
              }
              leaf dscp-out-profile {
                type ncs_template_dscp-type;
              }
              leaf lsp-exp-in-profile {
                type string;
              }
              leaf lsp-exp-out-profile {
                type string;
              }
              leaf dot1p-in-profile {
                type string;
              }
              leaf dot1p-out-profile {
                type string;
              }
              leaf de-mark {
                type string;
              }
              container port-redirect-group {
                leaf policer {
                  type string;
                }
                leaf queue {
                  type string;
                }
              }
            }
            container nc {
              // NCS expand uses statement
              leaf dscp-in-profile {
                type ncs_template_dscp-type;
              }
              leaf dscp-out-profile {
                type ncs_template_dscp-type;
              }
              leaf lsp-exp-in-profile {
                type string;
              }
              leaf lsp-exp-out-profile {
                type string;
              }
              leaf dot1p-in-profile {
                type string;
              }
              leaf dot1p-out-profile {
                type string;
              }
              leaf de-mark {
                type string;
              }
              container port-redirect-group {
                leaf policer {
                  type string;
                }
                leaf queue {
                  type string;
                }
              }
            }
          }
          leaf remark {
            type string;
          }
          container remarking {
            presence "true";
            leaf force {
              type empty;
            }
          }
          list prec {
            // NCS patched for predictable order
            ordered-by user;
            tailf:cli-suppress-mode;
            key "prec-value";
            leaf prec-value {
              tailf:cli-drop-node-name;
              type string;
            }
            leaf fc {
              type ncs_template_fc-name;
            }
            leaf profile {
              type string;
            }
          }
        }
      }
      list slope-policy {
        // NCS patched for predictable order
        ordered-by user;
        key "name";
        leaf name {
          type string;
        }
        leaf description {
          type string;
        }
        container exceed-slope {
          uses ncs_template_slope-params-grouping;
        }
        container high-slope {
          uses ncs_template_slope-params-grouping;
        }
        container highplus-slope {
          uses ncs_template_slope-params-grouping;
        }
        container low-slope {
          uses ncs_template_slope-params-grouping;
        }
      }
      list port-scheduler-policy {
        // NCS patched for predictable order
        ordered-by user;
        key "name";
        leaf name {
          type string;
        }
        leaf description {
          type string;
        }
        leaf dist-lag-rate-shared {
          type empty;
        }
        list group {
          // NCS patched for predictable order
          ordered-by user;
          key "name";
          leaf name {
            type ncs_template_string32;
          }
          container percent {
            tailf:cli-drop-node-name;
            leaf percent-rate {
              type string;
            }
            leaf cir {
              type string;
            }
          }
        }
        list level {
          // NCS patched for predictable order
          ordered-by user;
          tailf:cli-suppress-mode;
          key "priority-level";
          leaf priority-level {
            type string;
          }
          choice rate-choice {
            container pir {
              tailf:cli-drop-node-name;
              leaf rate {
                type string;
              }
              leaf cir {
                type string;
              }
            }
            container percent {
              tailf:cli-drop-node-name;
              leaf percent-rate {
                type string;
              }
              leaf percent-cir {
                type string;
              }
            }
          }
          leaf group {
            type ncs_template_string32;
          }
          leaf weight {
            type string;
          }
        }
        container max-rate {
          choice max-rate {
            leaf pir-rate {
              tailf:cli-drop-node-name;
              type string;
            }
            leaf percent {
              type string;
            }
          }
        }
        container orphan-override {
          leaf weight {
            type string;
          }
          leaf level {
            type string;
          }
          leaf cir-weight {
            type string;
          }
          leaf cir-level {
            type string;
          }
        }
      }
      list policer-control-policy {
        // NCS patched for predictable order
        ordered-by user;
        key "name";
        leaf name {
          type string;
        }
        leaf description {
          type string;
        }
        container root {
          leaf max-rate {
            type ncs_template_rate-type;
          }
        }
        container priority-mbs-thresholds {
          container min-thresh-separation {
            leaf size {
              tailf:cli-drop-node-name;
              type string;
            }
            leaf unit {
              tailf:cli-drop-node-name;
              type string;
            }
          }
          list priority {
            // NCS patched for predictable order
            ordered-by user;
            key "level";
            leaf level {
              type string;
            }
            container mbs-contribution {
              leaf size {
                tailf:cli-drop-node-name;
                type string;
              }
              leaf unit {
                tailf:cli-drop-node-name;
                type string;
              }
              leaf fixed {
                type empty;
              }
            }
          }
        }
      }
      list queue-mgmt {
        // NCS patched for predictable order
        ordered-by user;
        key "id";
        leaf id {
          type string;
        }
        leaf description {
          type string;
        }
        leaf mbs {
          type string;
        }
        leaf cbs {
          type string;
        }
        container high-slope {
          leaf shutdown {
            type string;
          }
        }
        container low-slope {
          leaf shutdown {
            type string;
          }
        }
      }
      list remark {
        // NCS patched for predictable order
        ordered-by user;
        key "policy-id";
        leaf policy-id {
          type string;
        }
        leaf remark-type {
          type string;
        }
        leaf description {
          type string;
        }
        list fc {
          // NCS patched for predictable order
          ordered-by user;
          key "fc-name";
          leaf fc-name {
            type ncs_template_fc-name;
          }
          leaf dot1p-in-profile {
            type string;
          }
          leaf dot1p-out-profile {
            type string;
          }
          leaf dot1p-lsp-exp-in-profile {
            type string;
          }
          leaf dot1p-lsp-exp-out-profile {
            type string;
          }
        }
      }
      leaf use-global-mpls-lsp-exp-profile {
        type string;
      }
    }
    list sfm {
      // NCS patched for predictable order
      ordered-by user;
      key "id";
      leaf id {
        type string;
      }
      leaf sfm-type {
        type string;
      }
      leaf shutdown {
        type string;
      }
    }
    container eth-cfm {
      container default-domain {
        list bridge-identifier {
          // NCS patched for predictable order
          ordered-by user;
          key "bridge-id";
          leaf bridge-id {
            type string;
          }
          leaf vlan {
            type string;
          }
          container mhf-creation {
            leaf mhf {
              tailf:cli-drop-node-name;
              type string;
            }
            leaf level {
              type string;
            }
          }
        }
      }
      list domain {
        // NCS patched for predictable order
        ordered-by user;
        key "id";
        leaf id {
          type string;
        }
        leaf format {
          type string;
        }
        leaf level {
          type string;
        }
        leaf name {
          type string;
        }
        leaf admin-name {
          type string;
        }
        list association {
          // NCS patched for predictable order
          ordered-by user;
          key "ma-index";
          leaf ma-index {
            type string;
          }
          leaf auto-mep-discovery {
            type empty;
          }
          leaf format {
            type string;
          }
          leaf name {
            type string;
          }
          leaf admin-name {
            type string;
          }
          container ccm-hold-time {
            leaf down {
              type string;
            }
          }
          leaf ccm-interval {
            type string;
          }
          list remote-mepid {
            // NCS patched for predictable order
            ordered-by user;
            tailf:cli-suppress-mode;
            key "mep-id";
            leaf mep-id {
              type string;
            }
            leaf remote-mac {
              type string;
            }
          }
          list bridge-identifier {
            // NCS patched for predictable order
            ordered-by user;
            key "id";
            leaf id {
              type string;
            }
            leaf bridge-name {
              type empty;
            }
            leaf mhf-creation {
              type string;
            }
            leaf vlan {
              type string;
            }
          }
        }
      }
    }
    list esa {
      // NCS patched for predictable order
      ordered-by user;
      key "id";
      leaf id {
        type string;
      }
      leaf description {
        type string;
      }
      list host-port {
        // NCS patched for predictable order
        ordered-by user;
        tailf:cli-suppress-mode;
        key "port";
        leaf port {
          type string;
        }
      }
      list vm {
        // NCS patched for predictable order
        ordered-by user;
        key "vm-id";
        leaf vm-id {
          type string;
        }
        leaf cores {
          type string;
        }
        leaf description {
          type string;
        }
        leaf host-port {
          type string;
        }
        leaf memory {
          type string;
        }
        leaf vm-type {
          type string;
        }
        leaf shutdown {
          type string;
        }
      }
      leaf shutdown {
        type string;
      }
    }
    container log {

      typedef severity-levels {
        type string;
      }
      leaf event-damping {
        type string;
      }
      container event-handling {
        list handler {
          // NCS patched for predictable order
          ordered-by user;
          key "name";
          leaf name {
            type string;
          }
          leaf description {
            type string;
          }
          container action-list {
            list entry {
              // NCS patched for predictable order
              ordered-by user;
              key "entry-id";
              leaf entry-id {
                type string;
              }
              leaf script-policy {
                type ncs_template_string32;
              }
              leaf shutdown {
                type string;
              }
            }
          }
          leaf shutdown {
            type string;
          }
        }
      }
      list file-id {
        // NCS patched for predictable order
        ordered-by user;
        key "id";
        leaf id {
          type string;
        }
        leaf name {
          type string;
        }
        leaf description {
          type string;
        }
        leaf location {
          type string;
        }
        container rollover {
          leaf id {
            tailf:cli-drop-node-name;
            type string;
          }
          leaf retention {
            type string;
          }
        }
      }
      list accounting-policy {
        // NCS patched for predictable order
        ordered-by user;
        key "acct-policy-id";
        leaf acct-policy-id {
          type string;
        }
        leaf collection-interval {
          type string;
        }
        leaf description {
          type string;
        }
        container custom-record {
          list queue {
            // NCS patched for predictable order
            ordered-by user;
            key "id";
            leaf id {
              type string;
            }

            grouping custom-record-counters-grouping {
              leaf in-profile-octets-forwarded-count {
                type empty;
              }
              leaf out-profile-octets-forwarded-count {
                type empty;
              }
            }
            container e-counters {
              uses custom-record-counters-grouping;
            }
            container i-counters {
              uses custom-record-counters-grouping;
            }
          }
        }
        leaf include-system-info {
          type empty;
        }
        leaf record {
          type string;
        }
        leaf default {
          type empty;
        }
        container to {
          leaf destination {
            tailf:cli-drop-node-name;
            type string;
          }
          leaf log-file-id {
            tailf:cli-drop-node-name;
            type string;
          }
        }
        leaf shutdown {
          type string;
        }
      }
      list event-control {
        // NCS patched for predictable order
        ordered-by user;
        tailf:cli-suppress-mode;
        key "name id";
        leaf name {
          type string;
        }
        leaf id {
          type string;
        }
        leaf mode {
          tailf:cli-drop-node-name;
          type string;
        }
        leaf severity-level {
          tailf:cli-drop-node-name;
          type severity-levels;
        }
        leaf throttle {
          type empty;
        }
        leaf disable-specific-throttle {
          tailf:cli-drop-node-name;
          type string;
        }
        container specific-throttle-rate {
          leaf event-limit {
            tailf:cli-drop-node-name;
            type string;
          }
          leaf interval {
            type string;
          }
        }
      }
      container event-trigger {
        list event {
          // NCS patched for predictable order
          ordered-by user;
          key "application-id event-name-id";
          leaf application-id {
            type string;
          }
          leaf event-name-id {
            type string;
          }
          list trigger-entry {
            // NCS patched for predictable order
            ordered-by user;
            key "entry-id";
            leaf entry-id {
              type string;
            }
            leaf event-handler {
              type string;
            }
            leaf log-filter {
              type string;
            }
            leaf shutdown {
              type string;
            }
          }
          leaf shutdown {
            type string;
          }
        }
      }
      list filter {
        // NCS patched for predictable order
        ordered-by user;
        key "filter-id";
        leaf filter-id {
          type string;
        }
        leaf default-action {
          type string;
        }
        leaf name {
          type string;
        }
        leaf description {
          type string;
        }
        list entry {
          // NCS patched for predictable order
          ordered-by user;
          key "entry-id";
          leaf entry-id {
            type string;
          }
          leaf action {
            type string;
          }
          leaf name {
            type string;
          }
          leaf description {
            type string;
          }
          container match {
            container application {
              leaf rule {
                tailf:cli-drop-node-name;
                type string;
              }
              leaf application-id {
                tailf:cli-drop-node-name;
                type string;
              }
            }
            container message {
              leaf rule {
                tailf:cli-drop-node-name;
                type string;
              }
              leaf pattern {
                type string;
              }
              leaf regexp {
                type empty;
              }
            }
            container number {
              leaf rule {
                tailf:cli-drop-node-name;
                type string;
              }
              leaf event-id {
                tailf:cli-drop-node-name;
                type string;
              }
            }
            container router {
              leaf rule {
                tailf:cli-drop-node-name;
                type string;
              }
              leaf router-instance {
                tailf:cli-drop-node-name;
                type string;
              }
              leaf regexp {
                type empty;
              }
            }
            container severity {
              leaf rule {
                tailf:cli-drop-node-name;
                type string;
              }
              leaf severity-level {
                tailf:cli-drop-node-name;
                type severity-levels;
              }
            }
            container subject {
              leaf rule {
                tailf:cli-drop-node-name;
                type string;
              }
              leaf subject {
                tailf:cli-drop-node-name;
                type string;
              }
              leaf regexp {
                type empty;
              }
            }
          }
        }
      }
      list snmp-trap-group {
        // NCS patched for predictable order
        ordered-by user;
        // NCS drop tailf-common:cli-diff-create-before statement
        key "id";
        leaf id {
          type string;
        }
        leaf name {
          type string;
        }
        list trap-target {
          // NCS patched for predictable order
          ordered-by user;
          tailf:cli-suppress-mode;
          key "name";
          leaf name {
            type string;
          }
          leaf address {
            type string;
          }
          leaf notify-community {
            type string;
          }
          leaf port {
            type string;
          }
          leaf version {
            tailf:cli-drop-node-name;
            type string;
          }
          leaf security-level {
            type string;
          }
          leaf replay {
            type empty;
          }
          leaf dying-gasp {
            type empty;
          }
        }
        leaf description {
          type string;
        }
      }
      container snmp-dying-gasp {

        grouping trap-target-grouping {
          leaf trap-target-group-num {
            tailf:cli-drop-node-name;
            type string;
          }
          leaf trap-target-name {
            tailf:cli-drop-node-name;
            type string;
          }
        }
        container primary {
          uses trap-target-grouping;
        }
        container secondary {
          uses trap-target-grouping;
        }
        container tertiary {
          uses trap-target-grouping;
        }
      }
      list log-id {
        // NCS patched for predictable order
        ordered-by user;
        key "id";
        leaf id {
          type string;
        }
        leaf name {
          type string;
        }
        leaf description {
          type string;
        }
        leaf filter {
          type string;
        }
        leaf-list from {
          // NCS patched for predictable order
          ordered-by user;
          type string;
        }
        leaf time-format {
          type string;
        }
        leaf netconf-stream {
          type string;
        }
        container to {
          choice choice {
            case file {
              leaf file {
                type string;
              }
            }
            case syslog {
              leaf syslog {
                type string;
              }
            }
            case cli {
              leaf cli {
                type empty;
              }
            }
            case console {
              leaf console {
                type empty;
              }
            }
            case netconf {
              leaf netconf {
                type empty;
              }
            }
            case snmp {
              container snmp {
                presence "true";
                leaf size {
                  tailf:cli-drop-node-name;
                  type string;
                }
              }
            }
            case memory {
              container memory {
                presence "true";
                leaf size {
                  tailf:cli-drop-node-name;
                  type string;
                }
              }
            }
            case session {
              leaf session {
                type string;
              }
            }
          }
        }
        leaf shutdown {
          type string;
        }
      }
      container route-preference {
        leaf primary {
          type string;
        }
        leaf secondary {
          type string;
        }
      }
      list syslog {
        // NCS patched for predictable order
        ordered-by user;
        key "id";
        leaf id {
          type string;
        }
        leaf name {
          type string;
        }
        leaf address {
          type string;
        }
        leaf description {
          type string;
        }
        leaf facility {
          type string;
        }
        leaf log-prefix {
          type string;
        }
        leaf level {
          type string;
        }
        leaf port {
          type string;
        }
      }
      container throttle-rate {
        leaf events {
          tailf:cli-drop-node-name;
          type string;
        }
        leaf interval {
          type string;
        }
      }
      container services-all-events {
        list service {
          // NCS patched for predictable order
          ordered-by user;
          tailf:cli-suppress-mode;
          key "service-id";
          leaf service-id {
            type string;
          }
        }
      }
    }
    container service {
      list customer {
        // NCS patched for predictable order
        ordered-by user;
        key "customer-id";
        leaf customer-id {
          type string;
        }
        leaf name {
          type string;
        }
        leaf contact {
          type string;
        }
        leaf description {
          type string;
        }
        list multi-service-site {
          // NCS patched for predictable order
          ordered-by user;
          key "customer-site-name";
          leaf customer-site-name {
            type string;
          }
          container assignment {
            choice choice {
              leaf port {
                type string;
              }
              leaf card {
                type string;
              }
            }
          }
          leaf description {
            type string;
          }
          container egress {
            container agg-rate-limit {
              presence "present";
              leaf agg-rate {
                tailf:cli-drop-node-name;
                // NCS drop mandatory statement
                type string;
              }
              leaf queue-frame-based-accounting {
                type empty;
              }
            }
            leaf policer-control-policy {
              type string;
            }
            leaf scheduler-policy {
              type string;
            }
            container scheduler-override {
              list scheduler {
                // NCS patched for predictable order
                ordered-by user;
                key "scheduler-name";
                leaf scheduler-name {
                  type string;
                }
                container rate {
                  leaf pir-rate {
                    tailf:cli-drop-node-name;
                    type string;
                  }
                  leaf cir {
                    type string;
                  }
                }
              }
            }
          }
          container ingress {
            leaf policer-control-policy {
              type string;
            }
            leaf scheduler-policy {
              type string;
            }
            container scheduler-override {
              list scheduler {
                // NCS patched for predictable order
                ordered-by user;
                key "scheduler-name";
                leaf scheduler-name {
                  type string;
                }
                container rate {
                  presence "present";
                  leaf pir-rate {
                    tailf:cli-drop-node-name;
                    // NCS drop mandatory statement
                    type string;
                  }
                  leaf cir {
                    type string;
                  }
                }
              }
            }
          }
          leaf tod-suite {
            type string;
          }
        }
        leaf phone {
          type string;
        }
      }
      list sdp {
        // NCS patched for predictable order
        ordered-by user;
        key "sdp-id";
        leaf sdp-id {
          type string;
        }
        list sr-te-lsp {
          // NCS patched for predictable order
          ordered-by user;
          tailf:cli-suppress-mode;
          key "lsp-id";
          leaf lsp-id {
            type string;
          }
        }
        container class-forwarding {
          presence "true";
          leaf default-lsp {
            type string;
          }
          leaf enforce-diffserv-lsp-fc {
            type empty;
          }
          list fc {
            // NCS patched for predictable order
            ordered-by user;
            tailf:cli-suppress-mode;
            key "class";
            leaf class {
              type ncs_template_fc-name;
            }
            leaf lsp {
              type string;
            }
          }
          leaf multicast-lsp {
            type string;
          }
          leaf shutdown {
            type string;
          }
        }
        list lsp {
          // NCS patched for predictable order
          ordered-by user;
          tailf:cli-suppress-mode;
          key "lsp-name";
          leaf lsp-name {
            type string;
          }
        }
        leaf far-end {
          type string;
        }
        leaf accounting-policy {
          type string;
        }
        leaf adv-mtu-override {
          type empty;
        }
        leaf bgp-tunnel {
          type empty;
        }
        container binding {
          leaf port {
            type string;
          }
          list pw-port {
            // NCS patched for predictable order
            ordered-by user;
            key "pw-port-id";
            leaf pw-port-id {
              type string;
            }
            leaf vc-id {
              type string;
            }
            leaf monitor-oper-group {
              type string;
            }
            container egress {
              container shaping {
                choice choice {
                  leaf vport {
                    type string;
                  }
                  leaf int-dest-id {
                    type string;
                  }
                }
              }
            }
            leaf vc-type {
              type string;
            }
            leaf vlan-vc-tag {
              type string;
            }
            leaf shutdown {
              type string;
            }
          }
        }
        leaf booking-factor {
          type string;
        }
        leaf collect-stats {
          type empty;
        }
        leaf delivery-type {
          tailf:cli-drop-node-name;
          type string;
        }
        leaf description {
          type string;
        }
        container keep-alive {
          leaf hello-time {
            type string;
          }
          leaf hold-down-time {
            type string;
          }
          leaf max-drop-count {
            type string;
          }
          leaf message-length {
            type string;
          }
          leaf timeout {
            type string;
          }
          leaf shutdown {
            type string;
          }
        }
        leaf metric {
          type string;
        }
        leaf sr-type {
          tailf:cli-drop-node-name;
          type string;
        }
        container mixed-lsp-mode {
          presence "true";
          // NCS drop tailf-common:cli-diff-create-before statement
          leaf revert-time {
            type string;
          }
        }
        leaf network-domain {
          type string;
        }
        leaf path-mtu {
          type string;
        }
        leaf pbb-etype {
          type string;
        }
        leaf signaling {
          type string;
        }
        leaf local-end {
          type string;
        }
        leaf tunnel-far-end {
          type string;
        }
        leaf vlan-vc-etype {
          type string;
        }
        leaf shutdown {
          type string;
        }
      }
      container sdp-group {
        list group-name {
          // NCS patched for predictable order
          ordered-by user;
          tailf:cli-suppress-mode;
          key "name";
          leaf name {
            type string;
          }
          leaf value {
            // NCS drop mandatory statement
            type string;
          }
        }
      }

      grouping service-epipe-cpipe-common-grouping {
        uses ncs_template_service-id-grouping;
        leaf customer {
          type string;
        }
        leaf name {
          type string;
        }
        leaf vc-switching {
          type empty;
        }
        leaf vpn {
          type string;
        }
        leaf description {
          type string;
        }
        leaf service-name {
          type string;
        }
        leaf service-mtu {
          type string;
        }
        list spoke-sdp {
          // NCS patched for predictable order
          ordered-by user;
          key "sdp-id vc-id";
          leaf description {
            type string;
          }
          container egress {
            container l2tpv3 {
              leaf cookie {
                type string;
              }
            }
            leaf vc-label {
              type string;
            }
          }
          container eth-cfm {
            uses ncs_template_eth-cfm;
          }
          leaf force-vlan-vc-forwarding {
            type empty;
          }
          leaf standby-signaling-slave {
            type empty;
          }
          container ingress {
            container l2tpv3 {
              leaf cookie {
                type string;
              }
            }
            leaf vc-label {
              type string;
            }
          }
          leaf pw-status-signaling {
            type empty;
          }
          leaf control-word {
            type empty;
          }
          leaf collect-stats {
            type empty;
          }
          container hash-label {
            presence "true";
            leaf signal-capability {
              type empty;
            }
          }
          leaf precedence {
            type string;
          }
          leaf vlan-vc-tag {
            type string;
          }
          leaf entropy-label {
            type empty;
          }
          leaf sdp-id {
            type string;
          }
          uses ncs_template_sdp-common;
        }
        list sap {
          // NCS patched for predictable order
          ordered-by user;
          key "sap-id";
          leaf sap-id {
            type string;
          }
          leaf endpoint {
            type string;
          }
          leaf description {
            type string;
          }
          leaf cflowd {
            type empty;
          }
          container cem {
            container packet {
              leaf jitter-buffer {
                type string;
              }
              leaf payload-size {
                type string;
              }
            }
            leaf-list report-alarm {
              // NCS patched for predictable order
              ordered-by user;
              type string;
            }
            leaf rtp-header {
              type empty;
            }
            leaf local-ecid {
              type string;
            }
            leaf remote-ecid {
              type string;
            }
            leaf remote-mac {
              type string;
            }
          }
          leaf accounting-policy {
            type string;
          }

          grouping vlan-manipulation-grouping {
            container vlan-manipulation {
              leaf preserve {
                type empty;
              }
              leaf push {
                type string;
              }
              container translate {
                leaf type {
                  tailf:cli-drop-node-name;
                  type string;
                }
                leaf qtag {
                  tailf:cli-drop-node-name;
                  type string;
                }
              }
            }
          }
          container egress {
            leaf egress-remark-policy {
              type string;
            }
            leaf qos {
              type string;
            }
            container agg-rate {
              container rate {
                leaf rate {
                  tailf:cli-drop-node-name;
                  type string;
                }
                leaf cir {
                  type string;
                }
              }
            }
            container agg-rate-limit {
              choice pir-choice {
                leaf pir-less {
                  tailf:cli-drop-node-name;
                  type string;
                }
                leaf pir {
                  type string;
                }
              }
              leaf cir {
                type string;
              }
            }
            container filter {
              uses ncs_template_filter-choice;
            }
            uses ncs_template_sap-queue-override-grouping;
            leaf scheduler-policy {
              type string;
            }
            uses ncs_template_sap-scheduler-override-grouping;
            container vlan-qos-policy {
              leaf vlan-qos-policy-name {
                tailf:cli-drop-node-name;
                type string;
              }
              leaf port-redirect {
                type empty;
              }
            }
            uses vlan-manipulation-grouping;
            container qtag-manipulation {
              leaf preserve {
                type empty;
              }
            }
          }
          container ingress {
            container aggregate-meter-rate {
              leaf value {
                tailf:cli-drop-node-name;
                type string;
              }
              leaf burst {
                type string;
              }
            }
            container aggregate-policer-rate {
              leaf rate {
                tailf:cli-drop-node-name;
                type string;
              }
              leaf burst {
                type string;
              }
            }
            container filter {
              uses ncs_template_filter-choice;
            }
            leaf match-qinq-dot1p {
              type string;
            }
            container qos {
              leaf policy-id {
                tailf:cli-drop-node-name;
                type string;
              }
              leaf shared-queuing {
                type empty;
              }
            }
            uses ncs_template_sap-queue-override-grouping;
            leaf scheduler-policy {
              type string;
            }
            uses vlan-manipulation-grouping;
            leaf vlan-translation {
              type string;
            }
            container agg-rate-limit {
              leaf agg-rate {
                tailf:cli-drop-node-name;
                type string;
              }
              leaf cir {
                type string;
              }
            }
            leaf scheduler-mode {
              type ncs_template_scheduler-mode;
            }
            uses ncs_template_sap-scheduler-override-grouping;
            container qtag-manipulation {
              leaf preserve {
                type empty;
              }
            }
          }
          leaf collect-stats {
            type empty;
          }
          container eth-cfm {
            uses ncs_template_eth-cfm;
            container mip {
              presence "true";
              leaf mac {
                type ncs_template_ieee-mac;
              }
            }
          }
          leaf multi-service-site {
            type string;
          }
          leaf oper-group {
            type string;
          }
          leaf dist-cpu-protection {
            type string;
          }
          leaf shutdown {
            type string;
          }
          container ethernet {
            leaf llf {
              type empty;
            }
          }
        }
        list endpoint {
          // NCS patched for predictable order
          ordered-by user;
          key "endpoint-name";
          leaf endpoint-name {
            type string;
          }
          leaf active-hold-delay {
            type string;
          }
          leaf description {
            type string;
          }
          leaf revert-time {
            type string;
          }
          leaf standby-signaling-master {
            type empty;
          }
          leaf standby-signaling-slave {
            type empty;
          }
        }
      }
      list cpipe {
        // NCS patched for predictable order
        ordered-by user;
        key "service-id";
        uses service-epipe-cpipe-common-grouping;
        leaf vc-type {
          type string;
        }
        leaf test {
          type empty;
        }
        leaf shutdown {
          type string;
        }
      }
      list epipe {
        // NCS patched for predictable order
        ordered-by user;
        key "service-id";
        uses service-epipe-cpipe-common-grouping {
          augment "sap" {
            container statistics {
              container ingress {
                leaf counter-mode {
                  type string;
                }
              }
            }
          }
          refine "spoke-sdp/endpoint";
        }
        container load-balancing {
          leaf per-service-hashing {
            type empty;
          }
        }
        leaf svc-sap-type {
          type string;
        }
        leaf customer-vid {
          type string;
        }
        list pw-port {
          // NCS patched for predictable order
          ordered-by user;
          key "pw-port-id fpe";
          leaf pw-port-id {
            type string;
          }
          leaf fpe {
            type string;
          }
          leaf shutdown {
            type string;
          }
        }
        list site {
          // NCS patched for predictable order
          ordered-by user;
          key "name";
          leaf name {
            type string;
          }
          leaf boot-timer {
            type string;
          }
          leaf sap {
            type string;
          }
          leaf site-activation-timer {
            type string;
          }
          leaf site-id {
            type string;
          }
          leaf shutdown {
            type string;
          }
        }
        container bgp {
          leaf route-distinguisher {
            type string;
          }
          container route-target {
            leaf export {
              type string;
            }
            leaf import {
              type string;
            }
          }
          leaf-list vsi-import {
            // NCS patched for predictable order
            ordered-by user;
            type string;
          }
          leaf-list vsi-export {
            // NCS patched for predictable order
            ordered-by user;
            type string;
          }
        }
        container bgp-evpn {
          presence "true";
          container local-ac-name {
            presence "true";
            leaf ac-name {
              tailf:cli-drop-node-name;
              type string;
            }
            leaf eth-tag {
              type string;
            }
          }
          container remote-ac-name {
            presence "true";
            leaf ac-name {
              tailf:cli-drop-node-name;
              type string;
            }
            leaf eth-tag {
              type string;
            }
          }
          list local-attachment-circuit {
            // NCS patched for predictable order
            ordered-by user;
            key "ac-name";
            leaf ac-name {
              type string;
            }
            leaf endpoint {
              type string;
            }
            leaf eth-tag {
              type string;
            }
          }
          list remote-attachment-circuit {
            // NCS patched for predictable order
            ordered-by user;
            key "ac-name";
            leaf ac-name {
              type string;
            }
            leaf endpoint {
              type string;
            }
            leaf eth-tag {
              type string;
            }
          }
          leaf evi {
            type string;
          }
          container mpls {
            presence "true";
            leaf control-word {
              type empty;
            }
            leaf bgp {
              type string;
            }
            leaf force-vlan-vc-forwarding {
              type empty;
            }
            leaf route-next-hop {
              type string;
            }
            leaf default-route-tag {
              type string;
            }
            container auto-bind-tunnel {
              leaf enforce-strict-tunnel-tagging {
                type empty;
              }
              uses ncs_template_resolution-filter-grouping;
            }
            leaf ecmp {
              type string;
            }
            leaf entropy-label {
              type empty;
            }
            leaf shutdown {
              type string;
            }
          }
        }
        leaf shutdown {
          type string;
        }
      }
      list oper-group {
        // NCS patched for predictable order
        ordered-by user;
        key "group-name";
        leaf group-name {
          type string;
        }
        container hold-time {
          container group {
            presence "true";
            leaf up {
              type string;
            }
            leaf down {
              type string;
            }
          }
        }
      }
      list ies {
        // NCS patched for predictable order
        ordered-by user;
        key "service-id";
        leaf service-id {
          type string;
        }
        leaf customer {
          type string;
        }
        leaf name {
          type string;
        }
        leaf description {
          type string;
        }
        list redundant-interface {
          // NCS patched for predictable order
          ordered-by user;
          key "id";
          leaf id {
            type string;
          }
          leaf description {
            type string;
          }
          leaf address {
            type string;
          }
          list spoke-sdp {
            // NCS patched for predictable order
            ordered-by user;
            key "sdp-id";
            leaf sdp-id {
              type string;
            }
            leaf shutdown {
              type string;
            }
          }
          leaf shutdown {
            type string;
          }
        }
        list subscriber-interface {
          // NCS patched for predictable order
          ordered-by user;
          key "id";
          uses ncs_template_subscriber-interface-grouping {
            refine "group-interface/tos-marking-state";
            augment "group-interface/sap" {
              leaf cpu-protection {
                type string;
              }
              list static-host {
                // NCS patched for predictable order
                ordered-by user;
                key "ip";
                leaf ip {
                  type string;
                }
                leaf shutdown {
                  type string;
                }
              }
            }
            augment "group-interface/dhcp" {
              leaf shutdown {
                type string;
              }
            }
          }
          container hold-time {
            list down {
              // NCS patched for predictable order
              ordered-by user;
              tailf:cli-suppress-mode;
              key "type";
              leaf type {
                type string;
              }
              leaf time {
                tailf:cli-drop-node-name;
                type string;
              }
              leaf init-only {
                type empty;
              }
            }
          }
          container ipv6 {
            presence "true";
            list address {
              // NCS patched for predictable order
              ordered-by user;
              tailf:cli-suppress-mode;
              key "ipv6-address";
              leaf ipv6-address {
                type string;
              }
              choice adr {
                leaf pd {
                  type empty;
                }
                leaf wan-host {
                  type empty;
                }
              }
            }
            container default-dns {
              leaf address {
                tailf:cli-drop-node-name;
                type string;
              }
              leaf secondary {
                type string;
              }
            }
            leaf delegated-prefix-length {
              type string;
            }
            leaf link-local-address {
              type string;
            }
            leaf allow-unmatching-prefixes {
              type empty;
            }
            container subscriber-prefixes {
              list prefix {
                // NCS patched for predictable order
                ordered-by user;
                tailf:cli-suppress-mode;
                key "ipv6-prefix";
                leaf ipv6-prefix {
                  type string;
                }
                leaf pd {
                  type empty;
                }
                leaf wan-host {
                  type empty;
                }
                leaf track-srrp {
                  type string;
                }
              }
            }
          }
          container dhcp {
            container gi-address {
              leaf gi-address-value {
                tailf:cli-drop-node-name;
                type string;
              }
              leaf src-ip-addr {
                type empty;
              }
            }
            leaf virtual-subnet {
              type empty;
            }
          }
          leaf shutdown {
            type string;
          }
        }
        list interface {
          // NCS patched for predictable order
          ordered-by user;
          key "ip-int-name";
          leaf ip-int-name {
            type string;
          }
          leaf tunnel {
            type empty;
          }
          leaf monitor-oper-group {
            type string;
          }
          leaf allow-directed-broadcasts {
            type empty;
          }
          leaf arp-learn-unsolicited {
            type empty;
          }
          leaf arp-populate {
            type empty;
          }
          leaf arp-timeout {
            type string;
          }
          leaf authentication-policy {
            type string;
          }
          container bfd {
            uses ncs_template_bfd-grouping;
          }
          uses ncs_template_cflowd-params-grouping;
          container cflowd {
            leaf id {
              tailf:cli-drop-node-name;
              type string;
            }
            leaf direction {
              tailf:cli-drop-node-name;
              type string;
            }
          }
          leaf cpu-protection {
            type string;
          }
          leaf delayed-enable {
            type string;
          }
          leaf description {
            type string;
          }
          container dhcp {
            leaf-list server {
              // NCS patched for predictable order
              ordered-by user;
              type string;
            }
            container gi-address {
              leaf gi-address-value {
                tailf:cli-drop-node-name;
                type string;
              }
              leaf src-ip-addr {
                type empty;
              }
            }
            leaf lease-populate {
              type string;
            }
            leaf trusted {
              type empty;
            }
            leaf shutdown {
              type string;
            }
          }
          leaf dynamic-tunnel-redundant-next-hop {
            type string;
          }
          leaf enable-ingress-stats {
            type empty;
          }
          leaf enable-mac-accounting {
            type empty;
          }
          container host-connectivity {
            leaf source {
              type string;
            }
            leaf interval {
              type string;
            }
            leaf action {
              type string;
            }
            leaf timeout {
              type string;
            }
            leaf count {
              type string;
            }
          }
          uses ncs_template_interface-icmp-grouping;
          leaf ip-mtu {
            type string;
          }
          container ipv6 {
            presence "true";
            leaf local-dhcp-server {
              type string;
            }
            uses ncs_template_ipv6-grouping;
            uses ncs_template_dhcp6-grouping;
          }
          leaf local-dhcp-server {
            type string;
          }
          leaf loopback {
            type empty;
          }
          leaf mac {
            type ncs_template_ieee-mac;
          }
          list sap {
            // NCS patched for predictable order
            ordered-by user;
            key "sap-id";
            leaf sap-id {
              type string;
            }
            leaf accounting-policy {
              type string;
            }
            leaf description {
              type string;
            }
            leaf dist-cpu-protection {
              type string;
            }
            leaf collect-stats {
              type empty;
            }
            container egress {
              choice agg {
                case new {
                  uses ncs_template_agg-rate-grouping;
                }
                case old {
                  container agg-rate-limit {
                    leaf agg-rate {
                      tailf:cli-drop-node-name;
                      type string;
                    }
                    leaf queue-frame-based-accounting {
                      type empty;
                    }
                  }
                }
              }
              container filter {
                leaf ip {
                  type ncs_template_filter-id;
                }
                leaf ipv6 {
                  type ncs_template_filter-id;
                }
              }
              leaf policer-control-policy {
                type string;
              }
              leaf qinq-mark-top-only {
                type empty;
              }
              leaf qos {
                type string;
              }
              uses ncs_template_sap-queue-override-grouping;
              leaf scheduler-mode {
                type ncs_template_scheduler-mode;
              }
              leaf scheduler-policy {
                type string;
              }
              uses ncs_template_sap-scheduler-override-grouping;
            }
            container ingress {
              leaf qos {
                type string;
              }
              container filter {
                uses ncs_template_filter-choice;
              }
              leaf flowspec {
                type string;
              }
              leaf flowspec-ipv6 {
                type string;
              }
              leaf match-qinq-dot1p {
                type string;
              }
              leaf policer-control-policy {
                type string;
              }
              container policer-control-override {
                presence "true";
                leaf max-rate {
                  type string;
                }
                container priority-mbs-thresholds {
                  container min-thresh-separation {
                    uses ncs_template_mbs-rate-grouping;
                  }
                  list priority {
                    // NCS patched for predictable order
                    ordered-by user;
                    key "level";
                    leaf level {
                      type string;
                    }
                    container mbs-contribution {
                      uses ncs_template_mbs-rate-grouping;
                    }
                  }
                }
              }
              uses ncs_template_sap-policer-override-grouping-ingress;
              uses ncs_template_sap-queue-override-grouping;
              leaf scheduler-policy {
                type string;
              }
              uses ncs_template_sap-scheduler-override-grouping;
            }
            leaf anti-spoof {
              type string;
            }
            leaf multi-service-site {
              type string;
            }
            container sub-sla-mgmt {
              presence "present";
              leaf def-sub-id {
                type string;
              }
              leaf def-sub-profile {
                type string;
              }
              container single-sub-parameters {
                presence "present";
                leaf profiled-traffic-only {
                  type empty;
                }
              }
              leaf shutdown {
                type string;
              }
            }
            leaf calling-station-id {
              type string;
            }
            list ip-tunnel {
              // NCS patched for predictable order
              ordered-by user;
              key "name";
              leaf name {
                type string;
              }
              leaf description {
                type string;
              }
              leaf dest-ip {
                type string;
              }
              container gre-header {
                presence "true";
              }
              leaf source {
                type string;
              }
              leaf remote-ip {
                type string;
              }
              leaf delivery-service {
                type string;
              }
              leaf shutdown {
                type string;
              }
            }
            leaf shutdown {
              type empty;
            }
          }
          list spoke-sdp {
            // NCS patched for predictable order
            ordered-by user;
            key "sdp-id vc-id";
            leaf sdp-id {
              type string;
            }
            leaf vc-id {
              type string;
            }
            leaf vc-type {
              type string;
            }
            container egress {
              container filter {
                uses ncs_template_filter-choice;
              }
            }
            container ingress {
              container filter {
                uses ncs_template_filter-choice;
              }
            }
            leaf shutdown {
              type string;
            }
          }
          leaf tos-marking-state {
            type string;
          }
          container urpf-check {
            leaf mode {
              type string;
            }
          }
          leaf vas-if-type {
            type string;
          }
          list vrrp {
            // NCS patched for predictable order
            ordered-by user;
            key "virtual-router-id";
            leaf virtual-router-id {
              type string;
            }
            leaf owner {
              type empty;
            }
            leaf passive {
              type empty;
            }
            uses ncs_template_authentication-key-grouping;
            leaf init-delay {
              type string;
            }
            leaf mac {
              type ncs_template_ieee-mac;
            }
            leaf master-int-inherit {
              type empty;
            }
            container message-interval {
              leaf seconds {
                tailf:cli-drop-node-name;
                type string;
              }
              leaf milliseconds {
                type string;
              }
            }
            leaf ping-reply {
              type empty;
            }
            leaf policy {
              type string;
            }
            leaf preempt {
              type empty;
            }
            leaf priority {
              type string;
            }
            leaf ssh-reply {
              type empty;
            }
            leaf standby-forwarding {
              type empty;
            }
            leaf telnet-reply {
              type empty;
            }
            leaf traceroute-reply {
              type empty;
            }
            list backup {
              // NCS patched for predictable order
              ordered-by user;
              tailf:cli-suppress-mode;
              key "address";
              leaf address {
                type string;
              }
            }
            leaf shutdown {
              type string;
            }
          }
          list secondary {
            // NCS patched for predictable order
            ordered-by user;
            tailf:cli-suppress-mode;
            key "address";
            leaf address {
              type string;
            }
            leaf broadcast {
              type string;
            }
          }
          container address {
            leaf ip-address {
              tailf:cli-drop-node-name;
              // NCS drop tailf-common:cli-diff-create-before statement
              type string;
            }
            leaf broadcast {
              type string;
            }
            leaf track-srrp {
              type string;
            }
          }
          list static-arp {
            // NCS patched for predictable order
            ordered-by user;
            tailf:cli-suppress-mode;
            key "ip-address";
            leaf ip-address {
              type string;
            }
            leaf ieee-address {
              tailf:cli-drop-node-name;
              type ncs_template_ieee-mac;
            }
          }
          leaf qos-route-lookup {
            type string;
          }
          container vpls {
            presence "true";
            leaf service-name {
              tailf:cli-drop-node-name;
              // NCS drop mandatory statement
              type string;
            }
            container egress {
              leaf reclassify-using-qos {
                type string;
              }
              leaf v4-routed-override-filter {
                type ncs_template_filter-id;
              }
            }
            container ingress {
              leaf v4-routed-override-filter {
                type ncs_template_filter-id;
              }
              leaf v6-routed-override-filter {
                type ncs_template_filter-id;
              }
            }
          }
          leaf shutdown {
            type empty;
          }
        }
        leaf service-name {
          type string;
        }
        leaf shutdown {
          type string;
        }
      }
      container proxy-arp-nd {
        list mac-list {
          // NCS patched for predictable order
          ordered-by user;
          key "name";
          leaf name {
            type string;
          }
          list mac {
            // NCS patched for predictable order
            ordered-by user;
            tailf:cli-suppress-mode;
            key "mac-id";
            leaf mac-id {
              type ncs_template_ieee-mac;
            }
          }
        }
      }
      container nat {
        list nat-policy {
          // NCS patched for predictable order
          ordered-by user;
          key "name";
          leaf name {
            type string;
          }
          container pool {
            leaf name {
              tailf:cli-drop-node-name;
              type string;
            }
            leaf router {
              type string;
            }
          }
          container timeouts {
            list timeouts {
              // NCS patched for predictable order
              ordered-by user;
              tailf:cli-drop-node-name;
              tailf:cli-suppress-mode;
              key "name";
              leaf name {
                type string;
              }
              leaf hrs {
                type string;
              }
              leaf min {
                type string;
              }
              leaf sec {
                type string;
              }
            }
          }
        }
      }
      list vpls {
        // NCS patched for predictable order
        ordered-by user;
        key "service-id";
        // NCS expand uses statement
        leaf service-id {
          type ncs_template_service-id;
        }
        leaf customer {
          type string;
        }
        leaf name {
          type string;
        }
        leaf etree {
          type empty;
        }
        leaf vpn {
          type string;
        }
        leaf m-vpls {
          type empty;
        }
        choice a {
          leaf b-vpls {
            type empty;
          }
          leaf i-vpls {
            type empty;
          }
          leaf r-vpls {
            type empty;
          }
        }
        leaf svc-sap-type {
          type string;
        }
        leaf description {
          type string;
        }
        leaf disable-learning {
          type empty;
        }
        leaf disable-aging {
          type empty;
        }
        leaf discard-unknown {
          type empty;
        }
        container allow-ip-int-bind {
          presence "true";
          leaf evpn-mpls-ecmp {
            type empty;
          }
          leaf forward-ipv4-multicast-to-ip-int {
            type empty;
          }
          leaf vxlan-ipv4-tep-ecmp {
            type empty;
          }
          container igmp-snooping {
            leaf mrouter-port {
              type empty;
            }
          }
        }
        leaf allow-ip-int-binding {
          type empty;
        }
        leaf service-name {
          type string;
        }
        list endpoint {
          // NCS patched for predictable order
          ordered-by user;
          key "endpoint-name";
          leaf endpoint-name {
            type string;
          }
          leaf description {
            type string;
          }
          leaf revert-time {
            type string;
          }
          leaf suppress-standby-signaling {
            type ncs_template_enable-disable;
          }
          container restrict-protected-src {
            presence "present";
            leaf restrict-protected-src-value {
              tailf:cli-drop-node-name;
              type string;
            }
          }
        }
        container eth-cfm {
          uses ncs_template_eth-cfm;
          leaf vmep-extensions {
            type empty;
          }
          leaf tunnel-fault {
            type string;
          }
        }
        leaf fdb-table-high-wmark {
          type string;
        }
        leaf fdb-table-low-wmark {
          type string;
        }
        leaf fdb-table-size {
          type string;
        }
        container igmp-snooping {
          leaf query-interval {
            type string;
          }
          leaf report-src-ip {
            type string;
          }
          leaf robust-count {
            type string;
          }
          leaf shutdown {
            type string;
          }
        }
        list site {
          // NCS patched for predictable order
          ordered-by user;
          key "name";
          leaf name {
            type string;
          }
          leaf site-id {
            type string;
          }
          leaf sap {
            type string;
          }
          leaf spoke-sdp {
            type string;
          }
          leaf shutdown {
            type string;
          }
        }
        list interface {
          // NCS patched for predictable order
          ordered-by user;
          key "ip-int-name";
          leaf ip-int-name {
            type string;
          }
          container address {
            choice a {
              leaf addr-and-prefix {
                tailf:cli-drop-node-name;
                type string;
              }
              case addr-and-netmask {
                leaf addr {
                  tailf:cli-drop-node-name;
                  type string;
                }
                leaf mask {
                  tailf:cli-drop-node-name;
                  type string;
                }
              }
            }
          }
          leaf arp-timeout {
            type string;
          }
          leaf description {
            type string;
          }
          leaf mac {
            type ncs_template_ieee-mac;
          }
          list static-arp {
            // NCS patched for predictable order
            ordered-by user;
            tailf:cli-suppress-mode;
            key "address";
            leaf address {
              type string;
            }
            leaf ieee-address {
              tailf:cli-drop-node-name;
              type ncs_template_ieee-mac;
            }
            leaf unnumbered {
              type empty;
            }
          }
          leaf unnumbered {
            type string;
          }
          leaf shutdown {
            type string;
          }
        }
        leaf local-age {
          type string;
        }
        container load-balancing {
          leaf per-service-hashing {
            type empty;
          }
          leaf spi-load-balancing {
            type empty;
          }
          leaf teid-load-balancing {
            type empty;
          }
        }
        container mac-move {
          leaf move-frequency {
            type string;
          }
          leaf number-retries {
            type string;
          }
          leaf retry-timeout {
            type string;
          }

          grouping vpls-mac-move-ports-grouping {
            leaf cumulative-factor {
              type string;
            }
            list sap {
              // NCS patched for predictable order
              ordered-by user;
              tailf:cli-suppress-mode;
              key "id";
              leaf id {
                type string;
              }
            }
            list spoke-sdp {
              // NCS patched for predictable order
              ordered-by user;
              tailf:cli-suppress-mode;
              key "id";
              leaf id {
                type string;
              }
            }
          }
          container primary-ports {
            uses vpls-mac-move-ports-grouping;
          }
          container secondary-ports {
            uses vpls-mac-move-ports-grouping;
          }
          leaf shutdown {
            type string;
          }
        }
        leaf mfib-table-high-wmark {
          type string;
        }
        leaf mfib-table-low-wmark {
          type string;
        }
        leaf mfib-table-size {
          type string;
        }
        container pbb {
          list backbone-vpls {
            // NCS patched for predictable order
            ordered-by user;
            key "service-id";
            leaf service-id {
              type ncs_template_service-id;
            }
            leaf isid {
              type string;
            }

            grouping service-vpls-mld-snooping-grouping {
              container mld-snooping {
                leaf mrouter-port {
                  type empty;
                }
              }
            }

            grouping service-vpls-igmp-snooping-grouping {
              container igmp-snooping {
                leaf mrouter-port {
                  type empty;
                }
              }
            }
            container igmp-snooping {
              leaf mrouter-dest {
                type string;
              }
            }
            container mld-snooping {
              leaf mrouter-dest {
                type string;
              }
            }
            list sap {
              // NCS patched for predictable order
              ordered-by user;
              key "sap-id";
              leaf sap-id {
                type string;
              }
              uses service-vpls-igmp-snooping-grouping;
              uses service-vpls-mld-snooping-grouping;
            }
            list sdp {
              // NCS patched for predictable order
              ordered-by user;
              key "sdp-id";
              leaf sdp-id {
                type string;
              }
              uses service-vpls-igmp-snooping-grouping;
              uses service-vpls-mld-snooping-grouping;
            }
            leaf stp {
              type empty;
            }
          }
          leaf force-qtag-forwarding {
            type empty;
          }
          leaf propagate-mac-flush-from-bvpls {
            type empty;
          }
          leaf-list send-bvpls-flush {
            // NCS patched for predictable order
            ordered-by user;
            type string;
          }
          leaf send-flush-on-bvpls-failure {
            type empty;
          }
          leaf source-bmac {
            type ncs_template_ieee-mac;
          }
          leaf use-sap-bmac {
            type empty;
          }
        }
        container proxy-arp {
          presence "true";
          list static {
            // NCS patched for predictable order
            ordered-by user;
            tailf:cli-suppress-mode;
            key "address";
            leaf address {
              type string;
            }
            leaf ieee-addr {
              // NCS drop mandatory statement
              tailf:cli-drop-node-name;
              type ncs_template_ieee-mac;
            }
          }
          leaf age-time {
            type string;
          }
          container dup-detect {
            leaf anti-spoof-mac {
              type ncs_template_ieee-mac;
            }
            leaf window {
              type string;
            }
            leaf num-moves {
              type string;
            }
            leaf hold-down {
              type string;
            }
          }
          list dynamic {
            // NCS patched for predictable order
            ordered-by user;
            key "address";
            leaf address {
              type string;
            }
            leaf mac-list {
              type string;
            }
            leaf resolve {
              type string;
            }
          }
          leaf dynamic-arp-populate {
            type empty;
          }
          leaf evpn-route-tag {
            type string;
          }
          leaf garp-flood-evpn {
            type string;
          }
          leaf send-refresh {
            type string;
          }
          leaf table-size {
            type string;
          }
          leaf unknown-arp-request-flood-evpn {
            type string;
          }
          leaf shutdown {
            type string;
          }
        }
        leaf propagate-mac-flush {
          type empty;
        }
        leaf remote-age {
          type string;
        }
        leaf send-flush-on-failure {
          type empty;
        }
        leaf service-mtu {
          type string;
        }
        list spb {
          // NCS patched for predictable order
          ordered-by user;
          key "isis-instance";
          leaf isis-instance {
            type string;
          }
          leaf fid {
            type string;
          }
          list level {
            // NCS patched for predictable order
            ordered-by user;
            key "level";
            leaf level {
              type string;
            }
            leaf bridge-priority {
              type string;
            }
            container ect-algorithm {
              leaf fid-range {
                type string;
              }
              leaf path-id {
                tailf:cli-drop-node-name;
                type string;
              }
            }
            container forwarding-tree-topology {
              leaf unicast {
                type string;
              }
            }
            leaf hello-interval {
              type string;
            }
            leaf hello-multiplier {
              type string;
            }
            leaf metric {
              type string;
            }
          }
          leaf lsp-pacing-interval {
            type string;
          }
          leaf retransmit-interval {
            type string;
          }
          leaf shutdown {
            type string;
          }
        }
        container stp {
          leaf forward-delay {
            type string;
          }
          leaf hello-time {
            type string;
          }
          leaf hold-count {
            type string;
          }
          leaf max-age {
            type string;
          }
          leaf mode {
            type string;
          }
          list mst-instance {
            // NCS patched for predictable order
            ordered-by user;
            key "mst-inst-number";
            leaf mst-inst-number {
              type string;
            }
            leaf mst-priority {
              type string;
            }
            list vlan-range {
              // NCS patched for predictable order
              ordered-by user;
              tailf:cli-suppress-mode;
              key "vlan";
              leaf vlan {
                type string;
              }
            }
          }
          leaf mst-max-hops {
            type string;
          }
          leaf mst-name {
            type string;
          }
          leaf mst-revision {
            type string;
          }
          leaf priority {
            type string;
          }
          leaf shutdown {
            type string;
          }
        }
        leaf def-mesh-vc-id {
          type string;
        }
        list mesh-sdp {
          // NCS patched for predictable order
          ordered-by user;
          key "sdp-id vc-id";
          uses ncs_template_sdp-spoke-mesh-common;
        }
        container pim-snooping {
          leaf shutdown {
            type string;
          }
        }
        list spoke-sdp {
          // NCS patched for predictable order
          ordered-by user;
          key "sdp-id vc-id";
          uses ncs_template_sdp-spoke-mesh-common;
          leaf leaf-ac {
            type empty;
          }
          leaf split-horizon-group {
            type string;
          }
          container dhcp {
            leaf description {
              type string;
            }
            leaf snoop {
              type empty;
            }
          }
          leaf bpdu-translation {
            type string;
          }
          leaf diable-aging {
            type empty;
          }
          leaf disable-learning {
            type empty;
          }
          leaf discard-unknown-source {
            type empty;
          }
          leaf l2pt-termination {
            type empty;
          }
          leaf entropy-label {
            type empty;
          }
          leaf limit-mac-move {
            type ncs_template_limit-mac-move;
          }
          leaf max-nbr-mac-addr {
            type string;
          }
          container stp {
            uses ncs_template_stp-common;
          }
          container oper-group-choice {
            tailf:cli-drop-node-name;
            leaf monitor-oper-group {
              type string;
            }
            leaf oper-group {
              type string;
            }
          }
          container transit-policy {
            leaf prefix {
              type string;
            }
          }
          leaf pw-status-signaling {
            type string;
          }
        }
        list sap {
          // NCS patched for predictable order
          ordered-by user;
          key "sap-id";
          leaf sap-id {
            type string;
          }
          leaf dist-cpu-protection {
            type string;
          }
          leaf leaf-ac {
            type empty;
          }
          list static-mac {
            // NCS patched for predictable order
            ordered-by user;
            tailf:cli-suppress-mode;
            key "mac";
            leaf mac {
              type ncs_template_ieee-mac;
            }
          }
          leaf eth-ring {
            type string;
          }
          container sub-sla-mgmt {
            container single-sub-parameters {
              leaf profiled-traffic-only {
                type empty;
              }
              container non-sub-traffic {
                leaf sub-profile {
                  type string;
                }
                leaf sla-profile {
                  type string;
                }
                leaf subscriber {
                  type string;
                }
              }
            }
            leaf shutdown {
              type string;
            }
          }
          leaf allow-dot1q-msaps {
            type empty;
          }
          leaf arp-reply-agent {
            tailf:cli-drop-node-name;
            type string;
          }
          leaf cflowd {
            type empty;
          }
          leaf split-horizon-group {
            type string;
          }
          leaf capture-sap {
            type empty;
          }
          leaf dhcp-python-policy {
            type ncs_template_string32;
          }
          leaf dhcp6-python-policy {
            type ncs_template_string32;
          }
          leaf-list trigger-packet {
            // NCS patched for predictable order
            ordered-by user;
            type string;
          }
          leaf authentication-policy {
            type string;
          }
          leaf accounting-policy {
            type string;
          }
          leaf anti-spoof {
            type string;
          }
          leaf app-profile {
            type string;
          }
          leaf auto-learn-mac-protect {
            type empty;
          }
          leaf bpdu-translation {
            type string;
          }
          leaf collect-stats {
            type empty;
          }
          leaf description {
            type string;
          }
          leaf disable-aging {
            type empty;
          }
          leaf disable-learning {
            type empty;
          }
          leaf discard-unknown-source {
            type empty;
          }
          container eth-cfm {
            uses ncs_template_eth-cfm;
            container mip {
              presence "true";
              leaf mac {
                type string;
              }
            }
          }
          leaf host-lockout-policy {
            type ncs_template_string32;
          }
          container igmp-snooping {
            uses ncs_template_igmp-snooping-grouping;
          }
          container ingress {
            // NCS expand uses statement
            container filter {
              // NCS expand uses statement
              leaf ip {
                type ncs_template_filter-id;
              }
              leaf ipv6 {
                type ncs_template_filter-id;
              }
              leaf mac {
                type ncs_template_filter-id;
              }
            }
            container aggregate-meter-rate {
              leaf value {
                tailf:cli-drop-node-name;
                type string;
              }
              leaf burst {
                type string;
              }
            }
            leaf match-qinq-dot1p {
              type string;
            }
            container qos {
              leaf policy-id {
                tailf:cli-drop-node-name;
                type string;
              }
              leaf shared-queuing {
                type empty;
              }
              leaf enable-table-classification {
                type empty;
              }
            }
            // NCS expand uses statement
            container queue-override {
              list queue {
                // NCS patched for predictable order
                ordered-by user;
                key "queue-id";
                leaf queue-id {
                  type string;
                }
                // NCS expand uses statement
                container adaptation-rule {
                  leaf pir {
                    type string;
                  }
                  leaf cir {
                    type string;
                  }
                }
                leaf avg-frame-overhead {
                  type string;
                }
                container mbs {
                  leaf val {
                    tailf:cli-drop-node-name;
                    type string;
                  }
                  leaf unit {
                    tailf:cli-drop-node-name;
                    type string;
                  }
                }
                leaf cbs {
                  type string;
                }
                leaf high-prio-only {
                  type string;
                }
                container rate {
                  leaf pir {
                    tailf:cli-drop-node-name;
                    type string;
                  }
                  leaf cir {
                    type string;
                  }
                }
                container parent {
                  leaf weight {
                    type string;
                  }
                  leaf cir-weight {
                    type string;
                  }
                }
                // NCS expand uses statement
                container percent-rate {
                  leaf pir {
                    tailf:cli-drop-node-name;
                    type string;
                  }
                  leaf cir {
                    type string;
                  }
                }
              }
            }
            leaf agg-shaper-rate {
              type string;
            }
            // NCS expand uses statement
            container policer-override {
              list policer {
                // NCS patched for predictable order
                ordered-by user;
                key "policer-id";
                leaf policer-id {
                  type string;
                }
                // NCS expand uses statement
                // NCS expand uses statement
                container cbs {
                  // NCS expand uses statement
                  leaf size {
                    tailf:cli-drop-node-name;
                    type string;
                  }
                  leaf unit {
                    tailf:cli-drop-node-name;
                    type string;
                  }
                }
                container mbs {
                  // NCS expand uses statement
                  leaf size {
                    tailf:cli-drop-node-name;
                    type string;
                  }
                  leaf unit {
                    tailf:cli-drop-node-name;
                    type string;
                  }
                }
                container rate {
                  leaf pir {
                    tailf:cli-drop-node-name;
                    type ncs_template_rate-type;
                  }
                  leaf cir {
                    type ncs_template_rate-type;
                  }
                }
                leaf stat-mode {
                  type ncs_template_policer-stat-mode;
                }
                container packet-byte-offset {
                  choice add-delete {
                    leaf add {
                      type string;
                    }
                    leaf subtract {
                      type string;
                    }
                  }
                }
              }
            }
            leaf policer-control-policy {
              type string;
            }
            leaf scheduler-policy {
              type string;
            }
            // NCS expand uses statement
            container scheduler-override {
              list scheduler {
                // NCS patched for predictable order
                ordered-by user;
                key "scheduler-policy-name";
                leaf scheduler-policy-name {
                  type string;
                }
                container parent {
                  leaf weight {
                    type string;
                  }
                  leaf cir-weight {
                    type string;
                  }
                }
                container rate {
                  leaf rate {
                    tailf:cli-drop-node-name;
                    type string;
                  }
                  leaf cir {
                    type string;
                  }
                }
              }
            }
            leaf vlan-translation {
              type string;
            }
            container aggregate-policer-rate {
              leaf rate {
                tailf:cli-drop-node-name;
                type string;
              }
              leaf burst {
                type string;
              }
            }
            container qtag-manipulation {
              leaf preserve {
                type empty;
              }
            }
          }
          leaf lag-link-map-profile {
            type string;
          }
          leaf l2pt-termination {
            type empty;
          }
          leaf limit-mac-move {
            type ncs_template_limit-mac-move;
          }
          leaf mac-pinning {
            type empty;
          }
          container managed-vlan-list {
            leaf default-sap {
              type empty;
            }
            leaf range {
              type string;
            }
          }
          leaf max-nbr-mac-addr {
            type string;
          }
          leaf monitor-oper-group {
            type string;
          }
          container msap-defaults {
            leaf group-interface {
              type string;
            }
            leaf policy {
              type ncs_template_string32;
            }
            leaf service {
              type ncs_template_service-id;
            }
          }
          container ipoe-session {
            uses ncs_template_ipoe-session-grouping;
          }
          leaf multi-service-site {
            type string;
          }
          leaf pppoe-policy {
            type ncs_template_string32;
          }
          container restrict-protected-src {
            presence "present";
            leaf restrict-protected-src-value {
              tailf:cli-drop-node-name;
              type string;
            }
          }
          leaf restrict-unprotected-dst {
            type empty;
          }
          leaf ring-node {
            type empty;
          }
          container egress {
            uses ncs_template_sap-egress-grouping;
          }
          container stp {
            uses ncs_template_stp-common;
            list mst-instance {
              // NCS patched for predictable order
              ordered-by user;
              key "mst-inst-number";
              leaf mst-inst-number {
                type string;
              }
              leaf mst-path-cost {
                type string;
              }
              leaf mst-priority {
                type string;
              }
            }
          }
          container statistics {
            container ingress {
              leaf counter-mode {
                type string;
              }
            }
          }
          leaf tod-suite {
            type string;
          }
          leaf track-srrp {
            type string;
          }
          leaf shutdown {
            type empty;
          }
        }
        list split-horizon-group {
          // NCS patched for predictable order
          ordered-by user;
          key "group-name";
          leaf group-name {
            type string;
          }
          leaf residential-group {
            type empty;
          }
          leaf auto-learn-mac-protect {
            type empty;
          }
          leaf description {
            type string;
          }
          container restrict-protected-src {
            presence "present";
            leaf restrict-protected-src-value {
              tailf:cli-drop-node-name;
              type string;
            }
          }
          leaf restrict-unprotected-dst {
            type empty;
          }
        }
        list bgp {
          // NCS patched for predictable order
          ordered-by user;
          key "bgp-id";
          leaf bgp-id {
            type string;
          }

          grouping pw-template-binding-grouping {
            leaf policy-id {
              type string;
            }
            leaf split-horizon-group {
              type string;
            }
          }
          list pw-template-bind {
            // NCS patched for predictable order
            ordered-by user;
            key "policy-id";
            uses pw-template-binding-grouping;
            leaf import-rt {
              type ncs_template_string32;
            }
          }
          list pw-template-binding {
            // NCS patched for predictable order
            ordered-by user;
            key "policy-id";
            uses pw-template-binding-grouping;
            leaf monitor-oper-group {
              type string;
            }
            container import-rt {
              leaf rt1 {
                tailf:cli-drop-node-name;
                type ncs_template_string32;
              }
              leaf rt2 {
                tailf:cli-drop-node-name;
                type ncs_template_string32;
              }
              leaf rt3 {
                tailf:cli-drop-node-name;
                type ncs_template_string32;
              }
              leaf rt4 {
                tailf:cli-drop-node-name;
                type ncs_template_string32;
              }
              leaf rt5 {
                tailf:cli-drop-node-name;
                type ncs_template_string32;
              }
            }
          }
          leaf route-distinguisher {
            type string;
          }
          container route-target {
            leaf export {
              type string;
            }
            leaf import {
              type string;
            }
          }
          leaf-list vsi-import {
            // NCS patched for predictable order
            ordered-by user;
            type string;
          }
          leaf-list vsi-export {
            // NCS patched for predictable order
            ordered-by user;
            type string;
          }
        }
        container bgp-ad {
          presence "true";
          leaf vpls-id {
            type ncs_template_service-id;
          }
          container vsi-id {
            leaf prefix {
              type string;
            }
          }
          leaf shutdown {
            type string;
          }
        }
        container bgp-evpn {
          presence "true";
          leaf unknown-mac-route {
            type empty;
          }
          leaf evi {
            type string;
          }
          container mac-duplication {
            container detect {
              leaf num-moves {
                type string;
              }
              leaf window {
                type string;
              }
            }
            leaf retry {
              type string;
            }
          }
          container ip-route-advertisement {
            presence "true";
            leaf incl-host {
              type empty;
            }
          }
          container mpls {
            presence "true";
            leaf bgp {
              type string;
            }
            leaf entropy-label {
              type empty;
            }
            leaf route-next-hop {
              type string;
            }
            leaf default-route-tag {
              type string;
            }
            leaf split-horizon-group {
              type string;
            }
            leaf control-word {
              type empty;
            }
            leaf restrict-protected-src {
              type string;
            }
            leaf force-vlan-vc-forwarding {
              type empty;
            }
            container auto-bind-tunnel {
              uses ncs_template_resolution-filter-grouping;
              leaf enforce-strict-tunnel-tagging {
                type empty;
              }
            }
            leaf ingress-replication-bum-label {
              type empty;
            }
            leaf ecmp {
              type string;
            }
            leaf oper-group {
              type string;
            }
            leaf shutdown {
              type string;
            }
          }
          container vxlan {
            presence "true";
            leaf shutdown {
              type string;
            }
            leaf bgp {
              type string;
            }
            leaf vxlan-instance {
              type string;
            }
          }
        }
        container static-mac {
          list mac {
            // NCS patched for predictable order
            ordered-by user;
            tailf:cli-suppress-mode;
            key "mac";
            leaf mac {
              type ncs_template_ieee-mac;
            }
            leaf create {
              type empty;
            }
            leaf black-hole {
              type empty;
            }
            leaf sap {
              type string;
            }
            leaf monitor {
              type string;
            }
          }
        }
        container bgp-vpls {
          leaf max-ve-id {
            type string;
          }
          container ve-name {
            leaf ve-name {
              tailf:cli-drop-node-name;
              type string;
            }
            leaf ve-id {
              type string;
            }
          }
          leaf shutdown {
            type string;
          }
        }
        list vxlan {
          // NCS patched for predictable order
          ordered-by user;
          key "vni";
          leaf instance {
            type string;
          }
          leaf vni {
            type string;
          }
          container assisted-replication {
            leaf role {
              tailf:cli-drop-node-name;
              type string;
            }
            leaf replicator-activation-time {
              type string;
            }
          }
          container network {
            container ingress {
              container qos {
                leaf network-policy-id {
                  tailf:cli-drop-node-name;
                  type string;
                }
                leaf fp-redirect-group {
                  type string;
                }
                leaf instance {
                  type string;
                }
              }
            }
          }
          leaf restrict-protected-src {
            type string;
          }
          leaf rx-discard-on-ndf {
            type string;
          }
        }
        leaf shutdown {
          type string;
        }
      }
      list vprn {
        // NCS patched for predictable order
        ordered-by user;
        key "service-id";
        uses ncs_template_service-id-grouping;
        leaf customer {
          type string;
        }
        leaf entropy-label {
          type empty;
        }
        container ntp {
          presence "true";
          leaf shutdown {
            type string;
          }
        }
        container management {
          presence "true";
          leaf allow-ftp {
            type empty;
          }
          leaf allow-grpc {
            type empty;
          }
          leaf allow-netconf {
            type empty;
          }
          leaf allow-ssh {
            type empty;
          }
          leaf allow-telnet {
            type empty;
          }
          leaf allow-telnet6 {
            type empty;
          }
        }
        container aaa {
          container remote-servers {

            grouping remote-servers-grouping {
              container accounting {
                presence "true";
                leaf record-type {
                  type string;
                }
              }
              container authorization {
                presence "true";
                leaf use-priv-lvl {
                  type empty;
                }
              }
              list server {
                // NCS patched for predictable order
                ordered-by user;
                tailf:cli-suppress-mode;
                unique "address";
                key "server-index";
                leaf server-index {
                  type string;
                }
                leaf address {
                  type string;
                }
                leaf secret {
                  type string;
                }
                leaf key-type {
                  tailf:cli-drop-node-name;
                  type string;
                }
                leaf port {
                  type string;
                }
              }
              container priv-lvl-map {
                list priv-lvl {
                  // NCS patched for predictable order
                  ordered-by user;
                  tailf:cli-suppress-mode;
                  key "priv-lvl";
                  leaf priv-lvl {
                    type string;
                  }
                  leaf user-profile {
                    tailf:cli-drop-node-name;
                    type string;
                  }
                }
              }
              leaf shutdown {
                type string;
              }
            }
            container tacplus {
              presence "true";
              uses remote-servers-grouping;
              leaf timeout {
                type string;
              }
            }
          }
        }
        leaf name {
          type string;
        }
        container maximum-ipv6-routes {
          leaf number {
            tailf:cli-drop-node-name;
            type string;
          }
          leaf threshold {
            type string;
          }
          leaf log-only {
            type empty;
          }
        }
        leaf multicast-info-policy {
          type ncs_template_string32;
        }
        leaf ecmp {
          type string;
        }
        leaf ignore-nh-metric {
          type empty;
        }
        leaf auto-bind {
          type string;
        }
        container auto-bind-tunnel {
          uses ncs_template_resolution-filter-grouping;
          leaf ecmp {
            type string;
          }
          leaf weighted-ecmp {
            type empty;
          }
        }
        container bgp {
          presence "true";
          leaf advertise-inactive {
            type empty;
          }
          leaf enable-peer-tracking {
            type empty;
          }
          leaf-list backup-path {
            // NCS patched for predictable order
            ordered-by user;
            type string;
          }
          leaf loop-detect {
            type string;
          }
          leaf rapid-withdrawal {
            type empty;
          }
          leaf damping {
            type empty;
          }
          leaf-list family {
            // NCS patched for predictable order
            ordered-by user;
            type ncs_template_family-names-type;
          }
          uses ncs_template_authentication-key-grouping;
          uses ncs_template_bgp-common-grouping;
          uses ncs_template_bgp-best-path-selection-grouping;
          uses ncs_template_bgp-local-as-grouping;
          leaf router-id {
            type string;
          }
          container error-handling {
            leaf update-fault-tolerance {
              type empty;
            }
          }
          uses ncs_template_bgp-import-export-grouping;
          uses ncs_template_bgp-graceful-restart-grouping;
          container monitor {
            leaf shutdown {
              type string;
            }
            leaf-list station {
              // NCS patched for predictable order
              ordered-by user;
              type string;
            }
          }
          container rib-management {
            container ipv4 {
              leaf-list leak-import {
                // NCS patched for predictable order
                ordered-by user;
                type string;
              }
            }
            container ipv6 {
              leaf-list leak-import {
                // NCS patched for predictable order
                ordered-by user;
                type string;
              }
            }
          }
          list group {
            // NCS patched for predictable order
            ordered-by user;
            key "name";
            leaf name {
              type string;
            }
            leaf damping {
              type empty;
            }
            leaf multihop {
              type string;
            }
            leaf passive {
              type empty;
            }
            uses ncs_template_enable-origin-validation-grouping;
            leaf enable-peer-tracking {
              type empty;
            }
            leaf loop-detect-threshold {
              type string;
            }
            leaf auth-keychain {
              type string;
            }
            container error-handling {
              leaf update-fault-tolerance {
                type empty;
              }
            }
            leaf as-override {
              type empty;
            }
            uses ncs_template_bgp-local-as-grouping;
            uses ncs_template_authentication-key-grouping;
            leaf bfd-enable {
              type empty;
            }
            leaf description {
              type string;
            }
            leaf keepalive {
              type string;
            }
            leaf hold-time {
              type string;
            }
            leaf med-out {
              type string;
            }
            leaf loop-detect {
              type string;
            }
            leaf-list disable-communities {
              // NCS patched for predictable order
              ordered-by user;
              type string;
            }
            leaf-list family {
              // NCS patched for predictable order
              ordered-by user;
              type string;
            }
            uses ncs_template_bgp-import-export-grouping;
            uses ncs_template_bgp-graceful-restart-grouping;
            leaf local-address {
              type string;
            }
            leaf min-route-advertisement {
              type string;
            }
            list neighbor {
              // NCS patched for predictable order
              ordered-by user;
              key "address";
              leaf address {
                type string;
              }
              uses ncs_template_enable-origin-validation-grouping;
              leaf local-preference {
                type string;
              }
              leaf advertise-inactive {
                type empty;
              }
              leaf as-override {
                type empty;
              }
              leaf bfd-enable {
                type empty;
              }
              leaf description {
                type string;
              }
              leaf-list family {
                // NCS patched for predictable order
                ordered-by user;
                type string;
              }
              uses ncs_template_bgp-graceful-restart-grouping;
              uses ncs_template_bgp-import-export-grouping;
              leaf local-address {
                type string;
              }
              uses ncs_template_bgp-local-as-grouping;
              leaf loop-detect {
                type string;
              }
              leaf med-out {
                type string;
              }
              leaf multihop {
                type string;
              }
              leaf peer-as {
                type string;
              }
              uses ncs_template_bgp-prefix-limit-grouping;
              leaf passive {
                type empty;
              }
              leaf ttl-security {
                type string;
              }
              container remove-private {
                presence "true";
                leaf-list options {
                  // NCS patched for predictable order
                  ordered-by user;
                  tailf:cli-drop-node-name;
                  type string;
                }
              }
              leaf split-horizon {
                type empty;
              }
              leaf type {
                type string;
              }
              uses ncs_template_authentication-key-grouping;
              leaf keepalive {
                type string;
              }
              leaf hold-time {
                type string;
              }
              leaf shutdown {
                type string;
              }
            }
            uses ncs_template_bgp-prefix-limit-grouping;
            leaf split-horizon {
              type empty;
            }
            leaf peer-as {
              type string;
            }
            container remove-private {
              presence "true";
              leaf-list options {
                // NCS patched for predictable order
                ordered-by user;
                tailf:cli-drop-node-name;
                type string;
              }
            }
            leaf type {
              type string;
            }
            leaf next-hop-self {
              type empty;
            }
            leaf preference {
              type string;
            }
            leaf local-preference {
              type string;
            }
            leaf shutdown {
              type string;
            }
          }
          leaf ibgp-multipath {
            type empty;
          }
          leaf med-out {
            type string;
          }
          leaf min-route-advertisement {
            type string;
          }
          uses ncs_template_bgp-multipath-grouping;
          uses ncs_template_bgp-multi-path-grouping;
          container next-hop-resolution {
            leaf policy {
              type string;
            }
          }
          leaf split-horizon {
            type empty;
          }
          leaf shutdown {
            type string;
          }
        }
        container bgp-ipvpn {
          container mpls {
            container auto-bind-tunnel {
              leaf resolution {
                type string;
              }
              container resolution-filter {
                leaf bgp {
                  type string;
                }
                leaf ldp {
                  type empty;
                }
                leaf rsvp {
                  type empty;
                }
                leaf sr-isis {
                  type empty;
                }
                leaf sr-ospf {
                  type empty;
                }
                leaf sr-ospf3 {
                  type empty;
                }
                leaf sr-policy {
                  type empty;
                }
                leaf sr-te {
                  type empty;
                }
              }
              leaf ecmp {
                type string;
              }
              leaf weighted-ecmp {
                type empty;
              }
            }
            leaf route-distinguisher {
              type string;
            }
            leaf-list vrf-import {
              // NCS patched for predictable order
              ordered-by user;
              type string;
            }
            leaf-list vrf-export {
              // NCS patched for predictable order
              ordered-by user;
              type string;
            }
            container vrf-target {
              leaf ext-community {
                tailf:cli-drop-node-name;
                type string;
              }
              leaf export {
                type string;
              }
              leaf import {
                type string;
              }
            }
            leaf shutdown {
              type string;
            }
          }
        }
        container bgp-evpn {
          container mpls {
            container auto-bind-tunnel {
              leaf resolution {
                type string;
              }
              container resolution-filter {
                leaf bgp {
                  type empty;
                }
                leaf ldp {
                  type empty;
                }
                leaf rsvp {
                  type empty;
                }
                leaf sr-isis {
                  type empty;
                }
                leaf sr-ospf {
                  type empty;
                }
                leaf sr-ospf3 {
                  type empty;
                }
                leaf sr-policy {
                  type empty;
                }
                leaf sr-te {
                  type empty;
                }
              }
            }
            leaf route-distinguisher {
              type string;
            }
            leaf-list vrf-import {
              // NCS patched for predictable order
              ordered-by user;
              type string;
            }
            leaf-list vrf-export {
              // NCS patched for predictable order
              ordered-by user;
              type string;
            }
            container vrf-target {
              leaf ext-community {
                tailf:cli-drop-node-name;
                type string;
              }
              leaf export {
                type string;
              }
              leaf import {
                type string;
              }
            }
            leaf shutdown {
              type string;
            }
          }
        }
        container bgp-shared-queue {
          presence "true";
          leaf cir {
            type ncs_template_rate-type;
          }
          leaf pir {
            type ncs_template_rate-type;
          }
        }
        leaf-list enable-bgp-vpn-backup {
          // NCS patched for predictable order
          ordered-by user;
          type string;
        }
        leaf export-inactive-bgp {
          type empty;
        }
        container grt-lookup {
          container enable-grt {
            presence "true";
            leaf allow-local-management {
              type empty;
            }
          }
          leaf-list export-grt {
            // NCS patched for predictable order
            ordered-by user;
            type string;
          }
          leaf export-limit {
            type string;
          }
          leaf-list import-grt {
            // NCS patched for predictable order
            ordered-by user;
            type string;
          }
          leaf export-v6-limit {
            type string;
          }
        }
        leaf label-mode {
          type string;
        }
        container mc-maximum-routes {
          leaf number {
            tailf:cli-drop-node-name;
            type string;
          }
          leaf log-only {
            type empty;
          }
          leaf threshold {
            type string;
          }
        }
        container rip {
          presence "true";
          uses ncs_template_authentication-key-grouping;
          leaf export {
            type string;
          }
          list group {
            // NCS patched for predictable order
            ordered-by user;
            key "name";
            leaf name {
              type string;
            }
            container timers {
              leaf update {
                tailf:cli-drop-node-name;
                type string;
              }
              leaf timeout {
                tailf:cli-drop-node-name;
                type string;
              }
              leaf flush {
                tailf:cli-drop-node-name;
                type string;
              }
            }
            uses ncs_template_authentication-key-grouping;
            list neighbor {
              // NCS patched for predictable order
              ordered-by user;
              key "intf-id";
              leaf intf-id {
                type ncs_template_string32;
              }
              uses ncs_template_authentication-key-grouping;
              leaf bfd-enable {
                type empty;
              }
              leaf receive {
                type string;
              }
              leaf split-horizon {
                type string;
              }
              container timers {
                leaf update {
                  tailf:cli-drop-node-name;
                  type string;
                }
                leaf timeout {
                  tailf:cli-drop-node-name;
                  type string;
                }
                leaf flush {
                  tailf:cli-drop-node-name;
                  type string;
                }
              }
              leaf shutdown {
                type string;
              }
            }
            leaf-list export {
              // NCS patched for predictable order
              ordered-by user;
              type string;
            }
            leaf shutdown {
              type string;
            }
          }
          leaf shutdown {
            type string;
          }
        }
        container ospf {
          presence "true";
          leaf router-id {
            tailf:cli-drop-node-name;
            type string;
          }
          leaf super-backbone {
            type empty;
          }
          container vpn-domain {
            leaf domain-type {
              tailf:cli-drop-node-name;
              type string;
            }
            leaf id {
              tailf:cli-drop-node-name;
              type string;
            }
          }
          leaf vpn-tag {
            type string;
          }
          list area {
            // NCS patched for predictable order
            ordered-by user;
            key "area-id";
            uses ncs_template_ospf-area-id-grouping;
            list interface {
              // NCS patched for predictable order
              ordered-by user;
              key "ip-int-name";
              leaf ip-int-name {
                type ncs_template_string32;
              }
              leaf mtu {
                type string;
              }
              leaf metric {
                type string;
              }
              container bfd-enable {
                presence "true";
              }
              leaf authentication-type {
                type string;
              }
              leaf interface-type {
                type string;
              }
              leaf hello-interval {
                type string;
              }
              leaf dead-interval {
                type string;
              }
              list message-digest-key {
                // NCS patched for predictable order
                ordered-by user;
                tailf:cli-suppress-mode;
                key "key-id";
                leaf key-id {
                  type string;
                }
                leaf md5 {
                  type empty;
                }
                leaf hash-value {
                  tailf:cli-drop-node-name;
                  type string;
                }
                leaf scheme {
                  tailf:cli-drop-node-name;
                  type ncs_template_hash-method;
                }
              }
              leaf shutdown {
                type string;
              }
            }
            list sham-link {
              // NCS patched for predictable order
              ordered-by user;
              key "ip-int-name ip-address";
              leaf ip-int-name {
                type ncs_template_string32;
              }
              leaf ip-address {
                type string;
              }
              leaf metric {
                type string;
              }
            }
          }
          leaf-list export {
            // NCS patched for predictable order
            ordered-by user;
            type string;
          }
          leaf shutdown {
            type string;
          }
        }
        list ospf3 {
          // NCS patched for predictable order
          ordered-by user;
          key "ospf-instance";
          leaf ospf-instance {
            type string;
          }
          leaf export {
            type string;
          }
          list area {
            // NCS patched for predictable order
            ordered-by user;
            key "area-id";
            uses ncs_template_ospf-area-id-grouping;
            list interface {
              // NCS patched for predictable order
              ordered-by user;
              key "ip-int-name";
              leaf ip-int-name {
                type ncs_template_string32;
              }
              leaf mtu {
                type string;
              }
              leaf metric {
                type string;
              }
              container bfd-enable {
                presence "true";
              }
              leaf authentication-type {
                type string;
              }
              leaf interface-type {
                type string;
              }
              leaf hello-interval {
                type string;
              }
              leaf dead-interval {
                type string;
              }
              list message-digest-key {
                // NCS patched for predictable order
                ordered-by user;
                tailf:cli-suppress-mode;
                key "key-id";
                leaf key-id {
                  type string;
                }
                leaf md5 {
                  type empty;
                }
                leaf hash-value {
                  tailf:cli-drop-node-name;
                  type string;
                }
                leaf scheme {
                  tailf:cli-drop-node-name;
                  type ncs_template_hash-method;
                }
              }
              leaf shutdown {
                type string;
              }
            }
          }
          leaf shutdown {
            type string;
          }
        }
        leaf description {
          type string;
        }
        container dhcp {
          uses ncs_template_local-dhcp-server-grouping;
        }
        container dhcp6 {
          list local-dhcp-server {
            // NCS patched for predictable order
            ordered-by user;
            key "server-name";
            leaf server-name {
              type ncs_template_string32;
            }
            leaf description {
              type string;
            }
            container use-link-address {
              presence "true";
              leaf scope {
                type string;
              }
            }
            list pool {
              // NCS patched for predictable order
              ordered-by user;
              key "pool-name";
              leaf pool-name {
                type ncs_template_string32;
              }
              container delegated-prefix-length {
                leaf prefix-length {
                  tailf:cli-drop-node-name;
                  type string;
                }
                leaf minimum {
                  type string;
                }
                leaf maximum {
                  type string;
                }
              }
              list prefix {
                // NCS patched for predictable order
                ordered-by user;
                key "ipv6-prefix";
                leaf ipv6-prefix {
                  type string;
                }
                leaf failover {
                  type string;
                }
                leaf pd {
                  type empty;
                }
                leaf wan-host {
                  type empty;
                }
                uses ncs_template_dhcp6-lease-timers-grouping;
              }
            }
            leaf shutdown {
              type string;
            }
          }
        }
        container igmp {

          grouping vprn-igmp-interface-grouping {
            leaf ip-int-name {
              type ncs_template_string32;
            }
            leaf disable-router-alert-check {
              type empty;
            }
            leaf import {
              type string;
            }
            leaf max-groups {
              type string;
            }
            leaf max-grp-sources {
              type string;
            }
            leaf max-sources {
              type string;
            }
            uses ncs_template_mcac-grouping;
            leaf sub-hosts-only {
              type empty;
            }
            leaf subnet-check {
              type empty;
            }
            leaf version {
              type string;
            }
            leaf shutdown {
              type string;
            }
          }

          grouping vrpn-igmp-grp-range-grouping {
            list grp-range {
              // NCS patched for predictable order
              ordered-by user;
              key "start end";
              leaf start {
                type string;
              }
              leaf end {
                type string;
              }
              list source {
                // NCS patched for predictable order
                ordered-by user;
                tailf:cli-suppress-mode;
                key "address";
                leaf address {
                  type string;
                }
              }
            }
          }

          grouping vprn-igmp-query-grouping {
            leaf query-response-interval {
              type string;
            }
            leaf query-last-member-interval {
              type string;
            }
            leaf query-last-listener-interval {
              type string;
            }
            leaf query-interval {
              type string;
            }
            leaf redundant-multicast {
              type empty;
            }
          }
          list group-interface {
            // NCS patched for predictable order
            ordered-by user;
            key "ip-int-name";
            leaf fwd-service {
              type string;
            }
            uses vprn-igmp-interface-grouping;
            leaf query-src-ip {
              type string;
            }
          }
          leaf grp-if-query-src-ip {
            type string;
          }
          list interface {
            // NCS patched for predictable order
            ordered-by user;
            key "ip-int-name";
            uses vprn-igmp-query-grouping;
            uses vprn-igmp-interface-grouping;
            container ssm-translate {
              uses vrpn-igmp-grp-range-grouping;
            }
            uses ncs_template_igmp-static-grouping;
          }
          uses vprn-igmp-query-grouping;
          leaf robust-count {
            type string;
          }
          container ssm-translate {
            uses vrpn-igmp-grp-range-grouping;
          }
          leaf shutdown {
            type string;
          }
        }
        list subscriber-interface {
          // NCS patched for predictable order
          ordered-by user;
          key "id";
          uses ncs_template_subscriber-interface-grouping {
            augment "group-interface" {
              leaf arp-timeout {
                type string;
              }
            }
            augment "group-interface/dhcp" {
              leaf shutdown {
                type string;
              }
            }
            augment "group-interface/sap" {
              list static-host {
                // NCS patched for predictable order
                ordered-by user;
                key "ip";
                leaf ip {
                  type string;
                }
                leaf shutdown {
                  type string;
                }
              }
            }
          }
          container dhcp {
            uses ncs_template_subscriber-interface-dhcp-common-grouping;
            leaf lease-populate {
              type string;
            }
            container relay-proxy {
              presence "true";
              leaf release-update-src-ip {
                type empty;
              }
              leaf siaddr-override {
                type string;
              }
            }
            leaf python-policy {
              type ncs_template_string32;
            }
            container option {
              container vendor-specific-option {
                leaf client-mac-address {
                  type empty;
                }
                leaf sap-id {
                  type empty;
                }
                leaf service-id {
                  type empty;
                }
                leaf string {
                  type string;
                }
                leaf system-id {
                  type empty;
                }
              }
            }
            leaf shutdown {
              type string;
            }
          }
          container ipv6 {
            presence "true";
            leaf allow-unmatching-prefixes {
              type empty;
            }
            leaf delegated-prefix-length {
              type string;
            }
            leaf link-local-address {
              type string;
            }
            container subscriber-prefixes {
              list prefix {
                // NCS patched for predictable order
                ordered-by user;
                tailf:cli-suppress-mode;
                key "ipv6-prefix";
                leaf ipv6-prefix {
                  type string;
                }
                leaf pd {
                  type empty;
                }
                leaf wan-host {
                  type empty;
                }
                leaf track-srrp {
                  type string;
                }
              }
            }
            container dhcp6 {
              container relay {
                leaf link-address {
                  type string;
                }
                leaf-list server {
                  // NCS patched for predictable order
                  ordered-by user;
                  type string;
                }
                leaf source-address {
                  type string;
                }
                leaf shutdown {
                  type string;
                }
              }
            }
            container router-advertisements {
              leaf managed-configuration {
                type empty;
              }
              leaf other-stateful-configuration {
                type empty;
              }
              leaf max-advertisement {
                type string;
              }
              container prefix-options {
                leaf autonomous {
                  type empty;
                }
                leaf on-link {
                  type string;
                }
                leaf preferred-lifetime {
                  type string;
                }
                leaf valid-lifetime {
                  type string;
                }
              }
              leaf shutdown {
                type string;
              }
            }
          }
          leaf shutdown {
            type string;
          }
        }
        list interface {
          // NCS patched for predictable order
          ordered-by user;
          key "ip-int-name";
          leaf ip-int-name {
            type ncs_template_string32;
          }
          leaf tunnel {
            type empty;
          }
          container arp-host-route {
            list populate {
              // NCS patched for predictable order
              ordered-by user;
              tailf:cli-suppress-mode;
              key "mode";
              leaf mode {
                type string;
              }
            }
          }
          leaf arp-timeout {
            type string;
          }
          leaf arp-learn-unsolicited {
            type empty;
          }
          leaf arp-proactive-refresh {
            type empty;
          }
          leaf arp-populate {
            type empty;
          }
          leaf arp-populate-host-route {
            type empty;
          }
          leaf local-proxy-arp {
            type empty;
          }
          container bfd {
            uses ncs_template_bfd-grouping;
          }
          uses ncs_template_cflowd-params-grouping;
          container dhcp {
            leaf description {
              type string;
            }
            container gi-address {
              leaf gi-address-value {
                tailf:cli-drop-node-name;
                type string;
              }
              leaf src-ip-addr {
                type empty;
              }
            }
            leaf lease-populate {
              type string;
            }
            uses ncs_template_dhcp-option-grouping {
              augment "option" {
                container circuit-id {
                  presence "true";
                  leaf id {
                    tailf:cli-drop-node-name;
                    type string;
                  }
                }
              }
              augment "option/vendor-specific-option" {
                leaf sap-id {
                  type empty;
                }
              }
            }
            leaf-list server {
              // NCS patched for predictable order
              ordered-by user;
              type string;
            }
            leaf trusted {
              type empty;
            }
            leaf use-arp {
              type empty;
            }
            leaf shutdown {
              type string;
            }
          }
          leaf dynamic-tunnel-redundant-next-hop {
            type string;
          }
          uses ncs_template_interface-icmp-grouping;
          leaf local-dhcp-server {
            type string;
          }
          list secondary {
            // NCS patched for predictable order
            ordered-by user;
            tailf:cli-suppress-mode;
            key "address";
            leaf address {
              type string;
            }
          }
          list address {
            // NCS patched for predictable order
            ordered-by user;
            tailf:cli-suppress-mode;
            key "ip-address";
            leaf ip-address {
              type string;
            }
          }
          list static-arp {
            // NCS patched for predictable order
            ordered-by user;
            tailf:cli-suppress-mode;
            key "address";
            leaf address {
              type string;
            }
            leaf ieee-address {
              tailf:cli-drop-node-name;
              type ncs_template_ieee-mac;
            }
            leaf unnumbered {
              type empty;
            }
          }
          leaf description {
            type string;
          }
          leaf enable-ingress-stats {
            type empty;
          }
          leaf ip-mtu {
            type string;
          }
          leaf loopback {
            type empty;
          }
          leaf mac {
            type ncs_template_ieee-mac;
          }
          list sap {
            // NCS patched for predictable order
            ordered-by user;
            key "sap-id";
            leaf sap-id {
              type string;
            }
            leaf accounting-policy {
              type string;
            }
            leaf bandwidth {
              type string;
            }
            leaf anti-spoof {
              type string;
            }
            leaf collect-stats {
              type empty;
            }
            leaf description {
              type string;
            }
            leaf multi-service-site {
              type string;
            }
            container egress {
              uses ncs_template_sap-egress-grouping;
            }
            container eth-cfm {
              uses ncs_template_eth-cfm;
            }
            container ingress {
              uses ncs_template_sap-ingress-grouping;
            }
            container ipsec-gw {
              leaf name {
                tailf:cli-drop-node-name;
                type string;
              }
              container cert {
                leaf cert-profile {
                  type ncs_template_string32;
                }
                container status-verify {
                  leaf default-result {
                    type string;
                  }
                }
                leaf trust-anchor-profile {
                  type ncs_template_string32;
                }
              }
              container default-secure-service {
                choice service {
                  leaf service-id {
                    tailf:cli-drop-node-name;
                    type ncs_template_service-id;
                  }
                  leaf name {
                    type string;
                  }
                }
                leaf interface {
                  type ncs_template_string32;
                }
              }
              leaf default-tunnel-template {
                type string;
              }
              leaf ike-policy {
                type string;
              }
              leaf local-gateway-address {
                type string;
              }
              container local-id {
                leaf type {
                  type string;
                }
                leaf value {
                  type string;
                }
              }
              leaf shutdown {
                type string;
              }
            }
            list ipsec-tunnel {
              // NCS patched for predictable order
              ordered-by user;
              key "ipsec-tunnel-name";
              leaf ipsec-tunnel-name {
                type ncs_template_string32;
              }
              leaf shutdown {
                type string;
              }
            }
            list ip-tunnel {
              // NCS patched for predictable order
              ordered-by user;
              key "ip-tunnel-name";
              leaf ip-tunnel-name {
                type ncs_template_string32;
              }
              leaf clear-df-bit {
                type empty;
              }
              leaf ip-mtu {
                type string;
              }
              leaf description {
                type string;
              }
              list dest-ip {
                // NCS patched for predictable order
                ordered-by user;
                tailf:cli-suppress-mode;
                key "ip-address";
                leaf ip-address {
                  type string;
                }
              }
              leaf gre-header {
                type empty;
              }
              leaf source {
                type string;
              }
              leaf remote-ip {
                type string;
              }
              leaf delivery-service {
                type string;
              }
              leaf shutdown {
                type string;
              }
            }
            leaf lag-link-map-profile {
              type string;
            }
            leaf dist-cpu-protection {
              type string;
            }
            leaf shutdown {
              type string;
            }
          }
          list spoke-sdp {
            // NCS patched for predictable order
            ordered-by user;
            key "sdp-id vc-id";
            leaf sdp-id {
              type string;
            }
            uses ncs_template_sdp-common;
            container egress {
              container filter {
                uses ncs_template_filter-choice;
              }
            }
            container ingress {
              container filter {
                uses ncs_template_filter-choice;
              }
            }
          }
          leaf tos-marking-state {
            type string;
          }
          container urpf-check {
            leaf mode {
              type string;
            }
          }
          container vpls {
            leaf service-name {
              tailf:cli-drop-node-name;
              type string;
            }
            container egress {
              leaf reclassify-using-qos {
                type string;
              }
              leaf v4-routed-override-filter {
                type ncs_template_filter-id;
              }
            }
            container ingress {
              leaf v4-routed-override-filter {
                type ncs_template_filter-id;
              }
              leaf v6-routed-override-filter {
                type ncs_template_filter-id;
              }
            }
            container evpn-tunnel {
              presence "true";
              leaf ipv6-gateway-address {
                type string;
              }
            }
            container evpn {
              container arp {
                leaf learn-dynamic {
                  type string;
                }
                list advertise {
                  // NCS patched for predictable order
                  ordered-by user;
                  tailf:cli-suppress-mode;
                  key "adv-type";
                  leaf adv-type {
                    type string;
                  }
                }
              }
              container nd {
                leaf learn-dynamic {
                  type string;
                }
                list advertise {
                  // NCS patched for predictable order
                  ordered-by user;
                  tailf:cli-suppress-mode;
                  key "type";
                  leaf type {
                    type string;
                  }
                  leaf route-tag {
                    type string;
                  }
                }
              }
            }
          }
          list vrrp {
            // NCS patched for predictable order
            ordered-by user;
            key "virtual-router-id";
            leaf virtual-router-id {
              type string;
            }
            leaf owner {
              type empty;
            }
            leaf passive {
              type empty;
            }
            uses ncs_template_authentication-key-grouping;
            list backup {
              // NCS patched for predictable order
              ordered-by user;
              tailf:cli-suppress-mode;
              key "addr";
              leaf addr {
                type string;
              }
            }
            container bfd-enable {
              leaf service-id {
                tailf:cli-drop-node-name;
                type string;
              }
              leaf interface {
                type string;
              }
              leaf dst-ip {
                type string;
              }
            }
            leaf init-delay {
              type string;
            }
            leaf mac {
              type ncs_template_ieee-mac;
            }
            leaf master-int-inherit {
              type empty;
            }
            container message-interval {
              leaf seconds {
                tailf:cli-drop-node-name;
                type string;
              }
              leaf milliseconds {
                type string;
              }
            }
            leaf ping-reply {
              type empty;
            }
            leaf policy {
              type string;
            }
            leaf preempt {
              type empty;
            }
            leaf priority {
              type string;
            }
            leaf ssh-reply {
              type empty;
            }
            leaf standby-forwarding {
              type empty;
            }
            leaf telnet-reply {
              type empty;
            }
            leaf traceroute-reply {
              type empty;
            }
            leaf shutdown {
              type empty;
            }
          }
          container ipv6 {
            presence "true";
            leaf local-dhcp-server {
              type ncs_template_string32;
            }
            uses ncs_template_ipv6-grouping;
            uses ncs_template_dhcp6-grouping;
            leaf nd-populate-host-route {
              type empty;
            }
            container nd-host-route {
              list populate {
                // NCS patched for predictable order
                ordered-by user;
                tailf:cli-suppress-mode;
                key "mode";
                leaf mode {
                  type string;
                }
              }
            }
            leaf stale-time {
              type string;
            }
          }
          leaf qos-route-lookup {
            type string;
          }
          leaf shutdown {
            type string;
          }
        }
        container ipsec {
          leaf allow-reverse-route-override {
            type string;
          }
          list security-policy {
            // NCS patched for predictable order
            ordered-by user;
            key "security-policy-id";
            leaf security-policy-id {
              type string;
            }
            list entry {
              // NCS patched for predictable order
              ordered-by user;
              key "entry-id";
              leaf entry-id {
                type string;
              }
              leaf local-ip {
                type string;
              }
              leaf local-v6-ip {
                type string;
              }
              leaf remote-ip {
                type string;
              }
              leaf remote-v6-ip {
                type string;
              }
            }
          }
        }
        container maximum-routes {
          leaf routes {
            tailf:cli-drop-node-name;
            type string;
          }
          leaf log-only {
            type empty;
          }
          leaf threshold {
            type string;
          }
        }
        uses ncs_template_nat-pool-grouping;
        container radius-server {
          uses ncs_template_radius-server-grouping;
        }
        container dns {
          presence "true";
          leaf default-domain {
            type string;
          }
          leaf ipv4-source-address {
            type string;
          }
          leaf ipv6-source-address {
            type string;
          }
          leaf primary-dns {
            type string;
          }
          leaf secondary-dns {
            type string;
          }
          leaf tertiary-dns {
            type string;
          }
          leaf shutdown {
            type string;
          }
        }
        container log {
          list filter {
            // NCS patched for predictable order
            ordered-by user;
            key "filter-id";
            leaf filter-id {
              type string;
            }
            leaf name {
              type string;
            }
            leaf default-action {
              type string;
            }
            leaf description {
              type string;
            }
            list entry {
              // NCS patched for predictable order
              ordered-by user;
              key "entry-id";
              leaf entry-id {
                type string;
              }
              leaf name {
                type string;
              }
              leaf action {
                type string;
              }
              leaf description {
                type string;
              }
              container match {
                container application {
                  leaf operator {
                    tailf:cli-drop-node-name;
                    type string;
                  }
                  leaf application-id {
                    tailf:cli-drop-node-name;
                    type string;
                  }
                }
                container message {
                  leaf operator {
                    tailf:cli-drop-node-name;
                    type string;
                  }
                  leaf pattern {
                    type string;
                  }
                  leaf regexp {
                    type empty;
                  }
                }
                container number {
                  leaf operator {
                    tailf:cli-drop-node-name;
                    type string;
                  }
                  leaf event-id {
                    tailf:cli-drop-node-name;
                    type string;
                  }
                }
                container severity {
                  leaf operator {
                    tailf:cli-drop-node-name;
                    type string;
                  }
                  leaf severity-level {
                    tailf:cli-drop-node-name;
                    type string;
                  }
                }
                container subject {
                  leaf operator {
                    tailf:cli-drop-node-name;
                    type string;
                  }
                  leaf subject {
                    tailf:cli-drop-node-name;
                    type string;
                  }
                  leaf regexp {
                    type empty;
                  }
                }
              }
            }
          }
          list syslog {
            // NCS patched for predictable order
            ordered-by user;
            key "syslog-id";
            leaf syslog-id {
              type string;
            }
            leaf name {
              type string;
            }
            leaf description {
              type string;
            }
            leaf address {
              type string;
            }
            leaf facility {
              type string;
            }
            leaf log-prefix {
              type string;
            }
            leaf port {
              type string;
            }
          }
          list snmp-trap-group {
            // NCS patched for predictable order
            ordered-by user;
            key "group-id";
            leaf group-id {
              type string;
            }
            leaf name {
              type string;
            }
            leaf description {
              type string;
            }
            list trap-target {
              // NCS patched for predictable order
              ordered-by user;
              tailf:cli-suppress-mode;
              key "name";
              leaf name {
                type string;
              }
              leaf address {
                type string;
              }
              leaf snmp-type {
                tailf:cli-drop-node-name;
                type string;
              }
              leaf notify-community {
                type string;
              }
              leaf security-level {
                type string;
              }
            }
          }
          list log-id {
            // NCS patched for predictable order
            ordered-by user;
            key "log-id";
            leaf log-id {
              type string;
            }
            leaf name {
              type string;
            }
            leaf description {
              type string;
            }
            leaf filter {
              type string;
            }
            leaf-list from {
              // NCS patched for predictable order
              ordered-by user;
              type string;
            }
            leaf netconf-stream {
              type string;
            }
            leaf shutdown {
              type string;
            }
            leaf time-format {
              type string;
            }
            container to {
              leaf destination {
                tailf:cli-drop-node-name;
                type string;
              }
              leaf size {
                tailf:cli-drop-node-name;
                type string;
              }
              leaf syslog-id {
                tailf:cli-drop-node-name;
                type string;
              }
            }
          }
        }
        list redundant-interface {
          // NCS patched for predictable order
          ordered-by user;
          key "ip-int-name";
          leaf ip-int-name {
            type ncs_template_string32;
          }
          leaf description {
            type string;
          }
          container address {
            leaf ip-address {
              tailf:cli-drop-node-name;
              type string;
            }
            leaf remote-ip {
              type string;
            }
          }
          list spoke-sdp {
            // NCS patched for predictable order
            ordered-by user;
            key "sdp-id-vc-id";
            leaf sdp-id-vc-id {
              type string;
            }
            leaf description {
              type string;
            }
            leaf shutdown {
              type string;
            }
          }
          leaf shutdown {
            type string;
          }
        }
        leaf route-distinguisher {
          type string;
        }
        container source-address {
          list application {
            // NCS patched for predictable order
            ordered-by user;
            tailf:cli-suppress-mode;
            key "app";
            leaf app {
              type string;
            }
            leaf source {
              tailf:cli-drop-node-name;
              type string;
            }
          }
          list application6 {
            // NCS patched for predictable order
            ordered-by user;
            tailf:cli-suppress-mode;
            key "app";
            leaf app {
              type string;
            }
            leaf source {
              tailf:cli-drop-node-name;
              type string;
            }
          }
        }
        container snmp {
          leaf access {
            type empty;
          }
          uses ncs_template_snmp-community-grouping;
        }
        list snmp-community {
          // NCS patched for predictable order
          ordered-by user;
          tailf:cli-suppress-mode;
          key "name type";
          leaf name {
            type string;
          }
          leaf type {
            tailf:cli-drop-node-name;
            type ncs_template_hash-method;
          }
          leaf access-parameters {
            tailf:cli-drop-node-name;
            type string;
          }
          leaf version {
            type string;
          }
        }
        leaf-list vrf-export {
          // NCS patched for predictable order
          ordered-by user;
          type string;
        }
        leaf-list vrf-import {
          // NCS patched for predictable order
          ordered-by user;
          type string;
        }
        container vrf-target {
          leaf export {
            type string;
          }
          leaf import {
            type string;
          }
          leaf ext-community {
            tailf:cli-drop-node-name;
            type string;
          }
        }
        leaf autonomous-system {
          type string;
        }
        list spoke-sdp {
          // NCS patched for predictable order
          ordered-by user;
          key "sdp-id";
          leaf sdp-id {
            type string;
          }
          leaf description {
            type string;
          }
          leaf shutdown {
            type string;
          }
        }
        leaf carrier-carrier-vpn {
          type empty;
        }
        leaf type {
          type string;
        }

        grouping service-vprn-static-route-grouping {
          leaf preference {
            type string;
          }
          leaf metric {
            type string;
          }
          leaf state {
            tailf:cli-drop-node-name;
            type ncs_template_enable-disable;
          }
          leaf tag {
            type string;
          }
          leaf bfd-enable {
            type empty;
          }
          leaf cpe-check {
            type string;
          }
          leaf drop-count {
            type string;
          }
          leaf interval {
            type string;
          }
          leaf log {
            type empty;
          }
          leaf prefix-list-name {
            type string;
          }
          leaf prefix-list-to-use {
            tailf:cli-drop-node-name;
            type string;
          }
          leaf community {
            type string;
          }
          leaf description {
            type string;
          }
        }
        list static-route-entry {
          // NCS patched for predictable order
          ordered-by user;
          key "route";
          leaf route {
            type string;
          }
          leaf-list community {
            // NCS patched for predictable order
            ordered-by user;
            type string;
          }
          list next-hop {
            // NCS patched for predictable order
            ordered-by user;
            key "next-hop";
            leaf next-hop {
              type string;
            }
            uses ncs_template_static-route-entry-nh-grouping;
            container prefix-list {
              leaf name {
                tailf:cli-drop-node-name;
                type string;
              }
              leaf modifyer {
                tailf:cli-drop-node-name;
                type string;
              }
            }
          }
          container grt {
            presence "true";
            leaf description {
              type string;
            }
            leaf metric {
              type string;
            }
            leaf preference {
              type string;
            }
            leaf shutdown {
              type string;
            }
          }
          list ipsec-tunnel {
            // NCS patched for predictable order
            ordered-by user;
            key "name";
            leaf name {
              type string;
            }
            leaf shutdown {
              type string;
            }
          }
          container black-hole {
            presence "true";
            uses ncs_template_static-route-entry-nh-grouping;
            container prefix-list {
              leaf name {
                tailf:cli-drop-node-name;
                type string;
              }
              leaf modifyer {
                tailf:cli-drop-node-name;
                type string;
              }
            }
          }
          list indirect {
            // NCS patched for predictable order
            ordered-by user;
            key "ip-address";
            leaf ip-address {
              type string;
            }
            uses ncs_template_static-route-entry-nh-grouping;
          }
          leaf tag {
            type string;
          }
        }
        container static-route {
          list static-route-next-hop {
            // NCS patched for predictable order
            ordered-by user;
            tailf:cli-drop-node-name;
            tailf:cli-suppress-mode;
            key "route next-hop";
            leaf route {
              type string;
            }
            leaf next-hop {
              type string;
            }
            uses service-vprn-static-route-grouping;
          }
          list static-route-indirect {
            // NCS patched for predictable order
            ordered-by user;
            tailf:cli-drop-node-name;
            tailf:cli-suppress-mode;
            key "route indirect";
            leaf route {
              type string;
            }
            leaf indirect {
              type string;
            }
            uses service-vprn-static-route-grouping;
          }
          list static-route-ipsec-tunnel {
            // NCS patched for predictable order
            ordered-by user;
            tailf:cli-drop-node-name;
            tailf:cli-suppress-mode;
            key "route ipsec-tunnel";
            leaf route {
              type string;
            }
            leaf ipsec-tunnel {
              type string;
            }
            uses service-vprn-static-route-grouping;
          }
          list static-route-indirect-blackhole {
            // NCS patched for predictable order
            ordered-by user;
            tailf:cli-drop-node-name;
            tailf:cli-suppress-mode;
            key "route";
            leaf route {
              type string;
            }
            leaf black-hole {
              type empty;
            }
            uses service-vprn-static-route-grouping;
          }
        }
        uses ncs_template_router-aggregate-grouping;
        container sgt-qos {
          list application {
            // NCS patched for predictable order
            ordered-by user;
            tailf:cli-suppress-mode;
            key "app-name";
            leaf app-name {
              type string;
            }
            leaf dscp {
              type string;
            }
            leaf dot1p {
              type string;
            }
          }
          list dscp {
            // NCS patched for predictable order
            ordered-by user;
            tailf:cli-suppress-mode;
            key "dscp-name";
            leaf dscp-name {
              type string;
            }
            leaf fc {
              type string;
            }
          }
        }
        container pim {
          uses ncs_template_pim-common-grouping;
          leaf ipv4-multicast-disable {
            type string;
          }
          leaf ipv6-multicast-disable {
            type string;
          }
          list interface {
            // NCS patched for predictable order
            ordered-by user;
            key "name";
            leaf name {
              type string;
            }
            leaf priority {
              type string;
            }
            leaf max-groups {
              type string;
            }
            leaf bfd-enable {
              type empty;
            }
            container sticky-dr {
              presence "true";
              leaf priority {
                type string;
              }
            }
            leaf multicast-senders {
              type string;
            }
            leaf hello-interval {
              type string;
            }
            leaf shutdown {
              type string;
            }
          }
          container rp {
            list anycast {
              // NCS patched for predictable order
              ordered-by user;
              key "rp-ip-address";
              leaf rp-ip-address {
                type string;
              }
              list rp-set-peer {
                // NCS patched for predictable order
                ordered-by user;
                tailf:cli-suppress-mode;
                key "ip-address";
                leaf ip-address {
                  type string;
                }
              }
            }
            leaf auto-rp-discovery {
              type empty;
            }
            container static {
              list address {
                // NCS patched for predictable order
                ordered-by user;
                key "address";
                leaf address {
                  type string;
                }
                list group-prefix {
                  // NCS patched for predictable order
                  ordered-by user;
                  tailf:cli-suppress-mode;
                  key "address";
                  leaf address {
                    type string;
                  }
                }
                leaf override {
                  type empty;
                }
              }
            }
            container bsr-candidate {
              leaf shutdown {
                type string;
              }
            }
            container rp-candidate {
              leaf shutdown {
                type string;
              }
            }
          }
          leaf shutdown {
            type string;
          }
        }
        container mvpn {
          container auto-discovery {
            leaf mode {
              tailf:cli-drop-node-name;
              // NCS drop tailf-common:cli-diff-create-before statement
              // NCS drop tailf-common:cli-diff-create-before statement
              // NCS drop tailf-common:cli-diff-create-before statement
              type string;
            }
            leaf source-address {
              type string;
            }
          }
          leaf c-mcast-signaling {
            type string;
          }
          container intersite-shared {
            choice intersite-shared {
              leaf-list arg {
                // NCS patched for predictable order
                ordered-by user;
                tailf:cli-drop-node-name;
                type string;
              }
              leaf disable {
                type empty;
              }
            }
          }
          leaf umh-selection {
            type string;
          }
          leaf mdt-type {
            type string;
          }
          container provider-tunnel {

            grouping inclusive-selective-common-grouping {
              container mldp {
                leaf shutdown {
                  type string;
                }
              }
            }
            container inclusive {
              uses inclusive-selective-common-grouping;
              container pim {
                presence "true";
                container options {
                  tailf:cli-drop-node-name;
                  leaf multicast-type {
                    tailf:cli-drop-node-name;
                    type string;
                  }
                  leaf grp-ip-address {
                    tailf:cli-drop-node-name;
                    type string;
                  }
                }
                leaf shutdown {
                  type string;
                }
              }
              container rsvp {
                presence "true";
                leaf lsp-template {
                  type string;
                }
                leaf shutdown {
                  type string;
                }
              }
            }
            container selective {
              uses inclusive-selective-common-grouping;
              leaf maximum-p2mp-spmsi {
                type string;
              }
              container pim {
                tailf:cli-drop-node-name;
                choice pim-choice {
                  leaf pim-asm {
                    type empty;
                  }
                  leaf pim-ssm {
                    type empty;
                  }
                }
                choice addr {
                  leaf address1 {
                    tailf:cli-drop-node-name;
                    type string;
                  }
                  leaf address2 {
                    tailf:cli-drop-node-name;
                    type string;
                  }
                }
                leaf netmask {
                  tailf:cli-drop-node-name;
                  type string;
                }
              }
              list data-threshold {
                // NCS patched for predictable order
                ordered-by user;
                tailf:cli-suppress-mode;
                key "c-grp-ip-addr-mask";
                leaf c-grp-ip-addr-mask {
                  tailf:cli-drop-node-name;
                  type string;
                }
                leaf s-pmsi-threshold {
                  tailf:cli-drop-node-name;
                  type string;
                }
              }
            }
          }
          list vrf-target {
            // NCS patched for predictable order
            ordered-by user;
            key "id";
            leaf id {
              type string;
            }
            leaf export {
              type string;
            }
            leaf import {
              type string;
            }
          }
        }
        container router-advertisement {
          list interface {
            // NCS patched for predictable order
            ordered-by user;
            key "ip-int-name";
            leaf ip-int-name {
              type ncs_template_string32;
            }
            leaf use-virtual-mac {
              type empty;
            }
            leaf shutdown {
              type string;
            }
          }
        }
        leaf router-id {
          type string;
        }
        list isis {
          // NCS patched for predictable order
          ordered-by user;
          key "id";
          leaf id {
            type string;
          }
          leaf area-id {
            type string;
          }
          leaf ipv6-routing {
            type string;
          }
          container multi-topology {
            leaf ipv6-unicast {
              type empty;
            }
          }
          list interface {
            // NCS patched for predictable order
            ordered-by user;
            key "name";
            leaf name {
              type string;
            }
            leaf passive {
              type empty;
            }
            leaf interface-type {
              type string;
            }
            leaf shutdown {
              type string;
            }
          }
          leaf router-id {
            type string;
          }
          leaf shutdown {
            type string;
          }
        }
        leaf service-name {
          type string;
        }
        leaf weighted-ecmp {
          type empty;
        }
        leaf shutdown {
          type string;
        }
      }
      list pw-template {
        // NCS patched for predictable order
        ordered-by user;
        key "policy-id";
        leaf policy-id {
          type string;
        }
        leaf use-provisioned-sdp {
          type empty;
        }
        leaf name {
          type string;
        }
        leaf auto-learn-mac-protect {
          type empty;
        }
        leaf disable-learning {
          type empty;
        }
        container egress {
          choice filter-name-choice {
            container filter {
              uses ncs_template_filter-choice;
            }
            container filter-name {
              uses ncs_template_filter-choice;
            }
          }
        }
        container ingress {
          choice filter-name-choice {
            container filter {
              uses ncs_template_filter-choice;
            }
            container filter-name {
              uses ncs_template_filter-choice;
            }
          }
        }
        container restrict-protected-src {
          presence "true";
          leaf value {
            tailf:cli-drop-node-name;
            type string;
          }
        }
        leaf mac-pinning {
          type empty;
        }
        leaf force-vlan-vc-forwarding {
          type empty;
        }
        container split-horizon-group {
          presence "true";
          leaf group-name {
            tailf:cli-drop-node-name;
            type string;
          }
          leaf auto-learn-mac-protect {
            type empty;
          }
          leaf description {
            type string;
          }
          container restrict-protected-src {
            presence "true";
            leaf option {
              tailf:cli-drop-node-name;
              type string;
            }
          }
          leaf restrict-unprotected-dst {
            type empty;
          }
        }
        leaf vc-type {
          type string;
        }
        leaf limit-mac-move {
          type string;
        }
      }
      container system {
        container bgp-evpn {
          container evpn-etree-leaf-label {
            presence "true";
            leaf label {
              tailf:cli-drop-node-name;
              type string;
            }
          }
          container ip-prefix-routes {
            leaf iff-attribute-uniform-propagation {
              type empty;
            }
            leaf iff-bgp-path-selection {
              type empty;
            }
          }
          leaf ingress-replication-bum-label-block {
            type string;
          }
          leaf route-distinguisher {
            type string;
          }
          list ethernet-segment {
            // NCS patched for predictable order
            ordered-by user;
            key "name";
            leaf name {
              type ncs_template_string32;
            }
            leaf ac-df-capability {
              type string;
            }
            container dot1q {
              list q-tag-range {
                // NCS patched for predictable order
                ordered-by user;
                tailf:cli-suppress-mode;
                key "start";
                leaf start {
                  type string;
                }
                leaf to {
                  type string;
                }
              }
            }
            leaf oper-group {
              type string;
            }
            leaf virtual {
              type empty;
            }
            leaf esi {
              type string;
            }
            leaf es-orig-ip {
              type string;
            }
            leaf route-next-hop {
              type string;
            }
            leaf es-activation-timer {
              type string;
            }
            leaf sdp {
              type string;
            }
            container service-carving {
              leaf mode {
                type string;
              }
              container manual {
                container preference {
                  presence "true";
                  leaf non-revertive {
                    type empty;
                  }
                  leaf value {
                    type string;
                  }
                }
              }
            }
            container multi-homing {
              leaf value {
                tailf:cli-drop-node-name;
                type string;
              }
              leaf no-esi-label {
                type empty;
              }
            }
            leaf lag {
              type string;
            }
            container qinq {
              container s-tag {
                leaf s-tag {
                  tailf:cli-drop-node-name;
                  type string;
                }
                leaf c-tag-range {
                  type string;
                }
                leaf to {
                  type string;
                }
              }
              list s-tag-range {
                // NCS patched for predictable order
                ordered-by user;
                tailf:cli-suppress-mode;
                key "start";
                leaf start {
                  type string;
                }
                leaf to {
                  type string;
                }
              }
            }
            leaf port {
              type string;
            }
            list vc-id-range {
              // NCS patched for predictable order
              ordered-by user;
              tailf:cli-suppress-mode;
              key "start";
              leaf start {
                type string;
              }
              leaf to {
                type string;
              }
            }
            leaf shutdown {
              type string;
            }
          }
        }
      }
      container template {
        list vpls-sap-template {
          // NCS patched for predictable order
          ordered-by user;
          key "name";
          leaf name {
            type ncs_template_string32;
          }
          container ingress {
            container qos {
              leaf policy-id {
                tailf:cli-drop-node-name;
                type string;
              }
              leaf shared-queuing {
                type empty;
              }
            }
          }
        }
      }
    }
    list router {
      // NCS patched for predictable order
      ordered-by user;
      key "router-name";
      leaf router-name {
        type ncs_template_router-type;
      }
      container flowspec {
        leaf ip-filter-max-size {
          type string;
        }
        leaf ipv6-filter-max-size {
          type string;
        }
      }
      container bfd {
        list bfd-template {
          // NCS patched for predictable order
          ordered-by user;
          key "template";
          leaf template {
            type string;
          }
          leaf echo-receive {
            type string;
          }
          leaf multiplier {
            type string;
          }
          leaf receive-interval {
            type string;
          }
          leaf transmit-interval {
            type string;
          }
          leaf type {
            type string;
          }
        }
        container seamless-bfd {
          list peer {
            // NCS patched for predictable order
            ordered-by user;
            key "address";
            leaf address {
              type string;
            }
            leaf discriminator {
              type string;
            }
          }
        }
      }
      leaf class-forwarding {
        type empty;
      }
      leaf ecmp {
        type string;
      }
      leaf-list leak-export {
        // NCS patched for predictable order
        ordered-by user;
        type string;
      }
      leaf leak-export-limit {
        type string;
      }
      leaf single-sfm-overload {
        type empty;
      }
      container segment-routing {
        container sr-policies {
          list static-policy {
            // NCS patched for predictable order
            ordered-by user;
            key "policy-id";
            leaf policy-id {
              type string;
            }
            leaf binding-sid {
              type string;
            }
            leaf color {
              type string;
            }
            leaf distinguisher {
              type string;
            }
            leaf endpoint {
              type string;
            }
            leaf head-end {
              type string;
            }
            list segment-list {
              // NCS patched for predictable order
              ordered-by user;
              key "id";
              leaf id {
                type string;
              }
              leaf weight {
                type string;
              }
              list segment {
                // NCS patched for predictable order
                ordered-by user;
                key "id";
                leaf id {
                  type string;
                }
                leaf mpls-label {
                  type string;
                }
              }
              leaf shutdown {
                type string;
              }
            }
            leaf shutdown {
              type string;
            }
          }
          leaf shutdown {
            type string;
          }
        }
      }
      container admin-tags {
        list admin-tag {
          // NCS patched for predictable order
          ordered-by user;
          tailf:cli-suppress-mode;
          key "tag";
          leaf tag {
            type ncs_template_string32;
          }
        }
        list route-admin-tag-policy {
          // NCS patched for predictable order
          ordered-by user;
          key "policy-name";
          leaf policy-name {
            type string;
          }
          list exclude {
            // NCS patched for predictable order
            ordered-by user;
            tailf:cli-suppress-mode;
            key "tag";
            leaf tag {
              type ncs_template_string32;
            }
          }
          list include {
            // NCS patched for predictable order
            ordered-by user;
            tailf:cli-suppress-mode;
            key "tag";
            leaf tag {
              type ncs_template_string32;
            }
          }
        }
      }
      leaf autonomous-system {
        type string;
      }
      leaf entropy-label {
        type empty;
      }
      leaf icmp-tunneling {
        type empty;
      }
      list interface {
        // NCS patched for predictable order
        ordered-by user;
        key "interface-name";
        leaf interface-name {
          type string;
        }
        leaf address {
          type string;
        }
        leaf description {
          type string;
        }
        leaf collect-stats {
          type empty;
        }
        container dhcp {
          leaf description {
            type string;
          }
          container gi-address {
            leaf gi-address-value {
              tailf:cli-drop-node-name;
              type string;
            }
            leaf src-ip-addr {
              type empty;
            }
          }
          uses ncs_template_dhcp-option-grouping {
            augment "option" {
              leaf circuit-id {
                type string;
              }
            }
            augment "option/vendor-specific-option" {
              leaf port-id {
                type empty;
              }
              leaf system-id {
                type empty;
              }
            }
          }
          leaf python-policy {
            type ncs_template_string32;
          }
          leaf relay-plain-bootp {
            type empty;
          }
          leaf-list server {
            // NCS patched for predictable order
            ordered-by user;
            type string;
          }
          leaf trusted {
            type empty;
          }
          leaf shutdown {
            type string;
          }
        }
        leaf dist-cpu-protection {
          type string;
        }
        container ldp-sync-timer {
          leaf ldp-sync-timer {
            tailf:cli-drop-node-name;
            type string;
          }
          leaf end-of-lib {
            type empty;
          }
        }
        container load-balancing {
          leaf lsr-load-balancing {
            type string;
          }
        }
        leaf local-dhcp-server {
          type string;
        }
        leaf cpu-protection {
          type string;
        }
        leaf loopback {
          type empty;
        }
        leaf enable-ingress-stats {
          type empty;
        }
        leaf unnumbered-mpls-tp {
          type empty;
        }
        leaf port {
          type string;
        }
        container egress {
          container filter {
            leaf ip {
              type ncs_template_filter-id;
            }
            leaf ipv6 {
              type ncs_template_filter-id;
            }
          }
          leaf queue-policy {
            type string;
          }
          container agg-rate-limit {
            leaf agg-rate {
              tailf:cli-drop-node-name;
              type string;
            }
            leaf cir {
              type string;
            }
          }
          leaf vlan-qos-policy {
            type string;
          }
          container agg-rate {
            container rate {
              leaf val {
                tailf:cli-drop-node-name;
                type string;
              }
              leaf cir {
                type string;
              }
            }
          }
          leaf egress-remark-policy {
            type string;
          }
        }
        container if-attribute {
          list admin-group {
            // NCS patched for predictable order
            ordered-by user;
            tailf:cli-suppress-mode;
            key "group-name";
            leaf group-name {
              type string;
            }
          }
          container delay {
            leaf static {
              type string;
            }
            leaf delay-selection {
              type string;
            }
            container dynamic {
              leaf measurement-template {
                type string;
              }
              container twamp-light {
                container ipv4 {
                  leaf source {
                    type string;
                  }
                  leaf destination {
                    type string;
                  }
                  leaf shutdown {
                    type string;
                  }
                }
                container ipv6 {
                  leaf source {
                    type string;
                  }
                  leaf destination {
                    type string;
                  }
                  leaf shutdown {
                    type string;
                  }
                }
              }
            }
          }
        }
        container ingress {
          container filter {
            leaf ip {
              type ncs_template_filter-id;
            }
            leaf ipv6 {
              type ncs_template_filter-id;
            }
          }
          leaf qos {
            type string;
          }
        }
        leaf lsr-load-balancing {
          type string;
        }
        uses ncs_template_interface-icmp-grouping;
        leaf ptp-hw-assist {
          type empty;
        }
        container urpf-check {
          leaf mode {
            type string;
          }
        }
        container ipv6 {
          leaf local-dhcp-server {
            type ncs_template_string32;
          }
          uses ncs_template_ipv6-grouping;
        }
        container bfd {
          uses ncs_template_bfd-grouping;
        }
        leaf autonomous-system {
          type string;
        }
        uses ncs_template_cflowd-params-grouping;
        container cflowd {
          leaf id {
            tailf:cli-drop-node-name;
            type string;
          }
          leaf direction {
            tailf:cli-drop-node-name;
            type string;
          }
        }
        container static-arp {
          leaf ip-address {
            tailf:cli-drop-node-name;
            type string;
          }
          leaf ieee-address {
            tailf:cli-drop-node-name;
            type ncs_template_ieee-mac;
          }
        }
        leaf tos-marking-state {
          type string;
        }
        container qos {
          leaf network-policy-id {
            tailf:cli-drop-node-name;
            type string;
          }
          leaf egress-port-redirect-group {
            type string;
          }
          leaf egress-instance {
            type string;
          }
          leaf ingress-fp-redirect-group {
            type string;
          }
          leaf ingress-instance {
            type string;
          }
        }
        leaf tcp-mss {
          type string;
        }
        leaf shutdown {
          type string;
        }
      }
      container tunnel-interface {
        list rsvp-p2mp {
          // NCS patched for predictable order
          ordered-by user;
          key "lsp-name";
          leaf lsp-name {
            type string;
          }
        }
      }
      container bgp {
        presence "present";
        uses ncs_template_router-bgp-add-paths-grouping;
        leaf initial-send-delay-zero {
          type empty;
        }
        container monitor {
          presence "true";
          leaf-list route-monitoring {
            // NCS patched for predictable order
            ordered-by user;
            type string;
          }
          leaf-list station {
            // NCS patched for predictable order
            ordered-by user;
            type string;
          }
          leaf shutdown {
            type string;
          }
        }
        leaf override-tunnel-elc {
          type empty;
        }
        leaf loop-detect-threshold {
          type string;
        }
        leaf-list advertise-external {
          // NCS patched for predictable order
          ordered-by user;
          type string;
        }
        leaf advertise-inactive {
          type empty;
        }
        leaf aggregator-id-zero {
          type empty;
        }
        leaf auth-keychain {
          type string;
        }
        uses ncs_template_prompted-authentication-key-grouping;
        leaf-list backup-path {
          // NCS patched for predictable order
          ordered-by user;
          type string;
        }
        uses ncs_template_bgp-best-path-selection-grouping;
        leaf bfd-enable {
          type empty;
        }
        container bgp-tunnel-metric {
          leaf metric {
            tailf:cli-drop-node-name;
            type string;
          }
          leaf prefer-aigp {
            type empty;
          }
        }
        leaf cluster {
          type string;
        }
        leaf connect-retry {
          type string;
        }
        leaf damping {
          type empty;
        }
        leaf description {
          type string;
        }
        leaf disable-4byte-asn {
          type empty;
        }
        leaf disable-client-reflect {
          type empty;
        }
        leaf-list disable-communities {
          // NCS patched for predictable order
          ordered-by user;
          type string;
        }
        leaf disable-fast-external-failover {
          type empty;
        }
        leaf disable-route-table-install {
          type empty;
        }
        leaf enable-inter-as-vpn {
          type empty;
        }
        leaf enable-peer-tracking {
          type empty;
        }
        leaf enable-rr-vpn-forwarding {
          type empty;
        }
        container error-handling {
          leaf update-fault-tolerance {
            type empty;
          }
        }
        leaf-list family {
          // NCS patched for predictable order
          ordered-by user;
          type ncs_template_family-names-type;
        }
        leaf flowspec-validate {
          type empty;
        }
        container flowspec {
          leaf validate-dest-prefix {
            type empty;
          }
        }
        leaf link-state-import-enable {
          type empty;
        }
        leaf link-state-export-enable {
          type empty;
        }
        uses ncs_template_bgp-graceful-restart-grouping;
        list group {
          // NCS patched for predictable order
          ordered-by user;
          key "id";
          leaf id {
            type string;
          }
          uses ncs_template_router-bgp-grouping;
          uses ncs_template_bgp-import-export-grouping;
          uses ncs_template_enable-origin-validation-grouping;
          container error-handling {
            leaf update-fault-tolerance {
              type empty;
            }
          }
          list neighbor {
            // NCS patched for predictable order
            ordered-by user;
            key "address";
            leaf address {
              type string;
            }
            uses ncs_template_router-bgp-grouping;
            uses ncs_template_enable-origin-validation-grouping;
            leaf-list advertise-label {
              // NCS patched for predictable order
              ordered-by user;
              type string;
            }
            uses ncs_template_bgp-import-export-grouping;
          }
          leaf-list next-hop-unchanged {
            // NCS patched for predictable order
            ordered-by user;
            type string;
          }
        }
        leaf ibgp-multipath {
          type empty;
        }
        container igp-shortcut {
          leaf value {
            tailf:cli-drop-node-name;
            type string;
          }
          leaf disallow-igp {
            type empty;
          }
        }
        uses ncs_template_bgp-import-export-grouping;
        uses ncs_template_bgp-common-grouping;
        uses ncs_template_bgp-local-as-grouping;
        leaf local-preference {
          type string;
        }
        leaf loop-detect {
          type string;
        }
        leaf med-out {
          type string;
        }
        leaf min-as-origination {
          type string;
        }
        leaf min-route-advertisement {
          type string;
        }
        leaf mp-bgp-keep {
          type empty;
        }
        leaf multihop {
          type string;
        }
        uses ncs_template_bgp-multipath-grouping;
        uses ncs_template_bgp-multi-path-grouping {
          augment "multi-path" {
            container label-ipv6 {
              uses ncs_template_max-paths-uneqcosts-grouping;
            }
          }
        }
        leaf mvpn-vrf-import-subtype-new {
          type empty;
        }
        uses ncs_template_bgp-next-hop-resolution-grouping;
        container outbound-route-filtering {
          container extended-community {
            leaf accept-orf {
              type empty;
            }
            container send-orf {
              presence "true";
              leaf-list send-orf {
                // NCS patched for predictable order
                ordered-by user;
                tailf:cli-drop-node-name;
                type string;
              }
            }
          }
        }
        container rib-management {
          container ipv4 {
            leaf-list leak-import {
              // NCS patched for predictable order
              ordered-by user;
              type string;
            }
          }
          container ipv6 {
            leaf-list leak-import {
              // NCS patched for predictable order
              ordered-by user;
              type string;
            }
            leaf route-table-import {
              type string;
            }
          }
          container label-ipv4 {
            leaf route-table-import {
              type string;
            }
          }
          container label-ipv6 {
            leaf route-table-import {
              type string;
            }
          }
        }
        leaf path-mtu-discovery {
          type empty;
        }
        leaf peer-tracking-policy {
          type string;
        }
        leaf purge-timer {
          type string;
        }
        leaf-list rapid-update {
          // NCS patched for predictable order
          ordered-by user;
          type string;
        }
        leaf rapid-withdrawal {
          type empty;
        }
        leaf-list remove-private {
          // NCS patched for predictable order
          ordered-by user;
          type string;
        }
        leaf-list route-target-list {
          // NCS patched for predictable order
          ordered-by user;
          type string;
        }
        leaf router-id {
          type string;
        }
        leaf selective-label-ipv4-install {
          type empty;
        }
        container segment-routing {
          presence "true";
          container prefix-sid-range {
            leaf global {
              type empty;
            }
          }
          leaf shutdown {
            type string;
          }
        }
        leaf split-horizon {
          type empty;
        }
        leaf transport-tunnel {
          type string;
        }
        leaf vpn-apply-export {
          type empty;
        }
        leaf vpn-apply-import {
          type empty;
        }
        leaf shutdown {
          type string;
        }
      }
      leaf ip-fast-reroute {
        type empty;
      }
      leaf fib-priority {
        type string;
      }
      container if-attribute {
        list admin-group {
          // NCS patched for predictable order
          ordered-by user;
          tailf:cli-suppress-mode;
          key "group-name";
          leaf group-name {
            type string;
          }
          leaf value {
            type string;
          }
        }
        list srlg-group {
          // NCS patched for predictable order
          ordered-by user;
          tailf:cli-suppress-mode;
          key "group-name";
          leaf group-name {
            type ncs_template_string32;
          }
          leaf value {
            type string;
          }
          leaf penalty-weight {
            type string;
          }
        }
      }
      container igmp {
        presence "present";

        grouping iface-grouping {
          leaf disable-router-alert-check {
            type empty;
          }
          leaf import {
            type string;
          }
          leaf max-groups {
            type string;
          }
          leaf max-grp-sources {
            type string;
          }
          leaf max-sources {
            type string;
          }
          uses ncs_template_mcac-grouping;
          leaf subnet-check {
            type string;
          }
          leaf version {
            type string;
          }
        }

        grouping igmp-common-grouping {
          leaf query-interval {
            type string;
          }
          leaf query-response-interval {
            type string;
          }
          container ssm-translate {
            list grp-range {
              // NCS patched for predictable order
              ordered-by user;
              key "start end";
              leaf start {
                type string;
              }
              leaf end {
                type string;
              }
              list source {
                // NCS patched for predictable order
                ordered-by user;
                tailf:cli-suppress-mode;
                key "ip-address";
                leaf ip-address {
                  type string;
                }
              }
            }
          }
        }
        list group-interface {
          // NCS patched for predictable order
          ordered-by user;
          key "ip-int-name";
          leaf ip-int-name {
            type string;
          }
          uses iface-grouping;
          leaf query-src-ip {
            type string;
          }
          leaf sub-hosts-only {
            type empty;
          }
          leaf shutdown {
            type string;
          }
        }
        leaf grp-if-query-src-ip {
          type string;
        }
        list interface {
          // NCS patched for predictable order
          ordered-by user;
          key "ip-int-name";
          leaf ip-int-name {
            type string;
          }
          uses iface-grouping;
          leaf query-last-listener-interval {
            type string;
          }
          leaf redundant-multicast {
            type empty;
          }
          uses igmp-common-grouping;
          uses ncs_template_igmp-static-grouping;
          leaf shutdown {
            type string;
          }
        }
        uses igmp-common-grouping;
        leaf query-last-member-interval {
          type string;
        }
        leaf robust-count {
          type string;
        }
        container tunnel-interface {
          list rsvp-p2mp {
            // NCS patched for predictable order
            ordered-by user;
            key "lsp-name";
            leaf lsp-name {
              type string;
            }
            uses ncs_template_igmp-static-grouping;
            leaf shutdown {
              type string;
            }
          }
        }
        leaf shutdown {
          type string;
        }
      }
      leaf router-id {
        type string;
      }
      list static-route {
        // NCS patched for predictable order
        ordered-by user;
        tailf:cli-suppress-mode;
        key "route";
        leaf route {
          type string;
        }
        choice nh {
          list next-hop {
            // NCS patched for predictable order
            ordered-by user;
            tailf:cli-suppress-mode;
            key "address";
            leaf address {
              type string;
            }
            uses ncs_template_static-route-extras-grouping;
          }
          leaf indirect {
            type string;
          }
          leaf black-hole {
            type empty;
          }
        }
        uses ncs_template_static-route-extras-grouping;
        choice rsvp-ldp {
          leaf rsvp-te {
            type empty;
          }
          leaf ldp {
            type empty;
          }
        }
        leaf disallow-igp {
          type empty;
        }
      }
      list static-route-entry {
        // NCS patched for predictable order
        ordered-by user;
        key "route";
        leaf route {
          type string;
        }
        list next-hop {
          // NCS patched for predictable order
          ordered-by user;
          key "address";
          leaf address {
            type string;
          }
          uses ncs_template_static-route-entry-nh-grouping;
        }
        list indirect {
          // NCS patched for predictable order
          ordered-by user;
          key "address";
          leaf address {
            type string;
          }
          uses ncs_template_static-route-entry-nh-grouping;
        }
        container black-hole {
          presence "true";
          uses ncs_template_static-route-entry-nh-grouping;
          container prefix-list {
            leaf name {
              tailf:cli-drop-node-name;
              type string;
            }
            leaf modifyer {
              tailf:cli-drop-node-name;
              type string;
            }
          }
        }
        leaf tag {
          type string;
        }
      }
      uses ncs_template_router-aggregate-grouping;

      grouping router-isis-grouping {
        leaf advertise-passive-only {
          type empty;
        }
        leaf prefix-attributes-tlv {
          type empty;
        }
        container entropy-label {
          leaf override-tunnel-elc {
            type empty;
          }
        }
        container database-export {
          leaf identifier {
            type string;
          }
          leaf bgp-ls-identifier {
            type string;
          }
        }
        leaf advertise-router-capability {
          type string;
        }
        container igp-shortcut {

          grouping res-filter-grouping {
            leaf resolution {
              type string;
            }
            container resolution-filter {
              list filter {
                // NCS patched for predictable order
                ordered-by user;
                tailf:cli-suppress-mode;
                tailf:cli-drop-node-name;
                key "filter";
                leaf filter {
                  type string;
                }
              }
            }
          }
          container tunnel-next-hop {
            // NCS drop config false container family
            container family-ipv4 {
              uses res-filter-grouping;
            }
            container family-ipv6 {
              uses res-filter-grouping;
            }
            container family-srv4 {
              uses res-filter-grouping;
            }
            container family-srv6 {
              uses res-filter-grouping;
            }
          }
          leaf shutdown {
            type string;
          }
        }
        leaf advertise-tunnel-link {
          type empty;
        }
        leaf all-l1isis {
          type string;
        }
        leaf all-l2isis {
          type string;
        }
        list area-id {
          // NCS patched for predictable order
          ordered-by user;
          tailf:cli-suppress-mode;
          key "id";
          leaf id {
            type string;
          }
        }
        leaf auth-keychain {
          type string;
        }
        leaf authentication-check {
          type string;
        }
        uses ncs_template_prompted-authentication-key-grouping;
        leaf authentication-type {
          type string;
        }
        leaf csnp-authentication {
          type string;
        }
        leaf default-route-tag {
          type string;
        }
        leaf disable-ldp-sync {
          type empty;
        }
        leaf-list export {
          // NCS patched for predictable order
          ordered-by user;
          type string;
        }
        container export-limit {
          leaf number {
            tailf:cli-drop-node-name;
            type string;
          }
          leaf log {
            type string;
          }
        }
        container graceful-restart {
          presence "true";
          leaf helper-disable {
            type empty;
          }
        }
        leaf hello-authentication {
          type string;
        }
        leaf hello-padding {
          type string;
        }
        leaf ignore-attached-bit {
          type empty;
        }
        leaf ignore-lsp-errors {
          type empty;
        }
        leaf iid-tlv-enable {
          type empty;
        }
        leaf standard-multi-instance {
          type empty;
        }
        list interface {
          // NCS patched for predictable order
          ordered-by user;
          key "name";
          leaf name {
            type string;
          }
          list bfd-enable {
            // NCS patched for predictable order
            ordered-by user;
            tailf:cli-suppress-mode;
            key "bfd-enable";
            leaf bfd-enable {
              type string;
            }
            leaf include-bfd-tlv {
              type empty;
            }
          }
          container ipv4-adjacency-sid {
            leaf label {
              type string;
            }
          }
          container ipv6-adjacency-sid {
            leaf label {
              type string;
            }
          }
          container ipv6-node-sid {
            leaf index {
              type string;
            }
          }
          leaf csnp-interval {
            type string;
          }
          leaf hello-authentication {
            type string;
          }
          uses ncs_template_prompted-hello-authentication-key-grouping;
          leaf hello-authentication-type {
            type string;
          }
          leaf interface-type {
            type string;
          }
          leaf ipv4-multicast-disable {
            type empty;
          }
          leaf ipv6-multicast-disable {
            type empty;
          }
          leaf ipv6-unicast-disable {
            type empty;
          }
          list level {
            // NCS patched for predictable order
            ordered-by user;
            key "id";
            leaf id {
              type string;
            }
            uses ncs_template_prompted-hello-authentication-key-grouping;
            leaf hello-authentication-type {
              type string;
            }
            leaf hello-interval {
              type string;
            }
            leaf hello-multiplier {
              type string;
            }
            leaf ipv4-multicast-metric {
              type string;
            }
            leaf ipv6-multicast-metric {
              type string;
            }
            leaf ipv6-unicast-metric {
              type string;
            }
            leaf metric {
              type string;
            }
            leaf passive {
              type empty;
            }
            leaf priority {
              type string;
            }
            leaf sd-offset {
              type string;
            }
            leaf sf-offset {
              type string;
            }
          }
          leaf level-capability {
            type string;
          }
          leaf loopfree-alternate-exclude {
            type empty;
          }
          leaf lsp-pacing-interval {
            type string;
          }
          leaf mesh-group {
            type string;
          }
          leaf passive {
            type empty;
          }
          leaf retransmit-interval {
            type string;
          }
          leaf tag {
            type string;
          }
          leaf shutdown {
            type string;
          }
        }
        leaf ipv4-multicast-routing {
          type string;
        }
        leaf ipv4-routing {
          type string;
        }
        leaf ipv6-routing {
          type string;
        }
        leaf ipv6-multicast-routing {
          type string;
        }
        leaf ldp-over-rsvp {
          type empty;
        }
        list level {
          // NCS patched for predictable order
          ordered-by user;
          key "id";
          leaf id {
            type string;
          }
          uses ncs_template_prompted-authentication-key-grouping;
          leaf authentication-type {
            type string;
          }
          leaf csnp-authentication {
            type string;
          }
          leaf default-ipv4-multicast-metric {
            type string;
          }
          leaf default-ipv6-multicast-metric {
            type string;
          }
          leaf default-ipv6-unicast-metric {
            type string;
          }
          leaf default-metric {
            type string;
          }
          leaf external-preference {
            type string;
          }
          leaf hello-authentication {
            type string;
          }
          leaf loopfree-alternate-exclude {
            type empty;
          }
          leaf preference {
            type string;
          }
          leaf psnp-authentication {
            type string;
          }
          leaf wide-metrics-only {
            type empty;
          }
        }
        leaf level-capability {
          type string;
        }
        list link-group {
          // NCS patched for predictable order
          ordered-by user;
          key "name";
          leaf name {
            type string;
          }
          list level {
            // NCS patched for predictable order
            ordered-by user;
            key "id";
            leaf id {
              type string;
            }
            leaf ipv6-unicast-metric-offset {
              type string;
            }
            leaf ipv4-unicast-metric-offset {
              type string;
            }
            leaf ipv6-multicast-metric-offset {
              type string;
            }
            leaf ipv4-multicast-metric-offset {
              type string;
            }
            list member {
              // NCS patched for predictable order
              ordered-by user;
              tailf:cli-suppress-mode;
              key "name";
              leaf name {
                type string;
              }
            }
            leaf revert-members {
              type string;
            }
            leaf oper-members {
              type string;
            }
          }
        }
        container loopfree-alternate {
          presence "true";
          leaf remote-lfa {
            type empty;
          }
          leaf max-pq-cost {
            type string;
          }
        }
        container loopfree-alternate-exclude {
          leaf-list prefix-policy {
            // NCS patched for predictable order
            ordered-by user;
            type string;
          }
        }
        leaf lsp-lifetime {
          type string;
        }
        leaf lsp-mtu-size {
          type string;
        }
        leaf lsp-refresh-interval {
          type string;
        }
        container multi-topology {
          leaf ipv6-unicast {
            type empty;
          }
        }
        leaf multicast-import {
          type string;
        }
        container overload {
          presence "true";
          leaf timeout {
            type string;
          }
          leaf max-metric {
            type empty;
          }
        }
        container overload-on-boot {
          presence "true";
          leaf timeout {
            type string;
          }
          leaf max-metric {
            type empty;
          }
        }
        leaf psnp-authentication {
          type string;
        }
        container reference-bandwidth {
          choice bandwidth {
            leaf bandwidth-in-kbps {
              tailf:cli-drop-node-name;
              type string;
            }
            leaf tbps {
              type string;
            }
            leaf gbps {
              type string;
            }
            leaf mbps {
              type string;
            }
            leaf kbps {
              type string;
            }
          }
        }
        leaf router-id {
          type string;
        }
        leaf rsvp-shortcut {
          type empty;
        }
        uses ncs_template_router-segment-routing-grouping;
        leaf strict-adjacency-check {
          type empty;
        }
        leaf suppress-attached-bit {
          type empty;
        }
        container timers {
          container spf-wait {
            leaf wait {
              tailf:cli-drop-node-name;
              type string;
            }
            leaf spf-initial-wait {
              type string;
            }
            leaf spf-second-wait {
              type string;
            }
          }
          container lsp-wait {
            leaf wait {
              tailf:cli-drop-node-name;
              type string;
            }
            leaf lsp-initial-wait {
              type string;
            }
            leaf lsp-second-wait {
              type string;
            }
          }
        }
        container spf-wait {
          leaf wait {
            tailf:cli-drop-node-name;
            type string;
          }
          leaf initial-wait {
            tailf:cli-drop-node-name;
            type string;
          }
          leaf second-wait {
            tailf:cli-drop-node-name;
            type string;
          }
        }
        container lsp-wait {
          leaf wait {
            tailf:cli-drop-node-name;
            type string;
          }
          leaf initial-wait {
            tailf:cli-drop-node-name;
            type string;
          }
          leaf second-wait {
            tailf:cli-drop-node-name;
            type string;
          }
        }
        leaf traffic-engineering {
          type empty;
        }
        container traffic-engineering-options {
          leaf advertise-delay {
            type empty;
          }
          container application-link-attributes {
            presence "true";
            leaf legacy {
              type empty;
            }
          }
          leaf ipv6 {
            type empty;
          }
        }
        leaf unicast-import-disable {
          type string;
        }
        leaf shutdown {
          type string;
        }
      }
      list isis-list {
        // NCS patched for predictable order
        ordered-by user;
        tailf:alt-name "isis";
        key "id";
        leaf id {
          type string;
        }
        leaf-list import {
          // NCS patched for predictable order
          ordered-by user;
          type string;
        }
        leaf system-id {
          type string;
        }
        uses router-isis-grouping {
          augment "interface" {
            container ipv4-node-sid {
              choice ipv4-node-sid {
                leaf index {
                  type string;
                }
                leaf label {
                  type string;
                }
              }
            }
          }
        }
        container alt-lsp-refresh-interval {
          tailf:alt-name "lsp-refresh-interval";
          leaf seconds {
            tailf:cli-drop-node-name;
            type string;
          }
          leaf half-lifetime {
            type ncs_template_enable-disable;
          }
        }
        container loopfree-alternates {
          container exclude {
            leaf-list prefix-policy {
              // NCS patched for predictable order
              ordered-by user;
              type string;
            }
          }
          container remote-lfa {
            presence "true";
            leaf max-pq-cost {
              type string;
            }
            container node-protect {
              presence "true";
              leaf max-pq-nodes {
                type string;
              }
            }
          }
          container ti-lfa {
            presence "true";
            leaf max-sr-frr-labels {
              type string;
            }
            leaf node-protect {
              type empty;
            }
          }
        }
        container rib-priority {
          container high {
            choice high-options {
              leaf prefix-list-name {
                tailf:cli-drop-node-name;
                type string;
              }
              leaf tag {
                type string;
              }
            }
          }
        }
      }
      container isis-container {
        tailf:alt-name "isis";
        presence "true";
        uses router-isis-grouping;
      }

      grouping router-ospf-grouping {
        leaf advertise-tunnel-link {
          type empty;
        }
        leaf advertise-router-capability {
          type string;
        }
        uses ncs_template_router-segment-routing-grouping;
        container loopfree-alternates {
          presence "true";
          container remote-lfa {
            presence "true";
          }
        }
        list area {
          // NCS patched for predictable order
          ordered-by user;
          key "area-id";
          uses ncs_template_ospf-area-id-grouping;

          grouping area-range-grouping {
            list area-range {
              // NCS patched for predictable order
              ordered-by user;
              tailf:cli-suppress-mode;
              key "ip-prefix-mask";
              leaf ip-prefix-mask {
                type string;
              }
              leaf adv-or-not {
                tailf:cli-drop-node-name;
                type string;
              }
            }
          }
          uses area-range-grouping;
          container nssa {
            uses area-range-grouping;
            leaf redistribute-external {
              type empty;
            }
            container originate-default-route {
              presence "true";
              leaf type-7 {
                type empty;
              }
              leaf no-adjancency {
                type empty;
              }
            }
            leaf summaries {
              type empty;
            }
          }
          list interface {
            // NCS patched for predictable order
            ordered-by user;
            key "name";
            leaf name {
              type string;
            }
            leaf secondary {
              type empty;
            }
            leaf bfd-enable {
              type empty;
            }
            leaf hello-interval {
              type string;
            }
            leaf dead-interval {
              type string;
            }
            leaf passive {
              type string;
            }
            list message-digest-key {
              // NCS patched for predictable order
              ordered-by user;
              tailf:cli-suppress-mode;
              key "key-id";
              leaf key-id {
                type string;
              }
              leaf md5 {
                type empty;
              }
              leaf hash-value {
                tailf:cli-drop-node-name;
                type string;
              }
              leaf scheme {
                tailf:cli-drop-node-name;
                type ncs_template_hash-method;
              }
            }
            leaf interface-type {
              type string;
            }
            leaf authentication-type {
              type string;
            }
            leaf metric {
              type string;
            }
            leaf mtu {
              type string;
            }
            container node-sid {
              leaf label {
                type string;
              }
            }
            leaf sid-protection {
              type string;
            }
            leaf shutdown {
              type string;
            }
          }
          container stub {
            leaf default-metric {
              type string;
            }
            leaf summaries {
              type string;
            }
          }
        }
        leaf asbr {
          type empty;
        }
        leaf compatible-rfc1583 {
          type empty;
        }
        leaf disable-ldp-sync {
          type empty;
        }
        leaf-list export {
          // NCS patched for predictable order
          ordered-by user;
          type string;
        }
        container export-limit {
          leaf limit {
            tailf:cli-drop-node-name;
            type string;
          }
          leaf log {
            type string;
          }
        }
        container external-db-overflow {
          leaf limit {
            tailf:cli-drop-node-name;
            type string;
          }
          leaf seconds {
            tailf:cli-drop-node-name;
            type string;
          }
        }
        leaf external-preference {
          type string;
        }
        container graceful-restart {
          leaf helper-disable {
            type empty;
          }
        }
        leaf ldp-over-rsvp {
          type empty;
        }
        leaf multicast-import {
          type empty;
        }
        leaf overload {
          type string;
        }
        container overload-alt {
          presence "true";
          tailf:alt-name "overload";
          leaf timeout {
            type string;
          }
        }
        leaf overload-include-stub {
          type empty;
        }
        container overload-on-boot {
          presence "true";
          leaf timeout {
            type string;
          }
        }
        leaf preference {
          type string;
        }
        leaf reference-bandwidth {
          type string;
        }
        leaf rsvp-shortcut {
          type empty;
        }
        container timers {
          leaf lsa-arrival {
            type string;
          }
        }
        leaf traffic-engineering {
          type empty;
        }
        leaf unicast-import-disable {
          type empty;
        }
        leaf shutdown {
          type string;
        }
      }
      list ospf-list {
        // NCS patched for predictable order
        ordered-by user;
        tailf:alt-name "ospf";
        key "ospf-instance";
        leaf ospf-instance {
          type string;
        }
        leaf router-id {
          tailf:cli-drop-node-name;
          type string;
        }
        uses router-ospf-grouping {
          augment "timers" {
            leaf lsa-accumulate {
              type string;
            }
            container lsa-generate {
              leaf max-lsa-wait {
                tailf:cli-drop-node-name;
                type string;
              }
              leaf lsa-initial-wait {
                tailf:cli-drop-node-name;
                type string;
              }
              leaf lsa-second-wait {
                tailf:cli-drop-node-name;
                type string;
              }
            }
            leaf redistribute-delay {
              type string;
            }
            container spf-wait {
              leaf max-spf-wait {
                tailf:cli-drop-node-name;
                type string;
              }
              leaf spf-initial-wait {
                tailf:cli-drop-node-name;
                type string;
              }
              leaf spf-second-wait {
                tailf:cli-drop-node-name;
                type string;
              }
            }
            container alt-lsa-generate {
              tailf:alt-name "lsa-generate";
              leaf max-lsa-wait {
                tailf:cli-drop-node-name;
                type string;
              }
              leaf lsa-initial-wait {
                type string;
              }
              leaf lsa-second-wait {
                type string;
              }
            }
            container alt-spf-wait {
              tailf:alt-name "spf-wait";
              leaf max-spf-wait {
                tailf:cli-drop-node-name;
                type string;
              }
              leaf spf-initial-wait {
                type string;
              }
              leaf spf-second-wait {
                type string;
              }
            }
            leaf incremental-spf-wait {
              type string;
            }
          }
        }
      }
      container ospf-container {
        tailf:alt-name "ospf";
        presence "true";
        leaf router-id {
          type string;
        }
        leaf router-id1 {
          tailf:cli-drop-node-name;
          type string;
        }
        uses router-ospf-grouping {
          augment "timers" {
            container lsa-generate {
              leaf max-lsa-wait {
                tailf:cli-drop-node-name;
                type string;
              }
              leaf lsa-initial-wait {
                tailf:cli-drop-node-name;
                type string;
              }
              leaf lsa-second-wait {
                tailf:cli-drop-node-name;
                type string;
              }
            }
            container spf-wait {
              leaf max-spf-wait {
                tailf:cli-drop-node-name;
                type string;
              }
              leaf spf-initial-wait {
                tailf:cli-drop-node-name;
                type string;
              }
              leaf spf-second-wait {
                tailf:cli-drop-node-name;
                type string;
              }
            }
          }
        }
      }

      grouping router-ospf3-grouping {
        list area {
          // NCS patched for predictable order
          ordered-by user;
          key "area-id";
          leaf area-id {
            type string;
          }
          list interface {
            // NCS patched for predictable order
            ordered-by user;
            key "interface-name";
            leaf interface-name {
              type string;
            }
            leaf interface-type {
              type string;
            }
            leaf passive {
              type empty;
            }
            leaf mtu {
              type string;
            }
            leaf metric {
              type string;
            }
            leaf shutdown {
              type string;
            }
          }
        }
        leaf shutdown {
          type string;
        }
      }
      list ospf3-list {
        // NCS patched for predictable order
        ordered-by user;
        tailf:alt-name "ospf3";
        key "ospf3-instance";
        leaf ospf3-instance {
          type string;
        }
        leaf router-id {
          tailf:cli-drop-node-name;
          type string;
        }
        uses router-ospf3-grouping;
      }
      container ospf3-container {
        tailf:alt-name "ospf3";
        presence "true";
        leaf router-id {
          type string;
        }
        uses router-ospf3-grouping;
      }
      container mcac {
        list policy {
          // NCS patched for predictable order
          ordered-by user;
          key "policy-name";
          leaf policy-name {
            type ncs_template_string32;
          }
          list bundle {
            // NCS patched for predictable order
            ordered-by user;
            key "bundle-name";
            leaf bundle-name {
              type ncs_template_string32;
            }
            leaf bandwidth {
              type string;
            }
            list channel {
              // NCS patched for predictable order
              ordered-by user;
              tailf:cli-suppress-mode;
              key "start-address end-address";
              leaf start-address {
                type string;
              }
              leaf end-address {
                type string;
              }
              leaf source {
                type string;
              }
              leaf bw {
                type string;
              }
              leaf class {
                type string;
              }
              leaf type {
                type string;
              }
            }
            leaf description {
              type string;
            }
            container mc-constraints {
              list lag-port-down {
                // NCS patched for predictable order
                ordered-by user;
                tailf:cli-suppress-mode;
                key "lag-id number-down";
                leaf lag-id {
                  type string;
                }
                leaf number-down {
                  type string;
                }
                leaf level {
                  type string;
                }
              }
              list level {
                // NCS patched for predictable order
                ordered-by user;
                tailf:cli-suppress-mode;
                key "level";
                leaf level {
                  type string;
                }
                leaf bw {
                  type string;
                }
              }
              leaf use-lag-port-weight {
                type empty;
              }
            }
            leaf shutdown {
              type string;
            }
          }
          leaf default-action {
            type string;
          }
          leaf description {
            type string;
          }
        }
      }
      container msdp {
        presence "present";
        leaf local-address {
          type string;
        }
        list group {
          // NCS patched for predictable order
          ordered-by user;
          key "group-name";
          leaf group-name {
            type string;
          }
          leaf mode {
            type string;
          }
          list peer {
            // NCS patched for predictable order
            ordered-by user;
            key "ip-address";
            leaf ip-address {
              type string;
            }
            leaf shutdown {
              type string;
            }
          }
          leaf shutdown {
            type string;
          }
        }
      }
      uses ncs_template_nat-pool-grouping;
      container l2tp {
        leaf local-address {
          type string;
        }
        leaf shutdown {
          type string;
        }
        list group {
          // NCS patched for predictable order
          ordered-by user;
          key "group-id";
          leaf group-id {
            type string;
          }
          leaf protocol {
            type string;
          }
          leaf local-address {
            type string;
          }
          list tunnel {
            // NCS patched for predictable order
            ordered-by user;
            key "tunnel-id";
            leaf tunnel-id {
              type string;
            }
            leaf local-name {
              type string;
            }
            leaf peer {
              type string;
            }
            leaf preference {
              type string;
            }
            container password {
              leaf id {
                tailf:cli-drop-node-name;
                type string;
              }
              leaf method {
                tailf:cli-drop-node-name;
                type ncs_template_hash-method;
              }
            }
            leaf remote-name {
              type string;
            }
            leaf load-balance-method {
              type string;
            }
            leaf shutdown {
              type string;
            }
          }
          leaf shutdown {
            type string;
          }
        }
      }
      container ldp {
        presence "present";
        container fast-reroute {
          presence "true";
          leaf backup-sr-tunnel {
            type empty;
          }
        }

        grouping router-ldp-hello-keepalive-grouping {
          container hello {
            leaf timeout {
              tailf:cli-drop-node-name;
              type string;
            }
            leaf factor {
              tailf:cli-drop-node-name;
              type string;
            }
          }
          container keepalive {
            leaf timeout {
              tailf:cli-drop-node-name;
              type string;
            }
            leaf factor {
              tailf:cli-drop-node-name;
              type string;
            }
          }
        }
        container aggregate-prefix-match {
          presence "present";
          leaf shutdown {
            type string;
          }
        }
        container egress-statistics {
          list fec-prefix {
            // NCS patched for predictable order
            ordered-by user;
            key "prefix";
            leaf prefix {
              type string;
            }
            leaf accounting-policy {
              type string;
            }
            leaf collect-stats {
              type empty;
            }
            leaf shutdown {
              type string;
            }
          }
        }
        leaf entropy-label-capability {
          type empty;
        }
        leaf-list export {
          // NCS patched for predictable order
          ordered-by user;
          type string;
        }
        list fec-originate {
          // NCS patched for predictable order
          ordered-by user;
          tailf:cli-suppress-mode;
          key "ip-prefix";
          leaf ip-prefix {
            type string;
          }
          leaf advertised-label {
            type string;
          }
          leaf pop {
            type empty;
          }
          leaf next-hop {
            type string;
          }
          leaf swap-label {
            type string;
          }
          leaf interface {
            type string;
          }
        }
        container graceful-restart {
          presence "true";
          leaf maximum-recovery-time {
            type string;
          }
        }
        container interface-parameters {
          list interface {
            // NCS patched for predictable order
            ordered-by user;
            key "name";
            leaf name {
              type string;
            }
            leaf dual-stack {
              type empty;
            }
            leaf bfd-enable {
              type empty;
            }
            leaf-list alt-bfd-enable {
              // NCS patched for predictable order
              ordered-by user;
              tailf:alt-name "bfd-enable";
              type string;
            }
            container ipv4 {
              uses router-ldp-hello-keepalive-grouping;
              container local-lsr-id {
                choice local-lsr-id-choice {
                  leaf local-lsr-id {
                    tailf:cli-drop-node-name;
                    type string;
                  }
                  leaf interface-name {
                    type string;
                  }
                }
              }
              container fec-type-capability {
                leaf p2mp-ipv4 {
                  type ncs_template_enable-disable;
                }
                leaf p2mp-ipv6 {
                  type ncs_template_enable-disable;
                }
                leaf prefix-ipv4 {
                  type ncs_template_enable-disable;
                }
                leaf prefix-ipv6 {
                  type ncs_template_enable-disable;
                }
              }
              leaf transport-address {
                type string;
              }
              leaf shutdown {
                type string;
              }
            }
            container ipv6 {
              uses router-ldp-hello-keepalive-grouping;
              leaf local-lsr-id {
                type string;
              }
              leaf transport-address {
                type string;
              }
              leaf shutdown {
                type string;
              }
            }
            leaf local-lsr-id {
              type string;
            }
            leaf multicast-traffic {
              type ncs_template_enable-disable;
            }
            leaf transport-address {
              type string;
            }
            leaf shutdown {
              type string;
            }
          }
          container ipv4 {
            uses router-ldp-hello-keepalive-grouping;
            leaf transport-address {
              type string;
            }
          }
          container ipv6 {
            leaf transport-address {
              type string;
            }
            uses router-ldp-hello-keepalive-grouping;
          }
          uses router-ldp-hello-keepalive-grouping;
        }
        container peer-parameters {
          list peer {
            // NCS patched for predictable order
            ordered-by user;
            key "addr";
            leaf addr {
              type string;
            }
            container authentication-key {
              leaf authentication-key {
                tailf:cli-drop-node-name;
                type string;
              }
              leaf scheme {
                tailf:cli-drop-node-name;
                type ncs_template_hash-method;
              }
            }
            leaf adv-adj-addr-only {
              type empty;
            }
            leaf export-prefixes {
              type string;
            }
          }
        }
        leaf prefer-tunnel-in-tunnel {
          type empty;
        }
        leaf shortcut-local-ttl-propagate {
          type string;
        }
        leaf shortcut-transit-ttl-propagate {
          type string;
        }
        container targeted-session {
          uses router-ldp-hello-keepalive-grouping;
          container ipv4 {
            uses router-ldp-hello-keepalive-grouping;
          }
          container ipv6 {
            uses router-ldp-hello-keepalive-grouping;
          }
          list peer {
            // NCS patched for predictable order
            ordered-by user;
            key "peer-address";
            leaf peer-address {
              type string;
            }
            leaf bfd-enable {
              type empty;
            }
            uses router-ldp-hello-keepalive-grouping;
            leaf local-lsr-id {
              type string;
            }
            container tunneling {
              presence "true";
              leaf lsp {
                type string;
              }
            }
            leaf shutdown {
              type string;
            }
          }
        }
        leaf-list export-tunnel-table {
          // NCS patched for predictable order
          ordered-by user;
          type string;
        }
        leaf implicit-null-label {
          type empty;
        }
        leaf label-withdrawal-delay {
          type string;
        }
        container session-parameters {
          list peer {
            // NCS patched for predictable order
            ordered-by user;
            key "ip-address";
            leaf ip-address {
              type string;
            }
            leaf adv-adj-addr-only {
              type empty;
            }
            leaf-list export-prefixes {
              // NCS patched for predictable order
              ordered-by user;
              type string;
            }
            container fec-type-capability {
              leaf prefix-ipv4 {
                type string;
              }
              leaf prefix-ipv6 {
                type string;
              }
            }
          }
        }
        container tcp-session-parameters {
          list peer-transport {
            // NCS patched for predictable order
            ordered-by user;
            key "ip-address";
            leaf ip-address {
              type string;
            }
            uses ncs_template_prompted-authentication-key-grouping;
            leaf path-mtu-discovery {
              type empty;
            }
            leaf ttl-security {
              type string;
            }
          }
        }
        container import-pmsi-routes {
          leaf mvpn {
            type empty;
          }
          leaf mvpn-no-export-community {
            type empty;
          }
        }
        leaf tunnel-table-pref {
          type string;
        }
        leaf shutdown {
          type string;
        }
      }
      container ldp-shortcut {
        presence "true";
        leaf value {
          tailf:cli-drop-node-name;
          type string;
        }
      }
      container dhcp {
        uses ncs_template_local-dhcp-server-grouping;
      }
      container dhcp6 {
        list local-dhcp-server {
          // NCS patched for predictable order
          ordered-by user;
          key "server-name";
          leaf server-name {
            type string;
          }
          leaf description {
            type string;
          }
          leaf user-ident {
            type string;
          }
          container use-link-address {
            presence "true";
            leaf scope {
              type string;
            }
          }
          container lease-hold-time {
            leaf days {
              type string;
            }
            leaf hrs {
              type string;
            }
            leaf min {
              type string;
            }
            leaf sec {
              type string;
            }
          }
          container lease-hold-time-for {
            leaf solicited-release {
              type empty;
            }
          }
          list pool {
            // NCS patched for predictable order
            ordered-by user;
            key "name";
            leaf name {
              type string;
            }
            leaf description {
              type string;
            }
            container delegated-prefix-length {
              leaf prefix-lenght {
                tailf:cli-drop-node-name;
                type string;
              }
              leaf minimum {
                type string;
              }
              leaf maximum {
                type string;
              }
            }
            container options {
              leaf-list dns-server {
                // NCS patched for predictable order
                ordered-by user;
                type string;
              }
              list custom-option {
                // NCS patched for predictable order
                ordered-by user;
                tailf:cli-suppress-mode;
                key "option-number";
                leaf option-number {
                  type string;
                }
                choice val {
                  leaf hex {
                    type string;
                  }
                  leaf string {
                    type string;
                  }
                }
              }
            }
            list prefix {
              // NCS patched for predictable order
              ordered-by user;
              key "address";
              leaf address {
                type string;
              }
              leaf pd {
                type empty;
              }
              leaf wan-host {
                type empty;
              }
              container preferred-lifetime {
                leaf days {
                  type string;
                }
                leaf hrs {
                  type string;
                }
                leaf min {
                  type string;
                }
                leaf sec {
                  type string;
                }
              }
              container rebind-timer {
                leaf days {
                  type string;
                }
                leaf hrs {
                  type string;
                }
                leaf min {
                  type string;
                }
                leaf sec {
                  type string;
                }
              }
              container renew-timer {
                leaf days {
                  type string;
                }
                leaf hrs {
                  type string;
                }
                leaf min {
                  type string;
                }
                leaf sec {
                  type string;
                }
              }
              container valid-lifetime {
                leaf days {
                  type string;
                }
                leaf hrs {
                  type string;
                }
                leaf min {
                  type string;
                }
                leaf sec {
                  type string;
                }
              }
            }
          }
          leaf use-pool-from-client {
            type empty;
          }
          leaf shutdown {
            type string;
          }
        }
      }
      container radius-server {
        uses ncs_template_radius-server-grouping;
      }
      container rip {
        list group {
          // NCS patched for predictable order
          ordered-by user;
          key "name";
          leaf name {
            type ncs_template_string32;
          }
          leaf description {
            type string;
          }
          leaf export {
            type string;
          }
          leaf metric-out {
            type string;
          }
          list neighbor {
            // NCS patched for predictable order
            ordered-by user;
            key "intf-id";
            leaf intf-id {
              type string;
            }
            container authentication-key {
              leaf key {
                tailf:cli-drop-node-name;
                type string;
              }
              leaf hash {
                tailf:cli-drop-node-name;
                type string;
              }
            }
            container timers {
              leaf update {
                tailf:cli-drop-node-name;
                type string;
              }
              leaf timeout {
                tailf:cli-drop-node-name;
                type string;
              }
              leaf flush {
                tailf:cli-drop-node-name;
                type string;
              }
            }
            leaf shutdown {
              type string;
            }
          }
          leaf shutdown {
            type string;
          }
        }
        leaf shutdown {
          type string;
        }
      }
      container mpls {
        presence "true";
        container auto-bandwidth-multipliers {
          leaf sample-multiplier {
            type string;
          }
          leaf adjust-multiplier {
            type string;
          }
        }
        leaf bypass-resignal-timer {
          type string;
        }
        leaf hold-timer {
          type string;
        }
        leaf cspf-on-loose-hop {
          type empty;
        }
        leaf p2mp-resignal-timer {
          type string;
        }
        leaf least-fill-reoptim-thd {
          type string;
        }
        leaf static-lsp-fast-retry {
          type string;
        }
        list path {
          // NCS patched for predictable order
          ordered-by user;
          key "name";
          leaf name {
            type string;
          }
          list hop {
            // NCS patched for predictable order
            ordered-by user;
            tailf:cli-suppress-mode;
            key "hop-number";
            leaf hop-number {
              type string;
            }
            leaf ip-address {
              tailf:cli-drop-node-name;
              type string;
            }
            leaf mode {
              tailf:cli-drop-node-name;
              type string;
            }
          }
          leaf shutdown {
            type string;
          }
        }
        container pce-report {
          leaf rsvp-te {
            type string;
          }
          leaf sr-te {
            type string;
          }
        }
        container sr-te-resignal {
          leaf resignal-timer {
            type string;
          }
          leaf resignal-on-igp-event {
            type empty;
          }
        }
        list admin-group {
          // NCS patched for predictable order
          ordered-by user;
          tailf:cli-suppress-mode;
          key "name";
          leaf name {
            type string;
          }
          leaf value {
            tailf:cli-drop-node-name;
            type string;
          }
        }
        leaf admin-group-frr {
          type empty;
        }
        leaf resignal-timer {
          type string;
        }
        container srlg-database {
          list router-id {
            // NCS patched for predictable order
            ordered-by user;
            key "ip-address";
            leaf ip-address {
              type string;
            }
            list interface {
              // NCS patched for predictable order
              ordered-by user;
              tailf:cli-suppress-mode;
              key "ip-address srlg-group";
              leaf ip-address {
                type string;
              }
              leaf srlg-group {
                type ncs_template_string32;
              }
            }
            leaf shutdown {
              type string;
            }
          }
        }
        container srlg-frr {
          presence "present";
          leaf strict {
            type empty;
          }
        }
        list srlg-group {
          // NCS patched for predictable order
          ordered-by user;
          key "name";
          leaf name {
            type string;
          }
          leaf value {
            type string;
          }
        }
        list interface {
          // NCS patched for predictable order
          ordered-by user;
          key "name";
          leaf name {
            type string;
          }
          leaf-list admin-group {
            // NCS patched for predictable order
            ordered-by user;
            type string;
          }
          list label-map {
            // NCS patched for predictable order
            ordered-by user;
            key "in-label";
            leaf in-label {
              type string;
            }
            leaf pop {
              type empty;
            }
            leaf shutdown {
              type string;
            }
          }
          leaf te-metric {
            type string;
          }
          list srlg-group {
            // NCS patched for predictable order
            ordered-by user;
            tailf:cli-suppress-mode;
            key "group-name";
            leaf group-name {
              type ncs_template_string32;
            }
          }
          leaf shutdown {
            type string;
          }
        }
        container pce-initiated-lsp {
          presence "true";
          container sr-te {
            leaf shutdown {
              type string;
            }
          }
        }
        list lsp-template {
          // NCS patched for predictable order
          ordered-by user;
          key "template";
          leaf template {
            type string;
          }
          leaf mode {
            tailf:cli-drop-node-name;
            type string;
          }
          leaf default-path {
            type string;
          }
          leaf path-computation-method {
            type string;
          }
          leaf label-stack-reduction {
            type empty;
          }
          container fast-reroute {
            leaf frr-method {
              tailf:cli-drop-node-name;
              type string;
            }
            leaf hop-limit {
              type string;
            }
          }
          leaf cspf {
            type empty;
          }
          container egress-statistics {
            leaf collect-stats {
              type empty;
            }
            leaf accounting-policy {
              type string;
            }
          }
          leaf template-id {
            type string;
          }
          container max-sr-labels {
            leaf label-stack-size {
              tailf:cli-drop-node-name;
              type string;
            }
            leaf additional-frr-labels {
              type string;
            }
          }
          leaf pce-report {
            type string;
          }
          leaf shutdown {
            type string;
          }
        }
        container auto-lsp {
          list lsp-template {
            // NCS patched for predictable order
            ordered-by user;
            tailf:cli-suppress-mode;
            key "template";
            leaf template {
              type string;
            }
            leaf-list policy {
              // NCS patched for predictable order
              ordered-by user;
              type string;
            }
          }
        }
        list lsp {
          // NCS patched for predictable order
          ordered-by user;
          key "name";
          leaf name {
            type string;
          }
          leaf label-stack-reduction {
            type empty;
          }
          leaf vprn-auto-bind {
            type string;
          }
          leaf bgp-transport-tunnel {
            type string;
          }
          leaf bgp-shortcut {
            type string;
          }
          leaf entropy-label {
            type string;
          }
          leaf metric {
            type string;
          }
          leaf metric-type {
            type string;
          }
          leaf bypass-only {
            type empty;
          }
          leaf p2mp-lsp {
            type empty;
          }
          leaf mpls-tp {
            type string;
          }
          leaf sr-te {
            type empty;
          }
          list admin-tag {
            // NCS patched for predictable order
            ordered-by user;
            tailf:cli-suppress-mode;
            key "tag";
            leaf tag {
              type ncs_template_string32;
            }
          }
          leaf to {
            type string;
          }
          leaf from {
            type string;
          }
          leaf-list exclude {
            // NCS patched for predictable order
            ordered-by user;
            type string;
          }
          container auto-bandwidth {
            container adjust-down {
              leaf percent {
                tailf:cli-drop-node-name;
                type string;
              }
              leaf bw {
                type string;
              }
            }
            container adjust-up {
              leaf percent {
                tailf:cli-drop-node-name;
                type string;
              }
              leaf bw {
                type string;
              }
            }
            list fc {
              // NCS patched for predictable order
              ordered-by user;
              tailf:cli-suppress-mode;
              key "fc-name";
              leaf fc-name {
                type ncs_template_fc-name;
              }
              leaf sampling-weight {
                type string;
              }
            }
            leaf max-bandwidth {
              type string;
            }
            leaf min-bandwidth {
              type string;
            }
            leaf monitor-bandwidth {
              type empty;
            }
            container multipliers {
              leaf sample-multiplier {
                type string;
              }
              leaf adjust-multiplier {
                type string;
              }
            }
            container overflow-limit {
              leaf number {
                tailf:cli-drop-node-name;
                type string;
              }
              leaf threshold {
                type string;
              }
              leaf bw {
                type string;
              }
            }
            container underflow-limit {
              leaf number {
                tailf:cli-drop-node-name;
                type string;
              }
              leaf threshold {
                type string;
              }
              leaf bw {
                type string;
              }
            }
          }
          container cspf {
            presence "true";
            leaf use-te-metric {
              type empty;
            }
          }
          container egress-statistics {
            leaf collect-stats {
              type empty;
            }
            leaf accounting-policy {
              type string;
            }
            leaf shutdown {
              type string;
            }
          }
          leaf adspec {
            type empty;
          }
          container fast-reroute {
            leaf frr-method {
              tailf:cli-drop-node-name;
              type string;
            }
            leaf hop-limit {
              type string;
            }
            leaf node-protect {
              type string;
            }
          }
          container igp-shortcut {
            leaf lfa {
              tailf:cli-drop-node-name;
              type string;
            }
            container relative-metric {
              presence "true";
              leaf offset {
                tailf:cli-drop-node-name;
                type string;
              }
            }
            leaf igp-shortcut {
              tailf:cli-drop-node-name;
              type string;
            }
          }
          list include {
            // NCS patched for predictable order
            ordered-by user;
            tailf:cli-suppress-mode;
            key "group";
            leaf group {
              type string;
            }
          }
          leaf least-fill {
            type empty;
          }
          container max-sr-labels {
            leaf label-stack-size {
              tailf:cli-drop-node-name;
              type string;
            }
            leaf additional-frr-labels {
              type string;
            }
          }
          leaf path-computation-method {
            type string;
          }
          leaf pce-control {
            type empty;
          }
          leaf pce-computation {
            type empty;
          }
          leaf pce-report {
            type string;
          }
          leaf propagate-admin-group {
            type empty;
          }

          grouping router-mpls-lsp-prim-sec-grouping {
            container bfd {
              leaf bfd-template {
                type string;
              }
              leaf bfd-enable {
                type empty;
              }
            }
            leaf path {
              type string;
            }
            leaf-list include {
              // NCS patched for predictable order
              ordered-by user;
              type string;
            }
            leaf-list exclude {
              // NCS patched for predictable order
              ordered-by user;
              type string;
            }
            leaf adaptive {
              type empty;
            }
            leaf bandwidth {
              type string;
            }
            leaf hop-limit {
              type string;
            }
            container priority {
              leaf setup-priority {
                tailf:cli-drop-node-name;
                type string;
              }
              leaf hold-priority {
                tailf:cli-drop-node-name;
                type string;
              }
            }
            leaf shutdown {
              type string;
            }
          }
          list primary {
            // NCS patched for predictable order
            ordered-by user;
            key "path";
            uses router-mpls-lsp-prim-sec-grouping;
          }
          list secondary {
            // NCS patched for predictable order
            ordered-by user;
            key "path";
            uses router-mpls-lsp-prim-sec-grouping;
            leaf standby {
              type empty;
            }
          }
          leaf retry-limit {
            type string;
          }
          leaf retry-timer {
            type string;
          }
          leaf shutdown {
            type string;
          }
        }
        list static-lsp {
          // NCS patched for predictable order
          ordered-by user;
          key "name";
          leaf name {
            type string;
          }
          container push {
            leaf label {
              tailf:cli-drop-node-name;
              type string;
            }
            leaf nexthop {
              type string;
            }
          }
          leaf to {
            type string;
          }
          leaf metric {
            type string;
          }
          leaf shutdown {
            type string;
          }
        }
        container ingress-statistics {
          list lsp {
            // NCS patched for predictable order
            ordered-by user;
            key "name";
            leaf name {
              type string;
            }
            leaf sender {
              type string;
            }
            leaf collect-stats {
              type empty;
            }
            leaf shutdown {
              type empty;
            }
          }
        }
        leaf p2p-active-path-fast-retry {
          type string;
        }
        leaf user-srlg-db {
          type ncs_template_enable-disable;
        }

        grouping entropy-label-grouping {
          container entropy-label {
            leaf rsvp-te {
              type string;
            }
            leaf sr-te {
              type string;
            }
          }
        }
        uses entropy-label-grouping;
        container tunnel-table-pref {
          leaf rsvp-te {
            type string;
          }
          leaf sr-te {
            type string;
          }
        }
        leaf shutdown {
          type string;
        }
      }
      container mpls-labels {
        leaf bgp-labels-hold-timer {
          type string;
        }
        container sr-labels {
          leaf start {
            type string;
          }
          leaf end {
            type string;
          }
        }
        leaf static-label-range {
          type string;
        }
        list reserved-label-block {
          // NCS patched for predictable order
          ordered-by user;
          key "name";
          leaf name {
            type string;
          }
          container start-label {
            leaf label {
              tailf:cli-drop-node-name;
              type string;
            }
            leaf end-label {
              type string;
            }
          }
        }
      }
      container origin-validation {
        list rpki-session {
          // NCS patched for predictable order
          ordered-by user;
          key "ip-address";
          leaf ip-address {
            type string;
          }
          leaf description {
            type string;
          }
          leaf port {
            type string;
          }
          leaf local-address {
            type string;
          }
          leaf shutdown {
            type string;
          }
        }
      }
      container rsvp {
        presence "present";
        leaf implicit-null-label {
          type empty;
        }
        list interface {
          // NCS patched for predictable order
          ordered-by user;
          key "name";
          leaf name {
            type string;
          }
          leaf bfd-enable {
            type empty;
          }
          leaf hello-interval {
            type string;
          }
          container refresh-reduction {
            leaf reliable-delivery {
              type empty;
            }
          }
          uses ncs_template_prompted-authentication-key-grouping;
          leaf subscription {
            type string;
          }
          leaf shutdown {
            type string;
          }
        }
        leaf node-id-in-rro {
          type string;
        }
        leaf refresh-reduction-over-bypass {
          type ncs_template_enable-disable;
        }
        leaf refresh-time {
          type string;
        }
        leaf shutdown {
          type string;
        }
      }
      container router-advertisement {
        list interface {
          // NCS patched for predictable order
          ordered-by user;
          key "ip-int-name";
          leaf ip-int-name {
            type string;
          }
          leaf current-hop-limit {
            type string;
          }
          leaf max-advertisement-interval {
            type string;
          }
          leaf min-advertisement-interval {
            type string;
          }
          leaf mtu {
            type string;
          }
          leaf managed-configuration {
            type empty;
          }
          leaf other-stateful-configuration {
            type empty;
          }
          list prefix {
            // NCS patched for predictable order
            ordered-by user;
            key "ipv6-prefix";
            leaf ipv6-prefix {
              type string;
            }
            leaf preferred-lifetime {
              type string;
            }
            leaf valid-lifetime {
              type string;
            }
          }
          leaf reachable-time {
            type string;
          }
          leaf retransmit-time {
            type string;
          }
          leaf router-lifetime {
            type string;
          }
          leaf use-virtual-mac {
            type empty;
          }
          leaf shutdown {
            type string;
          }
        }
      }
      container mld {
        list interface {
          // NCS patched for predictable order
          ordered-by user;
          key "ip-int-name";
          leaf ip-int-name {
            type string;
          }
          leaf shutdown {
            type string;
          }
        }
        leaf shutdown {
          type string;
        }
      }
      container pcep {
        container pcc {
          leaf keepalive {
            type string;
          }
          leaf dead-timer {
            type string;
          }
          leaf max-srte-pce-init-lsps {
            type string;
          }
          leaf redelegation-timer {
            type string;
          }
          container state-timer {
            leaf seconds {
              tailf:cli-drop-node-name;
              type string;
            }
            leaf action {
              type string;
            }
          }
          leaf local-address {
            type string;
          }
          list peer {
            // NCS patched for predictable order
            ordered-by user;
            key "address";
            leaf address {
              type string;
            }
            leaf preference {
              type string;
            }
            leaf route-preference {
              type string;
            }
            leaf shutdown {
              type string;
            }
          }
          leaf shutdown {
            type string;
          }
        }
      }
      container route-next-hop-policy {
        list template {
          // NCS patched for predictable order
          ordered-by user;
          key "template-name";
          leaf template-name {
            type string;
          }
          leaf protection-type {
            type string;
          }
          leaf nh-type {
            type string;
          }
          leaf srlg-enable {
            type empty;
          }
        }
      }
      container policy-options {
        list prefix-list {
          // NCS patched for predictable order
          ordered-by user;
          key "name";
          leaf name {
            type string;
          }
          list prefix {
            // NCS patched for predictable order
            ordered-by user;
            tailf:cli-suppress-mode;
            key "ip-prefix";
            leaf ip-prefix {
              type string;
            }
            leaf exact {
              type empty;
            }
            leaf longer {
              type empty;
            }
            leaf through {
              type string;
            }
            leaf prefix-length-range {
              type string;
            }
          }
        }
        list community {
          // NCS patched for predictable order
          ordered-by user;
          key "name";
          leaf name {
            type string;
          }
          leaf-list members {
            // NCS patched for predictable order
            ordered-by user;
            type string;
          }
          container expression {
            leaf expression {
              tailf:cli-drop-node-name;
              type string;
            }
            leaf exact {
              type empty;
            }
          }
        }
        list alt-community {
          // NCS patched for predictable order
          ordered-by user;
          tailf:cli-suppress-mode;
          tailf:alt-name "community";
          key "name";
          leaf name {
            type string;
          }
          leaf-list members {
            // NCS patched for predictable order
            ordered-by user;
            type string;
          }
          container expression {
            leaf expression {
              tailf:cli-drop-node-name;
              type string;
            }
            leaf exact {
              type empty;
            }
          }
        }
        list damping {
          // NCS patched for predictable order
          ordered-by user;
          key "name";
          leaf name {
            type string;
          }
          leaf half-life {
            type string;
          }
          leaf max-suppress {
            type string;
          }
          leaf reuse {
            type string;
          }
          leaf suppress {
            type string;
          }
        }
        list policy-statement {
          // NCS patched for predictable order
          ordered-by user;
          key "name";
          leaf name {
            type string;
          }
          leaf description {
            type string;
          }
          container default-action {
            uses ncs_template_policy-options-default-action-grouping;
          }
          list entry {
            // NCS patched for predictable order
            ordered-by user;
            key "id";
            leaf id {
              type string;
            }
            leaf description {
              type string;
            }
            container conditional-expression {
              presence "true";
              leaf route-exists {
                type string;
              }
            }
            container action {
              presence "true";
              leaf mode {
                tailf:cli-drop-node-name;
                type string;
              }
              uses ncs_template_policy-option-action-params-grouping;
              uses ncs_template_policy-options-action-fc-grouping;
            }
            leaf action-reject {
              type empty;
            }
            container from {
              presence "true";
              leaf area {
                type string;
              }
              leaf as-path {
                type string;
              }
              container as-path-length {
                leaf length {
                  tailf:cli-drop-node-name;
                  type string;
                }
                leaf operator {
                  tailf:cli-drop-node-name;
                  type string;
                }
              }
              leaf as-path-group {
                type string;
              }
              container community {
                leaf expression {
                  type empty;
                }
                leaf community {
                  tailf:cli-drop-node-name;
                  type string;
                }
              }
              container community-count {
                leaf count {
                  tailf:cli-drop-node-name;
                  type string;
                }
                leaf op {
                  tailf:cli-drop-node-name;
                  type string;
                }
                leaf val {
                  tailf:cli-drop-node-name;
                  type string;
                }
              }
              leaf external {
                type empty;
              }
              leaf evpn-type {
                type string;
              }
              container metric {
                leaf value {
                  tailf:cli-drop-node-name;
                  type string;
                }
                leaf comparator {
                  tailf:cli-drop-node-name;
                  type string;
                }
              }
              leaf next-hop {
                type string;
              }
              leaf-list family {
                // NCS patched for predictable order
                ordered-by user;
                type ncs_template_family-names-type;
              }
              leaf group-address {
                type string;
              }
              leaf host-ip {
                type string;
              }
              leaf interface {
                type string;
              }
              leaf level {
                type string;
              }
              container neighbor {
                choice a {
                  leaf ip-address {
                    tailf:cli-drop-node-name;
                    type string;
                  }
                  leaf prefix-list {
                    type string;
                  }
                }
              }
              leaf origin {
                type string;
              }
              leaf origin-validation-state {
                type string;
              }
              leaf path-type {
                type string;
              }
              leaf policy {
                type string;
              }
              leaf-list prefix-list {
                // NCS patched for predictable order
                ordered-by user;
                type string;
              }
              container protocol {
                leaf-list protocol {
                  // NCS patched for predictable order
                  ordered-by user;
                  tailf:cli-drop-node-name;
                  type ncs_template_policy-protocol;
                }
                choice instance-all {
                  leaf instance {
                    type string;
                  }
                  leaf all {
                    type empty;
                  }
                }
              }
              leaf source-address {
                type string;
              }
              leaf state {
                type string;
              }
              leaf tag {
                type ncs_template_policy-options-tag;
              }
              leaf type {
                type string;
              }
            }
            container to {
              presence "true";
              leaf level {
                type string;
              }
              leaf neighbor {
                type string;
              }
              leaf-list prefix-list {
                // NCS patched for predictable order
                ordered-by user;
                type string;
              }
              leaf-list protocol {
                // NCS patched for predictable order
                ordered-by user;
                type string;
              }
            }
          }
        }
        list as-path {
          // NCS patched for predictable order
          ordered-by user;
          key "name";
          leaf name {
            type string;
          }
          leaf expression {
            type string;
          }
        }
        list alt-as-path {
          // NCS patched for predictable order
          ordered-by user;
          tailf:cli-suppress-mode;
          tailf:alt-name "as-path";
          key "name";
          leaf name {
            type string;
          }
          leaf expression {
            type string;
          }
          leaf regexp {
            tailf:cli-drop-node-name;
            type string;
          }
        }
        list as-path-group {
          // NCS patched for predictable order
          ordered-by user;
          key "name";
          leaf name {
            type string;
          }
          list entry {
            // NCS patched for predictable order
            ordered-by user;
            tailf:cli-suppress-mode;
            key "entry-id";
            leaf entry-id {
              type string;
            }
            leaf expression {
              type string;
            }
          }
        }
      }
      container pim {
        list interface {
          // NCS patched for predictable order
          ordered-by user;
          key "ip-int-name";
          leaf ip-int-name {
            type string;
          }
          leaf assert-period {
            type string;
          }
          container bfd-enable {
            presence "true";
            leaf bfd-enable {
              tailf:cli-drop-node-name;
              type string;
            }
          }
          leaf bsm-check-rtr-alert {
            type empty;
          }
          leaf hello-interval {
            type string;
          }
          leaf hello-multiplier {
            type string;
          }
          leaf improved-assert {
            type string;
          }
          leaf instant-prune-echo {
            type empty;
          }
          leaf ipv4-multicast-disable {
            type string;
          }
          leaf ipv6-multicast-disable {
            type string;
          }
          leaf max-groups {
            type string;
          }
          uses ncs_template_mcac-grouping;
          leaf multicast-senders {
            type string;
          }
          leaf-list p2mp-ldp-tree-join {
            // NCS patched for predictable order
            ordered-by user;
            type string;
          }
          leaf priority {
            type string;
          }
          container sticky-dr {
            leaf priority {
              type string;
            }
            leaf three-way-hello {
              type empty;
            }
            leaf tracking-support {
              type empty;
            }
          }
          leaf shutdown {
            type string;
          }
        }
        leaf enable-mdt-spt {
          type empty;
        }
        leaf ipv4-multicast-disable {
          type string;
        }
        leaf ipv6-multicast-disable {
          type string;
        }
        leaf lag-usage-optimization {
          type empty;
        }
        leaf multicast-fast-failover {
          type empty;
        }
        leaf multicast6-fast-failover {
          type empty;
        }
        container rp {
          list anycast {
            // NCS patched for predictable order
            ordered-by user;
            key "rp-ip-address";
            leaf rp-ip-address {
              type string;
            }
            list rp-set-peer {
              // NCS patched for predictable order
              ordered-by user;
              tailf:cli-suppress-mode;
              key "ip-address";
              leaf ip-address {
                tailf:cli-drop-node-name;
                type string;
              }
            }
          }
          leaf-list bootstrap-import {
            // NCS patched for predictable order
            ordered-by user;
            type string;
          }
          leaf-list bootstrap-export {
            // NCS patched for predictable order
            ordered-by user;
            type string;
          }
          container static {
            list address {
              // NCS patched for predictable order
              ordered-by user;
              key "ip-address";
              leaf ip-address {
                type string;
              }
              list group-prefix {
                // NCS patched for predictable order
                ordered-by user;
                tailf:cli-suppress-mode;
                key "grp-ip-addr";
                leaf grp-ip-addr {
                  tailf:cli-drop-node-name;
                  type string;
                }
              }
              leaf override {
                type empty;
              }
            }
          }
          container bsr-candidate {
            leaf address {
              type string;
            }
            leaf hash-mask-len {
              type string;
            }
            leaf priority {
              type string;
            }
            leaf shutdown {
              type string;
            }
          }
          container rp-candidate {
            leaf address {
              type string;
            }
            list group-range {
              // NCS patched for predictable order
              ordered-by user;
              tailf:cli-suppress-mode;
              key "grp-ip-addr";
              leaf grp-ip-addr {
                type string;
              }
            }
            leaf holdtime {
              type string;
            }
            leaf priority {
              type string;
            }
            leaf shutdown {
              type string;
            }
          }
        }
        leaf rpf-table {
          type string;
        }
        uses ncs_template_pim-common-grouping;
        container ssm-groups {
          list group-range {
            // NCS patched for predictable order
            ordered-by user;
            tailf:cli-suppress-mode;
            key "prefix";
            leaf prefix {
              type string;
            }
          }
        }
        leaf shutdown {
          type string;
        }
      }
      container sgt-qos {
        list application {
          // NCS patched for predictable order
          ordered-by user;
          tailf:cli-suppress-mode;
          key "app-name";
          leaf app-name {
            type string;
          }
          choice choice {
            leaf dscp {
              type string;
            }
            leaf dot1p {
              type string;
            }
          }
        }
        list dscp {
          // NCS patched for predictable order
          ordered-by user;
          tailf:cli-suppress-mode;
          key "dscp-name";
          leaf dscp-name {
            type ncs_template_dscp-type;
          }
          leaf fc {
            type ncs_template_fc-name;
          }
        }
      }
      container ttl-propagate {
        leaf vprn-local {
          type string;
        }
        leaf vprn-transit {
          type string;
        }
      }
      container twamp-light {
        container reflector {
          presence "true";
          leaf description {
            type string;
          }
          leaf udp-port {
            type string;
          }
          leaf shutdown {
            type string;
          }
          list prefix {
            // NCS patched for predictable order
            ordered-by user;
            leaf description {
              type string;
            }
            key "ip-prefix";
            leaf ip-prefix {
              type string;
            }
          }
        }
      }
      container weighted-ecmp {
        presence "true";
        leaf strict {
          type empty;
        }
      }
    }
    container aaa {
      leaf radius-coa-port {
        type string;
      }
      list radius-script-policy {
        // NCS patched for predictable order
        ordered-by user;
        key "policy-name";
        leaf policy-name {
          type ncs_template_string32;
        }
        leaf description {
          type string;
        }
        container primary {
          leaf script-url {
            type string;
          }
          leaf shutdown {
            type string;
          }
        }
      }
      list radius-server-policy {
        // NCS patched for predictable order
        ordered-by user;
        key "policy-name";
        leaf policy-name {
          type ncs_template_string32;
        }
        leaf description {
          type string;
        }
        leaf acct-on-off {
          type empty;
        }
        leaf acct-request-script-policy {
          type ncs_template_string32;
        }
        leaf python-policy {
          type ncs_template_string32;
        }
        leaf accept-script-policy {
          type ncs_template_string32;
        }
        leaf auth-request-script-policy {
          type ncs_template_string32;
        }
        container servers {
          leaf access-algorithm {
            type string;
          }
          container buffering {

            grouping acct-grouping {
              leaf min {
                type string;
              }
              leaf max {
                type string;
              }
              leaf lifetime {
                type string;
              }
            }
            container acct-interim {
              uses acct-grouping;
            }
            container acct-start {
              uses acct-grouping;
            }
            container acct-stop {
              uses acct-grouping;
            }
          }
          container health-check {
            container down-timeout {
              leaf min {
                type string;
              }
              leaf sec {
                type string;
              }
            }
          }
          container hold-down-time {
            leaf sec {
              type string;
            }
            leaf min {
              type string;
            }
            leaf hrs {
              type string;
            }
            leaf days {
              type string;
            }
          }
          leaf retry {
            type string;
          }
          container timeout {
            leaf min {
              type string;
            }
            leaf sec {
              type string;
            }
          }
          leaf router {
            type string;
          }
          list server {
            // NCS patched for predictable order
            ordered-by user;
            tailf:cli-suppress-mode;
            key "server-index";
            leaf server-index {
              type string;
            }
            leaf name {
              type ncs_template_string32;
            }
          }
          leaf source-address {
            type string;
          }
        }
      }
      list diameter-peer-policy {
        // NCS patched for predictable order
        ordered-by user;
        key "peer-policy-name";
        leaf peer-policy-name {
          type ncs_template_string32;
        }
        leaf-list applications {
          // NCS patched for predictable order
          ordered-by user;
          type string;
        }
        leaf origin-host {
          type string;
        }
        leaf origin-realm {
          type string;
        }
        leaf source-address {
          type string;
        }
        list peer {
          // NCS patched for predictable order
          ordered-by user;
          key "name";
          leaf name {
            type ncs_template_string32;
          }
          leaf destination-host {
            type string;
          }
          leaf destination-realm {
            type string;
          }
          leaf address {
            type string;
          }
          container transport {
            leaf tcp {
              type empty;
            }
            leaf port {
              type string;
            }
          }
          leaf shutdown {
            type string;
          }
        }
      }
    }
    container system {
      container alarms {
        leaf max-cleared {
          type string;
        }
        leaf shutdown {
          type string;
        }
      }
      list alarm-contact-input {
        // NCS patched for predictable order
        ordered-by user;
        key "id";
        leaf id {
          type string;
        }
        leaf description {
          type string;
        }
        leaf alarm-output-severity {
          type string;
        }
        leaf trigger-alarm-msg {
          type string;
        }
        leaf shutdown {
          type string;
        }
      }
      container alarm-contact-output {
        presence "true";
        leaf shutdown {
          type string;
        }
      }
      container bluetooth {
        list module {
          // NCS patched for predictable order
          ordered-by user;
          key "name";
          leaf name {
            type string;
          }
        }
        leaf power {
          type string;
        }
        leaf advertising-timeout {
          type string;
        }
      }
      container fp {
        container options {
          container mpls {
            container entropy-label {
              leaf shutdown {
                type string;
              }
            }
          }
          container services {
            container vpls-evpn-mpls {
              leaf shutdown {
                type string;
              }
            }
          }
          container qos {
            container bum-policers {
              leaf shutdown {
                type string;
              }
            }
            container dscp-transparency {
              leaf shutdown {
                type string;
              }
            }
            container fc-4-profile {
              leaf shutdown {
                type string;
              }
            }
          }
          container router {
            container ecmp {
              leaf shutdown {
                type string;
              }
            }
          }
        }
      }
      container grpc {
        leaf allow-unsecure-connection {
          type empty;
        }
        container gnmi {
          leaf auto-config-save {
            type empty;
          }
          leaf shutdown {
            type string;
          }
        }
        container rib-api {
          leaf shutdown {
            type string;
          }
        }
        container md-cli {
          leaf shutdown {
            type string;
          }
        }
        container tcp-keepalive {
          leaf shutdown {
            type string;
          }
        }
        leaf tls-server-profile {
          type string;
        }
        leaf shutdown {
          type string;
        }
      }
      container satellite {
        list port-template {
          // NCS patched for predictable order
          ordered-by user;
          key "name";
          leaf name {
            type string;
          }
          leaf sat-type {
            // NCS drop mandatory statement
            type string;
          }
          list port {
            // NCS patched for predictable order
            ordered-by user;
            key "port-id";
            leaf port-id {
              type string;
            }
            leaf role {
              type string;
            }
          }
          leaf shutdown {
            type string;
          }
        }
        list eth-sat {
          // NCS patched for predictable order
          ordered-by user;
          key "id";
          leaf id {
            type string;
          }
          leaf description {
            type string;
          }
          leaf mac-address {
            type ncs_template_ieee-mac;
          }
          container sat-type {
            leaf type {
              tailf:cli-drop-node-name;
              type string;
            }
            container dynamic-uplink {
              leaf uplink-distribution {
                type string;
              }
            }
          }
          leaf client-down-delay {
            type string;
          }
          leaf feature {
            type string;
          }
          leaf enable-console-access {
            type string;
          }
          leaf software-repository {
            type string;
          }
          leaf sync-e {
            type empty;
          }
          leaf ptp-tc {
            type empty;
          }
          list port-map {
            // NCS patched for predictable order
            ordered-by user;
            tailf:cli-suppress-mode;
            key "client-port-id";
            leaf client-port-id {
              type string;
            }
            leaf primary {
              type string;
            }
            leaf secondary {
              type string;
            }
          }
          leaf shutdown {
            type string;
          }
        }
      }
      container port-topology {
        list port {
          // NCS patched for predictable order
          ordered-by user;
          tailf:cli-suppress-mode;
          // NCS drop tailf-common:cli-diff-create-before statement
          key "port-id";
          leaf port-id {
            type string;
          }
          leaf to {
            type string;
          }
        }
      }
      list power-shelf {
        // NCS patched for predictable order
        ordered-by user;
        key "power-shelf-id";
        leaf power-shelf-id {
          type string;
        }
        leaf description {
          type string;
        }
        leaf power-shelf-type {
          type string;
        }
        list power-module {
          // NCS patched for predictable order
          ordered-by user;
          key "power-module-id";
          leaf power-module-id {
            type string;
          }
          leaf power-module-type {
            type string;
          }
          leaf shutdown {
            type string;
          }
        }
        leaf shutdown {
          type string;
        }
      }
      container ip {
        leaf enforce-unique-if-index {
          type empty;
        }
      }
      list file-transmission-profile {
        // NCS patched for predictable order
        ordered-by user;
        key "name";
        leaf name {
          type ncs_template_string32;
        }
        leaf ipv4-source-address {
          type string;
        }
        container router {
          choice router {
            leaf router-name {
              tailf:cli-drop-node-name;
              type ncs_template_router-type;
            }
            leaf service {
              type string;
            }
          }
        }
      }
      container ptp {
        list alternate-profile {
          // NCS patched for predictable order
          ordered-by user;
          key "alternate-profile-name";
          leaf alternate-profile-name {
            type string;
          }
          leaf shutdown {
            type string;
          }
        }
        list clock {
          // NCS patched for predictable order
          ordered-by user;
          key "clock-id";
          leaf clock-id {
            type string;
          }
          leaf clock-mda {
            type string;
          }
          container clock-type {
            choice clock-type {
              leaf ordinary {
                type string;
              }
              leaf boundary {
                type empty;
              }
              leaf transparent-e2e {
                type empty;
              }
            }
          }
          leaf domain {
            type string;
          }
          leaf dynamic-peers {
            type empty;
          }
          leaf priority1 {
            type string;
          }
          leaf priority2 {
            type string;
          }
          leaf profile {
            type string;
          }
          leaf source-interface {
            type string;
          }
          list ptp-port {
            // NCS patched for predictable order
            ordered-by user;
            key "port-id";
            leaf port-id {
              type string;
            }
            leaf anno-rx-timeout {
              type string;
            }
            leaf log-anno-interval {
              type string;
            }
            leaf log-sync-interval {
              type string;
            }
            list peer {
              // NCS patched for predictable order
              ordered-by user;
              key "peer-id";
              leaf peer-id {
                type string;
              }
              leaf description {
                type string;
              }
              leaf ip-address {
                type string;
              }
            }
            leaf unicast-negotiate {
              type string;
            }
            leaf shutdown {
              type string;
            }
          }
          leaf shutdown {
            type string;
          }
        }
        container clock-type {
          leaf type {
            tailf:cli-drop-node-name;
            type string;
          }
          leaf role {
            tailf:cli-drop-node-name;
            type string;
          }
        }
        leaf domain {
          type string;
        }
        leaf domain-alt1 {
          tailf:alt-name "domain";
          type string;
        }
        leaf domain-alt2 {
          tailf:alt-name "domain";
          type string;
        }
        leaf domain-alt3 {
          tailf:alt-name "domain";
          type string;
        }
        leaf profile {
          type string;
        }
        list peer {
          // NCS patched for predictable order
          ordered-by user;
          key "ip-address";
          leaf ip-address {
            type string;
          }
          leaf local-priority {
            type string;
          }
          leaf shutdown {
            type string;
          }
        }
        list port {
          // NCS patched for predictable order
          ordered-by user;
          key "port-id";
          leaf port-id {
            type string;
          }
          leaf alternate-profile {
            type string;
          }
          leaf master-only {
            type string;
          }
          leaf address {
            type string;
          }
          leaf local-priority {
            type string;
          }
          leaf shutdown {
            type string;
          }
        }
        leaf shutdown {
          type string;
        }
      }
      container resource-profile {
        container ingress-internal-tcam {
          presence "true";
          list eth-cfm {
            // NCS patched for predictable order
            ordered-by user;
            key "id";
            leaf id {
              type string;
            }
            leaf down-mep {
              type string;
            }
          }
          leaf qos-sap-egress-resource {
            type string;
          }
          list qos-sap-ingress-resource {
            // NCS patched for predictable order
            ordered-by user;
            key "id";
            leaf id {
              type string;
            }
          }
          leaf qos-network-ingress-resource {
            type string;
          }
          list acl-sap-ingress {
            // NCS patched for predictable order
            ordered-by user;
            key "id";
            leaf id {
              type string;
            }
          }
          container qos {
            presence "true";
          }
        }
        container egress-internal-tcam {
          presence "true";
          list qos-sap-egress-resource {
            // NCS patched for predictable order
            ordered-by user;
            key "id";
            leaf id {
              type string;
            }
          }
          list qos-sap-ingress-resource {
            // NCS patched for predictable order
            ordered-by user;
            key "id";
            leaf id {
              type string;
            }
          }
          list acl-sap-egress {
            // NCS patched for predictable order
            ordered-by user;
            key "id";
            leaf id {
              type string;
            }
          }
        }
        leaf g8032-control-sap-tags {
          type string;
        }
        container router {
          presence "true";
        }
        container decommission {
          presence "true";
        }
      }
      container resource {
        list ecmp-profile {
          // NCS patched for predictable order
          ordered-by user;
          tailf:cli-suppress-mode;
          key "id";
          leaf id {
            type string;
          }
          leaf type {
            tailf:cli-drop-node-name;
            type string;
          }
          leaf links {
            type string;
          }
          leaf groups {
            type string;
          }
        }
      }
      container atm {
        leaf atm-location-id {
          type string;
        }
        container oam {
          leaf loopback-period {
            type string;
          }
          leaf retry-down {
            type string;
          }
          leaf retry-up {
            type string;
          }
        }
      }
      leaf boot-bad-exec {
        type string;
      }
      leaf boot-good-exec {
        type string;
      }
      list chassis-mode {
        // NCS patched for predictable order
        ordered-by user;
        key "chassis-mode";
        leaf chassis-mode {
          type string;
        }
        leaf force {
          type empty;
        }
        list power-supply {
          // NCS patched for predictable order
          ordered-by user;
          tailf:cli-suppress-mode;
          key "power-supply-id power-supply-type";
          leaf power-supply-id {
            type string;
          }
          leaf power-supply-type {
            type string;
          }
        }
      }
      leaf clli-code {
        type string;
      }
      leaf config-backup {
        type string;
      }
      leaf contact {
        type string;
      }
      leaf coordinates {
        type string;
      }
      container cron {
        uses ncs_template_cron-schedule-grouping;
      }
      container dns {
        container address-pref {
          choice choice {
            leaf ipv4-only {
              type empty;
            }
            leaf ipv6-first {
              type empty;
            }
          }
        }
      }
      leaf enable-icmp-vse {
        type empty;
      }
      container ethernet {
        container efm-oam {
          leaf grace-tx-enable {
            type empty;
          }
        }
        leaf new-qinq-untagged-sap {
          type empty;
        }
      }
      leaf l4-load-balancing {
        type empty;
      }
      leaf lacp-system-priority {
        type string;
      }
      container lldp {
        leaf message-fast-tx {
          type string;
        }
        leaf message-fast-tx-init {
          type string;
        }
        leaf reinit-delay {
          type string;
        }
        leaf tx-credit-max {
          type string;
        }
        leaf tx-hold-multiplier {
          type string;
        }
        leaf tx-interval {
          type string;
        }
        leaf notification-interval {
          type string;
        }
        leaf shutdown {
          type string;
        }
      }
      container load-balancing {
        leaf l4-load-balancing {
          type empty;
        }
        container hash-poly {
          leaf ecmp {
            type string;
          }
          leaf lag {
            type string;
          }
        }
        leaf lsr-load-balancing {
          type string;
        }
        leaf mc-enh-load-balancing {
          type empty;
        }
        leaf service-id-lag-hashing {
          type empty;
        }
        leaf system-ip-load-balancing {
          type empty;
        }
        container hash-algorithm {
          list polynomial {
            // NCS patched for predictable order
            ordered-by user;
            tailf:cli-suppress-mode;
            key "ptype";
            leaf ptype {
              type string;
            }
            leaf pval {
              tailf:cli-drop-node-name;
              type string;
            }
          }
        }
      }
      leaf location {
        type string;
      }
      container login-control {
        leaf exponential-backoff {
          type empty;
        }
        container ftp {
          leaf inbound-max-sessions {
            type string;
          }
        }
        leaf idle-timeout {
          type string;
        }
        leaf login-banner {
          type empty;
        }
        container motd {
          choice choice {
            leaf url {
              type string;
            }
            leaf text {
              type string;
            }
          }
        }
        container pre-login-message {
          presence "present";
          leaf login-text-string {
            tailf:cli-drop-node-name;
            type string;
          }
          leaf name {
            type empty;
          }
        }
        container ssh {
          leaf disable-graceful-shutdown {
            type empty;
          }
          leaf inbound-max-sessions {
            type string;
          }
          leaf outbound-max-sessions {
            type string;
          }
          leaf ttl-security {
            type string;
          }
        }
        container telnet {
          leaf enable-graceful-shutdown {
            type empty;
          }
          leaf inbound-max-sessions {
            type string;
          }
          leaf outbound-max-sessions {
            type string;
          }
          leaf ttl-security {
            type string;
          }
        }
      }
      container loopback-no-svc-port {
        leaf mac-swap {
          type empty;
        }
        leaf port-id {
          tailf:cli-drop-node-name;
          type string;
        }
      }
      container lsr-load-balancing {
        choice choice {
          leaf lbl-only {
            type empty;
          }
          leaf lbl-ip {
            type empty;
          }
          leaf ip-only {
            type empty;
          }
        }
      }
      container management-interface {
        container remote-management {
          leaf shutdown {
            type string;
          }
        }
        container cli {
          container classic-cli {
            leaf allow-immediate {
              type string;
            }
          }
          leaf-list cli-engine {
            // NCS patched for predictable order
            ordered-by user;
            type string;
          }
          container md-cli {
            leaf auto-config-save {
              type empty;
            }
            container environment {
              container command-completion {
                leaf enter {
                  type string;
                }
                leaf space {
                  type string;
                }
                leaf tab {
                  type string;
                }
              }
              container console {
                leaf length {
                  type string;
                }
                leaf width {
                  type string;
                }
              }
              container message-severity-level {
                leaf cli {
                  type string;
                }
              }
              leaf more {
                type string;
              }
              container progress-indicator {
                leaf delay {
                  type string;
                }
                leaf shutdown {
                  type string;
                }
              }
              container prompt {
                leaf context {
                  type string;
                }
                leaf newline {
                  type string;
                }
                leaf timestamp {
                  type empty;
                }
                leaf uncommitted-changes-indicator {
                  type string;
                }
              }
              leaf time-display {
                type string;
              }
            }
          }
        }
        leaf configuration-mode {
          type string;
        }
        leaf schema-path {
          type string;
        }
        container yang-modules {
          leaf base-r13-modules {
            type string;
          }
          leaf nokia-modules {
            type string;
          }
          leaf nokia-submodules {
            type string;
          }
          leaf nokia-combined-modules {
            type string;
          }
        }
      }
      leaf mc-enh-load-balancing {
        type empty;
      }
      leaf mixed-mode {
        type empty;
      }
      leaf name {
        type string;
      }
      container netconf {
        leaf auto-config-save {
          type empty;
        }
        container capabilities {
          leaf candidate {
            type string;
          }
          leaf writable-running {
            type empty;
          }
        }
        leaf shutdown {
          type string;
        }
      }
      container persistence {
        container ancp {
          leaf description {
            type string;
          }
          leaf location {
            type string;
          }
        }
        container application-assurance {
          leaf description {
            type string;
          }
          leaf location {
            type string;
          }
        }
        container dhcp-server {
          leaf description {
            type string;
          }
          leaf location {
            type string;
          }
        }
        container nat-port-forwarding {
          leaf description {
            type string;
          }
          leaf location {
            type string;
          }
        }
        container subscriber-mgmt {
          leaf description {
            type string;
          }
          leaf location {
            type string;
          }
        }
      }
      list power-module {
        // NCS patched for predictable order
        ordered-by user;
        key "power-module-id";
        leaf power-module-id {
          type string;
        }
        leaf power-module-type {
          type string;
        }
        leaf shutdown {
          type string;
        }
      }
      container power-management {
        list peq {
          // NCS patched for predictable order
          ordered-by user;
          key "id";
          leaf id {
            type string;
          }
          leaf chassis {
            type string;
          }
          leaf peq-type {
            type string;
          }
          leaf shutdown {
            type string;
          }
        }
        leaf mode {
          type string;
        }
        leaf power-safety-alert {
          type string;
        }
        leaf power-safety-level {
          type string;
        }
      }
      container script-control {
        list script {
          // NCS patched for predictable order
          ordered-by user;
          key "script-name";
          leaf script-name {
            type ncs_template_string32;
          }
          leaf owner {
            type ncs_template_string32;
          }
          leaf description {
            type string;
          }
          leaf location {
            type string;
          }
          leaf shutdown {
            type string;
          }
        }
        list script-policy {
          // NCS patched for predictable order
          ordered-by user;
          key "script-name";
          leaf script-name {
            type ncs_template_string32;
          }
          leaf owner {
            type ncs_template_string32;
          }
          leaf expire-time {
            type ncs_template_expire-time;
          }
          leaf lifetime {
            type ncs_template_expire-time;
          }
          leaf max-completed {
            type string;
          }
          leaf results {
            type string;
          }
          container script {
            leaf script-name {
              tailf:cli-drop-node-name;
              type ncs_template_string32;
            }
            leaf owner {
              type ncs_template_string32;
            }
          }
          leaf shutdown {
            type string;
          }
        }
      }
      container snmp {
        leaf engineID {
          type string;
        }
        leaf general-port {
          type string;
        }
        leaf packet-size {
          type string;
        }
        container streaming {
          leaf shutdown {
            type string;
          }
        }
        leaf shutdown {
          type string;
        }
      }
      container rollback {
        leaf local-max-checkpoints {
          type string;
        }
        leaf remote-max-checkpoints {
          type string;
        }
        leaf rescue-location {
          type string;
        }
        leaf rollback-location {
          type string;
        }
      }
      leaf system-ip-load-balancing {
        type empty;
      }
      container time {
        leaf prefer-local-time {
          type empty;
        }
        container ntp {
          leaf authentication-check {
            type string;
          }
          list authentication-key {
            // NCS patched for predictable order
            ordered-by user;
            tailf:cli-suppress-mode;
            key "key-id";
            leaf key-id {
              type string;
            }
            leaf key {
              type string;
            }
            leaf hash {
              tailf:cli-drop-node-name;
              type ncs_template_hash-method;
            }
            leaf type {
              type string;
            }
          }
          container ntp-server {
            presence "true";
            leaf authenticate {
              type empty;
            }
          }
          list server {
            // NCS patched for predictable order
            ordered-by user;
            tailf:cli-suppress-mode;
            key "address";
            leaf address {
              type string;
            }
            leaf key {
              type string;
            }
            leaf router {
              type ncs_template_router-type;
            }
            leaf version {
              type string;
            }
            leaf prefer {
              type empty;
            }
          }
          leaf shutdown {
            type string;
          }
        }
        container sntp {
          leaf broadcast-client {
            type empty;
          }
          list server-address {
            // NCS patched for predictable order
            ordered-by user;
            tailf:cli-suppress-mode;
            key "ip";
            leaf ip {
              type string;
            }
            leaf version {
              type string;
            }
            leaf mode {
              tailf:cli-drop-node-name;
              type string;
            }
            leaf interval {
              type string;
            }
          }
          leaf shutdown {
            type string;
          }
        }
        container zone {
          leaf name {
            tailf:cli-drop-node-name;
            type string;
          }
          leaf time {
            tailf:cli-drop-node-name;
            type string;
          }
        }
        list dst-zone {
          // NCS patched for predictable order
          ordered-by user;
          key "name";
          leaf name {
            type string;
          }
          container start {
            uses ncs_template_time-stamp;
          }
          container end {
            uses ncs_template_time-stamp;
          }
          leaf offset {
            type string;
          }
        }
      }
      container thresholds {
        container rmon {
          list alarm {
            // NCS patched for predictable order
            ordered-by user;
            tailf:cli-suppress-mode;
            key "rmon-alarm-id";
            leaf rmon-alarm-id {
              type string;
            }
            leaf variable-oid {
              type string;
            }
            leaf interval {
              type string;
            }
            leaf sample-type {
              tailf:cli-drop-node-name;
              type string;
            }
            leaf startup-alarm {
              type string;
            }
            leaf rising-event {
              type string;
            }
            leaf rising-threshold {
              type string;
            }
            leaf falling-event {
              type string;
            }
            leaf falling-threshold {
              type string;
            }
            leaf owner {
              type string;
            }
          }
          list event {
            // NCS patched for predictable order
            ordered-by user;
            tailf:cli-suppress-mode;
            key "rmon-event-id";
            leaf rmon-event-id {
              type string;
            }
            leaf event-type {
              tailf:cli-drop-node-name;
              type string;
            }
            leaf description {
              type string;
            }
            leaf owner {
              type string;
            }
          }
        }

        grouping memory-use-grouping {
          leaf rising-threshold {
            type string;
          }
          leaf falling-threshold {
            type string;
          }
          leaf interval {
            type string;
          }
          leaf rmon-event-type {
            tailf:cli-drop-node-name;
            type string;
          }
          leaf startup-alarm {
            type string;
          }
        }
        container memory-use-alarm {
          uses memory-use-grouping;
        }
        container memory-use-warn {
          uses memory-use-grouping;
        }

        grouping cflash-cap-grouping {
          leaf cflash-id {
            type string;
          }
          leaf rising-threshold {
            type string;
          }
          leaf falling-threshold {
            type string;
          }
          leaf interval {
            type string;
          }
          leaf rmon-event-type {
            tailf:cli-drop-node-name;
            type string;
          }
          leaf startup-alarm {
            type string;
          }
        }
        list cflash-cap-alarm {
          // NCS patched for predictable order
          ordered-by user;
          tailf:cli-suppress-mode;
          key "cflash-id";
          uses cflash-cap-grouping;
        }
        list cflash-cap-alarm-pct {
          // NCS patched for predictable order
          ordered-by user;
          tailf:cli-suppress-mode;
          key "cflash-id";
          uses cflash-cap-grouping;
        }
        list cflash-cap-warn {
          // NCS patched for predictable order
          ordered-by user;
          tailf:cli-suppress-mode;
          key "cflash-id";
          uses cflash-cap-grouping;
        }
        container kb-memory-use-alarm {
          leaf rising-threshold {
            type string;
          }
          leaf falling-threshold {
            type string;
          }
          leaf interval {
            type string;
          }
          leaf rmon-event-type {
            tailf:cli-drop-node-name;
            type string;
          }
          leaf startup-alarm {
            type string;
          }
        }
      }
      list power-supply {
        // NCS patched for predictable order
        ordered-by user;
        tailf:cli-suppress-mode;
        key "power-supply-id";
        leaf power-supply-id {
          type string;
        }
        leaf type {
          tailf:cli-drop-node-name;
          type string;
        }
        leaf ac_type {
          tailf:cli-drop-node-name;
          type string;
        }
      }
      container qos {

        grouping access-rate-grouping {
          leaf value {
            tailf:cli-drop-node-name;
            type string;
          }
          leaf unshaped-sap-cir {
            type string;
          }
        }
        container access-ingress-aggregate-rate {
          uses access-rate-grouping;
        }
        container network-ingress-aggregate-rate {
          uses access-rate-grouping;
        }
      }
      container vsd {
        leaf system-id {
          // NCS drop tailf-common:cli-diff-create-before statement
          type string;
        }
      }
      container xmpp {
        list server {
          // NCS patched for predictable order
          ordered-by user;
          key "name";
          leaf name {
            type string;
          }
          leaf domain-name {
            type string;
          }
          leaf router {
            type string;
          }
          leaf shutdown {
            type string;
          }
        }
      }
      container security {
        container management {
          leaf allow-ftp {
            type string;
          }
          leaf allow-grpc {
            type string;
          }
          leaf allow-netconf {
            type string;
          }
          leaf allow-ssh {
            type string;
          }
          leaf allow-telnet {
            type string;
          }
          leaf allow-telnet6 {
            type string;
          }
        }
        container hash-control {
          leaf read-version {
            type string;
          }
          leaf write-version {
            type string;
          }
        }
        list keychain {
          // NCS patched for predictable order
          ordered-by user;
          key "keychain-name";
          leaf keychain-name {
            type string;
          }
          container direction {
            container bi {
              list entry {
                // NCS patched for predictable order
                ordered-by user;
                key "id";
                leaf id {
                  type string;
                }
                leaf key {
                  type string;
                }
                leaf method {
                  tailf:cli-drop-node-name;
                  type ncs_template_hash-method;
                }
                leaf algorithm {
                  type string;
                }
                leaf begin-time {
                  type string;
                }
                leaf option {
                  type string;
                }
                leaf tolerance {
                  type string;
                }
                leaf shutdown {
                  type string;
                }
              }
            }
          }
          leaf description {
            type string;
          }
          leaf shutdown {
            type string;
          }
        }
        container management-interface {
          container classic-cli {
            leaf read-algorithm {
              type ncs_template_hash-hash2-all-hash;
            }
            leaf write-algorithm {
              type ncs_template_hash-hash2-cleartext;
            }
          }
          container grpc {
            leaf hash-algorithm {
              type ncs_template_hash-hash2-cleartext;
            }
          }
          container md-cli {
            leaf hash-algorithm {
              type ncs_template_hash-hash2-cleartext;
            }
          }
          container netconf {
            leaf hash-algorithm {
              type ncs_template_hash-hash2-cleartext;
            }
          }
        }
        container pki {
          container certificate-expiration-warning {
            leaf hours {
              tailf:cli-drop-node-name;
              type string;
            }
            leaf repeat {
              type string;
            }
          }
          container crl-expiration-warning {
            leaf hours {
              tailf:cli-drop-node-name;
              type string;
            }
            leaf repeat {
              type string;
            }
          }
          list ca-profile {
            // NCS patched for predictable order
            ordered-by user;
            key "name";
            leaf name {
              type ncs_template_string32;
            }
            leaf description {
              type string;
            }
            leaf cert-file {
              type string;
            }
            container cmpv2 {
              leaf accept-unprotected-errormsg {
                type empty;
              }
              leaf accept-unprotected-pkiconf {
                type empty;
              }
              leaf same-recipnonce-for-pollreq {
                type empty;
              }
              leaf always-set-sender-for-ir {
                type empty;
              }
              leaf http-response-timeout {
                type string;
              }
              container key-list {
                list key {
                  // NCS patched for predictable order
                  ordered-by user;
                  tailf:cli-suppress-mode;
                  key "reference";
                  leaf password {
                    tailf:cli-drop-node-name;
                    type string;
                  }
                  leaf hashing {
                    tailf:cli-drop-node-name;
                    type string;
                  }
                  leaf reference {
                    type string;
                  }
                }
              }
              leaf url {
                type string;
              }
              leaf response-signing-cert {
                type string;
              }
            }
            leaf crl-file {
              type string;
            }
            leaf revocation-check {
              type string;
            }
            container auto-crl-update {
              container pre-update-time {
                leaf days {
                  type string;
                }
                leaf hrs {
                  type string;
                }
              }
              leaf schedule-type {
                type string;
              }
              container crl-urls {
                list url-entry {
                  // NCS patched for predictable order
                  ordered-by user;
                  key "entry-id";
                  leaf entry-id {
                    type string;
                  }
                  leaf file-transmission-profile {
                    type ncs_template_string32;
                  }
                  leaf url {
                    type string;
                  }
                }
              }
              leaf shutdown {
                type string;
              }
            }
            leaf shutdown {
              type string;
            }
          }
        }
        list profile {
          // NCS patched for predictable order
          ordered-by user;
          key "name";
          leaf name {
            type string;
          }
          leaf default-action {
            type string;
          }
          list entry {
            // NCS patched for predictable order
            ordered-by user;
            key "entry-id";
            leaf entry-id {
              type string;
            }
            leaf action {
              type string;
            }
            leaf description {
              type string;
            }
            leaf match {
              type string;
            }
          }
          leaf li {
            type empty;
          }
          container netconf {
            container base-op-authorization {
              leaf action {
                type empty;
              }
              leaf cancel-commit {
                type empty;
              }
              leaf close-session {
                type empty;
              }
              leaf commit-op {
                type empty;
              }
              leaf commit {
                type empty;
              }
              leaf copy-config {
                type empty;
              }
              leaf create-subscription {
                type empty;
              }
              leaf delete-config {
                type empty;
              }
              leaf discard-changes {
                type empty;
              }
              leaf edit-config {
                type empty;
              }
              leaf get {
                type empty;
              }
              leaf get-config {
                type empty;
              }
              leaf get-data {
                type empty;
              }
              leaf get-schema {
                type empty;
              }
              leaf kill-session {
                type empty;
              }
              leaf lock {
                type empty;
              }
              leaf validate {
                type empty;
              }
            }
          }
          container grpc {
            container rpc-authorization {
              leaf gnoi-cert-mgmt-rotate {
                type string;
              }
              leaf gnoi-cert-mgmt-install {
                type string;
              }
              leaf gnoi-cert-mgmt-getcert {
                type string;
              }
              leaf gnoi-cert-mgmt-revoke {
                type string;
              }
              leaf gnoi-cert-mgmt-cangenerate {
                type string;
              }
              leaf gnoi-file-get {
                type string;
              }
              leaf gnoi-file-put {
                type string;
              }
              leaf gnoi-file-stat {
                type string;
              }
              leaf gnoi-file-remove {
                type string;
              }
              leaf gnoi-system-setpackage {
                type string;
              }
              leaf gnoi-system-switchcontrolprocessor {
                type string;
              }
              leaf gnoi-system-reboot {
                type string;
              }
              leaf gnoi-system-rebootstatus {
                type string;
              }
              leaf gnoi-system-cancelreboot {
                type string;
              }
              leaf gnmi-capabilities {
                type string;
              }
              leaf gnmi-get {
                type string;
              }
              leaf gnmi-set {
                type string;
              }
              leaf gnmi-subscribe {
                type string;
              }
              leaf md-cli-session {
                type string;
              }
              leaf rib-api-modify {
                type string;
              }
              leaf rib-api-getversion {
                type string;
              }
            }
          }
          leaf ssh-max-sessions {
            type string;
          }
        }
        container password {
          container admin-password {
            leaf password {
              tailf:cli-drop-node-name;
              type string;
            }
            leaf scheme {
              tailf:cli-drop-node-name;
              type ncs_template_hash-method;
            }
          }
          leaf aging {
            type string;
          }
          container complexity-rules {
            leaf minimum-length {
              type string;
            }
            container required {
              leaf lowercase {
                type string;
              }
              leaf uppercase {
                type string;
              }
              leaf numeric {
                type string;
              }
              leaf special-character {
                type string;
              }
            }
            leaf allow-user-name {
              type empty;
            }
          }
          container health-check {
            leaf interval {
              type string;
            }
            leaf no {
              type empty;
            }
          }
          container health-check-alt {
            tailf:alt-name "health-check";
            leaf interval {
              type string;
            }
          }
          leaf-list authentication-order {
            // NCS patched for predictable order
            ordered-by user;
            type string;
          }
          container attempts {
            leaf count {
              tailf:cli-drop-node-name;
              type string;
            }
            leaf time {
              type string;
            }
            leaf lockout {
              type string;
            }
          }
        }
        container radius {
          leaf authorization {
            type empty;
          }
          leaf accounting {
            type empty;
          }
          list server {
            // NCS patched for predictable order
            ordered-by user;
            tailf:cli-suppress-mode;
            key "server-index";
            leaf server-index {
              type string;
            }
            leaf address {
              // NCS drop mandatory statement
              type string;
            }
            leaf secret {
              // NCS drop mandatory statement
              type string;
            }
            leaf type {
              tailf:cli-drop-node-name;
              type ncs_template_hash-method;
            }
          }
          leaf shutdown {
            type string;
          }
        }
        container tech-support {
          leaf ts-location {
            type string;
          }
        }
        container tls {
          list cert-profile {
            // NCS patched for predictable order
            ordered-by user;
            key "profile-name";
            leaf profile-name {
              type string;
            }
            list entry {
              // NCS patched for predictable order
              ordered-by user;
              // NCS drop tailf-common:cli-diff-create-before statement
              key "entry-id";
              leaf entry-id {
                type string;
              }
              leaf cert {
                type string;
              }
              leaf key {
                type string;
              }
              container send-chain {
                list ca-profile {
                  // NCS patched for predictable order
                  ordered-by user;
                  tailf:cli-suppress-mode;
                  key "profile";
                  leaf profile {
                    type ncs_template_string32;
                  }
                }
              }
            }
            leaf shutdown {
              type string;
            }
          }
          list server-cipher-list {
            // NCS patched for predictable order
            ordered-by user;
            key "name";
            leaf name {
              type string;
            }
            list cipher {
              // NCS patched for predictable order
              ordered-by user;
              tailf:cli-suppress-mode;
              key "index";
              leaf index {
                type string;
              }
              leaf name {
                type string;
              }
            }
          }
          list server-tls-profile {
            // NCS patched for predictable order
            ordered-by user;
            key "name";
            leaf name {
              type string;
            }
            leaf cert-profile {
              type string;
            }
            leaf cipher-list {
              type string;
            }
            leaf shutdown {
              type string;
            }
          }
        }
        container tacplus {
          container accounting {
            presence "true";
            leaf record-type {
              type string;
            }
          }
          container authorization {
            presence "true";
            leaf use-prix-lvl {
              type empty;
            }
          }
          leaf interactive-authentication {
            type empty;
          }
          container priv-lvl-map {
            list priv-lvl {
              // NCS patched for predictable order
              ordered-by user;
              tailf:cli-suppress-mode;
              key "lvl";
              leaf lvl {
                type string;
              }
              leaf user-profile {
                tailf:cli-drop-node-name;
                type string;
              }
            }
          }
          leaf route-preference {
            type string;
          }
          list server {
            // NCS patched for predictable order
            ordered-by user;
            tailf:cli-suppress-mode;
            key "server-index";
            leaf server-index {
              type string;
            }
            leaf address {
              type string;
            }
            leaf secret {
              type string;
            }
            leaf hash {
              tailf:cli-drop-node-name;
              type ncs_template_hash-method;
            }
            leaf port {
              type string;
            }
          }
          leaf timeout {
            type string;
          }
          leaf use-default-template {
            type empty;
          }
          leaf shutdown {
            type string;
          }
        }
        leaf telnet-server {
          type empty;
        }
        leaf telnet6-server {
          type empty;
        }
        leaf ftp-server {
          type empty;
        }
        leaf per-peer-queuing {
          type empty;
        }
        container snmp {
          container access {
            list group {
              // NCS patched for predictable order
              ordered-by user;
              tailf:cli-suppress-mode;
              key "name security-model security-level";
              leaf name {
                type string;
              }
              leaf security-model {
                type string;
              }
              leaf security-level {
                type string;
              }
              container context {
                leaf context-name {
                  tailf:cli-drop-node-name;
                  type string;
                }
                leaf match {
                  tailf:cli-drop-node-name;
                  type string;
                }
                uses read-write-notify;
              }
              container read {
                tailf:cli-drop-node-name;
                uses read-write-notify;
              }

              grouping read-write-notify {
                leaf read {
                  type ncs_template_string32;
                }
                leaf write {
                  type ncs_template_string32;
                }
                leaf notify {
                  type ncs_template_string32;
                }
              }
            }
          }
          list src-access-list {
            // NCS patched for predictable order
            ordered-by user;
            key "list-name";
            leaf list-name {
              type ncs_template_string32;
            }
            list src-host {
              // NCS patched for predictable order
              ordered-by user;
              tailf:cli-suppress-mode;
              key "name";
              leaf name {
                type string;
              }
              leaf address {
                type string;
              }
            }
          }
          uses ncs_template_snmp-community-grouping;
          list usm-community {
            // NCS patched for predictable order
            ordered-by user;
            tailf:cli-suppress-mode;
            key "name type";
            leaf name {
              type string;
            }
            leaf type {
              tailf:cli-drop-node-name;
              type ncs_template_hash-method;
            }
            leaf group {
              type string;
            }
            leaf src-access-list {
              type ncs_template_string32;
            }
          }
          container attempts {
            leaf count {
              tailf:cli-drop-node-name;
              type string;
            }
            leaf time {
              type string;
            }
            leaf lockout {
              type string;
            }
          }
          list view {
            // NCS patched for predictable order
            ordered-by user;
            key "name subtree";
            leaf name {
              type ncs_template_string32;
            }
            leaf subtree {
              type string;
            }
            container mask {
              leaf mask-value {
                tailf:cli-drop-node-name;
                type string;
              }
              leaf type {
                type string;
              }
            }
          }
        }
        container source-address {
          list application {
            // NCS patched for predictable order
            ordered-by user;
            tailf:cli-suppress-mode;
            key "name";
            leaf name {
              type ncs_template_net-application;
            }
            leaf address {
              tailf:cli-drop-node-name;
              type string;
            }
          }
          list application6 {
            // NCS patched for predictable order
            ordered-by user;
            tailf:cli-suppress-mode;
            key "name";
            leaf name {
              type ncs_template_net-application;
            }
            leaf address {
              tailf:cli-drop-node-name;
              type string;
            }
          }
        }
        container ssh {
          leaf preserve-key {
            type empty;
          }
          leaf server-shutdown {
            type empty;
          }
          container key-re-exchange {
            container server {
              leaf mbytes {
                type string;
              }
              leaf minutes {
                type string;
              }
              leaf shutdown {
                type string;
              }
            }
            container client {
              leaf mbytes {
                type string;
              }
              leaf minutes {
                type string;
              }
              leaf shutdown {
                type string;
              }
            }
          }
          leaf permit-empty-passwords {
            type string;
          }
          leaf version {
            type string;
          }

          grouping cipher-list-grouping {
            list cipher {
              // NCS patched for predictable order
              ordered-by user;
              tailf:cli-suppress-mode;
              key "index";
              leaf index {
                type string;
              }
              leaf name {
                type string;
              }
            }
          }
          list client-cipher-list {
            // NCS patched for predictable order
            ordered-by user;
            key "protocol-version";
            uses cipher-list-grouping;
            leaf protocol-version {
              type string;
            }
          }
          container client-cipher-list-alt {
            tailf:alt-name "client-cipher-list";
            uses cipher-list-grouping;
          }
          list server-cipher-list {
            // NCS patched for predictable order
            ordered-by user;
            key "protocol-version";
            leaf protocol-version {
              type string;
            }
            uses cipher-list-grouping;
          }
          container server-cipher-list-alt {
            tailf:alt-name "server-cipher-list";
            uses cipher-list-grouping;
          }
          container server-kex-list {
            list kex {
              // NCS patched for predictable order
              ordered-by user;
              tailf:cli-suppress-mode;
              key "kex-id";
              unique "name";
              leaf kex-id {
                type string;
              }
              leaf name {
                type string;
              }
            }
          }
          container client-kex-list {
            list kex {
              // NCS patched for predictable order
              ordered-by user;
              tailf:cli-suppress-mode;
              key "kex-id";
              unique "name";
              leaf kex-id {
                type string;
              }
              leaf name {
                type string;
              }
            }
          }
          container server-mac-list {
            presence "true";
            list mac {
              // NCS patched for predictable order
              ordered-by user;
              tailf:cli-suppress-mode;
              key "index";
              leaf index {
                type string;
              }
              leaf name {
                type string;
              }
            }
          }
          container client-mac-list {
            presence "true";
            list mac {
              // NCS patched for predictable order
              ordered-by user;
              tailf:cli-suppress-mode;
              key "index";
              leaf index {
                type string;
              }
              leaf name {
                type string;
              }
            }
          }
        }
        list user-template {
          // NCS patched for predictable order
          ordered-by user;
          key "user-template-id";
          leaf user-template-id {
            type string;
          }
          leaf-list access {
            // NCS patched for predictable order
            ordered-by user;
            type string;
          }
          leaf profile {
            type string;
          }
        }
        list user {
          // NCS patched for predictable order
          ordered-by user;
          key "user-id";
          leaf user-id {
            type string;
          }
          leaf-list access {
            // NCS patched for predictable order
            ordered-by user;
            type string;
          }
          container console {
            leaf cannot-change-password {
              type empty;
            }
            leaf login-exec {
              type string;
            }
            container disable {
              leaf member {
                type string;
              }
            }
            list member {
              // NCS patched for predictable order
              ordered-by user;
              tailf:cli-suppress-mode;
              key "name";
              leaf name {
                type string;
              }
            }
            leaf new-password-at-login {
              type empty;
            }
          }
          leaf home-directory {
            type string;
          }
          container password {
            leaf id {
              tailf:cli-drop-node-name;
              type string;
            }
            leaf method {
              tailf:cli-drop-node-name;
              type ncs_template_hash-method;
            }
          }
          leaf restricted-to-home {
            type empty;
          }
          container public-keys {
            container rsa {
              list rsa-key {
                // NCS patched for predictable order
                ordered-by user;
                key "rsa-public-key-id";
                leaf rsa-public-key-id {
                  type string;
                }
                leaf description {
                  type string;
                }
                leaf key-value {
                  type string;
                }
              }
            }
            container ecdsa {
              list ecdsa-key {
                // NCS patched for predictable order
                ordered-by user;
                key "rsa-public-key-id";
                leaf rsa-public-key-id {
                  type string;
                }
                leaf description {
                  type string;
                }
                leaf key-value {
                  type string;
                }
              }
            }
          }
          list rsa-key {
            // NCS patched for predictable order
            ordered-by user;
            tailf:cli-suppress-mode;
            key "key-id";
            leaf key-id {
              type string;
            }
            leaf key {
              tailf:cli-drop-node-name;
              type string;
            }
          }
          container snmp {
            container authentication {
              leaf none {
                type empty;
              }
              leaf hash {
                type empty;
              }
              leaf hash2 {
                type empty;
              }
              leaf auth-type {
                tailf:cli-drop-node-name;
                type string;
              }
              leaf key-1 {
                tailf:cli-drop-node-name;
                type string;
              }
              leaf privacy {
                type string;
              }
              leaf key-2 {
                tailf:cli-drop-node-name;
                type string;
              }
              leaf hashval {
                tailf:cli-drop-node-name;
                type string;
              }
            }
            leaf group {
              type string;
            }
          }
        }
        container disable {
          leaf user {
            type string;
          }
        }
        container cpu-protection {
          leaf link-specific-rate {
            type string;
          }
          list policy {
            // NCS patched for predictable order
            ordered-by user;
            key "policy-id";
            leaf policy-id {
              type string;
            }
            leaf overall-rate {
              type string;
            }
            leaf out-profile-rate {
              type string;
            }
            leaf description {
              type string;
            }
            leaf per-source-rate {
              type string;
            }
          }
          container protocol-protection {
            presence "true";
            leaf allow-sham-links {
              type empty;
            }
            leaf block-pim-tunneled {
              type empty;
            }
          }
          leaf port-overall-rate {
            type string;
          }
        }
        container dist-cpu-protection {
          list policy {
            // NCS patched for predictable order
            ordered-by user;
            key "policy-id";
            leaf policy-id {
              type string;
            }
            leaf description {
              type string;
            }
            leaf type {
              type string;
            }
            list static-policer {
              // NCS patched for predictable order
              ordered-by user;
              key "policy-name";
              leaf policy-name {
                type string;
              }
              leaf description {
                type string;
              }
              container rate {
                choice rate {
                  container kbps {
                    leaf kilobits-per-second {
                      tailf:cli-drop-node-name;
                      type string;
                    }
                    leaf mbs {
                      type string;
                    }
                    leaf unit {
                      tailf:cli-drop-node-name;
                      type string;
                    }
                  }
                  container packets {
                    leaf ppi {
                      tailf:cli-drop-node-name;
                      type string;
                    }
                    leaf within {
                      type string;
                    }
                    leaf initial-delay {
                      type string;
                    }
                  }
                }
              }
              container exceed-action {

                grouping hold-down-grouping {
                  leaf hold-down {
                    type string;
                  }
                }
                choice exceed-action {
                  container discard {
                    presence "true";
                    uses hold-down-grouping;
                  }
                  container low-priority {
                    presence "true";
                    uses hold-down-grouping;
                  }
                }
              }
            }
            list protocol {
              // NCS patched for predictable order
              ordered-by user;
              key "name";
              leaf name {
                type string;
              }
              container enforcement {
                leaf policy-type {
                  tailf:cli-drop-node-name;
                  type string;
                }
                leaf policy-name {
                  tailf:cli-drop-node-name;
                  type string;
                }
              }
            }
          }
        }
        container cpm-filter {
          leaf default-action {
            type string;
          }
          container ip-filter {
            list entry {
              // NCS patched for predictable order
              ordered-by user;
              key "entry-id";
              leaf entry-id {
                type string;
              }
              container action {
                choice action-choice {
                  leaf drop {
                    type empty;
                  }
                  leaf accept {
                    type empty;
                  }
                  leaf queue {
                    type string;
                  }
                }
              }
              leaf description {
                type string;
              }
              leaf log {
                type string;
              }
              container match {
                presence "true";
                leaf protocol {
                  type ncs_template_protocol;
                }
                leaf dscp {
                  type ncs_template_dscp-type;
                }
                container dst-ip {
                  uses ncs_template_filter-match-ip-grouping;
                }
                container dst-port {
                  uses ncs_template_cpm-filter-match-port-grouping;
                }
                leaf fragment {
                  type string;
                }
                leaf icmp-code {
                  type string;
                }
                leaf icmp-type {
                  type ncs_template_icmp-type;
                }
                container ip-option {
                  leaf value {
                    tailf:cli-drop-node-name;
                    type string;
                  }
                  leaf mask {
                    tailf:cli-drop-node-name;
                    type string;
                  }
                }
                leaf multiple-option {
                  type string;
                }
                leaf option-present {
                  type string;
                }
                container port {
                  uses ncs_template_cpm-filter-match-port-grouping;
                }
                leaf router {
                  type string;
                }
                container src-ip {
                  uses ncs_template_filter-match-ip-grouping;
                }
                container src-port {
                  uses ncs_template_cpm-filter-match-port-grouping;
                }
                leaf tcp-ack {
                  type string;
                }
                leaf tcp-syn {
                  type string;
                }
              }
            }
            leaf shutdown {
              type string;
            }
          }
          container ipv6-filter {
            list entry {
              // NCS patched for predictable order
              ordered-by user;
              key "entry-id";
              leaf entry-id {
                type string;
              }
              container action {
                choice action-choice {
                  leaf drop {
                    type empty;
                  }
                  leaf accept {
                    type empty;
                  }
                  leaf queue {
                    type string;
                  }
                }
              }
              leaf description {
                type string;
              }
              leaf log {
                type string;
              }
              container match {
                presence "true";
                leaf fragment {
                  type string;
                }
                leaf next-header {
                  type ncs_template_protocol;
                }
                leaf dscp {
                  type ncs_template_dscp-type;
                }
                container dst-ip {
                  uses ncs_template_filter-match-ipv6-grouping;
                }
                container dst-port {
                  uses ncs_template_cpm-filter-match-port-grouping;
                }
                leaf flow-label {
                  type string;
                }
                leaf hop-by-hop-opt {
                  type string;
                }
                leaf icmp-code {
                  type string;
                }
                leaf icmp-type {
                  type ncs_template_icmpv6-type;
                }
                container port {
                  uses ncs_template_cpm-filter-match-port-grouping;
                }
                leaf router {
                  type string;
                }
                container src-ip {
                  uses ncs_template_filter-match-ipv6-grouping;
                }
                container src-port {
                  uses ncs_template_cpm-filter-match-port-grouping;
                }
                leaf tcp-ack {
                  type string;
                }
                leaf tcp-syn {
                  type string;
                }
              }
            }
            leaf shutdown {
              type string;
            }
          }
        }
        container cpm-queue {
          list queue {
            // NCS patched for predictable order
            ordered-by user;
            key "queue-id";
            leaf queue-id {
              type string;
            }
            leaf cbs {
              type string;
            }
            leaf mbs {
              type string;
            }
            container rate {
              leaf value {
                tailf:cli-drop-node-name;
                type string;
              }
              leaf cir {
                type string;
              }
            }
          }
        }
        container management-access-filter {
          container ip-filter {
            presence "true";
            leaf default-action {
              type ncs_template_filter-action;
            }
            list entry {
              // NCS patched for predictable order
              ordered-by user;
              key "entry-name";
              leaf entry-name {
                type string;
              }
              leaf action {
                type ncs_template_filter-action;
              }
              leaf description {
                type string;
              }
              leaf log {
                type empty;
              }
              container src-ip {
                choice format-choice {
                  container address-netmask {
                    tailf:cli-drop-node-name;
                    leaf address {
                      tailf:cli-drop-node-name;
                      type string;
                    }
                    leaf netmask {
                      tailf:cli-drop-node-name;
                      type string;
                    }
                  }
                  leaf ip-prefix-list {
                    type string;
                  }
                }
              }
              container dst-port {
                leaf port {
                  tailf:cli-drop-node-name;
                  type string;
                }
                leaf mask {
                  tailf:cli-drop-node-name;
                  type string;
                }
              }
              leaf src-port {
                type string;
              }
              container l4-src-port {
                leaf port {
                  tailf:cli-drop-node-name;
                  type string;
                }
                leaf mask {
                  tailf:cli-drop-node-name;
                  type string;
                }
              }
              leaf router {
                type ncs_template_router-type;
              }
              leaf protocol {
                type string;
              }
            }
            leaf shutdown {
              type string;
            }
          }
          container ipv6-filter {
            presence "true";
            leaf default-action {
              type ncs_template_filter-action;
            }
            list entry {
              // NCS patched for predictable order
              ordered-by user;
              key "entry-name";
              leaf entry-name {
                type string;
              }
              leaf action {
                type ncs_template_filter-action;
              }
              leaf description {
                type string;
              }
              container src-ip {
                choice format-choice {
                  leaf address {
                    tailf:cli-drop-node-name;
                    type string;
                  }
                  leaf ipv6-prefix-list {
                    type string;
                  }
                }
              }
              leaf src-port {
                type string;
              }
              container dst-port {
                leaf port {
                  tailf:cli-drop-node-name;
                  type string;
                }
                leaf mask {
                  tailf:cli-drop-node-name;
                  type string;
                }
              }
              leaf next-header {
                type string;
              }
              leaf log {
                type empty;
              }
              container l4-src-port {
                leaf port {
                  tailf:cli-drop-node-name;
                  type string;
                }
                leaf mask {
                  tailf:cli-drop-node-name;
                  type string;
                }
              }
              leaf router {
                type string;
              }
            }
            leaf shutdown {
              type string;
            }
          }
        }
        container vprn-aaa-server {
          leaf inband {
            type ncs_template_service-id;
          }
          leaf outband {
            type ncs_template_service-id;
          }
          leaf vprn {
            type ncs_template_service-id;
          }
        }
        container vprn-network-exceptions {
          presence "true";
          leaf number {
            tailf:cli-drop-node-name;
            type string;
          }
          leaf seconds {
            tailf:cli-drop-node-name;
            type string;
          }
        }
        container usb-port {
          presence "true";
          leaf shutdown {
            type string;
          }
        }
      }
      container sync-if-timing {
        leaf description {
          type string;
        }
        container gnss {
          leaf shutdown {
            type string;
          }
        }
        container ptp {
          leaf ql-override {
            type string;
          }
          leaf shutdown {
            type string;
          }
        }
        container bits {
          container input {
            leaf shutdown {
              type string;
            }
          }
        }
        container external {
          container input-interface {
            leaf type {
              type string;
            }
            leaf shutdown {
              type string;
            }
          }
        }
        leaf ql-selection {
          type empty;
        }
        container ref-order {

          typedef ref-order-type {
            type string;
          }
          leaf first {
            tailf:cli-drop-node-name;
            type ref-order-type;
          }
          leaf second {
            tailf:cli-drop-node-name;
            type ref-order-type;
          }
          leaf third {
            tailf:cli-drop-node-name;
            type ref-order-type;
          }
          leaf fourth {
            tailf:cli-drop-node-name;
            type ref-order-type;
          }
          leaf fifth {
            tailf:cli-drop-node-name;
            type ref-order-type;
          }
        }

        grouping ref-grouping {
          leaf ql-override {
            type string;
          }
          leaf source-port {
            type string;
          }
          leaf source-ptp-clock {
            type string;
          }
          leaf shutdown {
            type string;
          }
        }
        container ref1 {
          uses ref-grouping;
        }
        container ref2 {
          uses ref-grouping;
        }
        leaf revert {
          type empty;
        }
      }
      list software-repository {
        // NCS patched for predictable order
        ordered-by user;
        key "name";
        leaf name {
          type string;
        }
        leaf description {
          type string;
        }
        leaf primary-location {
          type string;
        }
        leaf secondary-location {
          type string;
        }
        leaf tertiary-location {
          type string;
        }
      }
      container telemetry {
        list destination-group {
          // NCS patched for predictable order
          ordered-by user;
          key "name";
          leaf name {
            type string;
          }
          leaf allow-unsecure-connection {
            type empty;
          }
          leaf description {
            type string;
          }
          list destination {
            // NCS patched for predictable order
            ordered-by user;
            key "address port";
            leaf address {
              type string;
            }
            leaf port {
              type string;
            }
            container router-instance {
              leaf router-id {
                tailf:cli-drop-node-name;
                type ncs_template_router-type;
              }
            }
          }
          container tcp-keepalive {
            leaf shutdown {
              type string;
            }
          }
        }
        container sensor-groups {
          list sensor-group {
            // NCS patched for predictable order
            ordered-by user;
            key "name";
            leaf name {
              type string;
            }
            leaf description {
              type string;
            }
            list path {
              // NCS patched for predictable order
              ordered-by user;
              key "path-string";
              leaf path-string {
                type string;
              }
            }
          }
        }
        container persistent-subscriptions {
          list subscription {
            // NCS patched for predictable order
            ordered-by user;
            key "name";
            leaf name {
              type string;
            }
            leaf description {
              type string;
            }
            leaf encoding {
              type string;
            }
            leaf sample-interval {
              type string;
            }
            leaf local-source-address {
              type string;
            }
            leaf destination-group {
              type string;
            }
            leaf mode {
              type string;
            }
            leaf sensor-group {
              type string;
            }
            leaf shutdown {
              type string;
            }
          }
        }
      }
    }
    container redundancy {
      container bgp-evpn-multi-homing {
        leaf boot-timer {
          type string;
        }
        leaf es-activation-timer {
          type string;
        }
      }
      container mgmt-ethernet {
        leaf revert {
          type string;
        }
      }
      container multi-chassis {
        list peer {
          // NCS patched for predictable order
          ordered-by user;
          key "address";
          leaf address {
            type string;
          }
          leaf description {
            type string;
          }
          leaf peer-name {
            type string;
          }
          container mc-lag {
            presence "true";
            leaf hold-on-neighbor-failure {
              type string;
            }
            leaf keep-alive-interval {
              type string;
            }
            list lag {
              // NCS patched for predictable order
              ordered-by user;
              tailf:cli-suppress-mode;
              key "lag-id";
              leaf lag-id {
                type string;
              }
              leaf lacp-key {
                type string;
              }
              leaf system-id {
                type ncs_template_ieee-mac;
              }
              leaf remote-lag {
                type string;
              }
              leaf system-priority {
                type string;
              }
              leaf source-bmac-lsb {
                type string;
              }
            }
            leaf shutdown {
              type string;
            }
          }
          leaf source-address {
            type string;
          }
          container sync {
            presence "true";
            list port {
              // NCS patched for predictable order
              ordered-by user;
              key "port-id";
              leaf port-id {
                type string;
              }
              list range {
                // NCS patched for predictable order
                ordered-by user;
                tailf:cli-suppress-mode;
                key "range-val";
                leaf range-val {
                  type string;
                }
                leaf sync-tag {
                  type string;
                }
              }
              leaf sync-tag {
                type string;
              }
            }
            leaf local-dhcp-server {
              type empty;
            }
            leaf python {
              type empty;
            }
            leaf srrp {
              type empty;
            }
            leaf-list sub-mgmt {
              // NCS patched for predictable order
              ordered-by user;
              type string;
            }
            leaf igmp {
              type empty;
            }
            leaf igmp-snooping {
              type empty;
            }
            leaf shutdown {
              type string;
            }
          }
          leaf shutdown {
            type string;
          }
        }
      }
      leaf rollback-sync {
        type empty;
      }
      leaf synchronize {
        type string;
      }
    }
    list connection-profile-vlan {
      // NCS patched for predictable order
      ordered-by user;
      // NCS drop tailf-common:cli-diff-create-before statement
      // NCS drop tailf-common:cli-diff-create-before statement
      // NCS drop tailf-common:cli-diff-create-before statement
      key "conn-prof-id";
      leaf conn-prof-id {
        type string;
      }
      leaf description {
        type string;
      }
      list vlan-range {
        // NCS patched for predictable order
        ordered-by user;
        key "from to";
        tailf:cli-suppress-mode;
        unique "from";
        leaf from {
          type string;
        }
        leaf to {
          type string;
        }
      }
    }
    list eth-ring {
      // NCS patched for predictable order
      ordered-by user;
      key "index";
      leaf index {
        type string;
      }
      leaf description {
        type string;
      }
      leaf revert-time {
        type string;
      }
      leaf rpl-node {
        type string;
      }
      list path {
        // NCS patched for predictable order
        ordered-by user;
        key "path-id";
        leaf path-id {
          type string;
        }
        leaf port {
          tailf:cli-drop-node-name;
          type string;
        }
        leaf raps-tag {
          type string;
        }
        leaf rpl-end {
          type empty;
        }
        container eth-cfm {
          uses ncs_template_eth-cfm {
            augment "mep" {
              leaf control-mep {
                type empty;
              }
            }
          }
        }
        leaf shutdown {
          type string;
        }
      }
      leaf shutdown {
        type string;
      }
    }
    container filter {
      list ip-filter {
        // NCS patched for predictable order
        ordered-by user;
        key "ip-filter-name";
        leaf ip-filter-name {
          type ncs_template_filter-id;
        }
        leaf name {
          type string;
        }
        leaf chain-to-system-filter {
          type empty;
        }
        list embed-filter {
          // NCS patched for predictable order
          ordered-by user;
          tailf:cli-suppress-mode;
          key "embed-filter-name";
          leaf embed-filter-name {
            type ncs_template_filter-id;
          }
          leaf router {
            type ncs_template_router-type;
          }
          leaf offset {
            type string;
          }
          leaf status {
            tailf:cli-drop-node-name;
            type string;
          }
        }
        leaf default-action {
          type string;
        }
        leaf filter-name {
          type string;
        }
        leaf scope {
          type string;
        }
        leaf description {
          type string;
        }
        list entry {
          // NCS patched for predictable order
          ordered-by user;
          uses ncs_template_ip-filter-entry-grouping;
          key "entry-name";
          leaf pbr-down-action-override {
            type string;
          }

          grouping ip-filter-entry-action-grouping-old {
            choice action-choice {
              container drop {
                presence "true";
                container packet-length {
                  leaf rule {
                    tailf:cli-drop-node-name;
                    type string;
                  }
                  leaf length {
                    tailf:cli-drop-node-name;
                    type string;
                  }
                }
              }
              leaf nat {
                type empty;
              }
              leaf http-redirect {
                type string;
              }
              container forward {
                presence "true";
                container next-hop {
                  choice next-hop-choice {
                    case na {
                      leaf ip-address {
                        tailf:cli-drop-node-name;
                        type string;
                      }
                    }
                    case nb {
                      leaf indirect {
                        type string;
                      }
                    }
                    case nc {
                      leaf interface {
                        type string;
                      }
                    }
                  }
                }
                leaf router {
                  type ncs_template_router-type;
                }
                leaf sap {
                  type string;
                }
                leaf sdp {
                  type string;
                }
                leaf redirect-policy {
                  type string;
                }
              }
            }
          }

          grouping ip-filter-entry-action-grouping-new {
            choice action-choice {
              container drop {
                presence "true";
                container packet-length {
                  choice rule-range {
                    container rule {
                      tailf:cli-drop-node-name;
                      leaf rule {
                        tailf:cli-drop-node-name;
                        type string;
                      }
                      leaf length {
                        tailf:cli-drop-node-name;
                        type string;
                      }
                    }
                    container range {
                      leaf start {
                        tailf:cli-drop-node-name;
                        type string;
                      }
                      leaf end {
                        tailf:cli-drop-node-name;
                        type string;
                      }
                    }
                  }
                }
              }
              leaf nat {
                type empty;
              }
              leaf http-redirect {
                type string;
              }
              container forward {
                presence "true";
                container vprn-target {
                  leaf bgp-nh {
                    type string;
                  }
                }
                container next-hop {
                  choice next-hop-choice {
                    case na {
                      leaf ip-address {
                        tailf:cli-drop-node-name;
                        type string;
                      }
                    }
                    case nb {
                      leaf indirect {
                        type string;
                      }
                    }
                    case nc {
                      leaf interface {
                        type string;
                      }
                    }
                  }
                }
                leaf router {
                  type ncs_template_service-id;
                }
                leaf lsp {
                  type string;
                }
                leaf sap {
                  type string;
                }
                leaf sdp {
                  type string;
                }
                leaf redirect-policy {
                  type string;
                }
              }
              leaf rate-limit {
                type string;
              }
            }
          }
          container action-flat {
            tailf:alt-name "action";
            uses ip-filter-entry-action-grouping-old;
          }
          container action {
            presence "true";
            uses ip-filter-entry-action-grouping-new;
          }
          leaf egress-pbr {
            type string;
          }
        }
      }
      list ipv6-filter {
        // NCS patched for predictable order
        ordered-by user;
        key "ip-filter-name";
        leaf ip-filter-name {
          type ncs_template_filter-id;
        }
        leaf name {
          type string;
        }
        leaf chain-to-system-filter {
          type empty;
        }
        leaf default-action {
          type string;
        }
        leaf filter-name {
          type string;
        }
        list embed-filter {
          // NCS patched for predictable order
          ordered-by user;
          tailf:cli-suppress-mode;
          key "embed-filter-name";
          leaf embed-filter-name {
            type ncs_template_filter-id;
          }
          leaf router {
            type ncs_template_router-type;
          }
          leaf offset {
            type string;
          }
          leaf status {
            tailf:cli-drop-node-name;
            type string;
          }
        }
        leaf scope {
          type string;
        }
        leaf description {
          type string;
        }
        list entry {
          // NCS patched for predictable order
          ordered-by user;
          uses ncs_template_ipv6-filter-entry-grouping;
          key "entry-name";
          leaf log {
            type string;
          }
          leaf action {
            type string;
          }
          container action-mode {
            tailf:alt-name "action";
            presence "true";
            leaf action {
              tailf:cli-drop-node-name;
              type string;
            }
            container rate-limit {
              leaf value {
                tailf:cli-drop-node-name;
                type string;
              }
            }
          }
        }
      }
      list mac-filter {
        // NCS patched for predictable order
        ordered-by user;
        key "mac-filter-name";
        leaf mac-filter-name {
          type ncs_template_filter-id;
        }
        leaf name {
          type string;
        }
        leaf default-action {
          type string;
        }
        leaf scope {
          type string;
        }
        leaf description {
          type string;
        }
        leaf filter-name {
          type string;
        }
        list entry {
          // NCS patched for predictable order
          ordered-by user;
          key "entry-name";
          leaf entry-name {
            type string;
          }
          leaf description {
            type string;
          }
          container match {
            container dot1p {
              leaf dot1p-value {
                tailf:cli-drop-node-name;
                type string;
              }
              leaf dot1p-mask {
                tailf:cli-drop-node-name;
                type string;
              }
            }
            container dst-mac {
              leaf mac {
                tailf:cli-drop-node-name;
                type string;
              }
              leaf mask {
                tailf:cli-drop-node-name;
                type string;
              }
            }
            container src-mac {
              leaf mac {
                tailf:cli-drop-node-name;
                type string;
              }
              leaf mask {
                tailf:cli-drop-node-name;
                type string;
              }
            }
            leaf frame-type {
              type string;
            }
            leaf etype {
              type string;
            }
          }
          container action-flat {
            tailf:alt-name "action";
            choice choice {
              case drop {
                leaf drop {
                  type empty;
                }
              }
              case forward {
                leaf forward {
                  type empty;
                }
                leaf sap {
                  type string;
                }
              }
            }
          }
          container action {
            choice choice {
              case drop {
                leaf drop {
                  type empty;
                }
              }
              case forward {
                leaf forward {
                  type empty;
                }
                leaf sap {
                  type string;
                }
              }
            }
          }
          leaf log {
            type string;
          }
        }
      }
      container match-list {

        grouping apply-path-grouping {
          container apply-path {
            list bgp-peers {
              // NCS patched for predictable order
              ordered-by user;
              tailf:cli-suppress-mode;
              key "id";
              leaf id {
                type string;
              }
              leaf router {
                type ncs_template_router-type;
              }
              leaf group {
                type string;
              }
              leaf neighbor {
                type string;
              }
            }
          }
        }
        list ip-prefix-list {
          // NCS patched for predictable order
          ordered-by user;
          key "name";
          leaf name {
            type string;
          }
          leaf description {
            type string;
          }
          list prefix {
            // NCS patched for predictable order
            ordered-by user;
            tailf:cli-suppress-mode;
            key "pfx";
            leaf pfx {
              type string;
            }
          }
          list prefix-exclude {
            // NCS patched for predictable order
            ordered-by user;
            tailf:cli-suppress-mode;
            key "address";
            leaf address {
              type string;
            }
          }
          uses apply-path-grouping;
        }
        list ipv6-prefix-list {
          // NCS patched for predictable order
          ordered-by user;
          key "name";
          leaf name {
            type string;
          }
          leaf description {
            type string;
          }
          list prefix {
            // NCS patched for predictable order
            ordered-by user;
            tailf:cli-suppress-mode;
            key "pfx";
            leaf pfx {
              type string;
            }
          }
          uses apply-path-grouping;
        }
        list port-list {
          // NCS patched for predictable order
          ordered-by user;
          key "port-list-name";
          leaf port-list-name {
            type ncs_template_string32;
          }
          leaf description {
            type string;
          }
          container port {
            list port {
              // NCS patched for predictable order
              ordered-by user;
              tailf:cli-drop-node-name;
              tailf:cli-suppress-mode;
              key "port-number";
              leaf port-number {
                type string;
              }
            }
            list range {
              // NCS patched for predictable order
              ordered-by user;
              tailf:cli-suppress-mode;
              key "start end";
              leaf start {
                type string;
              }
              leaf end {
                type string;
              }
            }
          }
        }
      }
      list log {
        // NCS patched for predictable order
        ordered-by user;
        key "log-id";
        leaf log-id {
          type string;
        }
        leaf description {
          type string;
        }
        container destination {
          choice choice {
            leaf memory {
              type string;
            }
            leaf syslog {
              type string;
            }
          }
        }
        leaf wrap-around {
          type string;
        }
        leaf shutdown {
          type string;
        }
      }
      list redirect-policy {
        // NCS patched for predictable order
        ordered-by user;
        key "redirect-policy-name";
        leaf redirect-policy-name {
          type string;
        }
        leaf description {
          type string;
        }
        list destination {
          // NCS patched for predictable order
          ordered-by user;
          key "ip-address";
          leaf ip-address {
            type string;
          }
          leaf description {
            type string;
          }
          container ping-test {
            presence "true";
            container drop-count {
              leaf consecutive-failures {
                tailf:cli-drop-node-name;
                type string;
              }
              leaf hold-down {
                type string;
              }
            }
            leaf interval {
              type string;
            }
            leaf timeout {
              type string;
            }
          }
          leaf priority {
            type string;
          }
          leaf shutdown {
            type string;
          }
        }
        leaf shutdown {
          type string;
        }
      }
      container system-filter {
        leaf ip {
          type ncs_template_filter-id;
        }
        leaf ipv6 {
          type ncs_template_filter-id;
        }
      }
    }
    container test-oam {
      container link-measurement {
        list measurement-template {
          // NCS patched for predictable order
          ordered-by user;
          key "template-name";
          leaf template-name {
            type string;
          }
          container aggregate-sample-window {
            leaf multiplier {
              type string;
            }
            leaf window-integrity {
              type string;
            }
            container threshold {
              leaf absolute {
                type string;
              }
              leaf relative {
                type string;
              }
            }
          }
          leaf delay {
            type string;
          }
          leaf description {
            type string;
          }
          leaf interval {
            type string;
          }
          container twamp-light {
            leaf dest-udp-port {
              type string;
            }
            leaf dscp {
              type ncs_template_dscp-type;
            }
            leaf fc {
              type ncs_template_fc-name;
            }
          }
          leaf shutdown {
            type string;
          }
        }
      }
      container twamp {
        container twamp-test-pdu {
          leaf ipv4-timestamping {
            type string;
          }
          leaf ipv6-timestamping {
            type string;
          }
        }
        container server {
          leaf inactivity-timeout {
            type string;
          }
          leaf max-conn-server {
            type string;
          }
          leaf max-sess-server {
            type string;
          }
          list prefix {
            // NCS patched for predictable order
            ordered-by user;
            key "ip-prefix";
            leaf ip-prefix {
              type string;
            }
            leaf description {
              type string;
            }
            leaf max-conn-prefix {
              type string;
            }
            leaf max-sess-prefix {
              type string;
            }
          }
          leaf shutdown {
            type string;
          }
        }
      }
    }
    container mirror {
      list mirror-dest {
        // NCS patched for predictable order
        ordered-by user;
        key "service-id";
        uses ncs_template_service-id-grouping;
        leaf name {
          type string;
        }
        list pcap {
          // NCS patched for predictable order
          ordered-by user;
          key "name";
          leaf name {
            type string;
          }
          leaf file-url {
            type string;
          }
        }
        leaf mirror-type {
          type string;
        }
        leaf type {
          type string;
        }
        leaf description {
          type string;
        }
        leaf enable-port-id {
          type empty;
        }
        container encap {
          list layer-3-encap {
            // NCS patched for predictable order
            ordered-by user;
            key "encap";
            leaf encap {
              type string;
            }
            leaf direction-bit {
              type empty;
            }
            container gateway {
              container ip {
                leaf src {
                  type string;
                }
                leaf dest {
                  type string;
                }
              }
              container udp {
                leaf src {
                  type string;
                }
                leaf dest {
                  type string;
                }
              }
            }
          }
        }
        list endpoint {
          // NCS patched for predictable order
          ordered-by user;
          key "endpoint-name";
          leaf endpoint-name {
            type ncs_template_string32;
          }
          leaf description {
            type string;
          }
          leaf revert-time {
            type string;
          }
        }
        leaf fc {
          type ncs_template_fc-name;
        }
        container isa-aa-group {
          leaf aa-group-id {
            tailf:cli-drop-node-name;
            type string;
          }
          leaf traffic-direction {
            tailf:cli-drop-node-name;
            type string;
          }
        }
        container remote-source {
          presence "true";
          leaf far-end {
            type string;
          }
          list spoke-sdp {
            // NCS patched for predictable order
            ordered-by user;
            key "sdp-id vc-id";
            leaf sdp-id {
              type string;
            }
            leaf vc-id {
              type string;
            }
            leaf endpoint {
              type ncs_template_string32;
            }
            leaf vc-type {
              type string;
            }
            leaf shutdown {
              type string;
            }
          }
        }
        list sap {
          // NCS patched for predictable order
          ordered-by user;
          key "sap-id";
          leaf sap-id {
            type string;
          }
          container cem {
            container packet {
              choice packet {
                leaf jitter-buffer {
                  type string;
                }
                leaf bytes {
                  type string;
                }
              }
            }
            leaf rtp-header {
              type empty;
            }
          }
          container egress {
            container ip-mirror {
              container sa-mac {
                leaf sa-mac {
                  tailf:cli-drop-node-name;
                  type ncs_template_ieee-mac;
                }
                leaf da-mac {
                  type ncs_template_ieee-mac;
                }
              }
            }
            leaf qos {
              type string;
            }
          }
        }
        leaf service-name {
          type string;
        }
        leaf shutdown {
          type string;
        }
        leaf slice-size {
          type string;
        }
        list spoke-sdp {
          // NCS patched for predictable order
          ordered-by user;
          key "sdp-id vc-id";
          leaf sdp-id {
            type string;
          }
          leaf vc-id {
            type string;
          }
          leaf endpoint {
            type ncs_template_string32;
          }
          leaf vc-type {
            type string;
          }
          leaf control-word {
            type empty;
          }
          leaf precedence {
            type string;
          }
          container egress {
            container l2tpv3 {
              leaf cookie {
                type string;
              }
            }
            leaf vc-label {
              type string;
            }
          }
          container ingress {
            leaf vc-label {
              type string;
            }
          }
          leaf shutdown {
            type string;
          }
        }
      }
      list mirror-source {
        // NCS patched for predictable order
        ordered-by user;
        key "service-id";
        leaf service-id {
          type ncs_template_service-id;
        }
        list port {
          // NCS patched for predictable order
          ordered-by user;
          tailf:cli-suppress-mode;
          key "name";
          leaf name {
            type string;
          }
          leaf egress {
            type empty;
          }
          leaf ingress {
            type empty;
          }
        }
        list sap {
          // NCS patched for predictable order
          ordered-by user;
          tailf:cli-suppress-mode;
          key "sap-id";
          leaf sap-id {
            type string;
          }
          leaf egress {
            type empty;
          }
          leaf ingress {
            type empty;
          }
        }
        leaf shutdown {
          type string;
        }
      }
    }
    container saa {
      list test {
        // NCS patched for predictable order
        ordered-by user;
        key "test-name";
        leaf test-name {
          type string;
        }
        leaf owner {
          type string;
        }
        leaf accounting-policy {
          type string;
        }
        leaf continuous {
          type empty;
        }
        leaf description {
          type string;
        }

        grouping saa-test-event-grouping {
          leaf rising-threshold {
            type string;
          }
          leaf falling-threshold {
            type string;
          }
          leaf direction {
            type string;
          }
        }
        list jitter-event {
          // NCS patched for predictable order
          ordered-by user;
          tailf:cli-suppress-mode;
          key "direction";
          uses saa-test-event-grouping;
        }
        list latency-event {
          // NCS patched for predictable order
          ordered-by user;
          tailf:cli-suppress-mode;
          key "direction";
          uses saa-test-event-grouping;
        }
        list loss-event {
          // NCS patched for predictable order
          ordered-by user;
          tailf:cli-suppress-mode;
          key "direction";
          uses saa-test-event-grouping;
        }
        container type {
          presence "true";
          container cpe-ping {
            leaf service {
              type ncs_template_service-id;
            }
            leaf destination {
              type string;
            }
            leaf source {
              type string;
            }
            leaf source-mac {
              type ncs_template_ieee-mac;
            }
            leaf fc {
              type ncs_template_fc-name;
            }
            leaf profile {
              type string;
            }
            leaf ttl {
              type string;
            }
            leaf count {
              type string;
            }
            leaf send-control {
              type empty;
            }
            leaf return-control {
              type empty;
            }
            leaf interval {
              type string;
            }
          }
          container icmp-ping {
            leaf ip-address {
              tailf:cli-drop-node-name;
              type string;
            }
            leaf size {
              type string;
            }
            leaf source {
              type string;
            }
            leaf interval {
              type string;
            }
            leaf count {
              type string;
            }
            leaf router {
              type string;
            }
            leaf router-instance {
              type string;
            }
          }
          container dns {
            leaf target-addr {
              type string;
            }
            leaf name-server {
              type string;
            }
            leaf source {
              type string;
            }
            leaf count {
              type string;
            }
            leaf timeout {
              type string;
            }
            leaf interval {
              type string;
            }
            leaf record-type {
              type string;
            }
          }
          container eth-cfm-two-way-delay {
            leaf mac-address {
              tailf:cli-drop-node-name;
              type ncs_template_ieee-mac;
            }
            leaf mep {
              type string;
            }
            leaf domain {
              type string;
            }
            leaf association {
              type string;
            }
            leaf fc {
              type ncs_template_fc-name;
            }
            leaf profile {
              type string;
            }
            leaf count {
              type string;
            }
            leaf timeout {
              type string;
            }
            leaf interval {
              type string;
            }
          }
          container lsp-ping {
            leaf lsp-name {
              tailf:cli-drop-node-name;
              type string;
            }
            leaf path {
              type string;
            }
            leaf fc {
              type ncs_template_fc-name;
            }
            leaf profile {
              type string;
            }
            leaf interval {
              type string;
            }
            leaf send-count {
              type string;
            }
            leaf size {
              type string;
            }
            leaf src-ip-address {
              type string;
            }
            leaf timeout {
              type string;
            }
            leaf ttl {
              type string;
            }
          }
          container sdp-ping {
            leaf orig-sdp-id {
              tailf:cli-drop-node-name;
              type string;
            }
            leaf resp-sdp {
              type string;
            }
            leaf fc {
              type ncs_template_fc-name;
            }
            leaf profile {
              type string;
            }
            leaf size {
              type string;
            }
            leaf count {
              type string;
            }
            leaf timeout {
              type string;
            }
            leaf interval {
              type string;
            }
          }
          container vprn-ping {
            leaf service-id {
              tailf:cli-drop-node-name;
              type ncs_template_service-id;
            }
            leaf source {
              type string;
            }
            leaf destination {
              type string;
            }
            leaf fc {
              type ncs_template_fc-name;
            }
            leaf profile {
              type string;
            }
            leaf size {
              type string;
            }
            leaf ttl {
              type string;
            }
            leaf count {
              type string;
            }
            leaf return-control {
              type empty;
            }
            leaf timeout {
              type string;
            }
            leaf interval {
              type string;
            }
          }
        }
        container trap-gen {
          leaf probe-fail-enable {
            type empty;
          }
          leaf probe-fail-threshold {
            type string;
          }
          leaf test-completion-enable {
            type empty;
          }
          leaf test-fail-enable {
            type empty;
          }
          leaf test-fail-threshold {
            type string;
          }
        }
        leaf probe-history {
          type string;
        }
        leaf shutdown {
          type string;
        }
      }
    }
    container subscriber-mgmt {
      list category-map {
        // NCS patched for predictable order
        ordered-by user;
        key "name";
        leaf name {
          type string;
        }
        leaf description {
          type string;
        }
        leaf gx-session-level-usage {
          type string;
        }
        list category {
          // NCS patched for predictable order
          ordered-by user;
          key "name";
          leaf name {
            type string;
          }
          leaf credit-type-override {
            type string;
          }
          leaf rating-group {
            type string;
          }
          list queue {
            // NCS patched for predictable order
            ordered-by user;
            tailf:cli-suppress-mode;
            key "id";
            leaf id {
              type string;
            }
            leaf type {
              tailf:cli-drop-node-name;
              type string;
            }
          }
          list policer {
            // NCS patched for predictable order
            ordered-by user;
            tailf:cli-suppress-mode;
            key "id";
            leaf id {
              type string;
            }
            leaf type {
              tailf:cli-drop-node-name;
              type string;
            }
          }
        }
      }
      list credit-control-policy {
        // NCS patched for predictable order
        ordered-by user;
        key "policy-name";
        leaf policy-name {
          type string;
        }
        leaf description {
          type string;
        }
        container credit-control-server {
          leaf diameter {
            type string;
          }
        }
        leaf default-category-map {
          type string;
        }
      }
      list diameter-application-policy {
        // NCS patched for predictable order
        ordered-by user;
        key "name";
        leaf name {
          type string;
        }
        leaf application {
          type string;
        }
        leaf diameter-peer-policy {
          type ncs_template_string32;
        }
        container on-failure {
          leaf failover {
            type string;
          }
          leaf handling {
            type string;
          }
        }
        container gy {
          container avp-subscription-id {
            leaf origin {
              tailf:cli-drop-node-name;
              type string;
            }
            leaf type {
              type string;
            }
          }
          container extended-failure-handling {
            leaf shutdown {
              type string;
            }
            container interim-credit {
              leaf max-attempts {
                type string;
              }
              leaf reporting {
                type empty;
              }
            }
          }
        }
      }
      list local-user-db {
        // NCS patched for predictable order
        ordered-by user;
        key "name";
        leaf name {
          type string;
        }
        container ipoe {
          leaf-list match-list {
            // NCS patched for predictable order
            ordered-by user;
            type string;
          }
          list host {
            // NCS patched for predictable order
            ordered-by user;
            key "host-name";
            leaf host-name {
              type string;
            }
            leaf auth-policy {
              type string;
            }
            list identification-strings {
              // NCS patched for predictable order
              ordered-by user;
              key "option-number";
              leaf option-number {
                type string;
              }
              leaf sla-profile-string {
                type string;
              }
              leaf sub-profile-string {
                type string;
              }
            }
            container msap-defaults {
              leaf group-interface {
                type string;
              }
              leaf policy {
                type string;
              }
              leaf service {
                type string;
              }
            }
            leaf ipv6-wan-address-pool {
              type string;
            }
            leaf ipv6-delegated-prefix-pool {
              type string;
            }
            container options {
              leaf subnet-mask {
                type string;
              }
              leaf default-router {
                type string;
              }
            }
            leaf server {
              type string;
            }
            container host-identification {
              container option60 {
                leaf string {
                  type string;
                }
              }
              container circuit-id {
                leaf string {
                  type string;
                }
              }
              leaf sap-id {
                type string;
              }
            }
            container address {
              leaf pool {
                type string;
              }
            }
            leaf shutdown {
              type string;
            }
          }
        }
        container ppp {
          leaf-list match-list {
            // NCS patched for predictable order
            ordered-by user;
            type string;
          }
          list host {
            // NCS patched for predictable order
            ordered-by user;
            key "host-name";
            leaf host-name {
              type string;
            }
            leaf auth-policy {
              type string;
            }
            leaf pre-auth-policy {
              type string;
            }
            container host-identification {
              container username {
                leaf name {
                  tailf:cli-drop-node-name;
                  type string;
                }
                leaf domain {
                  tailf:cli-drop-node-name;
                  type string;
                }
              }
            }
            container password {
              leaf ignore {
                type empty;
              }
            }
            container l2tp {
              container group {
                leaf name {
                  tailf:cli-drop-node-name;
                  type string;
                }
              }
            }
            container address {
              leaf pool {
                type string;
              }
            }
            leaf shutdown {
              type string;
            }
          }
        }
        leaf shutdown {
          type string;
        }
      }

      grouping radius-attributes-grouping {
        leaf access-loop-options {
          type empty;
        }
        leaf calling-station-id {
          type string;
        }
        leaf circuit-id {
          type empty;
        }
        leaf dhcp-vendor-class-id {
          type empty;
        }
        leaf mac-address {
          type empty;
        }
        leaf nas-port {
          type string;
        }
        container nas-port-id {
          presence "true";
          leaf prefix-string {
            type string;
          }
          leaf suffix {
            type string;
          }
        }
        container nas-port-type {
          presence "true";
          leaf port-type {
            tailf:cli-drop-node-name;
            type string;
          }
        }
        leaf nas-identifier {
          type empty;
        }
        leaf remote-id {
          type empty;
        }
        leaf tunnel-server-attrs {
          type empty;
        }
        leaf wifi-num-attached-ues {
          type empty;
        }
        leaf wifi-ssid-vlan {
          type empty;
        }
      }
      container auto-sub-id-key {
        leaf-list ppp-sub-id-key {
          // NCS patched for predictable order
          ordered-by user;
          type string;
        }
        leaf-list ipoe-sub-id-key {
          // NCS patched for predictable order
          ordered-by user;
          type string;
        }
      }
      list authentication-policy {
        // NCS patched for predictable order
        ordered-by user;
        key "name";
        leaf name {
          type string;
        }
        leaf description {
          type string;
        }
        container fallback-action {
          leaf accept {
            type empty;
          }
          leaf user-db {
            type ncs_template_string32;
          }
          leaf force-probing {
            type empty;
          }
        }
        container include-radius-attribute {
          container acct-session-id {
            presence "true";
            leaf session {
              tailf:cli-drop-node-name;
              type string;
            }
          }
          leaf called-station-id {
            type empty;
          }
          leaf dhcp-options {
            type empty;
          }
          leaf dhcp6-options {
            type empty;
          }
          leaf pppoe-service-name {
            type empty;
          }
          uses radius-attributes-grouping;
        }
        leaf re-authentication {
          type empty;
        }
        leaf radius-server-policy {
          type ncs_template_string32;
        }
        leaf-list send-acct-stop-on-fail {
          // NCS patched for predictable order
          ordered-by user;
          type string;
        }
        container password {
          leaf pw {
            tailf:cli-drop-node-name;
            type string;
          }
          leaf hashing-scheme {
            tailf:cli-drop-node-name;
            type ncs_template_hash-method;
          }
        }
        leaf pppoe-access-method {
          type string;
        }
        container user-name-format {
          leaf format {
            tailf:cli-drop-node-name;
            type string;
          }
        }
      }
      list host-lockout-policy {
        // NCS patched for predictable order
        ordered-by user;
        key "policy-name";
        leaf policy-name {
          type ncs_template_string32;
        }
        leaf description {
          type string;
        }
        leaf lockout-reset-time {
          type string;
        }
        container lockout-time {
          leaf min {
            type string;
          }
          leaf max {
            type string;
          }
        }
        leaf max-lockout-hosts {
          type string;
        }
        leaf host-key {
          type string;
        }
      }
      list msap-policy {
        // NCS patched for predictable order
        ordered-by user;
        key "msap-policy-name";
        leaf msap-policy-name {
          type ncs_template_string32;
        }
        container cpu-protection {
          leaf policy-id {
            tailf:cli-drop-node-name;
            type string;
          }
          leaf monitoring {
            tailf:cli-drop-node-name;
            type string;
          }
        }
        leaf dist-cpu-protection {
          type string;
        }
        leaf description {
          type string;
        }
        container sub-sla-mgmt {
          container def-sub-id {
            choice def-sub-id {
              leaf use-sap-id {
                type empty;
              }
              leaf use-auto-id {
                type empty;
              }
              leaf string {
                type string;
              }
            }
          }
          container def-inter-dest-id {
            leaf type {
              tailf:cli-drop-node-name;
              type string;
            }
          }
          leaf def-sub-profile {
            type string;
          }
          leaf def-sla-profile {
            type string;
          }
          leaf sub-ident-policy {
            type string;
          }
          container single-sub-parameters {
            leaf profiled-traffic-only {
              type empty;
            }
          }
        }
        container ies-vprn-only-sap-parameters {
          leaf anti-spoof {
            type string;
          }
          container ingress {
            container qos {
              tailf:cli-drop-node-name;
              leaf qos {
                type string;
              }
              leaf queueing {
                tailf:cli-drop-node-name;
                type string;
              }
            }
          }
          container egress {
            leaf qos {
              type string;
            }
          }
        }
      }
      list ipoe-session-policy {
        // NCS patched for predictable order
        ordered-by user;
        key "policy-name";
        leaf policy-name {
          type ncs_template_string32;
        }
        leaf description {
          type string;
        }
        container session-key {
          leaf sap {
            type empty;
          }
          leaf mac {
            type empty;
          }
          leaf cid {
            type empty;
          }
          leaf rid {
            type empty;
          }
        }
      }
      list ppp-policy {
        // NCS patched for predictable order
        ordered-by user;
        key "ppp-policy-name";
        leaf ppp-policy-name {
          type ncs_template_string32;
        }
        leaf description {
          type string;
        }
        leaf ppp-mtu {
          type string;
        }
        container default-pap-password {
          leaf password {
            tailf:cli-drop-node-name;
            type string;
          }
          leaf method {
            tailf:cli-drop-node-name;
            type ncs_template_hash-method;
          }
        }
        leaf default-user-name {
          type string;
        }
        container keepalive {
          leaf seconds {
            tailf:cli-drop-node-name;
            type string;
          }
          leaf hold-up-multiplier {
            type string;
          }
        }
        container max-sessions-per-mac {
          leaf sessions {
            tailf:cli-drop-node-name;
            type string;
          }
          leaf allow-same-circuit-id-for-dhcp {
            type empty;
          }
        }
        leaf ppp-authentication {
          type string;
        }
        leaf session-timeout {
          type string;
        }
      }
      list radius-accounting-policy {
        // NCS patched for predictable order
        ordered-by user;
        key "name";
        leaf name {
          type ncs_template_string32;
        }
        leaf delay-start-time {
          type string;
        }
        leaf queue-instance-accounting {
          type string;
        }
        container session-accounting {
          presence "true";
          leaf-list keywords {
            // NCS patched for predictable order
            ordered-by user;
            tailf:cli-drop-node-name;
            type string;
          }
        }
        leaf description {
          type string;
        }
        container host-accounting {
          presence "true";
          leaf interim-update {
            type empty;
          }
        }
        container include-radius-attribute {
          uses radius-attributes-grouping;
          leaf detailed-acct-attributes {
            type string;
          }
          leaf acct-authentic {
            type empty;
          }
          leaf acct-delay-time {
            type empty;
          }
          leaf alc-acct-triggered-reason {
            type empty;
          }
          leaf alc-error-code {
            type empty;
          }
          leaf all-authorized-session-addresses {
            type empty;
          }
          leaf brg-num-active-sessions {
            type empty;
          }
          leaf delegated-ipv6-prefix {
            type empty;
          }
          leaf framed-interface-id {
            type empty;
          }
          leaf framed-ip-netmask {
            type empty;
          }
          leaf framed-ipv6-route {
            type empty;
          }
          leaf framed-route {
            type empty;
          }
          leaf framed-ip-addr {
            type empty;
          }
          leaf framed-ipv6-prefix {
            type empty;
          }
          leaf ipv6-address {
            type empty;
          }
          leaf nat-port-range {
            type empty;
          }
          leaf std-acct-attributes {
            type empty;
          }
          leaf tunnel-client-attrs {
            type empty;
          }
          leaf steering-profile {
            type empty;
          }
          leaf sub-profile {
            type empty;
          }
          leaf sla-profile {
            type empty;
          }
          leaf subscriber-id {
            type empty;
          }
          leaf user-name {
            type empty;
          }
          leaf v6-aggregate-stats {
            type empty;
          }
          leaf wifi-rssi {
            type empty;
          }
        }
        leaf radius-server-policy {
          type ncs_template_string32;
        }
        leaf session-id-format {
          type string;
        }
        leaf update-interval {
          type string;
        }
      }
      list shcv-policy {
        // NCS patched for predictable order
        ordered-by user;
        key "shcv-policy-name";
        leaf shcv-policy-name {
          type string;
        }
        leaf description {
          type string;
        }
        container layer-3 {
          leaf source-ip-origin {
            type string;
          }
        }
        container periodic {
          leaf action {
            type string;
          }
          leaf interval {
            type string;
          }
          leaf retry-count {
            type string;
          }
          leaf timeout {
            type string;
          }
          leaf shutdown {
            type string;
          }
        }
        container trigger {

          grouping trigger-grouping {
            leaf shutdown {
              type string;
            }
            leaf retry-count {
              type string;
            }
            leaf timeout {
              type string;
            }
          }
          container ip-conflict {
            uses trigger-grouping;
          }
          container host-limit-exceeded {
            uses trigger-grouping;
          }
          container inactivity {
            // NCS expand uses statement
            leaf shutdown {
              type string;
            }
            leaf retry-count {
              type string;
            }
            leaf timeout {
              type string;
            }
          }
          container mobility {
            uses trigger-grouping;
          }
          container mac-learning {
            // NCS expand uses statement
            leaf shutdown {
              type string;
            }
            leaf retry-count {
              type string;
            }
            leaf timeout {
              type string;
            }
          }
        }
        container vpls {
          leaf source-ip {
            type string;
          }
          leaf source-mac {
            type ncs_template_ieee-mac;
          }
        }
      }
      list sla-profile {
        // NCS patched for predictable order
        ordered-by user;
        key "sla-profile-name";
        leaf sla-profile-name {
          type string;
        }
        leaf description {
          type string;
        }
        leaf credit-control-policy {
          type string;
        }
        container host-limit {
          leaf max-number-of-hosts {
            tailf:cli-drop-node-name;
            type string;
          }
          leaf remove-oldest {
            type empty;
          }
        }
        container host-limits {
          leaf ipv4-overall {
            type string;
          }
          leaf ipv4-dhcp {
            type string;
          }
          leaf ipv6-pd-ipoe-dhcp {
            type string;
          }
          leaf ipv6-wan-ipoe-dhcp {
            type string;
          }
          leaf ipv6-overall {
            type string;
          }
          leaf overall {
            type string;
          }
        }
        container ingress {
          list qos {
            // NCS patched for predictable order
            ordered-by user;
            key "id";
            leaf id {
              type string;
            }
            leaf queuing {
              tailf:cli-drop-node-name;
              type string;
            }
            list queue {
              // NCS patched for predictable order
              ordered-by user;
              key "queue-id";
              leaf queue-id {
                type string;
              }
              leaf stat-mode {
                type string;
              }
            }
            list policer {
              // NCS patched for predictable order
              ordered-by user;
              key "policer-id";
              leaf policer-id {
                type string;
              }
              leaf stat-mode {
                type ncs_template_policer-stat-mode;
              }
            }
          }
          leaf ip-filter {
            type ncs_template_filter-id;
          }
          leaf ipv6-filter {
            type ncs_template_filter-id;
          }
        }
        container egress {
          list qos {
            // NCS patched for predictable order
            ordered-by user;
            key "id";
            leaf id {
              type string;
            }
            leaf multipoint-shared {
              type empty;
            }
            leaf vport-scheduler {
              type empty;
            }
            list queue {
              // NCS patched for predictable order
              ordered-by user;
              key "queue-id";
              leaf queue-id {
                type string;
              }
              leaf stat-mode {
                type string;
              }
            }
            list policer {
              // NCS patched for predictable order
              ordered-by user;
              key "policer-id";
              leaf policer-id {
                type string;
              }
              leaf stat-mode {
                type ncs_template_policer-stat-mode;
              }
            }
          }
          leaf ip-filter {
            type ncs_template_filter-id;
          }
          leaf ipv6-filter {
            type ncs_template_filter-id;
          }
          leaf qos-marking-from-sap {
            type string;
          }
          list scheduler-policy {
            // NCS patched for predictable order
            ordered-by user;
            key "scheduler-policy-name";
            leaf scheduler-policy-name {
              type string;
            }
            list scheduler {
              // NCS patched for predictable order
              ordered-by user;
              tailf:cli-suppress-mode;
              key "scheduler-name";
              leaf scheduler-name {
                type string;
              }
              leaf rate {
                type ncs_template_rate-type;
              }
              leaf cir {
                type ncs_template_rate-type-with-sum;
              }
            }
          }
        }
      }
      list sub-ident-policy {
        // NCS patched for predictable order
        ordered-by user;
        key "sub-ident-policy-name";
        leaf sub-ident-policy-name {
          type string;
        }
        leaf description {
          type string;
        }
        container app-profile-map {
          leaf use-direct-map-as-default {
            type empty;
          }
        }
        leaf strings-from-option {
          type string;
        }
        container sub-profile-map {
          leaf use-direct-map-as-default {
            type empty;
          }
        }
        container sla-profile-map {
          leaf use-direct-map-as-default {
            type empty;
          }
        }
      }
      list igmp-policy {
        // NCS patched for predictable order
        ordered-by user;
        key "name";
        leaf name {
          type string;
        }
        leaf per-host-replication {
          type empty;
        }
        container static {
          list group {
            // NCS patched for predictable order
            ordered-by user;
            key "ip-address";
            leaf ip-address {
              type string;
            }
            leaf starg {
              type empty;
            }
          }
        }
      }
      list sub-profile {
        // NCS patched for predictable order
        ordered-by user;
        key "sub-profile-name";
        leaf sub-profile-name {
          type string;
        }
        leaf description {
          type string;
        }
        leaf igmp-policy {
          type string;
        }
        leaf accounting-policy {
          type string;
        }
        leaf nat-policy {
          type string;
        }
        leaf collect-stats {
          type empty;
        }
        container radius-accounting {
          leaf-list policy {
            // NCS patched for predictable order
            ordered-by user;
            type ncs_template_string32;
          }
        }
        container radius-accounting-policy {
          leaf acct-policy-name {
            tailf:cli-drop-node-name;
            type ncs_template_string32;
          }
          leaf duplicate {
            type ncs_template_string32;
          }
        }
        container sla-profile-map {
          leaf use-direct-map-as-default {
            type empty;
          }
          list entry {
            // NCS patched for predictable order
            ordered-by user;
            tailf:cli-suppress-mode;
            key "key";
            leaf key {
              type string;
            }
            leaf sla-profile {
              type string;
            }
          }
        }
        container egress {
          container scheduler-policy {
            leaf scheduler-policy-id {
              tailf:cli-drop-node-name;
              type string;
            }
            list scheduler {
              // NCS patched for predictable order
              ordered-by user;
              tailf:cli-suppress-mode;
              key "scheduler-id";
              leaf scheduler-id {
                type string;
              }
              leaf rate {
                type string;
              }
              leaf cir {
                type string;
              }
            }
          }
          container agg-rate-limit {
            leaf agg-rate {
              tailf:cli-drop-node-name;
              type string;
            }
            leaf queue-frame-based-accounting {
              type empty;
            }
          }
        }
      }
    }
    container vrrp {
      list policy {
        // NCS patched for predictable order
        ordered-by user;
        key "policy-id";
        leaf policy-id {
          type string;
        }
        leaf context {
          type ncs_template_service-id;
        }
        leaf delta-in-use-limit {
          type string;
        }
        leaf description {
          type string;
        }
        container priority-event {

          grouping priority-event-grouping {
            leaf hold-set {
              type string;
            }
            leaf hold-clear {
              type string;
            }
            container priority {
              leaf priority-level {
                tailf:cli-drop-node-name;
                type string;
              }
              leaf keyword {
                tailf:cli-drop-node-name;
                type string;
              }
            }
          }
          list host-unreachable {
            // NCS patched for predictable order
            ordered-by user;
            key "address";
            leaf address {
              type string;
            }
            uses priority-event-grouping;
            leaf drop-count {
              type string;
            }
            leaf interval {
              type string;
            }
            leaf padding-size {
              type string;
            }
            leaf timeout {
              type string;
            }
          }
          list lag-port-down {
            // NCS patched for predictable order
            ordered-by user;
            key "lag-id";
            leaf lag-id {
              type string;
            }
            uses priority-event-grouping;
            list number-down {
              // NCS patched for predictable order
              ordered-by user;
              key "number-of-lag-ports-down";
              leaf number-of-lag-ports-down {
                type string;
              }
              container priority {
                leaf priority-level {
                  tailf:cli-drop-node-name;
                  type string;
                }
                leaf keyword {
                  tailf:cli-drop-node-name;
                  type string;
                }
              }
            }
          }
          list mc-ipsec-non-forwarding {
            // NCS patched for predictable order
            ordered-by user;
            key "tunnel-grp-id";
            leaf tunnel-grp-id {
              type string;
            }
            uses priority-event-grouping;
          }
          list port-down {
            // NCS patched for predictable order
            ordered-by user;
            key "port-id";
            leaf port-id {
              type string;
            }
            uses priority-event-grouping;
          }
          list route-unknown {
            // NCS patched for predictable order
            ordered-by user;
            key "prefix";
            leaf prefix {
              type string;
            }
            uses priority-event-grouping;
            container less-specific {
              presence "true";
              leaf allow-default {
                type empty;
              }
            }
            list next-hop {
              // NCS patched for predictable order
              ordered-by user;
              tailf:cli-suppress-mode;
              key "address";
              leaf address {
                type string;
              }
            }
            list protocol {
              // NCS patched for predictable order
              ordered-by user;
              tailf:cli-suppress-mode;
              key "protocol";
              leaf protocol {
                type string;
              }
            }
          }
        }
      }
    }
    container bof {

      grouping bof-address-grouping {
        leaf address {
          type string;
        }
        leaf type {
          tailf:cli-drop-node-name;
          type string;
        }
      }
      list address {
        // NCS patched for predictable order
        ordered-by user;
        tailf:cli-suppress-mode;
        key "address";
        uses bof-address-grouping;
      }
      container auto-discover {
        presence "true";
        leaf id {
          type string;
        }
        leaf vlan {
          type string;
        }
      }
      leaf autonegotiate {
        type empty;
      }
      leaf console-speed {
        type string;
      }
      leaf dns-domain {
        type string;
      }
      leaf duplex {
        type string;
      }
      leaf fips-140-2 {
        type string;
      }
      leaf ip-mtu {
        type string;
      }
      leaf li-local-save {
        type string;
      }
      leaf li-separate {
        type string;
      }
      leaf persist {
        type string;
      }
      leaf primary-config {
        type string;
      }
      leaf primary-dns {
        type string;
      }
      leaf primary-image {
        type string;
      }
      leaf secondary-config {
        type string;
      }
      leaf secondary-dns {
        type string;
      }
      leaf secondary-image {
        type string;
      }
      leaf speed {
        type string;
      }

      grouping bof-static-route-grouping {
        leaf prefix {
          type string;
        }
        leaf next-hop {
          type string;
        }
      }
      list static-route {
        // NCS patched for predictable order
        ordered-by user;
        tailf:cli-suppress-mode;
        key "prefix";
        uses bof-static-route-grouping;
      }
      leaf tertiary-config {
        type string;
      }
      leaf tertiary-dns {
        type string;
      }
      leaf tertiary-image {
        type string;
      }
      leaf wait {
        type string;
      }
      leaf console-disabled {
        type string;
      }
      list eth-mgmt-address {
        // NCS patched for predictable order
        ordered-by user;
        tailf:cli-suppress-mode;
        key "address";
        uses bof-address-grouping;
      }
      leaf eth-mgmt-autoneg {
        type string;
      }
      leaf eth-mgmt-disabled {
        type string;
      }
      leaf eth-mgmt-duplex {
        type string;
      }
      list eth-mgmt-route {
        // NCS patched for predictable order
        ordered-by user;
        tailf:cli-suppress-mode;
        key "prefix";
        uses bof-static-route-grouping;
      }
      leaf eth-mgmt-speed {
        type string;
      }
      leaf uplinkA-address {
        type string;
      }
      leaf uplinkA-port {
        type string;
      }
      list uplinkA-route {
        // NCS patched for predictable order
        ordered-by user;
        tailf:cli-suppress-mode;
        key "prefix";
        uses bof-static-route-grouping;
      }
      leaf uplinkA-vlan {
        type string;
      }
      leaf uplinkA-autoneg {
        type empty;
      }
      leaf uplinkA-duplex {
        type string;
      }
      leaf uplinkA-speed {
        type string;
      }
      leaf uplinkB-address {
        type string;
      }
      leaf uplinkB-port {
        type string;
      }
      list uplinkB-route {
        // NCS patched for predictable order
        ordered-by user;
        tailf:cli-suppress-mode;
        key "prefix";
        uses bof-static-route-grouping;
      }
      leaf uplinkB-vlan {
        type string;
      }
      leaf uplinkB-autoneg {
        type empty;
      }
      leaf uplinkB-duplex {
        type string;
      }
      leaf uplinkB-speed {
        type string;
      }
      leaf uplink-mode {
        type string;
      }
      leaf usb-port-key {
        type string;
      }
      leaf license-file {
        type string;
      }
    }
    container debug {
      container lag {
        list lag-id {
          // NCS patched for predictable order
          ordered-by user;
          tailf:cli-suppress-mode;
          key "id";
          leaf id {
            type string;
          }
          container items {
            tailf:cli-drop-node-name;
            leaf-list debug-item {
              // NCS patched for predictable order
              ordered-by user;
              tailf:cli-drop-node-name;
              type string;
            }
            leaf-list port {
              // NCS patched for predictable order
              ordered-by user;
              type string;
            }
          }
        }
      }
      list mirror-source {
        // NCS patched for predictable order
        ordered-by user;
        key "service-id";
        leaf service-id {
          type ncs_template_service-id;
        }
        list ingress-label {
          // NCS patched for predictable order
          ordered-by user;
          tailf:cli-suppress-mode;
          key "label";
          leaf label {
            type string;
          }
        }
        list ip-filter {
          // NCS patched for predictable order
          ordered-by user;
          tailf:cli-suppress-mode;
          key "ip-filter-name";
          leaf ip-filter-name {
            type ncs_template_filter-id;
          }
          leaf-list entry {
            // NCS patched for predictable order
            ordered-by user;
            type string;
          }
        }
        list mac-filter {
          // NCS patched for predictable order
          ordered-by user;
          tailf:cli-suppress-mode;
          key "mac-filter-name";
          leaf mac-filter-name {
            type ncs_template_filter-id;
          }
          leaf-list entry {
            // NCS patched for predictable order
            ordered-by user;
            type string;
          }
        }
        list port {
          // NCS patched for predictable order
          ordered-by user;
          tailf:cli-suppress-mode;
          key "port-id";
          leaf lag {
            type empty;
          }
          leaf port-id {
            type string;
          }
          leaf ingress {
            type empty;
          }
          leaf egress {
            type empty;
          }
        }
        list sap {
          // NCS patched for predictable order
          ordered-by user;
          tailf:cli-suppress-mode;
          key "sap-id";
          leaf sap-id {
            type string;
          }
          leaf ingress {
            type empty;
          }
          leaf egress {
            type empty;
          }
        }
        list subscriber {
          // NCS patched for predictable order
          ordered-by user;
          tailf:cli-suppress-mode;
          key "sub-ident-string";
          leaf sub-ident-string {
            type string;
          }
          leaf sap {
            type string;
          }
          leaf ip {
            type string;
          }
          leaf mac {
            type ncs_template_ieee-mac;
          }
          leaf sla-profile-name {
            tailf:alt-name "sla-profile";
            type string;
          }
          leaf fc {
            type ncs_template_fc-name;
          }
          leaf ingress {
            type empty;
          }
          leaf egress {
            type empty;
          }
        }
        leaf shutdown {
          type string;
        }
      }

      grouping debug-router-grouping {
        container bgp {

          grouping neighbor-grouping {
            choice zzz {
              leaf neighbor {
                type string;
              }
              leaf group {
                type string;
              }
            }
          }
          container events {
            uses neighbor-grouping;
          }
          container packets {
            uses neighbor-grouping;
          }
        }
        container ip {
          leaf arp {
            type empty;
          }
          leaf icmp {
            type empty;
          }
          leaf icmp6 {
            type empty;
          }
        }
      }
      container router {
        list router-id {
          // NCS patched for predictable order
          ordered-by user;
          tailf:cli-drop-node-name;
          key "router-name";
          leaf router-name {
            type ncs_template_router-type;
          }
          // NCS expand uses statement
          container bgp {

            grouping neighbor-grouping {
              choice zzz {
                leaf neighbor {
                  type string;
                }
                leaf group {
                  type string;
                }
              }
            }
            container events {
              // NCS expand uses statement
              choice zzz {
                leaf neighbor {
                  type string;
                }
                leaf group {
                  type string;
                }
              }
            }
            container packets {
              // NCS expand uses statement
              choice zzz {
                leaf neighbor {
                  type string;
                }
                leaf group {
                  type string;
                }
              }
            }
          }
          container ip {
            leaf arp {
              type empty;
            }
            leaf icmp {
              type empty;
            }
            leaf icmp6 {
              type empty;
            }
          }
        }
        list service-name {
          // NCS patched for predictable order
          ordered-by user;
          key "name";
          leaf name {
            type string;
          }
          uses debug-router-grouping;
        }
      }
    }
    container external-alarms {
      list alarm {
        // NCS patched for predictable order
        ordered-by user;
        key "alarm-id";
        leaf alarm-id {
          type string;
        }
        leaf chassis-alarming {
          type string;
        }
        leaf description {
          type string;
        }
        leaf log {
          type string;
        }
        container thresholds {
          container analog {
            container level {
              leaf op {
                tailf:cli-drop-node-name;
                type string;
              }
              leaf millivolts {
                tailf:cli-drop-node-name;
                type string;
              }
            }
          }
        }
        container trigger {
          leaf type {
            tailf:cli-drop-node-name;
            type string;
          }
          leaf-list alarm-input {
            // NCS patched for predictable order
            ordered-by user;
            tailf:cli-drop-node-name;
            type string;
          }
        }
        leaf severity {
          type string;
        }
        leaf shutdown {
          type string;
        }
      }
    }
    container python {
      list python-policy {
        // NCS patched for predictable order
        ordered-by user;
        key "name";
        leaf name {
          type ncs_template_string32;
        }
        leaf description {
          type string;
        }
        list dhcp {
          // NCS patched for predictable order
          ordered-by user;
          tailf:cli-suppress-mode;
          key "type direction";
          leaf type {
            type string;
          }
          leaf direction {
            type string;
          }
          leaf script {
            type ncs_template_string32;
          }
        }
        list dhcp6 {
          // NCS patched for predictable order
          ordered-by user;
          tailf:cli-suppress-mode;
          key "type direction";
          leaf type {
            type string;
          }
          leaf direction {
            type string;
          }
          leaf script {
            type ncs_template_string32;
          }
        }
        list radius {
          // NCS patched for predictable order
          ordered-by user;
          tailf:cli-suppress-mode;
          key "type direction";
          leaf type {
            type string;
          }
          leaf direction {
            type string;
          }
          leaf script {
            type ncs_template_string32;
          }
        }
      }
      list python-script {
        // NCS patched for predictable order
        ordered-by user;
        key "name";
        leaf name {
          type ncs_template_string32;
        }
        leaf action-on-fail {
          type string;
        }
        leaf description {
          type string;
        }
        leaf primary-url {
          type string;
        }
        leaf shutdown {
          type string;
        }
      }
    }
    container commands {
      tailf:cli-drop-node-name;
    }
  }
  augment "/ncs:compliance/ncs:template/ncs:ned-id/ncs:config" {
    leaf model {
      tailf:alt-name "nedAluModel";
      type string;
    }
    leaf model-name {
      tailf:alt-name "nedAluModelName";
      type string;
    }
    leaf os-major {
      tailf:alt-name "nedAluOsMajor";
      type string;
    }
    leaf os-minor {
      tailf:alt-name "nedAluOsMinor";
      type string;
    }
    leaf os-patch {
      tailf:alt-name "nedAluOsPatch";
      type string;
    }
    leaf mode {
      tailf:alt-name "nedAluUseMode";
      type string;
    }
    leaf use-extra-get-port-speed {
      tailf:alt-name "nedAluUseExtraGetPortSpeed";
      type string;
    }
    leaf force-no-filter-name {
      tailf:alt-name "nedAluForceNoFilterName";
      type string;
    }
    container bfd {
      container seamless-bfd {
        list reflector {
          // NCS patched for predictable order
          ordered-by user;
          key "reflector-name";
          leaf reflector-name {
            type string;
          }
          leaf description {
            type string;
          }
          leaf local-state {
            type string;
          }
          leaf discriminator {
            type string;
          }
          leaf shutdown {
            type string;
          }
        }
      }
    }
    container bmp {
      list station {
        // NCS patched for predictable order
        ordered-by user;
        key "station-name";
        leaf station-name {
          type string;
        }
        container connection {
          leaf connect-retry {
            type string;
          }
          leaf local-address {
            type string;
          }
          container station-address {
            leaf address {
              tailf:cli-drop-node-name;
              type string;
            }
            leaf port {
              type string;
            }
          }
          leaf router {
            type string;
          }
          container tcp-keepalive {
            leaf keep-count {
              type string;
            }
            leaf keep-idle {
              type string;
            }
            leaf keep-interval {
              type string;
            }
            leaf shutdown {
              type string;
            }
          }
        }
        leaf description {
          type string;
        }
        leaf-list family {
          // NCS patched for predictable order
          ordered-by user;
          type string;
        }
        leaf initiation-message {
          type string;
        }
        leaf report-local-routes {
          type empty;
        }
        leaf stats-report-interval {
          type string;
        }
        leaf shutdown {
          type string;
        }
      }
      leaf shutdown {
        type string;
      }
    }
    container call-trace {
      container location {

        grouping cf-group {
          leaf disable {
            type empty;
          }
          leaf size-limit {
            type string;
          }
        }
        container cf1 {
          uses cf-group;
        }
        container cf2 {
          uses cf-group;
        }
      }
      list trace-profile {
        // NCS patched for predictable order
        ordered-by user;
        key "profile-name";
        leaf profile-name {
          type string;
        }
        leaf description {
          type string;
        }
        leaf debug-output {
          type empty;
        }
        leaf size-limit {
          type string;
        }
      }
    }
    list card {
      // NCS patched for predictable order
      ordered-by user;
      key "slot-number";
      leaf slot-number {
        type string;
      }
      container card-type {
        leaf card-type {
          tailf:cli-drop-node-name;
          type string;
        }
        leaf level {
          type string;
        }
      }
      leaf fail-on-error {
        type empty;
      }
      list mda {
        // NCS patched for predictable order
        ordered-by user;
        key "mda-slot";
        leaf mda-slot {
          type string;
        }
        list event {
          // NCS patched for predictable order
          ordered-by user;
          key "event-name";
          leaf event-name {
            type string;
          }
          leaf action {
            type string;
          }
          leaf action-alt {
            tailf:alt-name "action";
            type string;
          }
        }
        container mda-type {
          presence "true";
          leaf type {
            tailf:cli-drop-node-name;
            type string;
          }
          leaf level {
            type string;
          }
        }
        container access {
          container ingress {
            leaf fabric-policy {
              type string;
            }
          }
        }
        leaf fail-on-error {
          type empty;
        }
        container egress-xpl {
          leaf window {
            type string;
          }
        }
        container ingress {
          container mcast-path-management {
            leaf shutdown {
              type string;
            }
          }
        }
        container ingress-xpl {
          leaf window {
            type string;
          }
        }
        container network {
          container ingress {
            leaf fabric-policy {
              type string;
            }
            container pool {
              leaf slope-policy {
                type string;
              }
            }
            leaf queue-policy {
              type string;
            }
          }
        }
        leaf sync-e {
          type empty;
        }
        list upgrade {
          // NCS patched for predictable order
          ordered-by user;
          tailf:cli-suppress-mode;
          key "number";
          leaf number {
            type string;
          }
          leaf path {
            type string;
          }
        }
        leaf shutdown {
          type string;
        }
      }
      list fp {
        // NCS patched for predictable order
        ordered-by user;
        key "id";
        leaf id {
          type string;
        }
        leaf fp-resource-policy {
          type string;
        }
        leaf init-extract-prio-mode {
          type string;
        }
        container egress {
          container wred-queue-control {

            grouping max-min-grouping {
              leaf min {
                type string;
              }
              leaf max {
                type string;
              }
            }
            container buffer-allocation {
              uses max-min-grouping;
            }
            container resv-cbs {
              uses max-min-grouping;
            }
            leaf slope-policy {
              type string;
            }
            leaf shutdown {
              type string;
            }
          }
        }
        container ingress {
          container mcast-path-management {
            leaf bandwidth-policy {
              type string;
            }
            leaf shutdown {
              type string;
            }
          }
          container network {
            list queue-group {
              // NCS patched for predictable order
              ordered-by user;
              key "name instance";
              leaf name {
                type string;
              }
              leaf instance {
                type string;
              }
            }
            leaf queue-policy {
              type string;
            }
          }
        }
        container hi-bw-mcast-src {
          leaf alarm {
            type empty;
          }
          leaf default-paths-only {
            type empty;
          }
          leaf group {
            type string;
          }
        }
      }
      container xiom {
        container x1 {
          presence "true";
          container xiom-type {
            leaf type {
              tailf:cli-drop-node-name;
              type string;
            }
            leaf level {
              type string;
            }
          }
          list upgrade {
            // NCS patched for predictable order
            ordered-by user;
            tailf:cli-suppress-mode;
            key "id";
            leaf id {
              type string;
            }
            leaf path {
              type string;
            }
          }
          list mda {
            // NCS patched for predictable order
            ordered-by user;
            key "id";
            leaf id {
              type string;
            }
            leaf mda-type {
              type string;
            }
            leaf shutdown {
              type string;
            }
          }
          leaf shutdown {
            type string;
          }
        }
        container x2 {
          presence "true";
          container xiom-type {
            leaf type {
              tailf:cli-drop-node-name;
              type string;
            }
            leaf level {
              type string;
            }
          }
          list upgrade {
            // NCS patched for predictable order
            ordered-by user;
            tailf:cli-suppress-mode;
            key "id";
            leaf id {
              type string;
            }
            leaf path {
              type string;
            }
          }
          list mda {
            // NCS patched for predictable order
            ordered-by user;
            key "id";
            leaf id {
              type string;
            }
            leaf mda-type {
              type string;
            }
            leaf shutdown {
              type string;
            }
          }
          leaf shutdown {
            type string;
          }
        }
      }
      leaf reset-on-recoverable-error {
        type empty;
      }
      leaf shutdown {
        type string;
      }
      container redundancy {
        leaf revertive {
          type empty;
        }
        container takeover {
          leaf delay {
            type string;
          }
        }
      }
    }
    container cflowd {
      presence "present";
      leaf active-timeout {
        type string;
      }
      leaf active-flow-timeout {
        type string;
      }
      leaf cache-size {
        type string;
      }
      list collector {
        // NCS patched for predictable order
        ordered-by user;
        key "collector-id";
        leaf collector-id {
          type string;
        }
        leaf version {
          type string;
        }
        leaf description {
          type string;
        }
        leaf template-set {
          type string;
        }
        leaf router {
          type ncs_compliance_template_router-type;
        }
        container export-filter {
          container interface-list {
            list router {
              // NCS patched for predictable order
              ordered-by user;
              tailf:cli-suppress-mode;
              key "router-id interface";
              leaf router-id {
                type ncs_compliance_template_router-type;
              }
              leaf interface {
                type string;
              }
            }
            container service {
              list ies {
                // NCS patched for predictable order
                ordered-by user;
                tailf:cli-suppress-mode;
                key "ies-name interface";
                leaf ies-name {
                  type string;
                }
                leaf interface {
                  type string;
                }
              }
              list vprn {
                // NCS patched for predictable order
                ordered-by user;
                tailf:cli-suppress-mode;
                key "vprn-name interface";
                leaf vprn-name {
                  type string;
                }
                leaf interface {
                  type string;
                }
              }
            }
          }
        }
        leaf autonomous-system-type {
          type string;
        }
        leaf shutdown {
          type empty;
        }
      }
      leaf export-mode {
        type string;
      }
      leaf inactive-timeout {
        type string;
      }
      leaf inactive-flow-timeout {
        type string;
      }
      leaf overflow {
        type string;
      }
      leaf rate {
        type string;
      }
      leaf template-retransmit {
        type string;
      }
      list sample-profile {
        // NCS patched for predictable order
        ordered-by user;
        key "profile-id";
        leaf profile-id {
          type string;
        }
        leaf sample-rate {
          type string;
        }
      }
      leaf shutdown {
        type empty;
      }
    }
    list interface-group-handler {
      // NCS patched for predictable order
      ordered-by user;
      key "index";
      leaf index {
        type string;
      }
      leaf shutdown {
        type string;
      }
    }
    container ipsec {
      list ike-policy {
        // NCS patched for predictable order
        ordered-by user;
        key "ike-policy-id";
        leaf ike-policy-id {
          type string;
        }
        leaf auth-algorithm {
          type string;
        }
        leaf auth-method {
          type string;
        }
        leaf auto-eap-method {
          type string;
        }
        leaf auto-eap-own-method {
          type string;
        }
        leaf description {
          type string;
        }
        leaf dh-group {
          type string;
        }
        container dpd {
          presence "present";
          leaf interval {
            type string;
          }
          leaf max-retries {
            type string;
          }
          leaf reply-only {
            type empty;
          }
        }
        leaf encryption-algorithm {
          type string;
        }
        leaf ike-mode {
          type string;
        }
        leaf ike-transform {
          type string;
        }
        leaf ike-version {
          type string;
        }
        leaf ipsec-lifetime {
          type string;
        }
        leaf isakmp-lifetime {
          type string;
        }
        leaf match-peer-id-to-cert {
          type empty;
        }
        container nat-traversal {
          presence "present";
          leaf force {
            type empty;
          }
          leaf keep-alive-interval {
            type string;
          }
          leaf force-keep-alive {
            type empty;
          }
        }
        leaf own-auth-method {
          type string;
        }
        container pfs {
          presence "present";
          leaf dh-group {
            type string;
          }
        }
      }
      list ike-transform {
        // NCS patched for predictable order
        ordered-by user;
        key "ike-transform-id";
        leaf ike-transform-id {
          type string;
        }
        leaf dh-group {
          type string;
        }
        leaf ike-auth-algorithm {
          type string;
        }
        leaf ike-encryption-algorithm {
          type string;
        }
        leaf isakmp-lifetime {
          type string;
        }
      }
      list ipsec-transform {
        // NCS patched for predictable order
        ordered-by user;
        key "transform-id";
        leaf transform-id {
          type string;
        }
        leaf esp-auth-algorithm {
          type string;
        }
        leaf esp-encryption-algorithm {
          type string;
        }
        leaf ipsec-lifetime {
          type string;
        }
        leaf pfs-dh-group {
          type string;
        }
      }
      list cert-profile {
        // NCS patched for predictable order
        ordered-by user;
        key "profile-name";
        leaf profile-name {
          type ncs_compliance_template_string32;
        }
        list entry {
          // NCS patched for predictable order
          ordered-by user;
          key "entry-id";
          leaf entry-id {
            type string;
          }
          leaf cert {
            type string;
          }
          leaf key {
            type string;
          }
          container send-chain {
            list ca-profile {
              // NCS patched for predictable order
              ordered-by user;
              tailf:cli-suppress-mode;
              key "name";
              leaf name {
                type ncs_compliance_template_string32;
              }
            }
          }
        }
        leaf shutdown {
          type string;
        }
      }
      list static-sa {
        // NCS patched for predictable order
        ordered-by user;
        key "sa-name";
        leaf sa-name {
          type string;
        }
        container authentication {
          leaf auth-algorithm {
            tailf:cli-drop-node-name;
            type string;
          }
          leaf hex-or-ascii {
            tailf:cli-drop-node-name;
            type string;
          }
          leaf key-value {
            tailf:cli-drop-node-name;
            type string;
          }
          leaf hash-type {
            tailf:cli-drop-node-name;
            type ncs_compliance_template_hash-method;
          }
        }
        leaf description {
          type string;
        }
        leaf protocol {
          type string;
        }
        leaf spi {
          type string;
        }
      }
      list trust-anchor-profile {
        // NCS patched for predictable order
        ordered-by user;
        key "name";
        leaf name {
          type ncs_compliance_template_string32;
        }
        list trust-anchor {
          // NCS patched for predictable order
          ordered-by user;
          tailf:cli-suppress-mode;
          key "ca-profile-name";
          leaf ca-profile-name {
            type ncs_compliance_template_string32;
          }
        }
      }
      list tunnel-template {
        // NCS patched for predictable order
        ordered-by user;
        key "tunnel-template-id";
        leaf tunnel-template-id {
          type string;
        }
        leaf description {
          type string;
        }
        leaf clear-df-bit {
          type empty;
        }
        leaf ip-mtu {
          type string;
        }
        leaf encapsulated-ip-mtu {
          type string;
        }
        leaf sp-reverse-route {
          type empty;
        }
        leaf replay-window {
          type string;
        }
        leaf-list transform {
          // NCS patched for predictable order
          ordered-by user;
          type string;
        }
      }
    }
    list pw-port {
      // NCS patched for predictable order
      ordered-by user;
      key "pw-port-id";
      leaf pw-port-id {
        type string;
      }
      leaf description {
        type string;
      }
      leaf encap-type {
        type string;
      }
    }
    list port {
      // NCS patched for predictable order
      ordered-by user;
      key "port-id";
      leaf port-id {
        type string;
      }
      leaf description {
        type string;
      }
      container access {

        grouping port-xgress-grouping {
          container pool {
            leaf amber-alarm-threshold {
              type string;
            }
            leaf red-alarm-threshold {
              type string;
            }
            leaf resv-cbs {
              type string;
            }
            leaf slope-policy {
              type string;
            }
          }
        }
        container egress {
          uses port-xgress-grouping;
        }
        container ingress {
          uses port-xgress-grouping;
        }
      }
      leaf type {
        type string;
      }
      container aps {
        leaf neighbor {
          type string;
        }
        leaf switching-mode {
          type string;
        }
        leaf protect-circuit {
          type string;
        }
        container working-circuit {
          leaf port-id {
            tailf:cli-drop-node-name;
            type string;
          }
          leaf number {
            type string;
          }
        }
      }
      container connector {
        presence "true";
        container breakout {
          presence "true";
          leaf extra {
            tailf:cli-drop-node-name;
            type string;
          }
        }
        leaf rs-fec-mode {
          type string;
        }
      }
      container ethernet {
        leaf eth-bn-egress-rate-changes {
          type empty;
        }
        leaf egress-port-qos-policy {
          type string;
        }
        leaf connection-type {
          type string;
        }
        leaf mode {
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          type string;
        }
        leaf mode-alt {
          tailf:alt-name "mode";
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          type string;
        }
        container dampening {
          container suppress-threshold {
            leaf threshold {
              tailf:cli-drop-node-name;
              type string;
            }
            leaf reuse-threshold {
              type string;
            }
          }
          container half-life {
            leaf time {
              tailf:cli-drop-node-name;
              type string;
            }
            leaf max-suppress-time {
              type string;
            }
          }
          leaf shutdown {
            type string;
          }
        }
        leaf-list report-alarm {
          // NCS patched for predictable order
          ordered-by user;
          type string;
        }
        container disable {
          leaf-list report-alarm {
            // NCS patched for predictable order
            ordered-by user;
            type string;
          }
        }
        container access {
          leaf accounting-policy {
            type string;
          }
          leaf bandwidth {
            type string;
          }
          container egress {
            list vport {
              // NCS patched for predictable order
              ordered-by user;
              key "name";
              leaf name {
                type ncs_compliance_template_string32;
              }
              container agg-rate {
                leaf limit-unused-bandwidth {
                  type empty;
                }
                leaf rate {
                  type string;
                }
              }
              leaf description {
                type string;
              }
              leaf egress-rate-modify {
                type empty;
              }
              container host-match {
                list dest {
                  // NCS patched for predictable order
                  ordered-by user;
                  tailf:cli-suppress-mode;
                  key "destination-string";
                  leaf destination-string {
                    type ncs_compliance_template_string32;
                  }
                }
              }
              leaf mon-port-sch {
                type empty;
              }
              leaf port-scheduler-policy {
                type string;
              }
              leaf scheduler-policy {
                type string;
              }
            }
            list queue-group {
              // NCS patched for predictable order
              ordered-by user;
              key "queue-group-name";
              leaf queue-group-name {
                type string;
              }
              leaf instance {
                type string;
              }
              leaf description {
                type string;
              }
              container host-match {
                list dest {
                  // NCS patched for predictable order
                  ordered-by user;
                  tailf:cli-suppress-mode;
                  key "destination-string";
                  leaf destination-string {
                    type ncs_compliance_template_string32;
                  }
                }
              }
            }
            leaf qos {
              type string;
            }
          }
          container ingress {
            list queue-group {
              // NCS patched for predictable order
              ordered-by user;
              key "id";
              leaf id {
                type string;
              }
            }
          }
        }
        container crc-monitor {
          container sd-threshold {
            leaf treshold {
              tailf:cli-drop-node-name;
              type string;
            }
            leaf multiplier {
              type string;
            }
          }
          container sf-threshold {
            leaf treshold {
              tailf:cli-drop-node-name;
              type string;
            }
            leaf multiplier {
              type string;
            }
          }
          leaf window-size {
            type string;
          }
        }
        leaf collect-stats {
          type empty;
        }
        container autonegotiate {
          choice autonegotiate-choice {
            leaf disable {
              type empty;
            }
            leaf limited {
              type empty;
            }
          }
        }
        leaf dot1q-etype {
          type string;
        }
        container dot1x {
          container macsec {
            leaf rx-must-be-encrypted {
              type empty;
            }
            leaf-list exclude-protocol {
              // NCS patched for predictable order
              ordered-by user;
              type string;
            }
            list sub-port {
              // NCS patched for predictable order
              ordered-by user;
              key "port-id";
              leaf port-id {
                type string;
              }
              unique "ca-name";
              leaf ca-name {
                type string;
              }
              container encap-match {
                leaf encap {
                  tailf:cli-drop-node-name;
                  type string;
                }
                leaf encap-value {
                  tailf:cli-drop-node-name;
                  type string;
                }
              }
              leaf max-peer {
                type string;
              }
              leaf shutdown {
                type string;
              }
            }
          }
          leaf tunneling {
            type empty;
          }
        }
        container down-when-looped {
          leaf use-broadcast-address {
            type empty;
          }
          leaf shutdown {
            type string;
          }
        }
        leaf lacp-tunnel {
          type empty;
        }
        container efm-oam {
          leaf accept-remote-loopback {
            type empty;
          }
          leaf hold-time {
            type string;
          }
          container transmit-interval {
            leaf interval {
              tailf:cli-drop-node-name;
              type string;
            }
            leaf multiplier {
              type string;
            }
          }
          container link-monitoring {
            leaf shutdown {
              type string;
            }
          }
          leaf tunneling {
            type empty;
          }
          leaf shutdown {
            type string;
          }
        }
        container egress {
          list exp-secondary-shaper {
            // NCS patched for predictable order
            ordered-by user;
            key "secondary-shaper-name";
            leaf secondary-shaper-name {
              type string;
            }
            container agg-burst {
              container high-burst-increase {
                leaf size {
                  tailf:cli-drop-node-name;
                  type string;
                }
                leaf rate {
                  tailf:cli-drop-node-name;
                  type string;
                }
              }
              container low-burst-limit {
                leaf size {
                  tailf:cli-drop-node-name;
                  type string;
                }
                leaf rate {
                  tailf:cli-drop-node-name;
                  type string;
                }
              }
            }
            container class {
              leaf class-number {
                tailf:cli-drop-node-name;
                type string;
              }
              leaf rate {
                type string;
              }
            }
            leaf low-burst-max-class {
              type string;
            }
            container rate {
              leaf rate {
                tailf:cli-drop-node-name;
                type string;
              }
              leaf monitor-threshold {
                type string;
              }
            }
          }
          list queue-group {
            // NCS patched for predictable order
            ordered-by user;
            key "name";
            leaf name {
              type string;
            }
          }
          leaf scheduler-policy {
            type string;
          }
        }
        leaf egress-rate {
          type string;
        }
        leaf egress-scheduler-policy {
          // NCS drop tailf-common:cli-diff-create-before statement
          type string;
        }
        container egress-scheduler-override {
          presence "true";
          list level {
            // NCS patched for predictable order
            ordered-by user;
            tailf:cli-suppress-mode;
            key "priority-level";
            leaf priority-level {
              type string;
            }
            leaf rate {
              type string;
            }
            leaf cir {
              type string;
            }
          }
          leaf max-rate {
            type string;
          }
        }
        container hold-time {
          leaf up {
            type string;
          }
          leaf down {
            type string;
          }
          leaf unit {
            tailf:cli-drop-node-name;
            type string;
          }
        }
        leaf ingress-rate {
          type string;
        }
        container alt-ingress-rate {
          tailf:alt-name "ingress-rate";
          presence "true";
          leaf ingress-rate {
            tailf:cli-drop-node-name;
            type string;
          }
          leaf cbs {
            type string;
          }
          choice unit {
            leaf bytes {
              type empty;
            }
            leaf kilobytes {
              type empty;
            }
          }
          leaf src-pause {
            type empty;
          }
        }
        container lldp {
          list dest-mac {
            // NCS patched for predictable order
            ordered-by user;
            key "id";
            leaf id {
              type string;
            }
            leaf tunnel-nearest-bridge {
              type empty;
            }
            leaf notification {
              type empty;
            }
            leaf admin-status {
              type string;
            }
            leaf port-id-subtype {
              type string;
            }
            leaf-list tx-mgmt-address {
              // NCS patched for predictable order
              ordered-by user;
              type string;
            }
            leaf-list tx-tlvs {
              // NCS patched for predictable order
              ordered-by user;
              type string;
            }
          }
        }
        leaf encap-type {
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          type string;
        }
        leaf mac {
          type ncs_compliance_template_ieee-mac;
        }
        leaf mtu {
          type string;
        }
        leaf duplex {
          type string;
        }
        leaf speed {
          type ncs_compliance_template_port-speed;
        }
        leaf alt-speed {
          tailf:alt-name "speed";
          type ncs_compliance_template_port-speed;
        }
        container network {
          leaf accounting-policy {
            type string;
          }
          leaf collect-stats {
            type empty;
          }
          container egress {
            list queue-group {
              // NCS patched for predictable order
              ordered-by user;
              key "id";
              leaf id {
                type string;
              }
              leaf instance {
                type string;
              }
              leaf accounting-policy {
                type string;
              }
              uses ncs_compliance_template_agg-rate-grouping;
              leaf collect-stats {
                type empty;
              }
              leaf description {
                type string;
              }
              leaf policer-control-policy {
                type string;
              }
              container queue-overrides {
                list queue {
                  // NCS patched for predictable order
                  ordered-by user;
                  key "queue-id";
                  leaf queue-id {
                    type string;
                  }
                }
              }
              leaf scheduler-policy {
                type string;
              }
            }
          }
          leaf queue-policy {
            type string;
          }
          leaf scheduler-mode {
            type ncs_compliance_template_scheduler-mode;
          }
          leaf qos {
            type string;
          }
        }
        leaf qinq-etype {
          type string;
        }
        container ssm {
          leaf code-type {
            type string;
          }
          leaf tx-dus {
            type empty;
          }
          leaf shutdown {
            type string;
          }
        }
        leaf util-stats-interval {
          type string;
        }
        leaf xgig {
          type string;
        }
        leaf xor-mode {
          type string;
        }
        container down-on-internal-error {
          presence "true";
          leaf tx-disable {
            type empty;
          }
        }
        leaf rs-fec-mode {
          type string;
        }
      }
      container hybrid-buffer-allocation {

        grouping xgress-weights {
          leaf access {
            type string;
          }
          leaf network {
            type string;
          }
        }
        container egr-weight {
          uses xgress-weights;
        }
        container ing-weight {
          uses xgress-weights;
        }
      }
      container transceiver {
        leaf digital-coherent-optics {
          type empty;
        }
      }
      container dwdm {
        container amplifier {
          leaf-list report-alarms {
            // NCS patched for predictable order
            ordered-by user;
            type string;
          }
        }
        leaf channel {
          type string;
        }
        container coherent {
          leaf target-power {
            type string;
          }
          leaf compatibility {
            type string;
          }
          container sweep {
            leaf start {
              type string;
            }
            leaf end {
              type string;
            }
          }
          leaf channel {
            type string;
          }
          leaf mode {
            type string;
          }
          leaf rx-los-thresh {
            type string;
          }
        }
        leaf frequency {
          type string;
        }
        leaf rxdtv-adjust {
          type empty;
        }
        container tdcm {
          leaf channel {
            type string;
          }
          leaf dispersion {
            type string;
          }
          leaf mode {
            type string;
          }
          leaf-list report-alarms {
            // NCS patched for predictable order
            ordered-by user;
            type string;
          }
          container sweep {
            leaf start {
              type string;
            }
            leaf end {
              type string;
            }
          }
          leaf shutdown {
            type string;
          }
        }
      }
      container modify-buffer-allocation-rate {
        leaf egr-percentage-of-rate {
          type string;
        }
        leaf ing-percentage-of-rate {
          type string;
        }
      }
      container multilink-bundle {
        leaf fragment-threshold {
          type string;
        }
        list member {
          // NCS patched for predictable order
          ordered-by user;
          tailf:cli-suppress-mode;
          key "id";
          leaf id {
            type string;
          }
        }
      }
      container network {
        container egress {
          container pool {
            leaf slope-policy {
              type string;
            }
          }
        }
      }
      container otu {
        presence "present";
        leaf async-mapping {
          type empty;
        }
        leaf fec {
          type string;
        }
        leaf otu2-lan-data-rate {
          type string;
        }
        leaf-list report-alarm {
          // NCS patched for predictable order
          ordered-by user;
          type string;
        }
        leaf sd-threshold {
          type string;
        }
        leaf sf-sd-method {
          type string;
        }
        leaf sf-threshold {
          type string;
        }
        container sm-tti {
          container expected {
            choice expected {
              leaf string {
                type string;
              }
              leaf bytes {
                type string;
              }
              leaf use-rx {
                type empty;
              }
            }
          }
          container tx {
            choice tx {
              leaf string {
                type string;
              }
              leaf bytes {
                type string;
              }
            }
          }
        }
      }
      container sonet-sdh {
        leaf clock-source {
          type string;
        }
        leaf framing {
          type string;
        }
        list group {
          // NCS patched for predictable order
          ordered-by user;
          tailf:cli-suppress-mode;
          // NCS drop tailf-common:cli-diff-create-before statement
          key "sonet-sdh-index";
          leaf sonet-sdh-index {
            type string;
          }
          leaf payload {
            type string;
          }
        }
        container hold-time {
          leaf up {
            type string;
          }
          leaf down {
            type string;
          }
        }
        leaf loopback {
          type string;
        }

        grouping port-sonet-sdh-path-grouping {
          leaf mode {
            type string;
          }
          leaf encap-type {
            type string;
          }
          leaf egress-scheduler-policy {
            type string;
          }
          leaf crc {
            type string;
          }
          leaf scramble {
            type empty;
          }
          container network {
            leaf queue-policy {
              type string;
            }
          }
          leaf payload {
            type string;
          }
          container frame-relay {
            leaf lmi-type {
              type string;
            }
            leaf mode {
              type string;
            }
          }
          leaf-list report-alarm {
            // NCS patched for predictable order
            ordered-by user;
            type string;
          }
          leaf shutdown {
            type string;
          }
        }
        container path-sts3-wrapper {
          tailf:cli-drop-node-name;
          container path {
            container sts3 {
              presence "true";
              uses port-sonet-sdh-path-grouping;
            }
          }
        }
        list path {
          // NCS patched for predictable order
          ordered-by user;
          key "sonet-sdh-index";
          leaf sonet-sdh-index {
            type string;
          }
          uses port-sonet-sdh-path-grouping;
        }
        leaf-list report-alarm {
          // NCS patched for predictable order
          ordered-by user;
          type string;
        }
        container section-trace {
          choice a {
            leaf increment-z0 {
              type empty;
            }
            leaf byte {
              type string;
            }
            leaf string {
              type string;
            }
          }
        }
        leaf single-fiber {
          type empty;
        }
        leaf speed {
          type string;
        }
        leaf suppress-lo-alarm {
          type empty;
        }
        container threshold {
          leaf value {
            tailf:cli-drop-node-name;
            type string;
          }
          leaf rate {
            type string;
          }
        }
        leaf tx-dus {
          type empty;
        }
      }
      container tdm {
        leaf buildout {
          type string;
        }
        list ds1 {
          // NCS patched for predictable order
          ordered-by user;
          key "ds1-id";
          leaf ds1-id {
            type string;
          }
          container bert {
            leaf value {
              type string;
            }
            leaf duration {
              type string;
            }
          }
          leaf bit-error-insertion {
            type string;
          }
          leaf framing {
            type string;
          }
          list channel-group {
            // NCS patched for predictable order
            ordered-by user;
            key "id";
            leaf id {
              type string;
            }
            leaf clock-source {
              type string;
            }
            leaf encap-type {
              type string;
            }
            container ppp {
              leaf ber-sf-link-down {
                type empty;
              }
            }
            leaf timeslots {
              type string;
            }
            leaf shutdown {
              type string;
            }
          }
          leaf clock-source {
            type string;
          }
          leaf invert-data {
            type empty;
          }
          leaf loopback {
            type string;
          }
          leaf remote-loop-respond {
            type empty;
          }
          leaf-list report-alarm {
            // NCS patched for predictable order
            ordered-by user;
            type string;
          }
          leaf signal-mode {
            type string;
          }
          container threshold {
            leaf value {
              type string;
            }
            leaf rate {
              type string;
            }
          }
          leaf shutdown {
            type string;
          }
        }
        list ds3 {
          // NCS patched for predictable order
          ordered-by user;
          key "ds3-id";
          leaf ds3-id {
            type string;
          }
          container bert {
            leaf value {
              type string;
            }
          }
          leaf channelized {
            type string;
          }
          leaf clock-source {
            type string;
          }
          leaf encap-type {
            type string;
          }
          leaf shutdown {
            type string;
          }
        }
        list e1 {
          // NCS patched for predictable order
          ordered-by user;
          key "e1-id";
          leaf e1-id {
            type string;
          }
          leaf framing {
            type string;
          }
          leaf clock-source {
            type string;
          }
          list channel-group {
            // NCS patched for predictable order
            ordered-by user;
            key "channel-group-id";
            leaf channel-group-id {
              type string;
            }
            leaf encap-type {
              type string;
            }
            leaf-list timeslots {
              // NCS patched for predictable order
              ordered-by user;
              tailf:cli-range-list-syntax;
              type string;
            }
            leaf shutdown {
              type string;
            }
          }
          leaf shutdown {
            type string;
          }
        }
        leaf lbo {
          type string;
        }
        leaf length {
          type string;
        }
      }
      leaf shutdown {
        type string;
      }
    }
    container isa {
      list application-assurance-group {
        // NCS patched for predictable order
        ordered-by user;
        key "aa-group-id";
        leaf aa-group-id {
          type string;
        }
        leaf aa-sub-scale {
          type string;
        }
        leaf shutdown {
          type string;
        }
      }
      list tunnel-group {
        // NCS patched for predictable order
        ordered-by user;
        key "tunnel-group-id";
        leaf tunnel-group-id {
          type string;
        }
        leaf isa-scale-mode {
          type string;
        }
        leaf active-mda-number {
          type string;
        }
        leaf ipsec-responder-only {
          type empty;
        }
        leaf description {
          type string;
        }
        leaf multi-active {
          type empty;
        }
        list mda {
          // NCS patched for predictable order
          ordered-by user;
          tailf:cli-suppress-mode;
          key "mda";
          leaf mda {
            type string;
          }
        }
        leaf primary {
          type string;
        }
        list esa-vm {
          // NCS patched for predictable order
          ordered-by user;
          tailf:cli-suppress-mode;
          key "esa-id vm-id";
          leaf esa-id {
            type string;
          }
          leaf vm-id {
            type string;
          }
        }
        leaf reassembly {
          type string;
        }
        leaf shutdown {
          type string;
        }
      }
      list nat-group {
        // NCS patched for predictable order
        ordered-by user;
        key "nat-group-id";
        leaf nat-group-id {
          type string;
        }
        leaf description {
          type string;
        }
        leaf active-mda-limit {
          type string;
        }
        leaf mda {
          type string;
        }
        leaf shutdown {
          type string;
        }
      }
    }
    container port-xc {
      list pxc {
        // NCS patched for predictable order
        ordered-by user;
        // NCS drop tailf-common:cli-diff-create-before statement
        key "pxc-id";
        leaf pxc-id {
          type string;
        }
        leaf description {
          type string;
        }
        leaf port {
          type string;
        }
        leaf shutdown {
          type string;
        }
      }
    }
    container macsec {
      list connectivity-association {
        // NCS patched for predictable order
        ordered-by user;
        key "name";
        leaf name {
          type string;
        }
        leaf description {
          type string;
        }
        container static-cak {
          list pre-shared-key {
            // NCS patched for predictable order
            ordered-by user;
            key "key-id encryption-type";
            leaf key-id {
              type string;
            }
            leaf encryption-type {
              type string;
            }
            container cak {
              leaf val {
                tailf:cli-drop-node-name;
                type string;
              }
              leaf algo {
                tailf:cli-drop-node-name;
                type string;
              }
            }
            leaf ckn {
              type string;
            }
          }
        }
        leaf shutdown {
          type string;
        }
      }
    }
    list lag {
      // NCS patched for predictable order
      ordered-by user;
      // NCS drop tailf-common:cli-diff-create-before statement
      // NCS drop tailf-common:cli-diff-create-before statement
      // NCS drop tailf-common:cli-diff-create-before statement
      // NCS drop tailf-common:cli-diff-create-before statement
      // NCS drop tailf-common:cli-diff-create-before statement
      // NCS drop tailf-common:cli-diff-create-before statement
      // NCS drop tailf-common:cli-diff-create-before statement
      key "id";
      leaf id {
        type string;
      }
      leaf name {
        type string;
      }
      leaf description {
        type string;
      }
      container hash-weight-threshold {
        leaf weight {
          tailf:cli-drop-node-name;
          type string;
        }
        leaf action {
          type string;
        }
        leaf cost {
          type string;
        }
      }
      leaf port-weight-speed {
        type string;
      }
      container hold-time {
        leaf down {
          type string;
        }
      }
      container bfd {
        list family {
          // NCS patched for predictable order
          ordered-by user;
          key "family";
          leaf family {
            type string;
          }
          leaf bfd-on-distributing-only {
            type empty;
          }
          leaf local-ip-address {
            type string;
          }
          leaf max-admin-down-time {
            type string;
          }
          leaf max-setup-time {
            type string;
          }
          leaf multiplier {
            type string;
          }
          leaf receive-interval {
            type string;
          }
          leaf remote-ip-address {
            type string;
          }
          leaf transmit-interval {
            type string;
          }
          leaf shutdown {
            type string;
          }
        }
      }
      leaf port-type {
        type string;
      }
      list port {
        // NCS patched for predictable order
        ordered-by user;
        tailf:cli-suppress-mode;
        // NCS drop tailf-common:cli-diff-create-before statement
        key "port-id";
        leaf port-id {
          type string;
        }
        leaf sub-group {
          type string;
        }
        container priority {
          leaf priority {
            tailf:cli-drop-node-name;
            type string;
          }
          leaf sub-group {
            type string;
          }
        }
      }
      container per-link-hash {
        tailf:cli-drop-node-name;
        leaf per-link-hash {
          // NCS drop tailf-common:cli-diff-create-before statement
          // NCS drop tailf-common:cli-diff-create-before statement
          // NCS drop tailf-common:cli-diff-create-before statement
          // NCS drop tailf-common:cli-diff-create-before statement
          // NCS drop tailf-common:cli-diff-create-before statement
          type empty;
        }
        leaf weighted {
          type empty;
        }
        leaf auto-rebalance {
          type empty;
        }
      }
      container access {
        container adapt-qos {
          leaf adapt {
            tailf:cli-drop-node-name;
            type string;
          }
          leaf include-egr-hash-cfg {
            type empty;
          }
        }
        leaf per-fp-egr-queuing {
          type empty;
        }
        leaf per-fp-ing-queuing {
          type empty;
        }
        leaf per-fp-sap-instance {
          type empty;
        }
      }
      leaf mode {
        // NCS drop tailf-common:cli-diff-create-before statement
        // NCS drop tailf-common:cli-diff-create-before statement
        // NCS drop tailf-common:cli-diff-create-before statement
        // NCS drop tailf-common:cli-diff-create-before statement
        // NCS drop tailf-common:cli-diff-create-before statement
        // NCS drop tailf-common:cli-diff-create-before statement
        // NCS drop tailf-common:cli-diff-create-before statement
        // NCS drop tailf-common:cli-diff-create-before statement
        type string;
      }
      leaf monitor-oper-group {
        type string;
      }
      leaf encap-type {
        // NCS drop tailf-common:cli-diff-create-before statement
        // NCS drop tailf-common:cli-diff-create-before statement
        // NCS drop tailf-common:cli-diff-create-before statement
        // NCS drop tailf-common:cli-diff-create-before statement
        // NCS drop tailf-common:cli-diff-create-before statement
        // NCS drop tailf-common:cli-diff-create-before statement
        // NCS drop tailf-common:cli-diff-create-before statement
        type string;
      }
      leaf dynamic-cost {
        type empty;
      }
      leaf mac {
        type string;
      }
      list link-map-profile {
        // NCS patched for predictable order
        ordered-by user;
        key "link-map-profile-id";
        leaf link-map-profile-id {
          type string;
        }
        leaf description {
          type string;
        }
        leaf failure-mode {
          type string;
        }
        list link {
          // NCS patched for predictable order
          ordered-by user;
          tailf:cli-suppress-mode;
          key "port-id";
          leaf port-id {
            type string;
          }
          leaf role {
            tailf:cli-drop-node-name;
            type string;
          }
        }
      }
      container port-threshold {
        leaf value {
          tailf:cli-drop-node-name;
          type string;
        }
        leaf action {
          type string;
        }
      }
      container scheduler-mode {
        container vlan-qos {
          presence "true";
          list vlan-qos-policy {
            // NCS patched for predictable order
            ordered-by user;
            key "vlan-qos-policy-name";
            leaf vlan-qos-policy-name {
              type string;
            }
            container agg-rate {
              container rate {
                leaf pir {
                  tailf:cli-drop-node-name;
                  type string;
                }
                leaf cir {
                  type string;
                }
              }
            }
          }
        }
      }
      container lacp {
        leaf mode {
          tailf:cli-drop-node-name;
          type string;
        }
        leaf administrative-key {
          type string;
        }
        leaf system-id {
          type string;
        }
        leaf system-priority {
          type string;
        }
      }
      leaf lacp-mux-control {
        type string;
      }
      leaf lacp-xmit-interval {
        type string;
      }
      leaf lacp-xmit-standby {
        type empty;
      }
      container selection-criteria {
        leaf criteria {
          tailf:cli-drop-node-name;
          type string;
        }
        leaf slave-to-partner {
          type empty;
        }
        leaf subgroup-hold-time {
          type string;
        }
      }
      leaf standby-signaling {
        type string;
      }
      container weight-threshold {
        leaf value {
          tailf:cli-drop-node-name;
          type string;
        }
        leaf action {
          type string;
        }
      }
      leaf shutdown {
        type string;
      }
    }
    container fwd-path-ext {
      container sdp-id-range {
        leaf from {
          type string;
        }
        leaf to {
          type string;
        }
      }
      list fpe {
        // NCS patched for predictable order
        ordered-by user;
        key "fpe-id";
        leaf fpe-id {
          type string;
        }
        container path {
          leaf pxc {
            type string;
          }
          leaf xc-a {
            type string;
          }
          leaf xc-b {
            type string;
          }
        }
        leaf pw-port {
          type empty;
        }
      }
    }
    container cron {
      list script {
        // NCS patched for predictable order
        ordered-by user;
        key "id";
        leaf id {
          type string;
        }
        leaf description {
          type string;
        }
        leaf location {
          type string;
        }
        leaf shutdown {
          type string;
        }
      }
      list action {
        // NCS patched for predictable order
        ordered-by user;
        key "id";
        leaf id {
          type string;
        }
        leaf max-completed {
          type string;
        }
        leaf expire-time {
          type ncs_compliance_template_expire-time;
        }
        leaf lifetime {
          type ncs_compliance_template_expire-time;
        }
        leaf results {
          type string;
        }
        leaf script {
          type string;
        }
        leaf shutdown {
          type string;
        }
      }
      uses ncs_compliance_template_cron-schedule-grouping {
        augment "schedule" {
          leaf action {
            type string;
          }
        }
      }
    }
    container mcast-management {
      list bandwidth-policy {
        // NCS patched for predictable order
        ordered-by user;
        key "policy-name";
        leaf policy-name {
          type ncs_compliance_template_string32;
        }

        grouping path-grouping {
          leaf path-limit {
            type string;
          }
        }
        container primary-path {
          uses path-grouping;
        }
        container secondary-path {
          uses path-grouping;
        }
      }
      container chassis-level {
        leaf round-robin-inactive-records {
          type empty;
        }
        container per-mcast-plane-capacity {

          grouping capacity-percentage-grouping {
            leaf primary-percentage {
              tailf:cli-drop-node-name;
              type string;
            }
            leaf secondary {
              type string;
            }
          }
          container mcast-capacity {
            uses capacity-percentage-grouping;
          }
          container redundant-mcast-capacity {
            uses capacity-percentage-grouping;
          }
          leaf total-capacity {
            type string;
          }
        }
      }
      list multicast-info-policy {
        // NCS patched for predictable order
        ordered-by user;
        key "policy-name";
        leaf policy-name {
          type ncs_compliance_template_string32;
        }
        list bundle {
          // NCS patched for predictable order
          ordered-by user;
          key "bundle-name";
          leaf bundle-name {
            type ncs_compliance_template_string32;
          }
          leaf keepalive-override {
            type string;
          }
          list channel {
            // NCS patched for predictable order
            ordered-by user;
            key "ip-address";
            leaf ip-address {
              type string;
            }
            leaf second-ip-address {
              tailf:cli-drop-node-name;
              type string;
            }
            container bw-activity {
              leaf activity {
                tailf:cli-drop-node-name;
                type string;
              }
              leaf falling-delay {
                type string;
              }
              leaf black-hole-rate {
                type string;
              }
            }
          }
          leaf description {
            type string;
          }
        }
      }
    }
    container oam-pm {
      list bin-group {
        // NCS patched for predictable order
        ordered-by user;
        key "bin-group-number";
        leaf bin-group-number {
          type string;
        }
        leaf fd-bin-count {
          type string;
        }
        leaf fdr-bin-count {
          type string;
        }
        leaf ifdv-bin-count {
          type string;
        }
        leaf description {
          type string;
        }
        list bin-type {
          // NCS patched for predictable order
          ordered-by user;
          key "bt";
          leaf bt {
            type string;
          }
          list bin {
            // NCS patched for predictable order
            ordered-by user;
            key "bin-number";
            leaf bin-number {
              type string;
            }
            leaf lower-bound {
              type string;
            }
          }

          typedef bin-group-event-type {
            type string;
          }
          list delay-event {
            // NCS patched for predictable order
            ordered-by user;
            tailf:cli-suppress-mode;
            key "event-type";
            leaf event-type {
              type bin-group-event-type;
            }
            leaf lowest-bin {
              type string;
            }
            leaf threshold {
              type string;
            }
            leaf clear {
              type string;
            }
          }
          list delay-event-exclusion {
            // NCS patched for predictable order
            ordered-by user;
            tailf:cli-suppress-mode;
            key "event-type";
            leaf event-type {
              type bin-group-event-type;
            }
            leaf lowest-bin {
              type string;
            }
          }
        }
        leaf shutdown {
          type string;
        }
      }
      list session {
        // NCS patched for predictable order
        ordered-by user;
        key "session-name";
        leaf session-name {
          type ncs_compliance_template_string32;
        }
        leaf test-family {
          type string;
        }
        leaf session-type {
          type string;
        }
        leaf bin-group {
          type string;
        }
        leaf description {
          type string;
        }
        list meas-interval {
          // NCS patched for predictable order
          ordered-by user;
          // NCS drop tailf-common:cli-diff-create-before statement
          key "interval";
          leaf interval {
            type string;
          }
          leaf accounting-policy {
            type string;
          }
          leaf intervals-stored {
            type string;
          }
          container event-mon {
            leaf delay-events {
              type empty;
            }
            leaf loss-events {
              type empty;
            }
            leaf shutdown {
              type string;
            }
          }
        }
        container ip {
          leaf router-instance {
            type string;
          }
          leaf source-udp-port {
            type string;
          }
          leaf destination {
            type string;
          }
          leaf source {
            type string;
          }
          leaf dest-udp-port {
            type string;
          }
          list twamp-light {
            // NCS patched for predictable order
            ordered-by user;
            key "test-id";
            leaf test-id {
              type string;
            }
            leaf record-stats {
              type string;
            }
            leaf shutdown {
              type string;
            }
          }
        }
        container ethernet {
          leaf dest-mac {
            type ncs_compliance_template_ieee-mac;
          }
          leaf priority {
            type string;
          }
          container source {
            leaf mep {
              type string;
            }
            leaf domain {
              type string;
            }
            leaf association {
              type string;
            }
          }
          container dmm {
            leaf test-id {
              type string;
            }
            leaf shutdown {
              type string;
            }
          }
        }
      }
    }
    container qos {
      list adv-config-policy {
        // NCS patched for predictable order
        ordered-by user;
        key "adv-config-policy-name";
        leaf adv-config-policy-name {
          type string;
        }
        container child-control {
          container offered-measurement {
            leaf fast-start {
              type empty;
            }
            leaf fast-stop {
              type empty;
            }
          }
        }
        leaf description {
          type string;
        }
      }
      list dot1p-fc-map {
        // NCS patched for predictable order
        ordered-by user;
        key "name";
        leaf name {
          type string;
        }
        container default-action {
          leaf fc {
            type string;
          }
          leaf profile {
            type string;
          }
        }
        list dot1p {
          // NCS patched for predictable order
          ordered-by user;
          tailf:cli-suppress-mode;
          key "priority";
          leaf priority {
            type string;
          }
          leaf fc {
            type string;
          }
          leaf profile {
            type string;
          }
        }
      }
      list egress-remark-policy {
        // NCS patched for predictable order
        ordered-by user;
        key "egress-remark-policy-name";
        leaf egress-remark-policy-name {
          type string;
        }
        leaf description {
          type string;
        }
        list fc {
          // NCS patched for predictable order
          ordered-by user;
          key "fc-name";
          leaf fc-name {
            type ncs_compliance_template_fc-name;
          }
          container dscp {
            choice dscp {
              leaf dscp-name {
                tailf:cli-drop-node-name;
                type string;
              }
              case in-out {
                leaf in-profile {
                  type string;
                }
                leaf out-profile {
                  type string;
                }
              }
            }
          }
          container dot1p {
            uses ncs_compliance_template_dot1p-params-grouping;
          }
          container lsp-exp {
            choice lsp-exp {
              leaf lsp-exp-value {
                tailf:cli-drop-node-name;
                type string;
              }
              case in-out {
                leaf in-profile {
                  type string;
                }
                leaf out-profile {
                  type string;
                }
              }
            }
          }
        }
      }
      list fp-resource-policy {
        // NCS patched for predictable order
        ordered-by user;
        key "policy-id";
        leaf policy-id {
          type string;
        }
        leaf description {
          type string;
        }
      }
      container packet-byte-offset {
        leaf shutdown {
          type string;
        }
      }
      list ingress-classification-policy {
        // NCS patched for predictable order
        ordered-by user;
        key "name";
        leaf name {
          type string;
        }
        leaf description {
          type string;
        }
        leaf allow-attachment {
          type string;
        }
        container default-action {
          leaf fc {
            type ncs_compliance_template_fc-name;
          }
          leaf profile {
            type ncs_compliance_template_in-out;
          }
        }
        uses ncs_compliance_template_qos-dscp-list-grouping;
        uses ncs_compliance_template_qos-lsp-exp-grouping;
        uses ncs_compliance_template_qos-dot1p-list-grouping;
      }
      list network-ingress {
        // NCS patched for predictable order
        ordered-by user;
        key "name";
        leaf name {
          type string;
        }
        leaf description {
          type string;
        }
        leaf ingress-classification-policy {
          type string;
        }
        list policer {
          // NCS patched for predictable order
          ordered-by user;
          key "policer-id";
          leaf policer-id {
            type string;
          }
          // NCS expand uses statement
          container cbs {
            // NCS expand uses statement
            leaf size {
              tailf:cli-drop-node-name;
              type string;
            }
            leaf unit {
              tailf:cli-drop-node-name;
              type string;
            }
          }
          container mbs {
            // NCS expand uses statement
            leaf size {
              tailf:cli-drop-node-name;
              type string;
            }
            leaf unit {
              tailf:cli-drop-node-name;
              type string;
            }
          }
          container rate {
            leaf pir {
              tailf:cli-drop-node-name;
              type ncs_compliance_template_rate-type;
            }
            leaf cir {
              type ncs_compliance_template_rate-type;
            }
          }
          leaf stat-mode {
            type ncs_compliance_template_policer-stat-mode;
          }
        }
        list fc {
          // NCS patched for predictable order
          ordered-by user;
          key "fc-name";
          leaf fc-name {
            type ncs_compliance_template_fc-name;
          }
          leaf multicast-policer {
            type string;
          }
          leaf policer {
            type string;
          }
        }
      }
      list port-qos-policy {
        // NCS patched for predictable order
        ordered-by user;
        key "port-qos-policy-name";
        leaf port-qos-policy-name {
          type string;
        }
        leaf description {
          type string;
        }
        list queue {
          // NCS patched for predictable order
          ordered-by user;
          key "queue-id";
          leaf queue-id {
            type string;
          }
          leaf queue-mgmt {
            type string;
          }
          container scheduler-mode {
            leaf scheduler-mode {
              tailf:cli-drop-node-name;
              type string;
            }
            leaf pir-weight {
              type string;
            }
            uses ncs_compliance_template_qos-queue-percent-rate-grouping;
          }
        }
        container packet-byte-offset {
          leaf add {
            type string;
          }
          leaf subtract {
            type string;
          }
        }
        list wrr-weights {
          // NCS patched for predictable order
          ordered-by user;
          key "wrr-weights-id";
          leaf wrr-weights-id {
            type string;
          }
          leaf mc-weight {
            type string;
          }
          leaf uc-weight {
            type string;
          }
        }
      }
      list queue-mgmt-policy {
        // NCS patched for predictable order
        ordered-by user;
        key "queue-mgmt-name";
        leaf queue-mgmt-name {
          type string;
        }
        leaf description {
          type string;
        }
        container high-slope {
          uses ncs_compliance_template_slope-params-grouping;
        }
        container low-slope {
          uses ncs_compliance_template_slope-params-grouping;
        }
        container exceed-slope {
          uses ncs_compliance_template_slope-params-grouping;
        }
        container highplus-slope {
          uses ncs_compliance_template_slope-params-grouping;
        }
        leaf mbs {
          type string;
        }
      }
      list vlan-qos-policy {
        // NCS patched for predictable order
        ordered-by user;
        key "policy-id";
        leaf policy-id {
          type string;
        }
        leaf description {
          type string;
        }
        container packet-byte-offset {
          leaf add {
            type string;
          }
          leaf subtract {
            type string;
          }
        }
        leaf stat-mode {
          type string;
        }
        list cir-weight-profile {
          // NCS patched for predictable order
          ordered-by user;
          key "profile-id";
          leaf profile-id {
            type string;
          }
          leaf weight {
            type string;
          }
        }
        list queue {
          // NCS patched for predictable order
          ordered-by user;
          key "queue-id";
          leaf queue-id {
            type string;
          }
          uses ncs_compliance_template_qos-queue-percent-rate-grouping;
          leaf queue-mgmt {
            type string;
          }
          container queue-type {
            leaf queue-type-alt1 {
              tailf:cli-drop-node-name;
              type ncs_compliance_template_queue-type;
            }
            leaf queue-type-alt2 {
              tailf:cli-drop-node-name;
              type ncs_compliance_template_queue-type;
            }
            leaf queue-type-alt3 {
              tailf:cli-drop-node-name;
              type ncs_compliance_template_queue-type;
            }
            uses ncs_compliance_template_qos-queue-percent-rate-grouping;
            leaf cir-weight-profile {
              type string;
            }
          }
        }
      }
      leaf ldp-local-fc-enable {
        type string;
      }
      list dscp-classification {
        // NCS patched for predictable order
        ordered-by user;
        key "classification-id";
        leaf classification-id {
          type string;
        }
        leaf description {
          type string;
        }
        uses ncs_compliance_template_qos-dscp-list-grouping;
      }
      list fabric-profile {
        // NCS patched for predictable order
        ordered-by user;
        key "policy-id";
        leaf policy-id {
          type string;
        }
        leaf mode {
          tailf:cli-drop-node-name;
          type string;
        }
        container aggregate-rate {
          leaf rate {
            tailf:cli-drop-node-name;
            type string;
          }
          leaf unshaped-sap-cir {
            type string;
          }
        }
        leaf description {
          type string;
        }
        list dest-mda {
          // NCS patched for predictable order
          ordered-by user;
          key "id";
          leaf id {
            type string;
          }
          leaf rate {
            type string;
          }
        }
      }
      container match-list {
        list ip-prefix-list {
          // NCS patched for predictable order
          ordered-by user;
          key "ip-prefix-list-name";
          leaf ip-prefix-list-name {
            type ncs_compliance_template_string32;
          }
          leaf description {
            type string;
          }
          list prefix {
            // NCS patched for predictable order
            ordered-by user;
            tailf:cli-suppress-mode;
            key "ip-prefix";
            leaf ip-prefix {
              type string;
            }
          }
        }
        list ipv6-prefix-list {
          // NCS patched for predictable order
          ordered-by user;
          key "name";
          leaf name {
            type ncs_compliance_template_string32;
          }
          leaf description {
            type string;
          }
          list prefix {
            // NCS patched for predictable order
            ordered-by user;
            tailf:cli-suppress-mode;
            key "ip-prefix";
            leaf ip-prefix {
              type string;
            }
          }
        }
      }
      container mc-mlppp {
        list sap-egress {
          // NCS patched for predictable order
          ordered-by user;
          key "policy-id";
          uses ncs_compliance_template_sap-egress-common-grouping;
          list fc {
            // NCS patched for predictable order
            ordered-by user;
            key "fc-name";
            uses ncs_compliance_template_sap-egress-fc-grouping;
          }
          leaf scope {
            type string;
          }
        }
      }
      list network-queue {
        // NCS patched for predictable order
        ordered-by user;
        key "network-queue-name";
        leaf network-queue-name {
          type string;
        }
        leaf description {
          type string;
        }
        list queue {
          // NCS patched for predictable order
          ordered-by user;
          key "id";
          leaf id {
            type string;
          }
          leaf multipoint {
            type empty;
          }
          leaf queue-type {
            tailf:cli-drop-node-name;
            type ncs_compliance_template_queue-type;
          }
          leaf mbs {
            type string;
          }
          leaf cbs {
            type string;
          }
          leaf high-prio-only {
            type string;
          }
          container rate {
            leaf percent {
              tailf:cli-drop-node-name;
              type string;
            }
            leaf cir {
              type string;
            }
            leaf pir {
              type string;
            }
          }
          uses ncs_compliance_template_port-parent-grouping;
          leaf queue-mgmt {
            type string;
          }
          leaf queue-mode {
            type string;
          }
          uses ncs_compliance_template_queue-adaptation-grouping;
          container drop-tail {
            container low {
              leaf percent-reduction-from-mbs {
                type string;
              }
            }
          }
        }
        list fc {
          // NCS patched for predictable order
          ordered-by user;
          key "id";
          leaf id {
            type string;
          }
          leaf multicast-queue {
            type string;
          }
          leaf queue {
            type string;
          }
          container egress-hsmda {
            leaf queue {
              type string;
            }
          }
        }
      }
      container queue-group-templates {
        container egress {
          list queue-group {
            // NCS patched for predictable order
            ordered-by user;
            key "queue-group-name";
            uses ncs_compliance_template_queue-group-template-entry {
              augment "queue" {
                uses ncs_compliance_template_packet-byte-offset-grouping;
                leaf dynamic-mbs {
                  type empty;
                }
                leaf queue-delay {
                  type string;
                }
              }
            }
            leaf queues-hqos-manageable {
              type string;
            }
          }
        }
        container ingress {
          list queue-group {
            // NCS patched for predictable order
            ordered-by user;
            key "queue-group-name";
            uses ncs_compliance_template_queue-group-template-entry;
          }
        }
      }
      list scheduler-policy {
        // NCS patched for predictable order
        ordered-by user;
        key "scheduler-policy-name";
        leaf scheduler-policy-name {
          type string;
        }
        leaf description {
          type string;
        }
        leaf frame-based-accounting {
          type empty;
        }
        list tier {
          // NCS patched for predictable order
          ordered-by user;
          key "tier";
          leaf tier {
            type string;
          }
          list scheduler {
            // NCS patched for predictable order
            ordered-by user;
            key "scheduler-name";
            leaf scheduler-name {
              type string;
            }
            leaf description {
              type string;
            }
            container parent {
              presence "present";
              leaf scheduler-name {
                tailf:cli-drop-node-name;
                type string;
              }
              leaf weight {
                type string;
              }
              leaf level {
                type string;
              }
              leaf cir-weight {
                type string;
              }
              leaf cir-level {
                type string;
              }
            }
            container port-parent {
              presence "present";
              leaf weight {
                type string;
              }
              leaf level {
                type string;
              }
              leaf cir-weight {
                type string;
              }
              leaf cir-level {
                type string;
              }
            }
            container rate {
              presence "present";
              leaf pir-rate {
                tailf:cli-drop-node-name;
                // NCS drop mandatory statement
                type string;
              }
              leaf cir {
                type string;
              }
            }
            container mbs {
              leaf size {
                tailf:cli-drop-node-name;
                type string;
              }
              leaf unit {
                tailf:cli-drop-node-name;
                type string;
              }
            }
          }
        }
      }
      list shared-queue {
        // NCS patched for predictable order
        ordered-by user;
        key "policy-name";
        leaf policy-name {
          type string;
        }
        leaf description {
          type string;
        }
        container fc {
          presence "present";
          leaf fc-name {
            tailf:cli-drop-node-name;
            // NCS drop mandatory statement
            type string;
          }
          leaf broadcast-queue {
            type string;
          }
          leaf multicast-queue {
            type string;
          }
          leaf queue {
            type string;
          }
          leaf unknown-queue {
            type string;
          }
        }
        list queue {
          // NCS patched for predictable order
          ordered-by user;
          key "queue-id";
          leaf queue-id {
            type string;
          }
          leaf queue-type {
            tailf:cli-drop-node-name;
            type ncs_compliance_template_queue-type;
          }
          leaf multipoint {
            type empty;
          }
          leaf cbs {
            type string;
          }
          leaf high-prio-only {
            type string;
          }
          leaf mbs {
            type string;
          }
          leaf pool {
            type string;
          }
          container rate {
            leaf percent {
              tailf:cli-drop-node-name;
              type string;
            }
            leaf cir {
              type string;
            }
          }
        }
      }
      list mpls-lsp-exp-profile-map {
        // NCS patched for predictable order
        ordered-by user;
        // NCS drop tailf-common:cli-diff-create-before statement
        key "policy-id";
        leaf policy-id {
          type string;
        }
        leaf description {
          type string;
        }
        list lsp-exp {
          // NCS patched for predictable order
          ordered-by user;
          tailf:cli-suppress-mode;
          key "lsp-exp-value";
          leaf lsp-exp-value {
            type string;
          }
          leaf profile {
            type string;
          }
        }
      }
      list access-egress {
        // NCS patched for predictable order
        ordered-by user;
        key "policy-id";
        leaf policy-id {
          type string;
        }
        leaf remark {
          type string;
        }
        list fc {
          // NCS patched for predictable order
          ordered-by user;
          key "fc-name";
          leaf fc-name {
            type ncs_compliance_template_fc-name;
          }
          leaf dscp-in-profile {
            type ncs_compliance_template_dscp-type;
          }
          leaf dscp-out-profile {
            type ncs_compliance_template_dscp-type;
          }
          leaf dot1p-in-profile {
            type string;
          }
          leaf dot1p-out-profile {
            type string;
          }
        }
        leaf description {
          type string;
        }
        list queue {
          // NCS patched for predictable order
          ordered-by user;
          key "queue-id";
          leaf queue-id {
            type string;
          }
          uses ncs_compliance_template_queue-adaptation-grouping;
          leaf queue-mode {
            type string;
          }
          leaf queue-mgmt {
            type string;
          }
          container rate {
            leaf cir {
              type string;
            }
            leaf pir {
              type string;
            }
          }
        }
        container remarking {
          presence "true";
          leaf remarking {
            tailf:cli-drop-node-name;
            type string;
          }
        }
        leaf scope {
          type string;
        }
      }
      list sap-egress {
        // NCS patched for predictable order
        ordered-by user;
        key "policy-id";
        leaf name {
          type string;
        }
        uses ncs_compliance_template_qos-dot1p-list-grouping;
        uses ncs_compliance_template_sap-egress-common-grouping {
          augment "queue" {
            uses ncs_compliance_template_packet-byte-offset-grouping;
            leaf queue-mode {
              type string;
            }
            leaf queue-mgmt {
              type string;
            }
            leaf weight {
              type string;
            }
          }
          augment "queue/percent-rate" {
            leaf limit {
              tailf:cli-drop-node-name;
              type string;
            }
          }
        }
        leaf policers-hqos-manageable {
          type empty;
        }
        list fc {
          // NCS patched for predictable order
          ordered-by user;
          key "fc-name";
          uses ncs_compliance_template_sap-egress-fc-grouping;
          container policer {
            uses ncs_compliance_template_policer-ref-grouping;
            leaf port-redirect-group-queue {
              type empty;
            }
            leaf queue {
              type string;
            }
          }
        }
        leaf parent-location {
          type string;
        }
        list policer {
          // NCS patched for predictable order
          ordered-by user;
          key "policer-id";
          leaf policer-id {
            type string;
          }
          uses ncs_compliance_template_policer-grouping;
          uses ncs_compliance_template_port-parent-grouping;
          container percent-rate {
            leaf pir {
              tailf:cli-drop-node-name;
              type string;
            }
            leaf cir {
              type string;
            }
          }
        }
        leaf policy-name {
          type string;
        }
        container ip-criteria {
          uses ncs_compliance_template_ip-criteria-grouping;
        }
        container ipv6-criteria {
          uses ncs_compliance_template_ipv6-criteria-grouping;
        }
        list dscp {
          // NCS patched for predictable order
          ordered-by user;
          tailf:cli-suppress-mode;
          key "id";
          leaf id {
            type ncs_compliance_template_dscp-type;
          }
          leaf fc {
            type string;
          }
          leaf profile {
            type string;
          }
        }
        leaf remarking {
          type empty;
        }
        leaf remark {
          type string;
        }
        leaf scope {
          type string;
        }
      }
      list sap-ingress {
        // NCS patched for predictable order
        ordered-by user;
        key "policy-id";
        leaf policy-id {
          type string;
        }
        leaf name {
          type string;
        }
        leaf policer-allocation {
          type string;
        }
        leaf description {
          type string;
        }
        leaf ingress-classification-policy {
          type string;
        }
        leaf policy-name {
          type string;
        }
        list meter {
          // NCS patched for predictable order
          ordered-by user;
          key "meter-id";
          uses ncs_compliance_template_meter-grouping;
        }
        container num-qos-classifiers {
          leaf num-resources {
            tailf:cli-drop-node-name;
            type string;
          }
          leaf keyword {
            tailf:cli-drop-node-name;
            type string;
          }
        }
        list prec {
          // NCS patched for predictable order
          ordered-by user;
          key "ip-prec-value";
          tailf:cli-suppress-mode;
          leaf ip-prec-value {
            tailf:cli-drop-node-name;
            type string;
          }
          leaf fc {
            type ncs_compliance_template_fc-name;
          }
          leaf priority {
            type string;
          }
        }
        list queue {
          // NCS patched for predictable order
          ordered-by user;
          key "queue-id";
          leaf queue-id {
            type string;
          }
          uses ncs_compliance_template_queue-grouping {
            augment "percent-rate" {
              leaf limit {
                tailf:cli-drop-node-name;
                type string;
              }
            }
          }
          uses ncs_compliance_template_packet-byte-offset-grouping;
        }
        list policer {
          // NCS patched for predictable order
          ordered-by user;
          key "policer-id";
          leaf policer-id {
            type string;
          }
          uses ncs_compliance_template_policer-grouping;
        }
        list fc {
          // NCS patched for predictable order
          ordered-by user;
          key "fc-name";
          leaf fc-name {
            type string;
          }
          leaf egress-fc {
            type ncs_compliance_template_fc-name;
          }
          container queue {
            uses ncs_compliance_template_queue-ref-grouping;
          }
          container broadcast-queue {
            uses ncs_compliance_template_queue-ref-grouping;
          }
          container multicast-queue {
            uses ncs_compliance_template_queue-ref-grouping;
          }
          container unknown-queue {
            uses ncs_compliance_template_queue-ref-grouping;
          }
          container policer {
            uses ncs_compliance_template_policer-ref-grouping;
            leaf fp-redirect-group {
              type empty;
            }
          }
          container broadcast-policer {
            uses ncs_compliance_template_policer-ref-grouping;
            leaf fp-redirect-group {
              type empty;
            }
          }
          container multicast-policer {
            uses ncs_compliance_template_policer-ref-grouping;
            leaf fp-redirect-group {
              type empty;
            }
          }
          container unknown-policer {
            uses ncs_compliance_template_policer-ref-grouping;
            leaf fp-redirect-group {
              type empty;
            }
          }
          leaf profile {
            type string;
          }
          leaf broadcast-meter {
            type string;
          }
          leaf meter {
            type string;
          }
          leaf multicast-meter {
            type string;
          }
          leaf unknown-meter {
            type string;
          }

          grouping remark-choice-grouping {
            choice remark-choice {
              leaf dscp {
                type ncs_compliance_template_dscp-type;
              }
              leaf prec {
                type string;
              }
            }
          }
          container in-remark {
            uses remark-choice-grouping;
          }
          container out-remark {
            uses remark-choice-grouping;
          }
          leaf de-1-out-profile {
            type empty;
          }
        }
        container ip-criteria {
          uses ncs_compliance_template_ip-criteria-grouping;
        }
        container ipv6-criteria {
          uses ncs_compliance_template_ipv6-criteria-grouping;
        }
        container mac-criteria {
          uses ncs_compliance_template_mac-criteria-grouping;
        }
        leaf default-fc {
          type ncs_compliance_template_fc-name;
        }
        leaf default-priority {
          type string;
        }
        leaf dscp-classification {
          type string;
        }
        list dot1p {
          // NCS patched for predictable order
          ordered-by user;
          tailf:cli-suppress-mode;
          key "id";
          leaf id {
            type string;
          }
          leaf fc {
            type ncs_compliance_template_fc-name;
          }
          leaf priority {
            type string;
          }
        }
        list lsp-exp {
          // NCS patched for predictable order
          ordered-by user;
          tailf:cli-suppress-mode;
          key "id";
          leaf id {
            type string;
          }
          leaf fc {
            type ncs_compliance_template_fc-name;
          }
          leaf priority {
            type string;
          }
        }
        list dscp {
          // NCS patched for predictable order
          ordered-by user;
          tailf:cli-suppress-mode;
          key "id";
          leaf id {
            type ncs_compliance_template_dscp-type;
          }
          leaf fc {
            type string;
          }
          leaf priority {
            type string;
          }
        }
      }
      list network {
        // NCS patched for predictable order
        ordered-by user;
        key "id";
        leaf id {
          type string;
        }
        leaf network-policy-type {
          type string;
        }
        leaf name {
          type string;
        }
        leaf description {
          type string;
        }
        container ingress {
          list dscp {
            // NCS patched for predictable order
            ordered-by user;
            tailf:cli-suppress-mode;
            key "id";
            leaf id {
              type ncs_compliance_template_dscp-type;
            }
            leaf fc {
              type string;
            }
            leaf profile {
              type ncs_compliance_template_in-out;
            }
          }
          leaf ler-use-dscp {
            type empty;
          }
          uses ncs_compliance_template_qos-lsp-exp-grouping;
          uses ncs_compliance_template_qos-dot1p-list-grouping;
          container default-action {
            leaf fc {
              type ncs_compliance_template_fc-name;
            }
            leaf profile {
              type string;
            }
          }
          list meter {
            // NCS patched for predictable order
            ordered-by user;
            key "meter-id";
            uses ncs_compliance_template_meter-grouping;
          }
          leaf mpls-lsp-exp-profile {
            type string;
          }
          list fc {
            // NCS patched for predictable order
            ordered-by user;
            key "class";
            leaf class {
              type string;
            }
            leaf meter {
              type string;
            }
            leaf multicast-meter {
              type string;
            }
            list fp-redirect-group {
              // NCS patched for predictable order
              ordered-by user;
              tailf:cli-suppress-mode;
              key "policer-type";
              leaf policer-type {
                type string;
              }
              leaf policer-id {
                tailf:cli-drop-node-name;
                type string;
              }
            }
          }
        }
        container egress {

          grouping egress-fc-settings-grouping {
            leaf dscp-in-profile {
              type ncs_compliance_template_dscp-type;
            }
            leaf dscp-out-profile {
              type ncs_compliance_template_dscp-type;
            }
            leaf lsp-exp-in-profile {
              type string;
            }
            leaf lsp-exp-out-profile {
              type string;
            }
            leaf dot1p-in-profile {
              type string;
            }
            leaf dot1p-out-profile {
              type string;
            }
            leaf de-mark {
              type string;
            }
            container port-redirect-group {
              leaf policer {
                type string;
              }
              leaf queue {
                type string;
              }
            }
          }
          list dscp {
            // NCS patched for predictable order
            ordered-by user;
            tailf:cli-suppress-mode;
            key "id";
            leaf id {
              type ncs_compliance_template_dscp-type;
            }
            leaf fc {
              type string;
            }
            leaf profile {
              type ncs_compliance_template_in-out;
            }
          }
          container fc {
            container af {
              // NCS expand uses statement
              leaf dscp-in-profile {
                type ncs_compliance_template_dscp-type;
              }
              leaf dscp-out-profile {
                type ncs_compliance_template_dscp-type;
              }
              leaf lsp-exp-in-profile {
                type string;
              }
              leaf lsp-exp-out-profile {
                type string;
              }
              leaf dot1p-in-profile {
                type string;
              }
              leaf dot1p-out-profile {
                type string;
              }
              leaf de-mark {
                type string;
              }
              container port-redirect-group {
                leaf policer {
                  type string;
                }
                leaf queue {
                  type string;
                }
              }
            }
            container be {
              // NCS expand uses statement
              leaf dscp-in-profile {
                type ncs_compliance_template_dscp-type;
              }
              leaf dscp-out-profile {
                type ncs_compliance_template_dscp-type;
              }
              leaf lsp-exp-in-profile {
                type string;
              }
              leaf lsp-exp-out-profile {
                type string;
              }
              leaf dot1p-in-profile {
                type string;
              }
              leaf dot1p-out-profile {
                type string;
              }
              leaf de-mark {
                type string;
              }
              container port-redirect-group {
                leaf policer {
                  type string;
                }
                leaf queue {
                  type string;
                }
              }
            }
            container ef {
              // NCS expand uses statement
              leaf dscp-in-profile {
                type ncs_compliance_template_dscp-type;
              }
              leaf dscp-out-profile {
                type ncs_compliance_template_dscp-type;
              }
              leaf lsp-exp-in-profile {
                type string;
              }
              leaf lsp-exp-out-profile {
                type string;
              }
              leaf dot1p-in-profile {
                type string;
              }
              leaf dot1p-out-profile {
                type string;
              }
              leaf de-mark {
                type string;
              }
              container port-redirect-group {
                leaf policer {
                  type string;
                }
                leaf queue {
                  type string;
                }
              }
            }
            container h1 {
              // NCS expand uses statement
              leaf dscp-in-profile {
                type ncs_compliance_template_dscp-type;
              }
              leaf dscp-out-profile {
                type ncs_compliance_template_dscp-type;
              }
              leaf lsp-exp-in-profile {
                type string;
              }
              leaf lsp-exp-out-profile {
                type string;
              }
              leaf dot1p-in-profile {
                type string;
              }
              leaf dot1p-out-profile {
                type string;
              }
              leaf de-mark {
                type string;
              }
              container port-redirect-group {
                leaf policer {
                  type string;
                }
                leaf queue {
                  type string;
                }
              }
            }
            container h2 {
              // NCS expand uses statement
              leaf dscp-in-profile {
                type ncs_compliance_template_dscp-type;
              }
              leaf dscp-out-profile {
                type ncs_compliance_template_dscp-type;
              }
              leaf lsp-exp-in-profile {
                type string;
              }
              leaf lsp-exp-out-profile {
                type string;
              }
              leaf dot1p-in-profile {
                type string;
              }
              leaf dot1p-out-profile {
                type string;
              }
              leaf de-mark {
                type string;
              }
              container port-redirect-group {
                leaf policer {
                  type string;
                }
                leaf queue {
                  type string;
                }
              }
            }
            container l1 {
              // NCS expand uses statement
              leaf dscp-in-profile {
                type ncs_compliance_template_dscp-type;
              }
              leaf dscp-out-profile {
                type ncs_compliance_template_dscp-type;
              }
              leaf lsp-exp-in-profile {
                type string;
              }
              leaf lsp-exp-out-profile {
                type string;
              }
              leaf dot1p-in-profile {
                type string;
              }
              leaf dot1p-out-profile {
                type string;
              }
              leaf de-mark {
                type string;
              }
              container port-redirect-group {
                leaf policer {
                  type string;
                }
                leaf queue {
                  type string;
                }
              }
            }
            container l2 {
              // NCS expand uses statement
              leaf dscp-in-profile {
                type ncs_compliance_template_dscp-type;
              }
              leaf dscp-out-profile {
                type ncs_compliance_template_dscp-type;
              }
              leaf lsp-exp-in-profile {
                type string;
              }
              leaf lsp-exp-out-profile {
                type string;
              }
              leaf dot1p-in-profile {
                type string;
              }
              leaf dot1p-out-profile {
                type string;
              }
              leaf de-mark {
                type string;
              }
              container port-redirect-group {
                leaf policer {
                  type string;
                }
                leaf queue {
                  type string;
                }
              }
            }
            container nc {
              // NCS expand uses statement
              leaf dscp-in-profile {
                type ncs_compliance_template_dscp-type;
              }
              leaf dscp-out-profile {
                type ncs_compliance_template_dscp-type;
              }
              leaf lsp-exp-in-profile {
                type string;
              }
              leaf lsp-exp-out-profile {
                type string;
              }
              leaf dot1p-in-profile {
                type string;
              }
              leaf dot1p-out-profile {
                type string;
              }
              leaf de-mark {
                type string;
              }
              container port-redirect-group {
                leaf policer {
                  type string;
                }
                leaf queue {
                  type string;
                }
              }
            }
          }
          leaf remark {
            type string;
          }
          container remarking {
            presence "true";
            leaf force {
              type empty;
            }
          }
          list prec {
            // NCS patched for predictable order
            ordered-by user;
            tailf:cli-suppress-mode;
            key "prec-value";
            leaf prec-value {
              tailf:cli-drop-node-name;
              type string;
            }
            leaf fc {
              type ncs_compliance_template_fc-name;
            }
            leaf profile {
              type string;
            }
          }
        }
      }
      list slope-policy {
        // NCS patched for predictable order
        ordered-by user;
        key "name";
        leaf name {
          type string;
        }
        leaf description {
          type string;
        }
        container exceed-slope {
          uses ncs_compliance_template_slope-params-grouping;
        }
        container high-slope {
          uses ncs_compliance_template_slope-params-grouping;
        }
        container highplus-slope {
          uses ncs_compliance_template_slope-params-grouping;
        }
        container low-slope {
          uses ncs_compliance_template_slope-params-grouping;
        }
      }
      list port-scheduler-policy {
        // NCS patched for predictable order
        ordered-by user;
        key "name";
        leaf name {
          type string;
        }
        leaf description {
          type string;
        }
        leaf dist-lag-rate-shared {
          type empty;
        }
        list group {
          // NCS patched for predictable order
          ordered-by user;
          key "name";
          leaf name {
            type ncs_compliance_template_string32;
          }
          container percent {
            tailf:cli-drop-node-name;
            leaf percent-rate {
              type string;
            }
            leaf cir {
              type string;
            }
          }
        }
        list level {
          // NCS patched for predictable order
          ordered-by user;
          tailf:cli-suppress-mode;
          key "priority-level";
          leaf priority-level {
            type string;
          }
          choice rate-choice {
            container pir {
              tailf:cli-drop-node-name;
              leaf rate {
                type string;
              }
              leaf cir {
                type string;
              }
            }
            container percent {
              tailf:cli-drop-node-name;
              leaf percent-rate {
                type string;
              }
              leaf percent-cir {
                type string;
              }
            }
          }
          leaf group {
            type ncs_compliance_template_string32;
          }
          leaf weight {
            type string;
          }
        }
        container max-rate {
          choice max-rate {
            leaf pir-rate {
              tailf:cli-drop-node-name;
              type string;
            }
            leaf percent {
              type string;
            }
          }
        }
        container orphan-override {
          leaf weight {
            type string;
          }
          leaf level {
            type string;
          }
          leaf cir-weight {
            type string;
          }
          leaf cir-level {
            type string;
          }
        }
      }
      list policer-control-policy {
        // NCS patched for predictable order
        ordered-by user;
        key "name";
        leaf name {
          type string;
        }
        leaf description {
          type string;
        }
        container root {
          leaf max-rate {
            type ncs_compliance_template_rate-type;
          }
        }
        container priority-mbs-thresholds {
          container min-thresh-separation {
            leaf size {
              tailf:cli-drop-node-name;
              type string;
            }
            leaf unit {
              tailf:cli-drop-node-name;
              type string;
            }
          }
          list priority {
            // NCS patched for predictable order
            ordered-by user;
            key "level";
            leaf level {
              type string;
            }
            container mbs-contribution {
              leaf size {
                tailf:cli-drop-node-name;
                type string;
              }
              leaf unit {
                tailf:cli-drop-node-name;
                type string;
              }
              leaf fixed {
                type empty;
              }
            }
          }
        }
      }
      list queue-mgmt {
        // NCS patched for predictable order
        ordered-by user;
        key "id";
        leaf id {
          type string;
        }
        leaf description {
          type string;
        }
        leaf mbs {
          type string;
        }
        leaf cbs {
          type string;
        }
        container high-slope {
          leaf shutdown {
            type string;
          }
        }
        container low-slope {
          leaf shutdown {
            type string;
          }
        }
      }
      list remark {
        // NCS patched for predictable order
        ordered-by user;
        key "policy-id";
        leaf policy-id {
          type string;
        }
        leaf remark-type {
          type string;
        }
        leaf description {
          type string;
        }
        list fc {
          // NCS patched for predictable order
          ordered-by user;
          key "fc-name";
          leaf fc-name {
            type ncs_compliance_template_fc-name;
          }
          leaf dot1p-in-profile {
            type string;
          }
          leaf dot1p-out-profile {
            type string;
          }
          leaf dot1p-lsp-exp-in-profile {
            type string;
          }
          leaf dot1p-lsp-exp-out-profile {
            type string;
          }
        }
      }
      leaf use-global-mpls-lsp-exp-profile {
        type string;
      }
    }
    list sfm {
      // NCS patched for predictable order
      ordered-by user;
      key "id";
      leaf id {
        type string;
      }
      leaf sfm-type {
        type string;
      }
      leaf shutdown {
        type string;
      }
    }
    container eth-cfm {
      container default-domain {
        list bridge-identifier {
          // NCS patched for predictable order
          ordered-by user;
          key "bridge-id";
          leaf bridge-id {
            type string;
          }
          leaf vlan {
            type string;
          }
          container mhf-creation {
            leaf mhf {
              tailf:cli-drop-node-name;
              type string;
            }
            leaf level {
              type string;
            }
          }
        }
      }
      list domain {
        // NCS patched for predictable order
        ordered-by user;
        key "id";
        leaf id {
          type string;
        }
        leaf format {
          type string;
        }
        leaf level {
          type string;
        }
        leaf name {
          type string;
        }
        leaf admin-name {
          type string;
        }
        list association {
          // NCS patched for predictable order
          ordered-by user;
          key "ma-index";
          leaf ma-index {
            type string;
          }
          leaf auto-mep-discovery {
            type empty;
          }
          leaf format {
            type string;
          }
          leaf name {
            type string;
          }
          leaf admin-name {
            type string;
          }
          container ccm-hold-time {
            leaf down {
              type string;
            }
          }
          leaf ccm-interval {
            type string;
          }
          list remote-mepid {
            // NCS patched for predictable order
            ordered-by user;
            tailf:cli-suppress-mode;
            key "mep-id";
            leaf mep-id {
              type string;
            }
            leaf remote-mac {
              type string;
            }
          }
          list bridge-identifier {
            // NCS patched for predictable order
            ordered-by user;
            key "id";
            leaf id {
              type string;
            }
            leaf bridge-name {
              type empty;
            }
            leaf mhf-creation {
              type string;
            }
            leaf vlan {
              type string;
            }
          }
        }
      }
    }
    list esa {
      // NCS patched for predictable order
      ordered-by user;
      key "id";
      leaf id {
        type string;
      }
      leaf description {
        type string;
      }
      list host-port {
        // NCS patched for predictable order
        ordered-by user;
        tailf:cli-suppress-mode;
        key "port";
        leaf port {
          type string;
        }
      }
      list vm {
        // NCS patched for predictable order
        ordered-by user;
        key "vm-id";
        leaf vm-id {
          type string;
        }
        leaf cores {
          type string;
        }
        leaf description {
          type string;
        }
        leaf host-port {
          type string;
        }
        leaf memory {
          type string;
        }
        leaf vm-type {
          type string;
        }
        leaf shutdown {
          type string;
        }
      }
      leaf shutdown {
        type string;
      }
    }
    container log {

      typedef severity-levels {
        type string;
      }
      leaf event-damping {
        type string;
      }
      container event-handling {
        list handler {
          // NCS patched for predictable order
          ordered-by user;
          key "name";
          leaf name {
            type string;
          }
          leaf description {
            type string;
          }
          container action-list {
            list entry {
              // NCS patched for predictable order
              ordered-by user;
              key "entry-id";
              leaf entry-id {
                type string;
              }
              leaf script-policy {
                type ncs_compliance_template_string32;
              }
              leaf shutdown {
                type string;
              }
            }
          }
          leaf shutdown {
            type string;
          }
        }
      }
      list file-id {
        // NCS patched for predictable order
        ordered-by user;
        key "id";
        leaf id {
          type string;
        }
        leaf name {
          type string;
        }
        leaf description {
          type string;
        }
        leaf location {
          type string;
        }
        container rollover {
          leaf id {
            tailf:cli-drop-node-name;
            type string;
          }
          leaf retention {
            type string;
          }
        }
      }
      list accounting-policy {
        // NCS patched for predictable order
        ordered-by user;
        key "acct-policy-id";
        leaf acct-policy-id {
          type string;
        }
        leaf collection-interval {
          type string;
        }
        leaf description {
          type string;
        }
        container custom-record {
          list queue {
            // NCS patched for predictable order
            ordered-by user;
            key "id";
            leaf id {
              type string;
            }

            grouping custom-record-counters-grouping {
              leaf in-profile-octets-forwarded-count {
                type empty;
              }
              leaf out-profile-octets-forwarded-count {
                type empty;
              }
            }
            container e-counters {
              uses custom-record-counters-grouping;
            }
            container i-counters {
              uses custom-record-counters-grouping;
            }
          }
        }
        leaf include-system-info {
          type empty;
        }
        leaf record {
          type string;
        }
        leaf default {
          type empty;
        }
        container to {
          leaf destination {
            tailf:cli-drop-node-name;
            type string;
          }
          leaf log-file-id {
            tailf:cli-drop-node-name;
            type string;
          }
        }
        leaf shutdown {
          type string;
        }
      }
      list event-control {
        // NCS patched for predictable order
        ordered-by user;
        tailf:cli-suppress-mode;
        key "name id";
        leaf name {
          type string;
        }
        leaf id {
          type string;
        }
        leaf mode {
          tailf:cli-drop-node-name;
          type string;
        }
        leaf severity-level {
          tailf:cli-drop-node-name;
          type severity-levels;
        }
        leaf throttle {
          type empty;
        }
        leaf disable-specific-throttle {
          tailf:cli-drop-node-name;
          type string;
        }
        container specific-throttle-rate {
          leaf event-limit {
            tailf:cli-drop-node-name;
            type string;
          }
          leaf interval {
            type string;
          }
        }
      }
      container event-trigger {
        list event {
          // NCS patched for predictable order
          ordered-by user;
          key "application-id event-name-id";
          leaf application-id {
            type string;
          }
          leaf event-name-id {
            type string;
          }
          list trigger-entry {
            // NCS patched for predictable order
            ordered-by user;
            key "entry-id";
            leaf entry-id {
              type string;
            }
            leaf event-handler {
              type string;
            }
            leaf log-filter {
              type string;
            }
            leaf shutdown {
              type string;
            }
          }
          leaf shutdown {
            type string;
          }
        }
      }
      list filter {
        // NCS patched for predictable order
        ordered-by user;
        key "filter-id";
        leaf filter-id {
          type string;
        }
        leaf default-action {
          type string;
        }
        leaf name {
          type string;
        }
        leaf description {
          type string;
        }
        list entry {
          // NCS patched for predictable order
          ordered-by user;
          key "entry-id";
          leaf entry-id {
            type string;
          }
          leaf action {
            type string;
          }
          leaf name {
            type string;
          }
          leaf description {
            type string;
          }
          container match {
            container application {
              leaf rule {
                tailf:cli-drop-node-name;
                type string;
              }
              leaf application-id {
                tailf:cli-drop-node-name;
                type string;
              }
            }
            container message {
              leaf rule {
                tailf:cli-drop-node-name;
                type string;
              }
              leaf pattern {
                type string;
              }
              leaf regexp {
                type empty;
              }
            }
            container number {
              leaf rule {
                tailf:cli-drop-node-name;
                type string;
              }
              leaf event-id {
                tailf:cli-drop-node-name;
                type string;
              }
            }
            container router {
              leaf rule {
                tailf:cli-drop-node-name;
                type string;
              }
              leaf router-instance {
                tailf:cli-drop-node-name;
                type string;
              }
              leaf regexp {
                type empty;
              }
            }
            container severity {
              leaf rule {
                tailf:cli-drop-node-name;
                type string;
              }
              leaf severity-level {
                tailf:cli-drop-node-name;
                type severity-levels;
              }
            }
            container subject {
              leaf rule {
                tailf:cli-drop-node-name;
                type string;
              }
              leaf subject {
                tailf:cli-drop-node-name;
                type string;
              }
              leaf regexp {
                type empty;
              }
            }
          }
        }
      }
      list snmp-trap-group {
        // NCS patched for predictable order
        ordered-by user;
        // NCS drop tailf-common:cli-diff-create-before statement
        key "id";
        leaf id {
          type string;
        }
        leaf name {
          type string;
        }
        list trap-target {
          // NCS patched for predictable order
          ordered-by user;
          tailf:cli-suppress-mode;
          key "name";
          leaf name {
            type string;
          }
          leaf address {
            type string;
          }
          leaf notify-community {
            type string;
          }
          leaf port {
            type string;
          }
          leaf version {
            tailf:cli-drop-node-name;
            type string;
          }
          leaf security-level {
            type string;
          }
          leaf replay {
            type empty;
          }
          leaf dying-gasp {
            type empty;
          }
        }
        leaf description {
          type string;
        }
      }
      container snmp-dying-gasp {

        grouping trap-target-grouping {
          leaf trap-target-group-num {
            tailf:cli-drop-node-name;
            type string;
          }
          leaf trap-target-name {
            tailf:cli-drop-node-name;
            type string;
          }
        }
        container primary {
          uses trap-target-grouping;
        }
        container secondary {
          uses trap-target-grouping;
        }
        container tertiary {
          uses trap-target-grouping;
        }
      }
      list log-id {
        // NCS patched for predictable order
        ordered-by user;
        key "id";
        leaf id {
          type string;
        }
        leaf name {
          type string;
        }
        leaf description {
          type string;
        }
        leaf filter {
          type string;
        }
        leaf-list from {
          // NCS patched for predictable order
          ordered-by user;
          type string;
        }
        leaf time-format {
          type string;
        }
        leaf netconf-stream {
          type string;
        }
        container to {
          choice choice {
            case file {
              leaf file {
                type string;
              }
            }
            case syslog {
              leaf syslog {
                type string;
              }
            }
            case cli {
              leaf cli {
                type empty;
              }
            }
            case console {
              leaf console {
                type empty;
              }
            }
            case netconf {
              leaf netconf {
                type empty;
              }
            }
            case snmp {
              container snmp {
                presence "true";
                leaf size {
                  tailf:cli-drop-node-name;
                  type string;
                }
              }
            }
            case memory {
              container memory {
                presence "true";
                leaf size {
                  tailf:cli-drop-node-name;
                  type string;
                }
              }
            }
            case session {
              leaf session {
                type string;
              }
            }
          }
        }
        leaf shutdown {
          type string;
        }
      }
      container route-preference {
        leaf primary {
          type string;
        }
        leaf secondary {
          type string;
        }
      }
      list syslog {
        // NCS patched for predictable order
        ordered-by user;
        key "id";
        leaf id {
          type string;
        }
        leaf name {
          type string;
        }
        leaf address {
          type string;
        }
        leaf description {
          type string;
        }
        leaf facility {
          type string;
        }
        leaf log-prefix {
          type string;
        }
        leaf level {
          type string;
        }
        leaf port {
          type string;
        }
      }
      container throttle-rate {
        leaf events {
          tailf:cli-drop-node-name;
          type string;
        }
        leaf interval {
          type string;
        }
      }
      container services-all-events {
        list service {
          // NCS patched for predictable order
          ordered-by user;
          tailf:cli-suppress-mode;
          key "service-id";
          leaf service-id {
            type string;
          }
        }
      }
    }
    container service {
      list customer {
        // NCS patched for predictable order
        ordered-by user;
        key "customer-id";
        leaf customer-id {
          type string;
        }
        leaf name {
          type string;
        }
        leaf contact {
          type string;
        }
        leaf description {
          type string;
        }
        list multi-service-site {
          // NCS patched for predictable order
          ordered-by user;
          key "customer-site-name";
          leaf customer-site-name {
            type string;
          }
          container assignment {
            choice choice {
              leaf port {
                type string;
              }
              leaf card {
                type string;
              }
            }
          }
          leaf description {
            type string;
          }
          container egress {
            container agg-rate-limit {
              presence "present";
              leaf agg-rate {
                tailf:cli-drop-node-name;
                // NCS drop mandatory statement
                type string;
              }
              leaf queue-frame-based-accounting {
                type empty;
              }
            }
            leaf policer-control-policy {
              type string;
            }
            leaf scheduler-policy {
              type string;
            }
            container scheduler-override {
              list scheduler {
                // NCS patched for predictable order
                ordered-by user;
                key "scheduler-name";
                leaf scheduler-name {
                  type string;
                }
                container rate {
                  leaf pir-rate {
                    tailf:cli-drop-node-name;
                    type string;
                  }
                  leaf cir {
                    type string;
                  }
                }
              }
            }
          }
          container ingress {
            leaf policer-control-policy {
              type string;
            }
            leaf scheduler-policy {
              type string;
            }
            container scheduler-override {
              list scheduler {
                // NCS patched for predictable order
                ordered-by user;
                key "scheduler-name";
                leaf scheduler-name {
                  type string;
                }
                container rate {
                  presence "present";
                  leaf pir-rate {
                    tailf:cli-drop-node-name;
                    // NCS drop mandatory statement
                    type string;
                  }
                  leaf cir {
                    type string;
                  }
                }
              }
            }
          }
          leaf tod-suite {
            type string;
          }
        }
        leaf phone {
          type string;
        }
      }
      list sdp {
        // NCS patched for predictable order
        ordered-by user;
        key "sdp-id";
        leaf sdp-id {
          type string;
        }
        list sr-te-lsp {
          // NCS patched for predictable order
          ordered-by user;
          tailf:cli-suppress-mode;
          key "lsp-id";
          leaf lsp-id {
            type string;
          }
        }
        container class-forwarding {
          presence "true";
          leaf default-lsp {
            type string;
          }
          leaf enforce-diffserv-lsp-fc {
            type empty;
          }
          list fc {
            // NCS patched for predictable order
            ordered-by user;
            tailf:cli-suppress-mode;
            key "class";
            leaf class {
              type ncs_compliance_template_fc-name;
            }
            leaf lsp {
              type string;
            }
          }
          leaf multicast-lsp {
            type string;
          }
          leaf shutdown {
            type string;
          }
        }
        list lsp {
          // NCS patched for predictable order
          ordered-by user;
          tailf:cli-suppress-mode;
          key "lsp-name";
          leaf lsp-name {
            type string;
          }
        }
        leaf far-end {
          type string;
        }
        leaf accounting-policy {
          type string;
        }
        leaf adv-mtu-override {
          type empty;
        }
        leaf bgp-tunnel {
          type empty;
        }
        container binding {
          leaf port {
            type string;
          }
          list pw-port {
            // NCS patched for predictable order
            ordered-by user;
            key "pw-port-id";
            leaf pw-port-id {
              type string;
            }
            leaf vc-id {
              type string;
            }
            leaf monitor-oper-group {
              type string;
            }
            container egress {
              container shaping {
                choice choice {
                  leaf vport {
                    type string;
                  }
                  leaf int-dest-id {
                    type string;
                  }
                }
              }
            }
            leaf vc-type {
              type string;
            }
            leaf vlan-vc-tag {
              type string;
            }
            leaf shutdown {
              type string;
            }
          }
        }
        leaf booking-factor {
          type string;
        }
        leaf collect-stats {
          type empty;
        }
        leaf delivery-type {
          tailf:cli-drop-node-name;
          type string;
        }
        leaf description {
          type string;
        }
        container keep-alive {
          leaf hello-time {
            type string;
          }
          leaf hold-down-time {
            type string;
          }
          leaf max-drop-count {
            type string;
          }
          leaf message-length {
            type string;
          }
          leaf timeout {
            type string;
          }
          leaf shutdown {
            type string;
          }
        }
        leaf metric {
          type string;
        }
        leaf sr-type {
          tailf:cli-drop-node-name;
          type string;
        }
        container mixed-lsp-mode {
          presence "true";
          // NCS drop tailf-common:cli-diff-create-before statement
          leaf revert-time {
            type string;
          }
        }
        leaf network-domain {
          type string;
        }
        leaf path-mtu {
          type string;
        }
        leaf pbb-etype {
          type string;
        }
        leaf signaling {
          type string;
        }
        leaf local-end {
          type string;
        }
        leaf tunnel-far-end {
          type string;
        }
        leaf vlan-vc-etype {
          type string;
        }
        leaf shutdown {
          type string;
        }
      }
      container sdp-group {
        list group-name {
          // NCS patched for predictable order
          ordered-by user;
          tailf:cli-suppress-mode;
          key "name";
          leaf name {
            type string;
          }
          leaf value {
            // NCS drop mandatory statement
            type string;
          }
        }
      }

      grouping service-epipe-cpipe-common-grouping {
        uses ncs_compliance_template_service-id-grouping;
        leaf customer {
          type string;
        }
        leaf name {
          type string;
        }
        leaf vc-switching {
          type empty;
        }
        leaf vpn {
          type string;
        }
        leaf description {
          type string;
        }
        leaf service-name {
          type string;
        }
        leaf service-mtu {
          type string;
        }
        list spoke-sdp {
          // NCS patched for predictable order
          ordered-by user;
          key "sdp-id vc-id";
          leaf description {
            type string;
          }
          container egress {
            container l2tpv3 {
              leaf cookie {
                type string;
              }
            }
            leaf vc-label {
              type string;
            }
          }
          container eth-cfm {
            uses ncs_compliance_template_eth-cfm;
          }
          leaf force-vlan-vc-forwarding {
            type empty;
          }
          leaf standby-signaling-slave {
            type empty;
          }
          container ingress {
            container l2tpv3 {
              leaf cookie {
                type string;
              }
            }
            leaf vc-label {
              type string;
            }
          }
          leaf pw-status-signaling {
            type empty;
          }
          leaf control-word {
            type empty;
          }
          leaf collect-stats {
            type empty;
          }
          container hash-label {
            presence "true";
            leaf signal-capability {
              type empty;
            }
          }
          leaf precedence {
            type string;
          }
          leaf vlan-vc-tag {
            type string;
          }
          leaf entropy-label {
            type empty;
          }
          leaf sdp-id {
            type string;
          }
          uses ncs_compliance_template_sdp-common;
        }
        list sap {
          // NCS patched for predictable order
          ordered-by user;
          key "sap-id";
          leaf sap-id {
            type string;
          }
          leaf endpoint {
            type string;
          }
          leaf description {
            type string;
          }
          leaf cflowd {
            type empty;
          }
          container cem {
            container packet {
              leaf jitter-buffer {
                type string;
              }
              leaf payload-size {
                type string;
              }
            }
            leaf-list report-alarm {
              // NCS patched for predictable order
              ordered-by user;
              type string;
            }
            leaf rtp-header {
              type empty;
            }
            leaf local-ecid {
              type string;
            }
            leaf remote-ecid {
              type string;
            }
            leaf remote-mac {
              type string;
            }
          }
          leaf accounting-policy {
            type string;
          }

          grouping vlan-manipulation-grouping {
            container vlan-manipulation {
              leaf preserve {
                type empty;
              }
              leaf push {
                type string;
              }
              container translate {
                leaf type {
                  tailf:cli-drop-node-name;
                  type string;
                }
                leaf qtag {
                  tailf:cli-drop-node-name;
                  type string;
                }
              }
            }
          }
          container egress {
            leaf egress-remark-policy {
              type string;
            }
            leaf qos {
              type string;
            }
            container agg-rate {
              container rate {
                leaf rate {
                  tailf:cli-drop-node-name;
                  type string;
                }
                leaf cir {
                  type string;
                }
              }
            }
            container agg-rate-limit {
              choice pir-choice {
                leaf pir-less {
                  tailf:cli-drop-node-name;
                  type string;
                }
                leaf pir {
                  type string;
                }
              }
              leaf cir {
                type string;
              }
            }
            container filter {
              uses ncs_compliance_template_filter-choice;
            }
            uses ncs_compliance_template_sap-queue-override-grouping;
            leaf scheduler-policy {
              type string;
            }
            uses ncs_compliance_template_sap-scheduler-override-grouping;
            container vlan-qos-policy {
              leaf vlan-qos-policy-name {
                tailf:cli-drop-node-name;
                type string;
              }
              leaf port-redirect {
                type empty;
              }
            }
            uses vlan-manipulation-grouping;
            container qtag-manipulation {
              leaf preserve {
                type empty;
              }
            }
          }
          container ingress {
            container aggregate-meter-rate {
              leaf value {
                tailf:cli-drop-node-name;
                type string;
              }
              leaf burst {
                type string;
              }
            }
            container aggregate-policer-rate {
              leaf rate {
                tailf:cli-drop-node-name;
                type string;
              }
              leaf burst {
                type string;
              }
            }
            container filter {
              uses ncs_compliance_template_filter-choice;
            }
            leaf match-qinq-dot1p {
              type string;
            }
            container qos {
              leaf policy-id {
                tailf:cli-drop-node-name;
                type string;
              }
              leaf shared-queuing {
                type empty;
              }
            }
            uses ncs_compliance_template_sap-queue-override-grouping;
            leaf scheduler-policy {
              type string;
            }
            uses vlan-manipulation-grouping;
            leaf vlan-translation {
              type string;
            }
            container agg-rate-limit {
              leaf agg-rate {
                tailf:cli-drop-node-name;
                type string;
              }
              leaf cir {
                type string;
              }
            }
            leaf scheduler-mode {
              type ncs_compliance_template_scheduler-mode;
            }
            uses ncs_compliance_template_sap-scheduler-override-grouping;
            container qtag-manipulation {
              leaf preserve {
                type empty;
              }
            }
          }
          leaf collect-stats {
            type empty;
          }
          container eth-cfm {
            uses ncs_compliance_template_eth-cfm;
            container mip {
              presence "true";
              leaf mac {
                type ncs_compliance_template_ieee-mac;
              }
            }
          }
          leaf multi-service-site {
            type string;
          }
          leaf oper-group {
            type string;
          }
          leaf dist-cpu-protection {
            type string;
          }
          leaf shutdown {
            type string;
          }
          container ethernet {
            leaf llf {
              type empty;
            }
          }
        }
        list endpoint {
          // NCS patched for predictable order
          ordered-by user;
          key "endpoint-name";
          leaf endpoint-name {
            type string;
          }
          leaf active-hold-delay {
            type string;
          }
          leaf description {
            type string;
          }
          leaf revert-time {
            type string;
          }
          leaf standby-signaling-master {
            type empty;
          }
          leaf standby-signaling-slave {
            type empty;
          }
        }
      }
      list cpipe {
        // NCS patched for predictable order
        ordered-by user;
        key "service-id";
        uses service-epipe-cpipe-common-grouping;
        leaf vc-type {
          type string;
        }
        leaf test {
          type empty;
        }
        leaf shutdown {
          type string;
        }
      }
      list epipe {
        // NCS patched for predictable order
        ordered-by user;
        key "service-id";
        uses service-epipe-cpipe-common-grouping {
          augment "sap" {
            container statistics {
              container ingress {
                leaf counter-mode {
                  type string;
                }
              }
            }
          }
          refine "spoke-sdp/endpoint";
        }
        container load-balancing {
          leaf per-service-hashing {
            type empty;
          }
        }
        leaf svc-sap-type {
          type string;
        }
        leaf customer-vid {
          type string;
        }
        list pw-port {
          // NCS patched for predictable order
          ordered-by user;
          key "pw-port-id fpe";
          leaf pw-port-id {
            type string;
          }
          leaf fpe {
            type string;
          }
          leaf shutdown {
            type string;
          }
        }
        list site {
          // NCS patched for predictable order
          ordered-by user;
          key "name";
          leaf name {
            type string;
          }
          leaf boot-timer {
            type string;
          }
          leaf sap {
            type string;
          }
          leaf site-activation-timer {
            type string;
          }
          leaf site-id {
            type string;
          }
          leaf shutdown {
            type string;
          }
        }
        container bgp {
          leaf route-distinguisher {
            type string;
          }
          container route-target {
            leaf export {
              type string;
            }
            leaf import {
              type string;
            }
          }
          leaf-list vsi-import {
            // NCS patched for predictable order
            ordered-by user;
            type string;
          }
          leaf-list vsi-export {
            // NCS patched for predictable order
            ordered-by user;
            type string;
          }
        }
        container bgp-evpn {
          presence "true";
          container local-ac-name {
            presence "true";
            leaf ac-name {
              tailf:cli-drop-node-name;
              type string;
            }
            leaf eth-tag {
              type string;
            }
          }
          container remote-ac-name {
            presence "true";
            leaf ac-name {
              tailf:cli-drop-node-name;
              type string;
            }
            leaf eth-tag {
              type string;
            }
          }
          list local-attachment-circuit {
            // NCS patched for predictable order
            ordered-by user;
            key "ac-name";
            leaf ac-name {
              type string;
            }
            leaf endpoint {
              type string;
            }
            leaf eth-tag {
              type string;
            }
          }
          list remote-attachment-circuit {
            // NCS patched for predictable order
            ordered-by user;
            key "ac-name";
            leaf ac-name {
              type string;
            }
            leaf endpoint {
              type string;
            }
            leaf eth-tag {
              type string;
            }
          }
          leaf evi {
            type string;
          }
          container mpls {
            presence "true";
            leaf control-word {
              type empty;
            }
            leaf bgp {
              type string;
            }
            leaf force-vlan-vc-forwarding {
              type empty;
            }
            leaf route-next-hop {
              type string;
            }
            leaf default-route-tag {
              type string;
            }
            container auto-bind-tunnel {
              leaf enforce-strict-tunnel-tagging {
                type empty;
              }
              uses ncs_compliance_template_resolution-filter-grouping;
            }
            leaf ecmp {
              type string;
            }
            leaf entropy-label {
              type empty;
            }
            leaf shutdown {
              type string;
            }
          }
        }
        leaf shutdown {
          type string;
        }
      }
      list oper-group {
        // NCS patched for predictable order
        ordered-by user;
        key "group-name";
        leaf group-name {
          type string;
        }
        container hold-time {
          container group {
            presence "true";
            leaf up {
              type string;
            }
            leaf down {
              type string;
            }
          }
        }
      }
      list ies {
        // NCS patched for predictable order
        ordered-by user;
        key "service-id";
        leaf service-id {
          type string;
        }
        leaf customer {
          type string;
        }
        leaf name {
          type string;
        }
        leaf description {
          type string;
        }
        list redundant-interface {
          // NCS patched for predictable order
          ordered-by user;
          key "id";
          leaf id {
            type string;
          }
          leaf description {
            type string;
          }
          leaf address {
            type string;
          }
          list spoke-sdp {
            // NCS patched for predictable order
            ordered-by user;
            key "sdp-id";
            leaf sdp-id {
              type string;
            }
            leaf shutdown {
              type string;
            }
          }
          leaf shutdown {
            type string;
          }
        }
        list subscriber-interface {
          // NCS patched for predictable order
          ordered-by user;
          key "id";
          uses ncs_compliance_template_subscriber-interface-grouping {
            refine "group-interface/tos-marking-state";
            augment "group-interface/sap" {
              leaf cpu-protection {
                type string;
              }
              list static-host {
                // NCS patched for predictable order
                ordered-by user;
                key "ip";
                leaf ip {
                  type string;
                }
                leaf shutdown {
                  type string;
                }
              }
            }
            augment "group-interface/dhcp" {
              leaf shutdown {
                type string;
              }
            }
          }
          container hold-time {
            list down {
              // NCS patched for predictable order
              ordered-by user;
              tailf:cli-suppress-mode;
              key "type";
              leaf type {
                type string;
              }
              leaf time {
                tailf:cli-drop-node-name;
                type string;
              }
              leaf init-only {
                type empty;
              }
            }
          }
          container ipv6 {
            presence "true";
            list address {
              // NCS patched for predictable order
              ordered-by user;
              tailf:cli-suppress-mode;
              key "ipv6-address";
              leaf ipv6-address {
                type string;
              }
              choice adr {
                leaf pd {
                  type empty;
                }
                leaf wan-host {
                  type empty;
                }
              }
            }
            container default-dns {
              leaf address {
                tailf:cli-drop-node-name;
                type string;
              }
              leaf secondary {
                type string;
              }
            }
            leaf delegated-prefix-length {
              type string;
            }
            leaf link-local-address {
              type string;
            }
            leaf allow-unmatching-prefixes {
              type empty;
            }
            container subscriber-prefixes {
              list prefix {
                // NCS patched for predictable order
                ordered-by user;
                tailf:cli-suppress-mode;
                key "ipv6-prefix";
                leaf ipv6-prefix {
                  type string;
                }
                leaf pd {
                  type empty;
                }
                leaf wan-host {
                  type empty;
                }
                leaf track-srrp {
                  type string;
                }
              }
            }
          }
          container dhcp {
            container gi-address {
              leaf gi-address-value {
                tailf:cli-drop-node-name;
                type string;
              }
              leaf src-ip-addr {
                type empty;
              }
            }
            leaf virtual-subnet {
              type empty;
            }
          }
          leaf shutdown {
            type string;
          }
        }
        list interface {
          // NCS patched for predictable order
          ordered-by user;
          key "ip-int-name";
          leaf ip-int-name {
            type string;
          }
          leaf tunnel {
            type empty;
          }
          leaf monitor-oper-group {
            type string;
          }
          leaf allow-directed-broadcasts {
            type empty;
          }
          leaf arp-learn-unsolicited {
            type empty;
          }
          leaf arp-populate {
            type empty;
          }
          leaf arp-timeout {
            type string;
          }
          leaf authentication-policy {
            type string;
          }
          container bfd {
            uses ncs_compliance_template_bfd-grouping;
          }
          uses ncs_compliance_template_cflowd-params-grouping;
          container cflowd {
            leaf id {
              tailf:cli-drop-node-name;
              type string;
            }
            leaf direction {
              tailf:cli-drop-node-name;
              type string;
            }
          }
          leaf cpu-protection {
            type string;
          }
          leaf delayed-enable {
            type string;
          }
          leaf description {
            type string;
          }
          container dhcp {
            leaf-list server {
              // NCS patched for predictable order
              ordered-by user;
              type string;
            }
            container gi-address {
              leaf gi-address-value {
                tailf:cli-drop-node-name;
                type string;
              }
              leaf src-ip-addr {
                type empty;
              }
            }
            leaf lease-populate {
              type string;
            }
            leaf trusted {
              type empty;
            }
            leaf shutdown {
              type string;
            }
          }
          leaf dynamic-tunnel-redundant-next-hop {
            type string;
          }
          leaf enable-ingress-stats {
            type empty;
          }
          leaf enable-mac-accounting {
            type empty;
          }
          container host-connectivity {
            leaf source {
              type string;
            }
            leaf interval {
              type string;
            }
            leaf action {
              type string;
            }
            leaf timeout {
              type string;
            }
            leaf count {
              type string;
            }
          }
          uses ncs_compliance_template_interface-icmp-grouping;
          leaf ip-mtu {
            type string;
          }
          container ipv6 {
            presence "true";
            leaf local-dhcp-server {
              type string;
            }
            uses ncs_compliance_template_ipv6-grouping;
            uses ncs_compliance_template_dhcp6-grouping;
          }
          leaf local-dhcp-server {
            type string;
          }
          leaf loopback {
            type empty;
          }
          leaf mac {
            type ncs_compliance_template_ieee-mac;
          }
          list sap {
            // NCS patched for predictable order
            ordered-by user;
            key "sap-id";
            leaf sap-id {
              type string;
            }
            leaf accounting-policy {
              type string;
            }
            leaf description {
              type string;
            }
            leaf dist-cpu-protection {
              type string;
            }
            leaf collect-stats {
              type empty;
            }
            container egress {
              choice agg {
                case new {
                  uses ncs_compliance_template_agg-rate-grouping;
                }
                case old {
                  container agg-rate-limit {
                    leaf agg-rate {
                      tailf:cli-drop-node-name;
                      type string;
                    }
                    leaf queue-frame-based-accounting {
                      type empty;
                    }
                  }
                }
              }
              container filter {
                leaf ip {
                  type ncs_compliance_template_filter-id;
                }
                leaf ipv6 {
                  type ncs_compliance_template_filter-id;
                }
              }
              leaf policer-control-policy {
                type string;
              }
              leaf qinq-mark-top-only {
                type empty;
              }
              leaf qos {
                type string;
              }
              uses ncs_compliance_template_sap-queue-override-grouping;
              leaf scheduler-mode {
                type ncs_compliance_template_scheduler-mode;
              }
              leaf scheduler-policy {
                type string;
              }
              uses ncs_compliance_template_sap-scheduler-override-grouping;
            }
            container ingress {
              leaf qos {
                type string;
              }
              container filter {
                uses ncs_compliance_template_filter-choice;
              }
              leaf flowspec {
                type string;
              }
              leaf flowspec-ipv6 {
                type string;
              }
              leaf match-qinq-dot1p {
                type string;
              }
              leaf policer-control-policy {
                type string;
              }
              container policer-control-override {
                presence "true";
                leaf max-rate {
                  type string;
                }
                container priority-mbs-thresholds {
                  container min-thresh-separation {
                    uses ncs_compliance_template_mbs-rate-grouping;
                  }
                  list priority {
                    // NCS patched for predictable order
                    ordered-by user;
                    key "level";
                    leaf level {
                      type string;
                    }
                    container mbs-contribution {
                      uses ncs_compliance_template_mbs-rate-grouping;
                    }
                  }
                }
              }
              uses ncs_compliance_template_sap-policer-override-grouping-ingress;
              uses ncs_compliance_template_sap-queue-override-grouping;
              leaf scheduler-policy {
                type string;
              }
              uses ncs_compliance_template_sap-scheduler-override-grouping;
            }
            leaf anti-spoof {
              type string;
            }
            leaf multi-service-site {
              type string;
            }
            container sub-sla-mgmt {
              presence "present";
              leaf def-sub-id {
                type string;
              }
              leaf def-sub-profile {
                type string;
              }
              container single-sub-parameters {
                presence "present";
                leaf profiled-traffic-only {
                  type empty;
                }
              }
              leaf shutdown {
                type string;
              }
            }
            leaf calling-station-id {
              type string;
            }
            list ip-tunnel {
              // NCS patched for predictable order
              ordered-by user;
              key "name";
              leaf name {
                type string;
              }
              leaf description {
                type string;
              }
              leaf dest-ip {
                type string;
              }
              container gre-header {
                presence "true";
              }
              leaf source {
                type string;
              }
              leaf remote-ip {
                type string;
              }
              leaf delivery-service {
                type string;
              }
              leaf shutdown {
                type string;
              }
            }
            leaf shutdown {
              type empty;
            }
          }
          list spoke-sdp {
            // NCS patched for predictable order
            ordered-by user;
            key "sdp-id vc-id";
            leaf sdp-id {
              type string;
            }
            leaf vc-id {
              type string;
            }
            leaf vc-type {
              type string;
            }
            container egress {
              container filter {
                uses ncs_compliance_template_filter-choice;
              }
            }
            container ingress {
              container filter {
                uses ncs_compliance_template_filter-choice;
              }
            }
            leaf shutdown {
              type string;
            }
          }
          leaf tos-marking-state {
            type string;
          }
          container urpf-check {
            leaf mode {
              type string;
            }
          }
          leaf vas-if-type {
            type string;
          }
          list vrrp {
            // NCS patched for predictable order
            ordered-by user;
            key "virtual-router-id";
            leaf virtual-router-id {
              type string;
            }
            leaf owner {
              type empty;
            }
            leaf passive {
              type empty;
            }
            uses ncs_compliance_template_authentication-key-grouping;
            leaf init-delay {
              type string;
            }
            leaf mac {
              type ncs_compliance_template_ieee-mac;
            }
            leaf master-int-inherit {
              type empty;
            }
            container message-interval {
              leaf seconds {
                tailf:cli-drop-node-name;
                type string;
              }
              leaf milliseconds {
                type string;
              }
            }
            leaf ping-reply {
              type empty;
            }
            leaf policy {
              type string;
            }
            leaf preempt {
              type empty;
            }
            leaf priority {
              type string;
            }
            leaf ssh-reply {
              type empty;
            }
            leaf standby-forwarding {
              type empty;
            }
            leaf telnet-reply {
              type empty;
            }
            leaf traceroute-reply {
              type empty;
            }
            list backup {
              // NCS patched for predictable order
              ordered-by user;
              tailf:cli-suppress-mode;
              key "address";
              leaf address {
                type string;
              }
            }
            leaf shutdown {
              type string;
            }
          }
          list secondary {
            // NCS patched for predictable order
            ordered-by user;
            tailf:cli-suppress-mode;
            key "address";
            leaf address {
              type string;
            }
            leaf broadcast {
              type string;
            }
          }
          container address {
            leaf ip-address {
              tailf:cli-drop-node-name;
              // NCS drop tailf-common:cli-diff-create-before statement
              type string;
            }
            leaf broadcast {
              type string;
            }
            leaf track-srrp {
              type string;
            }
          }
          list static-arp {
            // NCS patched for predictable order
            ordered-by user;
            tailf:cli-suppress-mode;
            key "ip-address";
            leaf ip-address {
              type string;
            }
            leaf ieee-address {
              tailf:cli-drop-node-name;
              type ncs_compliance_template_ieee-mac;
            }
          }
          leaf qos-route-lookup {
            type string;
          }
          container vpls {
            presence "true";
            leaf service-name {
              tailf:cli-drop-node-name;
              // NCS drop mandatory statement
              type string;
            }
            container egress {
              leaf reclassify-using-qos {
                type string;
              }
              leaf v4-routed-override-filter {
                type ncs_compliance_template_filter-id;
              }
            }
            container ingress {
              leaf v4-routed-override-filter {
                type ncs_compliance_template_filter-id;
              }
              leaf v6-routed-override-filter {
                type ncs_compliance_template_filter-id;
              }
            }
          }
          leaf shutdown {
            type empty;
          }
        }
        leaf service-name {
          type string;
        }
        leaf shutdown {
          type string;
        }
      }
      container proxy-arp-nd {
        list mac-list {
          // NCS patched for predictable order
          ordered-by user;
          key "name";
          leaf name {
            type string;
          }
          list mac {
            // NCS patched for predictable order
            ordered-by user;
            tailf:cli-suppress-mode;
            key "mac-id";
            leaf mac-id {
              type ncs_compliance_template_ieee-mac;
            }
          }
        }
      }
      container nat {
        list nat-policy {
          // NCS patched for predictable order
          ordered-by user;
          key "name";
          leaf name {
            type string;
          }
          container pool {
            leaf name {
              tailf:cli-drop-node-name;
              type string;
            }
            leaf router {
              type string;
            }
          }
          container timeouts {
            list timeouts {
              // NCS patched for predictable order
              ordered-by user;
              tailf:cli-drop-node-name;
              tailf:cli-suppress-mode;
              key "name";
              leaf name {
                type string;
              }
              leaf hrs {
                type string;
              }
              leaf min {
                type string;
              }
              leaf sec {
                type string;
              }
            }
          }
        }
      }
      list vpls {
        // NCS patched for predictable order
        ordered-by user;
        key "service-id";
        // NCS expand uses statement
        leaf service-id {
          type ncs_compliance_template_service-id;
        }
        leaf customer {
          type string;
        }
        leaf name {
          type string;
        }
        leaf etree {
          type empty;
        }
        leaf vpn {
          type string;
        }
        leaf m-vpls {
          type empty;
        }
        choice a {
          leaf b-vpls {
            type empty;
          }
          leaf i-vpls {
            type empty;
          }
          leaf r-vpls {
            type empty;
          }
        }
        leaf svc-sap-type {
          type string;
        }
        leaf description {
          type string;
        }
        leaf disable-learning {
          type empty;
        }
        leaf disable-aging {
          type empty;
        }
        leaf discard-unknown {
          type empty;
        }
        container allow-ip-int-bind {
          presence "true";
          leaf evpn-mpls-ecmp {
            type empty;
          }
          leaf forward-ipv4-multicast-to-ip-int {
            type empty;
          }
          leaf vxlan-ipv4-tep-ecmp {
            type empty;
          }
          container igmp-snooping {
            leaf mrouter-port {
              type empty;
            }
          }
        }
        leaf allow-ip-int-binding {
          type empty;
        }
        leaf service-name {
          type string;
        }
        list endpoint {
          // NCS patched for predictable order
          ordered-by user;
          key "endpoint-name";
          leaf endpoint-name {
            type string;
          }
          leaf description {
            type string;
          }
          leaf revert-time {
            type string;
          }
          leaf suppress-standby-signaling {
            type ncs_compliance_template_enable-disable;
          }
          container restrict-protected-src {
            presence "present";
            leaf restrict-protected-src-value {
              tailf:cli-drop-node-name;
              type string;
            }
          }
        }
        container eth-cfm {
          uses ncs_compliance_template_eth-cfm;
          leaf vmep-extensions {
            type empty;
          }
          leaf tunnel-fault {
            type string;
          }
        }
        leaf fdb-table-high-wmark {
          type string;
        }
        leaf fdb-table-low-wmark {
          type string;
        }
        leaf fdb-table-size {
          type string;
        }
        container igmp-snooping {
          leaf query-interval {
            type string;
          }
          leaf report-src-ip {
            type string;
          }
          leaf robust-count {
            type string;
          }
          leaf shutdown {
            type string;
          }
        }
        list site {
          // NCS patched for predictable order
          ordered-by user;
          key "name";
          leaf name {
            type string;
          }
          leaf site-id {
            type string;
          }
          leaf sap {
            type string;
          }
          leaf spoke-sdp {
            type string;
          }
          leaf shutdown {
            type string;
          }
        }
        list interface {
          // NCS patched for predictable order
          ordered-by user;
          key "ip-int-name";
          leaf ip-int-name {
            type string;
          }
          container address {
            choice a {
              leaf addr-and-prefix {
                tailf:cli-drop-node-name;
                type string;
              }
              case addr-and-netmask {
                leaf addr {
                  tailf:cli-drop-node-name;
                  type string;
                }
                leaf mask {
                  tailf:cli-drop-node-name;
                  type string;
                }
              }
            }
          }
          leaf arp-timeout {
            type string;
          }
          leaf description {
            type string;
          }
          leaf mac {
            type ncs_compliance_template_ieee-mac;
          }
          list static-arp {
            // NCS patched for predictable order
            ordered-by user;
            tailf:cli-suppress-mode;
            key "address";
            leaf address {
              type string;
            }
            leaf ieee-address {
              tailf:cli-drop-node-name;
              type ncs_compliance_template_ieee-mac;
            }
            leaf unnumbered {
              type empty;
            }
          }
          leaf unnumbered {
            type string;
          }
          leaf shutdown {
            type string;
          }
        }
        leaf local-age {
          type string;
        }
        container load-balancing {
          leaf per-service-hashing {
            type empty;
          }
          leaf spi-load-balancing {
            type empty;
          }
          leaf teid-load-balancing {
            type empty;
          }
        }
        container mac-move {
          leaf move-frequency {
            type string;
          }
          leaf number-retries {
            type string;
          }
          leaf retry-timeout {
            type string;
          }

          grouping vpls-mac-move-ports-grouping {
            leaf cumulative-factor {
              type string;
            }
            list sap {
              // NCS patched for predictable order
              ordered-by user;
              tailf:cli-suppress-mode;
              key "id";
              leaf id {
                type string;
              }
            }
            list spoke-sdp {
              // NCS patched for predictable order
              ordered-by user;
              tailf:cli-suppress-mode;
              key "id";
              leaf id {
                type string;
              }
            }
          }
          container primary-ports {
            uses vpls-mac-move-ports-grouping;
          }
          container secondary-ports {
            uses vpls-mac-move-ports-grouping;
          }
          leaf shutdown {
            type string;
          }
        }
        leaf mfib-table-high-wmark {
          type string;
        }
        leaf mfib-table-low-wmark {
          type string;
        }
        leaf mfib-table-size {
          type string;
        }
        container pbb {
          list backbone-vpls {
            // NCS patched for predictable order
            ordered-by user;
            key "service-id";
            leaf service-id {
              type ncs_compliance_template_service-id;
            }
            leaf isid {
              type string;
            }

            grouping service-vpls-mld-snooping-grouping {
              container mld-snooping {
                leaf mrouter-port {
                  type empty;
                }
              }
            }

            grouping service-vpls-igmp-snooping-grouping {
              container igmp-snooping {
                leaf mrouter-port {
                  type empty;
                }
              }
            }
            container igmp-snooping {
              leaf mrouter-dest {
                type string;
              }
            }
            container mld-snooping {
              leaf mrouter-dest {
                type string;
              }
            }
            list sap {
              // NCS patched for predictable order
              ordered-by user;
              key "sap-id";
              leaf sap-id {
                type string;
              }
              uses service-vpls-igmp-snooping-grouping;
              uses service-vpls-mld-snooping-grouping;
            }
            list sdp {
              // NCS patched for predictable order
              ordered-by user;
              key "sdp-id";
              leaf sdp-id {
                type string;
              }
              uses service-vpls-igmp-snooping-grouping;
              uses service-vpls-mld-snooping-grouping;
            }
            leaf stp {
              type empty;
            }
          }
          leaf force-qtag-forwarding {
            type empty;
          }
          leaf propagate-mac-flush-from-bvpls {
            type empty;
          }
          leaf-list send-bvpls-flush {
            // NCS patched for predictable order
            ordered-by user;
            type string;
          }
          leaf send-flush-on-bvpls-failure {
            type empty;
          }
          leaf source-bmac {
            type ncs_compliance_template_ieee-mac;
          }
          leaf use-sap-bmac {
            type empty;
          }
        }
        container proxy-arp {
          presence "true";
          list static {
            // NCS patched for predictable order
            ordered-by user;
            tailf:cli-suppress-mode;
            key "address";
            leaf address {
              type string;
            }
            leaf ieee-addr {
              // NCS drop mandatory statement
              tailf:cli-drop-node-name;
              type ncs_compliance_template_ieee-mac;
            }
          }
          leaf age-time {
            type string;
          }
          container dup-detect {
            leaf anti-spoof-mac {
              type ncs_compliance_template_ieee-mac;
            }
            leaf window {
              type string;
            }
            leaf num-moves {
              type string;
            }
            leaf hold-down {
              type string;
            }
          }
          list dynamic {
            // NCS patched for predictable order
            ordered-by user;
            key "address";
            leaf address {
              type string;
            }
            leaf mac-list {
              type string;
            }
            leaf resolve {
              type string;
            }
          }
          leaf dynamic-arp-populate {
            type empty;
          }
          leaf evpn-route-tag {
            type string;
          }
          leaf garp-flood-evpn {
            type string;
          }
          leaf send-refresh {
            type string;
          }
          leaf table-size {
            type string;
          }
          leaf unknown-arp-request-flood-evpn {
            type string;
          }
          leaf shutdown {
            type string;
          }
        }
        leaf propagate-mac-flush {
          type empty;
        }
        leaf remote-age {
          type string;
        }
        leaf send-flush-on-failure {
          type empty;
        }
        leaf service-mtu {
          type string;
        }
        list spb {
          // NCS patched for predictable order
          ordered-by user;
          key "isis-instance";
          leaf isis-instance {
            type string;
          }
          leaf fid {
            type string;
          }
          list level {
            // NCS patched for predictable order
            ordered-by user;
            key "level";
            leaf level {
              type string;
            }
            leaf bridge-priority {
              type string;
            }
            container ect-algorithm {
              leaf fid-range {
                type string;
              }
              leaf path-id {
                tailf:cli-drop-node-name;
                type string;
              }
            }
            container forwarding-tree-topology {
              leaf unicast {
                type string;
              }
            }
            leaf hello-interval {
              type string;
            }
            leaf hello-multiplier {
              type string;
            }
            leaf metric {
              type string;
            }
          }
          leaf lsp-pacing-interval {
            type string;
          }
          leaf retransmit-interval {
            type string;
          }
          leaf shutdown {
            type string;
          }
        }
        container stp {
          leaf forward-delay {
            type string;
          }
          leaf hello-time {
            type string;
          }
          leaf hold-count {
            type string;
          }
          leaf max-age {
            type string;
          }
          leaf mode {
            type string;
          }
          list mst-instance {
            // NCS patched for predictable order
            ordered-by user;
            key "mst-inst-number";
            leaf mst-inst-number {
              type string;
            }
            leaf mst-priority {
              type string;
            }
            list vlan-range {
              // NCS patched for predictable order
              ordered-by user;
              tailf:cli-suppress-mode;
              key "vlan";
              leaf vlan {
                type string;
              }
            }
          }
          leaf mst-max-hops {
            type string;
          }
          leaf mst-name {
            type string;
          }
          leaf mst-revision {
            type string;
          }
          leaf priority {
            type string;
          }
          leaf shutdown {
            type string;
          }
        }
        leaf def-mesh-vc-id {
          type string;
        }
        list mesh-sdp {
          // NCS patched for predictable order
          ordered-by user;
          key "sdp-id vc-id";
          uses ncs_compliance_template_sdp-spoke-mesh-common;
        }
        container pim-snooping {
          leaf shutdown {
            type string;
          }
        }
        list spoke-sdp {
          // NCS patched for predictable order
          ordered-by user;
          key "sdp-id vc-id";
          uses ncs_compliance_template_sdp-spoke-mesh-common;
          leaf leaf-ac {
            type empty;
          }
          leaf split-horizon-group {
            type string;
          }
          container dhcp {
            leaf description {
              type string;
            }
            leaf snoop {
              type empty;
            }
          }
          leaf bpdu-translation {
            type string;
          }
          leaf diable-aging {
            type empty;
          }
          leaf disable-learning {
            type empty;
          }
          leaf discard-unknown-source {
            type empty;
          }
          leaf l2pt-termination {
            type empty;
          }
          leaf entropy-label {
            type empty;
          }
          leaf limit-mac-move {
            type ncs_compliance_template_limit-mac-move;
          }
          leaf max-nbr-mac-addr {
            type string;
          }
          container stp {
            uses ncs_compliance_template_stp-common;
          }
          container oper-group-choice {
            tailf:cli-drop-node-name;
            leaf monitor-oper-group {
              type string;
            }
            leaf oper-group {
              type string;
            }
          }
          container transit-policy {
            leaf prefix {
              type string;
            }
          }
          leaf pw-status-signaling {
            type string;
          }
        }
        list sap {
          // NCS patched for predictable order
          ordered-by user;
          key "sap-id";
          leaf sap-id {
            type string;
          }
          leaf dist-cpu-protection {
            type string;
          }
          leaf leaf-ac {
            type empty;
          }
          list static-mac {
            // NCS patched for predictable order
            ordered-by user;
            tailf:cli-suppress-mode;
            key "mac";
            leaf mac {
              type ncs_compliance_template_ieee-mac;
            }
          }
          leaf eth-ring {
            type string;
          }
          container sub-sla-mgmt {
            container single-sub-parameters {
              leaf profiled-traffic-only {
                type empty;
              }
              container non-sub-traffic {
                leaf sub-profile {
                  type string;
                }
                leaf sla-profile {
                  type string;
                }
                leaf subscriber {
                  type string;
                }
              }
            }
            leaf shutdown {
              type string;
            }
          }
          leaf allow-dot1q-msaps {
            type empty;
          }
          leaf arp-reply-agent {
            tailf:cli-drop-node-name;
            type string;
          }
          leaf cflowd {
            type empty;
          }
          leaf split-horizon-group {
            type string;
          }
          leaf capture-sap {
            type empty;
          }
          leaf dhcp-python-policy {
            type ncs_compliance_template_string32;
          }
          leaf dhcp6-python-policy {
            type ncs_compliance_template_string32;
          }
          leaf-list trigger-packet {
            // NCS patched for predictable order
            ordered-by user;
            type string;
          }
          leaf authentication-policy {
            type string;
          }
          leaf accounting-policy {
            type string;
          }
          leaf anti-spoof {
            type string;
          }
          leaf app-profile {
            type string;
          }
          leaf auto-learn-mac-protect {
            type empty;
          }
          leaf bpdu-translation {
            type string;
          }
          leaf collect-stats {
            type empty;
          }
          leaf description {
            type string;
          }
          leaf disable-aging {
            type empty;
          }
          leaf disable-learning {
            type empty;
          }
          leaf discard-unknown-source {
            type empty;
          }
          container eth-cfm {
            uses ncs_compliance_template_eth-cfm;
            container mip {
              presence "true";
              leaf mac {
                type string;
              }
            }
          }
          leaf host-lockout-policy {
            type ncs_compliance_template_string32;
          }
          container igmp-snooping {
            uses ncs_compliance_template_igmp-snooping-grouping;
          }
          container ingress {
            // NCS expand uses statement
            container filter {
              // NCS expand uses statement
              leaf ip {
                type ncs_compliance_template_filter-id;
              }
              leaf ipv6 {
                type ncs_compliance_template_filter-id;
              }
              leaf mac {
                type ncs_compliance_template_filter-id;
              }
            }
            container aggregate-meter-rate {
              leaf value {
                tailf:cli-drop-node-name;
                type string;
              }
              leaf burst {
                type string;
              }
            }
            leaf match-qinq-dot1p {
              type string;
            }
            container qos {
              leaf policy-id {
                tailf:cli-drop-node-name;
                type string;
              }
              leaf shared-queuing {
                type empty;
              }
              leaf enable-table-classification {
                type empty;
              }
            }
            // NCS expand uses statement
            container queue-override {
              list queue {
                // NCS patched for predictable order
                ordered-by user;
                key "queue-id";
                leaf queue-id {
                  type string;
                }
                // NCS expand uses statement
                container adaptation-rule {
                  leaf pir {
                    type string;
                  }
                  leaf cir {
                    type string;
                  }
                }
                leaf avg-frame-overhead {
                  type string;
                }
                container mbs {
                  leaf val {
                    tailf:cli-drop-node-name;
                    type string;
                  }
                  leaf unit {
                    tailf:cli-drop-node-name;
                    type string;
                  }
                }
                leaf cbs {
                  type string;
                }
                leaf high-prio-only {
                  type string;
                }
                container rate {
                  leaf pir {
                    tailf:cli-drop-node-name;
                    type string;
                  }
                  leaf cir {
                    type string;
                  }
                }
                container parent {
                  leaf weight {
                    type string;
                  }
                  leaf cir-weight {
                    type string;
                  }
                }
                // NCS expand uses statement
                container percent-rate {
                  leaf pir {
                    tailf:cli-drop-node-name;
                    type string;
                  }
                  leaf cir {
                    type string;
                  }
                }
              }
            }
            leaf agg-shaper-rate {
              type string;
            }
            // NCS expand uses statement
            container policer-override {
              list policer {
                // NCS patched for predictable order
                ordered-by user;
                key "policer-id";
                leaf policer-id {
                  type string;
                }
                // NCS expand uses statement
                // NCS expand uses statement
                container cbs {
                  // NCS expand uses statement
                  leaf size {
                    tailf:cli-drop-node-name;
                    type string;
                  }
                  leaf unit {
                    tailf:cli-drop-node-name;
                    type string;
                  }
                }
                container mbs {
                  // NCS expand uses statement
                  leaf size {
                    tailf:cli-drop-node-name;
                    type string;
                  }
                  leaf unit {
                    tailf:cli-drop-node-name;
                    type string;
                  }
                }
                container rate {
                  leaf pir {
                    tailf:cli-drop-node-name;
                    type ncs_compliance_template_rate-type;
                  }
                  leaf cir {
                    type ncs_compliance_template_rate-type;
                  }
                }
                leaf stat-mode {
                  type ncs_compliance_template_policer-stat-mode;
                }
                container packet-byte-offset {
                  choice add-delete {
                    leaf add {
                      type string;
                    }
                    leaf subtract {
                      type string;
                    }
                  }
                }
              }
            }
            leaf policer-control-policy {
              type string;
            }
            leaf scheduler-policy {
              type string;
            }
            // NCS expand uses statement
            container scheduler-override {
              list scheduler {
                // NCS patched for predictable order
                ordered-by user;
                key "scheduler-policy-name";
                leaf scheduler-policy-name {
                  type string;
                }
                container parent {
                  leaf weight {
                    type string;
                  }
                  leaf cir-weight {
                    type string;
                  }
                }
                container rate {
                  leaf rate {
                    tailf:cli-drop-node-name;
                    type string;
                  }
                  leaf cir {
                    type string;
                  }
                }
              }
            }
            leaf vlan-translation {
              type string;
            }
            container aggregate-policer-rate {
              leaf rate {
                tailf:cli-drop-node-name;
                type string;
              }
              leaf burst {
                type string;
              }
            }
            container qtag-manipulation {
              leaf preserve {
                type empty;
              }
            }
          }
          leaf lag-link-map-profile {
            type string;
          }
          leaf l2pt-termination {
            type empty;
          }
          leaf limit-mac-move {
            type ncs_compliance_template_limit-mac-move;
          }
          leaf mac-pinning {
            type empty;
          }
          container managed-vlan-list {
            leaf default-sap {
              type empty;
            }
            leaf range {
              type string;
            }
          }
          leaf max-nbr-mac-addr {
            type string;
          }
          leaf monitor-oper-group {
            type string;
          }
          container msap-defaults {
            leaf group-interface {
              type string;
            }
            leaf policy {
              type ncs_compliance_template_string32;
            }
            leaf service {
              type ncs_compliance_template_service-id;
            }
          }
          container ipoe-session {
            uses ncs_compliance_template_ipoe-session-grouping;
          }
          leaf multi-service-site {
            type string;
          }
          leaf pppoe-policy {
            type ncs_compliance_template_string32;
          }
          container restrict-protected-src {
            presence "present";
            leaf restrict-protected-src-value {
              tailf:cli-drop-node-name;
              type string;
            }
          }
          leaf restrict-unprotected-dst {
            type empty;
          }
          leaf ring-node {
            type empty;
          }
          container egress {
            uses ncs_compliance_template_sap-egress-grouping;
          }
          container stp {
            uses ncs_compliance_template_stp-common;
            list mst-instance {
              // NCS patched for predictable order
              ordered-by user;
              key "mst-inst-number";
              leaf mst-inst-number {
                type string;
              }
              leaf mst-path-cost {
                type string;
              }
              leaf mst-priority {
                type string;
              }
            }
          }
          container statistics {
            container ingress {
              leaf counter-mode {
                type string;
              }
            }
          }
          leaf tod-suite {
            type string;
          }
          leaf track-srrp {
            type string;
          }
          leaf shutdown {
            type empty;
          }
        }
        list split-horizon-group {
          // NCS patched for predictable order
          ordered-by user;
          key "group-name";
          leaf group-name {
            type string;
          }
          leaf residential-group {
            type empty;
          }
          leaf auto-learn-mac-protect {
            type empty;
          }
          leaf description {
            type string;
          }
          container restrict-protected-src {
            presence "present";
            leaf restrict-protected-src-value {
              tailf:cli-drop-node-name;
              type string;
            }
          }
          leaf restrict-unprotected-dst {
            type empty;
          }
        }
        list bgp {
          // NCS patched for predictable order
          ordered-by user;
          key "bgp-id";
          leaf bgp-id {
            type string;
          }

          grouping pw-template-binding-grouping {
            leaf policy-id {
              type string;
            }
            leaf split-horizon-group {
              type string;
            }
          }
          list pw-template-bind {
            // NCS patched for predictable order
            ordered-by user;
            key "policy-id";
            uses pw-template-binding-grouping;
            leaf import-rt {
              type ncs_compliance_template_string32;
            }
          }
          list pw-template-binding {
            // NCS patched for predictable order
            ordered-by user;
            key "policy-id";
            uses pw-template-binding-grouping;
            leaf monitor-oper-group {
              type string;
            }
            container import-rt {
              leaf rt1 {
                tailf:cli-drop-node-name;
                type ncs_compliance_template_string32;
              }
              leaf rt2 {
                tailf:cli-drop-node-name;
                type ncs_compliance_template_string32;
              }
              leaf rt3 {
                tailf:cli-drop-node-name;
                type ncs_compliance_template_string32;
              }
              leaf rt4 {
                tailf:cli-drop-node-name;
                type ncs_compliance_template_string32;
              }
              leaf rt5 {
                tailf:cli-drop-node-name;
                type ncs_compliance_template_string32;
              }
            }
          }
          leaf route-distinguisher {
            type string;
          }
          container route-target {
            leaf export {
              type string;
            }
            leaf import {
              type string;
            }
          }
          leaf-list vsi-import {
            // NCS patched for predictable order
            ordered-by user;
            type string;
          }
          leaf-list vsi-export {
            // NCS patched for predictable order
            ordered-by user;
            type string;
          }
        }
        container bgp-ad {
          presence "true";
          leaf vpls-id {
            type ncs_compliance_template_service-id;
          }
          container vsi-id {
            leaf prefix {
              type string;
            }
          }
          leaf shutdown {
            type string;
          }
        }
        container bgp-evpn {
          presence "true";
          leaf unknown-mac-route {
            type empty;
          }
          leaf evi {
            type string;
          }
          container mac-duplication {
            container detect {
              leaf num-moves {
                type string;
              }
              leaf window {
                type string;
              }
            }
            leaf retry {
              type string;
            }
          }
          container ip-route-advertisement {
            presence "true";
            leaf incl-host {
              type empty;
            }
          }
          container mpls {
            presence "true";
            leaf bgp {
              type string;
            }
            leaf entropy-label {
              type empty;
            }
            leaf route-next-hop {
              type string;
            }
            leaf default-route-tag {
              type string;
            }
            leaf split-horizon-group {
              type string;
            }
            leaf control-word {
              type empty;
            }
            leaf restrict-protected-src {
              type string;
            }
            leaf force-vlan-vc-forwarding {
              type empty;
            }
            container auto-bind-tunnel {
              uses ncs_compliance_template_resolution-filter-grouping;
              leaf enforce-strict-tunnel-tagging {
                type empty;
              }
            }
            leaf ingress-replication-bum-label {
              type empty;
            }
            leaf ecmp {
              type string;
            }
            leaf oper-group {
              type string;
            }
            leaf shutdown {
              type string;
            }
          }
          container vxlan {
            presence "true";
            leaf shutdown {
              type string;
            }
            leaf bgp {
              type string;
            }
            leaf vxlan-instance {
              type string;
            }
          }
        }
        container static-mac {
          list mac {
            // NCS patched for predictable order
            ordered-by user;
            tailf:cli-suppress-mode;
            key "mac";
            leaf mac {
              type ncs_compliance_template_ieee-mac;
            }
            leaf create {
              type empty;
            }
            leaf black-hole {
              type empty;
            }
            leaf sap {
              type string;
            }
            leaf monitor {
              type string;
            }
          }
        }
        container bgp-vpls {
          leaf max-ve-id {
            type string;
          }
          container ve-name {
            leaf ve-name {
              tailf:cli-drop-node-name;
              type string;
            }
            leaf ve-id {
              type string;
            }
          }
          leaf shutdown {
            type string;
          }
        }
        list vxlan {
          // NCS patched for predictable order
          ordered-by user;
          key "vni";
          leaf instance {
            type string;
          }
          leaf vni {
            type string;
          }
          container assisted-replication {
            leaf role {
              tailf:cli-drop-node-name;
              type string;
            }
            leaf replicator-activation-time {
              type string;
            }
          }
          container network {
            container ingress {
              container qos {
                leaf network-policy-id {
                  tailf:cli-drop-node-name;
                  type string;
                }
                leaf fp-redirect-group {
                  type string;
                }
                leaf instance {
                  type string;
                }
              }
            }
          }
          leaf restrict-protected-src {
            type string;
          }
          leaf rx-discard-on-ndf {
            type string;
          }
        }
        leaf shutdown {
          type string;
        }
      }
      list vprn {
        // NCS patched for predictable order
        ordered-by user;
        key "service-id";
        uses ncs_compliance_template_service-id-grouping;
        leaf customer {
          type string;
        }
        leaf entropy-label {
          type empty;
        }
        container ntp {
          presence "true";
          leaf shutdown {
            type string;
          }
        }
        container management {
          presence "true";
          leaf allow-ftp {
            type empty;
          }
          leaf allow-grpc {
            type empty;
          }
          leaf allow-netconf {
            type empty;
          }
          leaf allow-ssh {
            type empty;
          }
          leaf allow-telnet {
            type empty;
          }
          leaf allow-telnet6 {
            type empty;
          }
        }
        container aaa {
          container remote-servers {

            grouping remote-servers-grouping {
              container accounting {
                presence "true";
                leaf record-type {
                  type string;
                }
              }
              container authorization {
                presence "true";
                leaf use-priv-lvl {
                  type empty;
                }
              }
              list server {
                // NCS patched for predictable order
                ordered-by user;
                tailf:cli-suppress-mode;
                unique "address";
                key "server-index";
                leaf server-index {
                  type string;
                }
                leaf address {
                  type string;
                }
                leaf secret {
                  type string;
                }
                leaf key-type {
                  tailf:cli-drop-node-name;
                  type string;
                }
                leaf port {
                  type string;
                }
              }
              container priv-lvl-map {
                list priv-lvl {
                  // NCS patched for predictable order
                  ordered-by user;
                  tailf:cli-suppress-mode;
                  key "priv-lvl";
                  leaf priv-lvl {
                    type string;
                  }
                  leaf user-profile {
                    tailf:cli-drop-node-name;
                    type string;
                  }
                }
              }
              leaf shutdown {
                type string;
              }
            }
            container tacplus {
              presence "true";
              uses remote-servers-grouping;
              leaf timeout {
                type string;
              }
            }
          }
        }
        leaf name {
          type string;
        }
        container maximum-ipv6-routes {
          leaf number {
            tailf:cli-drop-node-name;
            type string;
          }
          leaf threshold {
            type string;
          }
          leaf log-only {
            type empty;
          }
        }
        leaf multicast-info-policy {
          type ncs_compliance_template_string32;
        }
        leaf ecmp {
          type string;
        }
        leaf ignore-nh-metric {
          type empty;
        }
        leaf auto-bind {
          type string;
        }
        container auto-bind-tunnel {
          uses ncs_compliance_template_resolution-filter-grouping;
          leaf ecmp {
            type string;
          }
          leaf weighted-ecmp {
            type empty;
          }
        }
        container bgp {
          presence "true";
          leaf advertise-inactive {
            type empty;
          }
          leaf enable-peer-tracking {
            type empty;
          }
          leaf-list backup-path {
            // NCS patched for predictable order
            ordered-by user;
            type string;
          }
          leaf loop-detect {
            type string;
          }
          leaf rapid-withdrawal {
            type empty;
          }
          leaf damping {
            type empty;
          }
          leaf-list family {
            // NCS patched for predictable order
            ordered-by user;
            type ncs_compliance_template_family-names-type;
          }
          uses ncs_compliance_template_authentication-key-grouping;
          uses ncs_compliance_template_bgp-common-grouping;
          uses ncs_compliance_template_bgp-best-path-selection-grouping;
          uses ncs_compliance_template_bgp-local-as-grouping;
          leaf router-id {
            type string;
          }
          container error-handling {
            leaf update-fault-tolerance {
              type empty;
            }
          }
          uses ncs_compliance_template_bgp-import-export-grouping;
          uses ncs_compliance_template_bgp-graceful-restart-grouping;
          container monitor {
            leaf shutdown {
              type string;
            }
            leaf-list station {
              // NCS patched for predictable order
              ordered-by user;
              type string;
            }
          }
          container rib-management {
            container ipv4 {
              leaf-list leak-import {
                // NCS patched for predictable order
                ordered-by user;
                type string;
              }
            }
            container ipv6 {
              leaf-list leak-import {
                // NCS patched for predictable order
                ordered-by user;
                type string;
              }
            }
          }
          list group {
            // NCS patched for predictable order
            ordered-by user;
            key "name";
            leaf name {
              type string;
            }
            leaf damping {
              type empty;
            }
            leaf multihop {
              type string;
            }
            leaf passive {
              type empty;
            }
            uses ncs_compliance_template_enable-origin-validation-grouping;
            leaf enable-peer-tracking {
              type empty;
            }
            leaf loop-detect-threshold {
              type string;
            }
            leaf auth-keychain {
              type string;
            }
            container error-handling {
              leaf update-fault-tolerance {
                type empty;
              }
            }
            leaf as-override {
              type empty;
            }
            uses ncs_compliance_template_bgp-local-as-grouping;
            uses ncs_compliance_template_authentication-key-grouping;
            leaf bfd-enable {
              type empty;
            }
            leaf description {
              type string;
            }
            leaf keepalive {
              type string;
            }
            leaf hold-time {
              type string;
            }
            leaf med-out {
              type string;
            }
            leaf loop-detect {
              type string;
            }
            leaf-list disable-communities {
              // NCS patched for predictable order
              ordered-by user;
              type string;
            }
            leaf-list family {
              // NCS patched for predictable order
              ordered-by user;
              type string;
            }
            uses ncs_compliance_template_bgp-import-export-grouping;
            uses ncs_compliance_template_bgp-graceful-restart-grouping;
            leaf local-address {
              type string;
            }
            leaf min-route-advertisement {
              type string;
            }
            list neighbor {
              // NCS patched for predictable order
              ordered-by user;
              key "address";
              leaf address {
                type string;
              }
              uses ncs_compliance_template_enable-origin-validation-grouping;
              leaf local-preference {
                type string;
              }
              leaf advertise-inactive {
                type empty;
              }
              leaf as-override {
                type empty;
              }
              leaf bfd-enable {
                type empty;
              }
              leaf description {
                type string;
              }
              leaf-list family {
                // NCS patched for predictable order
                ordered-by user;
                type string;
              }
              uses ncs_compliance_template_bgp-graceful-restart-grouping;
              uses ncs_compliance_template_bgp-import-export-grouping;
              leaf local-address {
                type string;
              }
              uses ncs_compliance_template_bgp-local-as-grouping;
              leaf loop-detect {
                type string;
              }
              leaf med-out {
                type string;
              }
              leaf multihop {
                type string;
              }
              leaf peer-as {
                type string;
              }
              uses ncs_compliance_template_bgp-prefix-limit-grouping;
              leaf passive {
                type empty;
              }
              leaf ttl-security {
                type string;
              }
              container remove-private {
                presence "true";
                leaf-list options {
                  // NCS patched for predictable order
                  ordered-by user;
                  tailf:cli-drop-node-name;
                  type string;
                }
              }
              leaf split-horizon {
                type empty;
              }
              leaf type {
                type string;
              }
              uses ncs_compliance_template_authentication-key-grouping;
              leaf keepalive {
                type string;
              }
              leaf hold-time {
                type string;
              }
              leaf shutdown {
                type string;
              }
            }
            uses ncs_compliance_template_bgp-prefix-limit-grouping;
            leaf split-horizon {
              type empty;
            }
            leaf peer-as {
              type string;
            }
            container remove-private {
              presence "true";
              leaf-list options {
                // NCS patched for predictable order
                ordered-by user;
                tailf:cli-drop-node-name;
                type string;
              }
            }
            leaf type {
              type string;
            }
            leaf next-hop-self {
              type empty;
            }
            leaf preference {
              type string;
            }
            leaf local-preference {
              type string;
            }
            leaf shutdown {
              type string;
            }
          }
          leaf ibgp-multipath {
            type empty;
          }
          leaf med-out {
            type string;
          }
          leaf min-route-advertisement {
            type string;
          }
          uses ncs_compliance_template_bgp-multipath-grouping;
          uses ncs_compliance_template_bgp-multi-path-grouping;
          container next-hop-resolution {
            leaf policy {
              type string;
            }
          }
          leaf split-horizon {
            type empty;
          }
          leaf shutdown {
            type string;
          }
        }
        container bgp-ipvpn {
          container mpls {
            container auto-bind-tunnel {
              leaf resolution {
                type string;
              }
              container resolution-filter {
                leaf bgp {
                  type string;
                }
                leaf ldp {
                  type empty;
                }
                leaf rsvp {
                  type empty;
                }
                leaf sr-isis {
                  type empty;
                }
                leaf sr-ospf {
                  type empty;
                }
                leaf sr-ospf3 {
                  type empty;
                }
                leaf sr-policy {
                  type empty;
                }
                leaf sr-te {
                  type empty;
                }
              }
              leaf ecmp {
                type string;
              }
              leaf weighted-ecmp {
                type empty;
              }
            }
            leaf route-distinguisher {
              type string;
            }
            leaf-list vrf-import {
              // NCS patched for predictable order
              ordered-by user;
              type string;
            }
            leaf-list vrf-export {
              // NCS patched for predictable order
              ordered-by user;
              type string;
            }
            container vrf-target {
              leaf ext-community {
                tailf:cli-drop-node-name;
                type string;
              }
              leaf export {
                type string;
              }
              leaf import {
                type string;
              }
            }
            leaf shutdown {
              type string;
            }
          }
        }
        container bgp-evpn {
          container mpls {
            container auto-bind-tunnel {
              leaf resolution {
                type string;
              }
              container resolution-filter {
                leaf bgp {
                  type empty;
                }
                leaf ldp {
                  type empty;
                }
                leaf rsvp {
                  type empty;
                }
                leaf sr-isis {
                  type empty;
                }
                leaf sr-ospf {
                  type empty;
                }
                leaf sr-ospf3 {
                  type empty;
                }
                leaf sr-policy {
                  type empty;
                }
                leaf sr-te {
                  type empty;
                }
              }
            }
            leaf route-distinguisher {
              type string;
            }
            leaf-list vrf-import {
              // NCS patched for predictable order
              ordered-by user;
              type string;
            }
            leaf-list vrf-export {
              // NCS patched for predictable order
              ordered-by user;
              type string;
            }
            container vrf-target {
              leaf ext-community {
                tailf:cli-drop-node-name;
                type string;
              }
              leaf export {
                type string;
              }
              leaf import {
                type string;
              }
            }
            leaf shutdown {
              type string;
            }
          }
        }
        container bgp-shared-queue {
          presence "true";
          leaf cir {
            type ncs_compliance_template_rate-type;
          }
          leaf pir {
            type ncs_compliance_template_rate-type;
          }
        }
        leaf-list enable-bgp-vpn-backup {
          // NCS patched for predictable order
          ordered-by user;
          type string;
        }
        leaf export-inactive-bgp {
          type empty;
        }
        container grt-lookup {
          container enable-grt {
            presence "true";
            leaf allow-local-management {
              type empty;
            }
          }
          leaf-list export-grt {
            // NCS patched for predictable order
            ordered-by user;
            type string;
          }
          leaf export-limit {
            type string;
          }
          leaf-list import-grt {
            // NCS patched for predictable order
            ordered-by user;
            type string;
          }
          leaf export-v6-limit {
            type string;
          }
        }
        leaf label-mode {
          type string;
        }
        container mc-maximum-routes {
          leaf number {
            tailf:cli-drop-node-name;
            type string;
          }
          leaf log-only {
            type empty;
          }
          leaf threshold {
            type string;
          }
        }
        container rip {
          presence "true";
          uses ncs_compliance_template_authentication-key-grouping;
          leaf export {
            type string;
          }
          list group {
            // NCS patched for predictable order
            ordered-by user;
            key "name";
            leaf name {
              type string;
            }
            container timers {
              leaf update {
                tailf:cli-drop-node-name;
                type string;
              }
              leaf timeout {
                tailf:cli-drop-node-name;
                type string;
              }
              leaf flush {
                tailf:cli-drop-node-name;
                type string;
              }
            }
            uses ncs_compliance_template_authentication-key-grouping;
            list neighbor {
              // NCS patched for predictable order
              ordered-by user;
              key "intf-id";
              leaf intf-id {
                type ncs_compliance_template_string32;
              }
              uses ncs_compliance_template_authentication-key-grouping;
              leaf bfd-enable {
                type empty;
              }
              leaf receive {
                type string;
              }
              leaf split-horizon {
                type string;
              }
              container timers {
                leaf update {
                  tailf:cli-drop-node-name;
                  type string;
                }
                leaf timeout {
                  tailf:cli-drop-node-name;
                  type string;
                }
                leaf flush {
                  tailf:cli-drop-node-name;
                  type string;
                }
              }
              leaf shutdown {
                type string;
              }
            }
            leaf-list export {
              // NCS patched for predictable order
              ordered-by user;
              type string;
            }
            leaf shutdown {
              type string;
            }
          }
          leaf shutdown {
            type string;
          }
        }
        container ospf {
          presence "true";
          leaf router-id {
            tailf:cli-drop-node-name;
            type string;
          }
          leaf super-backbone {
            type empty;
          }
          container vpn-domain {
            leaf domain-type {
              tailf:cli-drop-node-name;
              type string;
            }
            leaf id {
              tailf:cli-drop-node-name;
              type string;
            }
          }
          leaf vpn-tag {
            type string;
          }
          list area {
            // NCS patched for predictable order
            ordered-by user;
            key "area-id";
            uses ncs_compliance_template_ospf-area-id-grouping;
            list interface {
              // NCS patched for predictable order
              ordered-by user;
              key "ip-int-name";
              leaf ip-int-name {
                type ncs_compliance_template_string32;
              }
              leaf mtu {
                type string;
              }
              leaf metric {
                type string;
              }
              container bfd-enable {
                presence "true";
              }
              leaf authentication-type {
                type string;
              }
              leaf interface-type {
                type string;
              }
              leaf hello-interval {
                type string;
              }
              leaf dead-interval {
                type string;
              }
              list message-digest-key {
                // NCS patched for predictable order
                ordered-by user;
                tailf:cli-suppress-mode;
                key "key-id";
                leaf key-id {
                  type string;
                }
                leaf md5 {
                  type empty;
                }
                leaf hash-value {
                  tailf:cli-drop-node-name;
                  type string;
                }
                leaf scheme {
                  tailf:cli-drop-node-name;
                  type ncs_compliance_template_hash-method;
                }
              }
              leaf shutdown {
                type string;
              }
            }
            list sham-link {
              // NCS patched for predictable order
              ordered-by user;
              key "ip-int-name ip-address";
              leaf ip-int-name {
                type ncs_compliance_template_string32;
              }
              leaf ip-address {
                type string;
              }
              leaf metric {
                type string;
              }
            }
          }
          leaf-list export {
            // NCS patched for predictable order
            ordered-by user;
            type string;
          }
          leaf shutdown {
            type string;
          }
        }
        list ospf3 {
          // NCS patched for predictable order
          ordered-by user;
          key "ospf-instance";
          leaf ospf-instance {
            type string;
          }
          leaf export {
            type string;
          }
          list area {
            // NCS patched for predictable order
            ordered-by user;
            key "area-id";
            uses ncs_compliance_template_ospf-area-id-grouping;
            list interface {
              // NCS patched for predictable order
              ordered-by user;
              key "ip-int-name";
              leaf ip-int-name {
                type ncs_compliance_template_string32;
              }
              leaf mtu {
                type string;
              }
              leaf metric {
                type string;
              }
              container bfd-enable {
                presence "true";
              }
              leaf authentication-type {
                type string;
              }
              leaf interface-type {
                type string;
              }
              leaf hello-interval {
                type string;
              }
              leaf dead-interval {
                type string;
              }
              list message-digest-key {
                // NCS patched for predictable order
                ordered-by user;
                tailf:cli-suppress-mode;
                key "key-id";
                leaf key-id {
                  type string;
                }
                leaf md5 {
                  type empty;
                }
                leaf hash-value {
                  tailf:cli-drop-node-name;
                  type string;
                }
                leaf scheme {
                  tailf:cli-drop-node-name;
                  type ncs_compliance_template_hash-method;
                }
              }
              leaf shutdown {
                type string;
              }
            }
          }
          leaf shutdown {
            type string;
          }
        }
        leaf description {
          type string;
        }
        container dhcp {
          uses ncs_compliance_template_local-dhcp-server-grouping;
        }
        container dhcp6 {
          list local-dhcp-server {
            // NCS patched for predictable order
            ordered-by user;
            key "server-name";
            leaf server-name {
              type ncs_compliance_template_string32;
            }
            leaf description {
              type string;
            }
            container use-link-address {
              presence "true";
              leaf scope {
                type string;
              }
            }
            list pool {
              // NCS patched for predictable order
              ordered-by user;
              key "pool-name";
              leaf pool-name {
                type ncs_compliance_template_string32;
              }
              container delegated-prefix-length {
                leaf prefix-length {
                  tailf:cli-drop-node-name;
                  type string;
                }
                leaf minimum {
                  type string;
                }
                leaf maximum {
                  type string;
                }
              }
              list prefix {
                // NCS patched for predictable order
                ordered-by user;
                key "ipv6-prefix";
                leaf ipv6-prefix {
                  type string;
                }
                leaf failover {
                  type string;
                }
                leaf pd {
                  type empty;
                }
                leaf wan-host {
                  type empty;
                }
                uses ncs_compliance_template_dhcp6-lease-timers-grouping;
              }
            }
            leaf shutdown {
              type string;
            }
          }
        }
        container igmp {

          grouping vprn-igmp-interface-grouping {
            leaf ip-int-name {
              type ncs_compliance_template_string32;
            }
            leaf disable-router-alert-check {
              type empty;
            }
            leaf import {
              type string;
            }
            leaf max-groups {
              type string;
            }
            leaf max-grp-sources {
              type string;
            }
            leaf max-sources {
              type string;
            }
            uses ncs_compliance_template_mcac-grouping;
            leaf sub-hosts-only {
              type empty;
            }
            leaf subnet-check {
              type empty;
            }
            leaf version {
              type string;
            }
            leaf shutdown {
              type string;
            }
          }

          grouping vrpn-igmp-grp-range-grouping {
            list grp-range {
              // NCS patched for predictable order
              ordered-by user;
              key "start end";
              leaf start {
                type string;
              }
              leaf end {
                type string;
              }
              list source {
                // NCS patched for predictable order
                ordered-by user;
                tailf:cli-suppress-mode;
                key "address";
                leaf address {
                  type string;
                }
              }
            }
          }

          grouping vprn-igmp-query-grouping {
            leaf query-response-interval {
              type string;
            }
            leaf query-last-member-interval {
              type string;
            }
            leaf query-last-listener-interval {
              type string;
            }
            leaf query-interval {
              type string;
            }
            leaf redundant-multicast {
              type empty;
            }
          }
          list group-interface {
            // NCS patched for predictable order
            ordered-by user;
            key "ip-int-name";
            leaf fwd-service {
              type string;
            }
            uses vprn-igmp-interface-grouping;
            leaf query-src-ip {
              type string;
            }
          }
          leaf grp-if-query-src-ip {
            type string;
          }
          list interface {
            // NCS patched for predictable order
            ordered-by user;
            key "ip-int-name";
            uses vprn-igmp-query-grouping;
            uses vprn-igmp-interface-grouping;
            container ssm-translate {
              uses vrpn-igmp-grp-range-grouping;
            }
            uses ncs_compliance_template_igmp-static-grouping;
          }
          uses vprn-igmp-query-grouping;
          leaf robust-count {
            type string;
          }
          container ssm-translate {
            uses vrpn-igmp-grp-range-grouping;
          }
          leaf shutdown {
            type string;
          }
        }
        list subscriber-interface {
          // NCS patched for predictable order
          ordered-by user;
          key "id";
          uses ncs_compliance_template_subscriber-interface-grouping {
            augment "group-interface" {
              leaf arp-timeout {
                type string;
              }
            }
            augment "group-interface/dhcp" {
              leaf shutdown {
                type string;
              }
            }
            augment "group-interface/sap" {
              list static-host {
                // NCS patched for predictable order
                ordered-by user;
                key "ip";
                leaf ip {
                  type string;
                }
                leaf shutdown {
                  type string;
                }
              }
            }
          }
          container dhcp {
            uses ncs_compliance_template_subscriber-interface-dhcp-common-grouping;
            leaf lease-populate {
              type string;
            }
            container relay-proxy {
              presence "true";
              leaf release-update-src-ip {
                type empty;
              }
              leaf siaddr-override {
                type string;
              }
            }
            leaf python-policy {
              type ncs_compliance_template_string32;
            }
            container option {
              container vendor-specific-option {
                leaf client-mac-address {
                  type empty;
                }
                leaf sap-id {
                  type empty;
                }
                leaf service-id {
                  type empty;
                }
                leaf string {
                  type string;
                }
                leaf system-id {
                  type empty;
                }
              }
            }
            leaf shutdown {
              type string;
            }
          }
          container ipv6 {
            presence "true";
            leaf allow-unmatching-prefixes {
              type empty;
            }
            leaf delegated-prefix-length {
              type string;
            }
            leaf link-local-address {
              type string;
            }
            container subscriber-prefixes {
              list prefix {
                // NCS patched for predictable order
                ordered-by user;
                tailf:cli-suppress-mode;
                key "ipv6-prefix";
                leaf ipv6-prefix {
                  type string;
                }
                leaf pd {
                  type empty;
                }
                leaf wan-host {
                  type empty;
                }
                leaf track-srrp {
                  type string;
                }
              }
            }
            container dhcp6 {
              container relay {
                leaf link-address {
                  type string;
                }
                leaf-list server {
                  // NCS patched for predictable order
                  ordered-by user;
                  type string;
                }
                leaf source-address {
                  type string;
                }
                leaf shutdown {
                  type string;
                }
              }
            }
            container router-advertisements {
              leaf managed-configuration {
                type empty;
              }
              leaf other-stateful-configuration {
                type empty;
              }
              leaf max-advertisement {
                type string;
              }
              container prefix-options {
                leaf autonomous {
                  type empty;
                }
                leaf on-link {
                  type string;
                }
                leaf preferred-lifetime {
                  type string;
                }
                leaf valid-lifetime {
                  type string;
                }
              }
              leaf shutdown {
                type string;
              }
            }
          }
          leaf shutdown {
            type string;
          }
        }
        list interface {
          // NCS patched for predictable order
          ordered-by user;
          key "ip-int-name";
          leaf ip-int-name {
            type ncs_compliance_template_string32;
          }
          leaf tunnel {
            type empty;
          }
          container arp-host-route {
            list populate {
              // NCS patched for predictable order
              ordered-by user;
              tailf:cli-suppress-mode;
              key "mode";
              leaf mode {
                type string;
              }
            }
          }
          leaf arp-timeout {
            type string;
          }
          leaf arp-learn-unsolicited {
            type empty;
          }
          leaf arp-proactive-refresh {
            type empty;
          }
          leaf arp-populate {
            type empty;
          }
          leaf arp-populate-host-route {
            type empty;
          }
          leaf local-proxy-arp {
            type empty;
          }
          container bfd {
            uses ncs_compliance_template_bfd-grouping;
          }
          uses ncs_compliance_template_cflowd-params-grouping;
          container dhcp {
            leaf description {
              type string;
            }
            container gi-address {
              leaf gi-address-value {
                tailf:cli-drop-node-name;
                type string;
              }
              leaf src-ip-addr {
                type empty;
              }
            }
            leaf lease-populate {
              type string;
            }
            uses ncs_compliance_template_dhcp-option-grouping {
              augment "option" {
                container circuit-id {
                  presence "true";
                  leaf id {
                    tailf:cli-drop-node-name;
                    type string;
                  }
                }
              }
              augment "option/vendor-specific-option" {
                leaf sap-id {
                  type empty;
                }
              }
            }
            leaf-list server {
              // NCS patched for predictable order
              ordered-by user;
              type string;
            }
            leaf trusted {
              type empty;
            }
            leaf use-arp {
              type empty;
            }
            leaf shutdown {
              type string;
            }
          }
          leaf dynamic-tunnel-redundant-next-hop {
            type string;
          }
          uses ncs_compliance_template_interface-icmp-grouping;
          leaf local-dhcp-server {
            type string;
          }
          list secondary {
            // NCS patched for predictable order
            ordered-by user;
            tailf:cli-suppress-mode;
            key "address";
            leaf address {
              type string;
            }
          }
          list address {
            // NCS patched for predictable order
            ordered-by user;
            tailf:cli-suppress-mode;
            key "ip-address";
            leaf ip-address {
              type string;
            }
          }
          list static-arp {
            // NCS patched for predictable order
            ordered-by user;
            tailf:cli-suppress-mode;
            key "address";
            leaf address {
              type string;
            }
            leaf ieee-address {
              tailf:cli-drop-node-name;
              type ncs_compliance_template_ieee-mac;
            }
            leaf unnumbered {
              type empty;
            }
          }
          leaf description {
            type string;
          }
          leaf enable-ingress-stats {
            type empty;
          }
          leaf ip-mtu {
            type string;
          }
          leaf loopback {
            type empty;
          }
          leaf mac {
            type ncs_compliance_template_ieee-mac;
          }
          list sap {
            // NCS patched for predictable order
            ordered-by user;
            key "sap-id";
            leaf sap-id {
              type string;
            }
            leaf accounting-policy {
              type string;
            }
            leaf bandwidth {
              type string;
            }
            leaf anti-spoof {
              type string;
            }
            leaf collect-stats {
              type empty;
            }
            leaf description {
              type string;
            }
            leaf multi-service-site {
              type string;
            }
            container egress {
              uses ncs_compliance_template_sap-egress-grouping;
            }
            container eth-cfm {
              uses ncs_compliance_template_eth-cfm;
            }
            container ingress {
              uses ncs_compliance_template_sap-ingress-grouping;
            }
            container ipsec-gw {
              leaf name {
                tailf:cli-drop-node-name;
                type string;
              }
              container cert {
                leaf cert-profile {
                  type ncs_compliance_template_string32;
                }
                container status-verify {
                  leaf default-result {
                    type string;
                  }
                }
                leaf trust-anchor-profile {
                  type ncs_compliance_template_string32;
                }
              }
              container default-secure-service {
                choice service {
                  leaf service-id {
                    tailf:cli-drop-node-name;
                    type ncs_compliance_template_service-id;
                  }
                  leaf name {
                    type string;
                  }
                }
                leaf interface {
                  type ncs_compliance_template_string32;
                }
              }
              leaf default-tunnel-template {
                type string;
              }
              leaf ike-policy {
                type string;
              }
              leaf local-gateway-address {
                type string;
              }
              container local-id {
                leaf type {
                  type string;
                }
                leaf value {
                  type string;
                }
              }
              leaf shutdown {
                type string;
              }
            }
            list ipsec-tunnel {
              // NCS patched for predictable order
              ordered-by user;
              key "ipsec-tunnel-name";
              leaf ipsec-tunnel-name {
                type ncs_compliance_template_string32;
              }
              leaf shutdown {
                type string;
              }
            }
            list ip-tunnel {
              // NCS patched for predictable order
              ordered-by user;
              key "ip-tunnel-name";
              leaf ip-tunnel-name {
                type ncs_compliance_template_string32;
              }
              leaf clear-df-bit {
                type empty;
              }
              leaf ip-mtu {
                type string;
              }
              leaf description {
                type string;
              }
              list dest-ip {
                // NCS patched for predictable order
                ordered-by user;
                tailf:cli-suppress-mode;
                key "ip-address";
                leaf ip-address {
                  type string;
                }
              }
              leaf gre-header {
                type empty;
              }
              leaf source {
                type string;
              }
              leaf remote-ip {
                type string;
              }
              leaf delivery-service {
                type string;
              }
              leaf shutdown {
                type string;
              }
            }
            leaf lag-link-map-profile {
              type string;
            }
            leaf dist-cpu-protection {
              type string;
            }
            leaf shutdown {
              type string;
            }
          }
          list spoke-sdp {
            // NCS patched for predictable order
            ordered-by user;
            key "sdp-id vc-id";
            leaf sdp-id {
              type string;
            }
            uses ncs_compliance_template_sdp-common;
            container egress {
              container filter {
                uses ncs_compliance_template_filter-choice;
              }
            }
            container ingress {
              container filter {
                uses ncs_compliance_template_filter-choice;
              }
            }
          }
          leaf tos-marking-state {
            type string;
          }
          container urpf-check {
            leaf mode {
              type string;
            }
          }
          container vpls {
            leaf service-name {
              tailf:cli-drop-node-name;
              type string;
            }
            container egress {
              leaf reclassify-using-qos {
                type string;
              }
              leaf v4-routed-override-filter {
                type ncs_compliance_template_filter-id;
              }
            }
            container ingress {
              leaf v4-routed-override-filter {
                type ncs_compliance_template_filter-id;
              }
              leaf v6-routed-override-filter {
                type ncs_compliance_template_filter-id;
              }
            }
            container evpn-tunnel {
              presence "true";
              leaf ipv6-gateway-address {
                type string;
              }
            }
            container evpn {
              container arp {
                leaf learn-dynamic {
                  type string;
                }
                list advertise {
                  // NCS patched for predictable order
                  ordered-by user;
                  tailf:cli-suppress-mode;
                  key "adv-type";
                  leaf adv-type {
                    type string;
                  }
                }
              }
              container nd {
                leaf learn-dynamic {
                  type string;
                }
                list advertise {
                  // NCS patched for predictable order
                  ordered-by user;
                  tailf:cli-suppress-mode;
                  key "type";
                  leaf type {
                    type string;
                  }
                  leaf route-tag {
                    type string;
                  }
                }
              }
            }
          }
          list vrrp {
            // NCS patched for predictable order
            ordered-by user;
            key "virtual-router-id";
            leaf virtual-router-id {
              type string;
            }
            leaf owner {
              type empty;
            }
            leaf passive {
              type empty;
            }
            uses ncs_compliance_template_authentication-key-grouping;
            list backup {
              // NCS patched for predictable order
              ordered-by user;
              tailf:cli-suppress-mode;
              key "addr";
              leaf addr {
                type string;
              }
            }
            container bfd-enable {
              leaf service-id {
                tailf:cli-drop-node-name;
                type string;
              }
              leaf interface {
                type string;
              }
              leaf dst-ip {
                type string;
              }
            }
            leaf init-delay {
              type string;
            }
            leaf mac {
              type ncs_compliance_template_ieee-mac;
            }
            leaf master-int-inherit {
              type empty;
            }
            container message-interval {
              leaf seconds {
                tailf:cli-drop-node-name;
                type string;
              }
              leaf milliseconds {
                type string;
              }
            }
            leaf ping-reply {
              type empty;
            }
            leaf policy {
              type string;
            }
            leaf preempt {
              type empty;
            }
            leaf priority {
              type string;
            }
            leaf ssh-reply {
              type empty;
            }
            leaf standby-forwarding {
              type empty;
            }
            leaf telnet-reply {
              type empty;
            }
            leaf traceroute-reply {
              type empty;
            }
            leaf shutdown {
              type empty;
            }
          }
          container ipv6 {
            presence "true";
            leaf local-dhcp-server {
              type ncs_compliance_template_string32;
            }
            uses ncs_compliance_template_ipv6-grouping;
            uses ncs_compliance_template_dhcp6-grouping;
            leaf nd-populate-host-route {
              type empty;
            }
            container nd-host-route {
              list populate {
                // NCS patched for predictable order
                ordered-by user;
                tailf:cli-suppress-mode;
                key "mode";
                leaf mode {
                  type string;
                }
              }
            }
            leaf stale-time {
              type string;
            }
          }
          leaf qos-route-lookup {
            type string;
          }
          leaf shutdown {
            type string;
          }
        }
        container ipsec {
          leaf allow-reverse-route-override {
            type string;
          }
          list security-policy {
            // NCS patched for predictable order
            ordered-by user;
            key "security-policy-id";
            leaf security-policy-id {
              type string;
            }
            list entry {
              // NCS patched for predictable order
              ordered-by user;
              key "entry-id";
              leaf entry-id {
                type string;
              }
              leaf local-ip {
                type string;
              }
              leaf local-v6-ip {
                type string;
              }
              leaf remote-ip {
                type string;
              }
              leaf remote-v6-ip {
                type string;
              }
            }
          }
        }
        container maximum-routes {
          leaf routes {
            tailf:cli-drop-node-name;
            type string;
          }
          leaf log-only {
            type empty;
          }
          leaf threshold {
            type string;
          }
        }
        uses ncs_compliance_template_nat-pool-grouping;
        container radius-server {
          uses ncs_compliance_template_radius-server-grouping;
        }
        container dns {
          presence "true";
          leaf default-domain {
            type string;
          }
          leaf ipv4-source-address {
            type string;
          }
          leaf ipv6-source-address {
            type string;
          }
          leaf primary-dns {
            type string;
          }
          leaf secondary-dns {
            type string;
          }
          leaf tertiary-dns {
            type string;
          }
          leaf shutdown {
            type string;
          }
        }
        container log {
          list filter {
            // NCS patched for predictable order
            ordered-by user;
            key "filter-id";
            leaf filter-id {
              type string;
            }
            leaf name {
              type string;
            }
            leaf default-action {
              type string;
            }
            leaf description {
              type string;
            }
            list entry {
              // NCS patched for predictable order
              ordered-by user;
              key "entry-id";
              leaf entry-id {
                type string;
              }
              leaf name {
                type string;
              }
              leaf action {
                type string;
              }
              leaf description {
                type string;
              }
              container match {
                container application {
                  leaf operator {
                    tailf:cli-drop-node-name;
                    type string;
                  }
                  leaf application-id {
                    tailf:cli-drop-node-name;
                    type string;
                  }
                }
                container message {
                  leaf operator {
                    tailf:cli-drop-node-name;
                    type string;
                  }
                  leaf pattern {
                    type string;
                  }
                  leaf regexp {
                    type empty;
                  }
                }
                container number {
                  leaf operator {
                    tailf:cli-drop-node-name;
                    type string;
                  }
                  leaf event-id {
                    tailf:cli-drop-node-name;
                    type string;
                  }
                }
                container severity {
                  leaf operator {
                    tailf:cli-drop-node-name;
                    type string;
                  }
                  leaf severity-level {
                    tailf:cli-drop-node-name;
                    type string;
                  }
                }
                container subject {
                  leaf operator {
                    tailf:cli-drop-node-name;
                    type string;
                  }
                  leaf subject {
                    tailf:cli-drop-node-name;
                    type string;
                  }
                  leaf regexp {
                    type empty;
                  }
                }
              }
            }
          }
          list syslog {
            // NCS patched for predictable order
            ordered-by user;
            key "syslog-id";
            leaf syslog-id {
              type string;
            }
            leaf name {
              type string;
            }
            leaf description {
              type string;
            }
            leaf address {
              type string;
            }
            leaf facility {
              type string;
            }
            leaf log-prefix {
              type string;
            }
            leaf port {
              type string;
            }
          }
          list snmp-trap-group {
            // NCS patched for predictable order
            ordered-by user;
            key "group-id";
            leaf group-id {
              type string;
            }
            leaf name {
              type string;
            }
            leaf description {
              type string;
            }
            list trap-target {
              // NCS patched for predictable order
              ordered-by user;
              tailf:cli-suppress-mode;
              key "name";
              leaf name {
                type string;
              }
              leaf address {
                type string;
              }
              leaf snmp-type {
                tailf:cli-drop-node-name;
                type string;
              }
              leaf notify-community {
                type string;
              }
              leaf security-level {
                type string;
              }
            }
          }
          list log-id {
            // NCS patched for predictable order
            ordered-by user;
            key "log-id";
            leaf log-id {
              type string;
            }
            leaf name {
              type string;
            }
            leaf description {
              type string;
            }
            leaf filter {
              type string;
            }
            leaf-list from {
              // NCS patched for predictable order
              ordered-by user;
              type string;
            }
            leaf netconf-stream {
              type string;
            }
            leaf shutdown {
              type string;
            }
            leaf time-format {
              type string;
            }
            container to {
              leaf destination {
                tailf:cli-drop-node-name;
                type string;
              }
              leaf size {
                tailf:cli-drop-node-name;
                type string;
              }
              leaf syslog-id {
                tailf:cli-drop-node-name;
                type string;
              }
            }
          }
        }
        list redundant-interface {
          // NCS patched for predictable order
          ordered-by user;
          key "ip-int-name";
          leaf ip-int-name {
            type ncs_compliance_template_string32;
          }
          leaf description {
            type string;
          }
          container address {
            leaf ip-address {
              tailf:cli-drop-node-name;
              type string;
            }
            leaf remote-ip {
              type string;
            }
          }
          list spoke-sdp {
            // NCS patched for predictable order
            ordered-by user;
            key "sdp-id-vc-id";
            leaf sdp-id-vc-id {
              type string;
            }
            leaf description {
              type string;
            }
            leaf shutdown {
              type string;
            }
          }
          leaf shutdown {
            type string;
          }
        }
        leaf route-distinguisher {
          type string;
        }
        container source-address {
          list application {
            // NCS patched for predictable order
            ordered-by user;
            tailf:cli-suppress-mode;
            key "app";
            leaf app {
              type string;
            }
            leaf source {
              tailf:cli-drop-node-name;
              type string;
            }
          }
          list application6 {
            // NCS patched for predictable order
            ordered-by user;
            tailf:cli-suppress-mode;
            key "app";
            leaf app {
              type string;
            }
            leaf source {
              tailf:cli-drop-node-name;
              type string;
            }
          }
        }
        container snmp {
          leaf access {
            type empty;
          }
          uses ncs_compliance_template_snmp-community-grouping;
        }
        list snmp-community {
          // NCS patched for predictable order
          ordered-by user;
          tailf:cli-suppress-mode;
          key "name type";
          leaf name {
            type string;
          }
          leaf type {
            tailf:cli-drop-node-name;
            type ncs_compliance_template_hash-method;
          }
          leaf access-parameters {
            tailf:cli-drop-node-name;
            type string;
          }
          leaf version {
            type string;
          }
        }
        leaf-list vrf-export {
          // NCS patched for predictable order
          ordered-by user;
          type string;
        }
        leaf-list vrf-import {
          // NCS patched for predictable order
          ordered-by user;
          type string;
        }
        container vrf-target {
          leaf export {
            type string;
          }
          leaf import {
            type string;
          }
          leaf ext-community {
            tailf:cli-drop-node-name;
            type string;
          }
        }
        leaf autonomous-system {
          type string;
        }
        list spoke-sdp {
          // NCS patched for predictable order
          ordered-by user;
          key "sdp-id";
          leaf sdp-id {
            type string;
          }
          leaf description {
            type string;
          }
          leaf shutdown {
            type string;
          }
        }
        leaf carrier-carrier-vpn {
          type empty;
        }
        leaf type {
          type string;
        }

        grouping service-vprn-static-route-grouping {
          leaf preference {
            type string;
          }
          leaf metric {
            type string;
          }
          leaf state {
            tailf:cli-drop-node-name;
            type ncs_compliance_template_enable-disable;
          }
          leaf tag {
            type string;
          }
          leaf bfd-enable {
            type empty;
          }
          leaf cpe-check {
            type string;
          }
          leaf drop-count {
            type string;
          }
          leaf interval {
            type string;
          }
          leaf log {
            type empty;
          }
          leaf prefix-list-name {
            type string;
          }
          leaf prefix-list-to-use {
            tailf:cli-drop-node-name;
            type string;
          }
          leaf community {
            type string;
          }
          leaf description {
            type string;
          }
        }
        list static-route-entry {
          // NCS patched for predictable order
          ordered-by user;
          key "route";
          leaf route {
            type string;
          }
          leaf-list community {
            // NCS patched for predictable order
            ordered-by user;
            type string;
          }
          list next-hop {
            // NCS patched for predictable order
            ordered-by user;
            key "next-hop";
            leaf next-hop {
              type string;
            }
            uses ncs_compliance_template_static-route-entry-nh-grouping;
            container prefix-list {
              leaf name {
                tailf:cli-drop-node-name;
                type string;
              }
              leaf modifyer {
                tailf:cli-drop-node-name;
                type string;
              }
            }
          }
          container grt {
            presence "true";
            leaf description {
              type string;
            }
            leaf metric {
              type string;
            }
            leaf preference {
              type string;
            }
            leaf shutdown {
              type string;
            }
          }
          list ipsec-tunnel {
            // NCS patched for predictable order
            ordered-by user;
            key "name";
            leaf name {
              type string;
            }
            leaf shutdown {
              type string;
            }
          }
          container black-hole {
            presence "true";
            uses ncs_compliance_template_static-route-entry-nh-grouping;
            container prefix-list {
              leaf name {
                tailf:cli-drop-node-name;
                type string;
              }
              leaf modifyer {
                tailf:cli-drop-node-name;
                type string;
              }
            }
          }
          list indirect {
            // NCS patched for predictable order
            ordered-by user;
            key "ip-address";
            leaf ip-address {
              type string;
            }
            uses ncs_compliance_template_static-route-entry-nh-grouping;
          }
          leaf tag {
            type string;
          }
        }
        container static-route {
          list static-route-next-hop {
            // NCS patched for predictable order
            ordered-by user;
            tailf:cli-drop-node-name;
            tailf:cli-suppress-mode;
            key "route next-hop";
            leaf route {
              type string;
            }
            leaf next-hop {
              type string;
            }
            uses service-vprn-static-route-grouping;
          }
          list static-route-indirect {
            // NCS patched for predictable order
            ordered-by user;
            tailf:cli-drop-node-name;
            tailf:cli-suppress-mode;
            key "route indirect";
            leaf route {
              type string;
            }
            leaf indirect {
              type string;
            }
            uses service-vprn-static-route-grouping;
          }
          list static-route-ipsec-tunnel {
            // NCS patched for predictable order
            ordered-by user;
            tailf:cli-drop-node-name;
            tailf:cli-suppress-mode;
            key "route ipsec-tunnel";
            leaf route {
              type string;
            }
            leaf ipsec-tunnel {
              type string;
            }
            uses service-vprn-static-route-grouping;
          }
          list static-route-indirect-blackhole {
            // NCS patched for predictable order
            ordered-by user;
            tailf:cli-drop-node-name;
            tailf:cli-suppress-mode;
            key "route";
            leaf route {
              type string;
            }
            leaf black-hole {
              type empty;
            }
            uses service-vprn-static-route-grouping;
          }
        }
        uses ncs_compliance_template_router-aggregate-grouping;
        container sgt-qos {
          list application {
            // NCS patched for predictable order
            ordered-by user;
            tailf:cli-suppress-mode;
            key "app-name";
            leaf app-name {
              type string;
            }
            leaf dscp {
              type string;
            }
            leaf dot1p {
              type string;
            }
          }
          list dscp {
            // NCS patched for predictable order
            ordered-by user;
            tailf:cli-suppress-mode;
            key "dscp-name";
            leaf dscp-name {
              type string;
            }
            leaf fc {
              type string;
            }
          }
        }
        container pim {
          uses ncs_compliance_template_pim-common-grouping;
          leaf ipv4-multicast-disable {
            type string;
          }
          leaf ipv6-multicast-disable {
            type string;
          }
          list interface {
            // NCS patched for predictable order
            ordered-by user;
            key "name";
            leaf name {
              type string;
            }
            leaf priority {
              type string;
            }
            leaf max-groups {
              type string;
            }
            leaf bfd-enable {
              type empty;
            }
            container sticky-dr {
              presence "true";
              leaf priority {
                type string;
              }
            }
            leaf multicast-senders {
              type string;
            }
            leaf hello-interval {
              type string;
            }
            leaf shutdown {
              type string;
            }
          }
          container rp {
            list anycast {
              // NCS patched for predictable order
              ordered-by user;
              key "rp-ip-address";
              leaf rp-ip-address {
                type string;
              }
              list rp-set-peer {
                // NCS patched for predictable order
                ordered-by user;
                tailf:cli-suppress-mode;
                key "ip-address";
                leaf ip-address {
                  type string;
                }
              }
            }
            leaf auto-rp-discovery {
              type empty;
            }
            container static {
              list address {
                // NCS patched for predictable order
                ordered-by user;
                key "address";
                leaf address {
                  type string;
                }
                list group-prefix {
                  // NCS patched for predictable order
                  ordered-by user;
                  tailf:cli-suppress-mode;
                  key "address";
                  leaf address {
                    type string;
                  }
                }
                leaf override {
                  type empty;
                }
              }
            }
            container bsr-candidate {
              leaf shutdown {
                type string;
              }
            }
            container rp-candidate {
              leaf shutdown {
                type string;
              }
            }
          }
          leaf shutdown {
            type string;
          }
        }
        container mvpn {
          container auto-discovery {
            leaf mode {
              tailf:cli-drop-node-name;
              // NCS drop tailf-common:cli-diff-create-before statement
              // NCS drop tailf-common:cli-diff-create-before statement
              // NCS drop tailf-common:cli-diff-create-before statement
              type string;
            }
            leaf source-address {
              type string;
            }
          }
          leaf c-mcast-signaling {
            type string;
          }
          container intersite-shared {
            choice intersite-shared {
              leaf-list arg {
                // NCS patched for predictable order
                ordered-by user;
                tailf:cli-drop-node-name;
                type string;
              }
              leaf disable {
                type empty;
              }
            }
          }
          leaf umh-selection {
            type string;
          }
          leaf mdt-type {
            type string;
          }
          container provider-tunnel {

            grouping inclusive-selective-common-grouping {
              container mldp {
                leaf shutdown {
                  type string;
                }
              }
            }
            container inclusive {
              uses inclusive-selective-common-grouping;
              container pim {
                presence "true";
                container options {
                  tailf:cli-drop-node-name;
                  leaf multicast-type {
                    tailf:cli-drop-node-name;
                    type string;
                  }
                  leaf grp-ip-address {
                    tailf:cli-drop-node-name;
                    type string;
                  }
                }
                leaf shutdown {
                  type string;
                }
              }
              container rsvp {
                presence "true";
                leaf lsp-template {
                  type string;
                }
                leaf shutdown {
                  type string;
                }
              }
            }
            container selective {
              uses inclusive-selective-common-grouping;
              leaf maximum-p2mp-spmsi {
                type string;
              }
              container pim {
                tailf:cli-drop-node-name;
                choice pim-choice {
                  leaf pim-asm {
                    type empty;
                  }
                  leaf pim-ssm {
                    type empty;
                  }
                }
                choice addr {
                  leaf address1 {
                    tailf:cli-drop-node-name;
                    type string;
                  }
                  leaf address2 {
                    tailf:cli-drop-node-name;
                    type string;
                  }
                }
                leaf netmask {
                  tailf:cli-drop-node-name;
                  type string;
                }
              }
              list data-threshold {
                // NCS patched for predictable order
                ordered-by user;
                tailf:cli-suppress-mode;
                key "c-grp-ip-addr-mask";
                leaf c-grp-ip-addr-mask {
                  tailf:cli-drop-node-name;
                  type string;
                }
                leaf s-pmsi-threshold {
                  tailf:cli-drop-node-name;
                  type string;
                }
              }
            }
          }
          list vrf-target {
            // NCS patched for predictable order
            ordered-by user;
            key "id";
            leaf id {
              type string;
            }
            leaf export {
              type string;
            }
            leaf import {
              type string;
            }
          }
        }
        container router-advertisement {
          list interface {
            // NCS patched for predictable order
            ordered-by user;
            key "ip-int-name";
            leaf ip-int-name {
              type ncs_compliance_template_string32;
            }
            leaf use-virtual-mac {
              type empty;
            }
            leaf shutdown {
              type string;
            }
          }
        }
        leaf router-id {
          type string;
        }
        list isis {
          // NCS patched for predictable order
          ordered-by user;
          key "id";
          leaf id {
            type string;
          }
          leaf area-id {
            type string;
          }
          leaf ipv6-routing {
            type string;
          }
          container multi-topology {
            leaf ipv6-unicast {
              type empty;
            }
          }
          list interface {
            // NCS patched for predictable order
            ordered-by user;
            key "name";
            leaf name {
              type string;
            }
            leaf passive {
              type empty;
            }
            leaf interface-type {
              type string;
            }
            leaf shutdown {
              type string;
            }
          }
          leaf router-id {
            type string;
          }
          leaf shutdown {
            type string;
          }
        }
        leaf service-name {
          type string;
        }
        leaf weighted-ecmp {
          type empty;
        }
        leaf shutdown {
          type string;
        }
      }
      list pw-template {
        // NCS patched for predictable order
        ordered-by user;
        key "policy-id";
        leaf policy-id {
          type string;
        }
        leaf use-provisioned-sdp {
          type empty;
        }
        leaf name {
          type string;
        }
        leaf auto-learn-mac-protect {
          type empty;
        }
        leaf disable-learning {
          type empty;
        }
        container egress {
          choice filter-name-choice {
            container filter {
              uses ncs_compliance_template_filter-choice;
            }
            container filter-name {
              uses ncs_compliance_template_filter-choice;
            }
          }
        }
        container ingress {
          choice filter-name-choice {
            container filter {
              uses ncs_compliance_template_filter-choice;
            }
            container filter-name {
              uses ncs_compliance_template_filter-choice;
            }
          }
        }
        container restrict-protected-src {
          presence "true";
          leaf value {
            tailf:cli-drop-node-name;
            type string;
          }
        }
        leaf mac-pinning {
          type empty;
        }
        leaf force-vlan-vc-forwarding {
          type empty;
        }
        container split-horizon-group {
          presence "true";
          leaf group-name {
            tailf:cli-drop-node-name;
            type string;
          }
          leaf auto-learn-mac-protect {
            type empty;
          }
          leaf description {
            type string;
          }
          container restrict-protected-src {
            presence "true";
            leaf option {
              tailf:cli-drop-node-name;
              type string;
            }
          }
          leaf restrict-unprotected-dst {
            type empty;
          }
        }
        leaf vc-type {
          type string;
        }
        leaf limit-mac-move {
          type string;
        }
      }
      container system {
        container bgp-evpn {
          container evpn-etree-leaf-label {
            presence "true";
            leaf label {
              tailf:cli-drop-node-name;
              type string;
            }
          }
          container ip-prefix-routes {
            leaf iff-attribute-uniform-propagation {
              type empty;
            }
            leaf iff-bgp-path-selection {
              type empty;
            }
          }
          leaf ingress-replication-bum-label-block {
            type string;
          }
          leaf route-distinguisher {
            type string;
          }
          list ethernet-segment {
            // NCS patched for predictable order
            ordered-by user;
            key "name";
            leaf name {
              type ncs_compliance_template_string32;
            }
            leaf ac-df-capability {
              type string;
            }
            container dot1q {
              list q-tag-range {
                // NCS patched for predictable order
                ordered-by user;
                tailf:cli-suppress-mode;
                key "start";
                leaf start {
                  type string;
                }
                leaf to {
                  type string;
                }
              }
            }
            leaf oper-group {
              type string;
            }
            leaf virtual {
              type empty;
            }
            leaf esi {
              type string;
            }
            leaf es-orig-ip {
              type string;
            }
            leaf route-next-hop {
              type string;
            }
            leaf es-activation-timer {
              type string;
            }
            leaf sdp {
              type string;
            }
            container service-carving {
              leaf mode {
                type string;
              }
              container manual {
                container preference {
                  presence "true";
                  leaf non-revertive {
                    type empty;
                  }
                  leaf value {
                    type string;
                  }
                }
              }
            }
            container multi-homing {
              leaf value {
                tailf:cli-drop-node-name;
                type string;
              }
              leaf no-esi-label {
                type empty;
              }
            }
            leaf lag {
              type string;
            }
            container qinq {
              container s-tag {
                leaf s-tag {
                  tailf:cli-drop-node-name;
                  type string;
                }
                leaf c-tag-range {
                  type string;
                }
                leaf to {
                  type string;
                }
              }
              list s-tag-range {
                // NCS patched for predictable order
                ordered-by user;
                tailf:cli-suppress-mode;
                key "start";
                leaf start {
                  type string;
                }
                leaf to {
                  type string;
                }
              }
            }
            leaf port {
              type string;
            }
            list vc-id-range {
              // NCS patched for predictable order
              ordered-by user;
              tailf:cli-suppress-mode;
              key "start";
              leaf start {
                type string;
              }
              leaf to {
                type string;
              }
            }
            leaf shutdown {
              type string;
            }
          }
        }
      }
      container template {
        list vpls-sap-template {
          // NCS patched for predictable order
          ordered-by user;
          key "name";
          leaf name {
            type ncs_compliance_template_string32;
          }
          container ingress {
            container qos {
              leaf policy-id {
                tailf:cli-drop-node-name;
                type string;
              }
              leaf shared-queuing {
                type empty;
              }
            }
          }
        }
      }
    }
    list router {
      // NCS patched for predictable order
      ordered-by user;
      key "router-name";
      leaf router-name {
        type ncs_compliance_template_router-type;
      }
      container flowspec {
        leaf ip-filter-max-size {
          type string;
        }
        leaf ipv6-filter-max-size {
          type string;
        }
      }
      container bfd {
        list bfd-template {
          // NCS patched for predictable order
          ordered-by user;
          key "template";
          leaf template {
            type string;
          }
          leaf echo-receive {
            type string;
          }
          leaf multiplier {
            type string;
          }
          leaf receive-interval {
            type string;
          }
          leaf transmit-interval {
            type string;
          }
          leaf type {
            type string;
          }
        }
        container seamless-bfd {
          list peer {
            // NCS patched for predictable order
            ordered-by user;
            key "address";
            leaf address {
              type string;
            }
            leaf discriminator {
              type string;
            }
          }
        }
      }
      leaf class-forwarding {
        type empty;
      }
      leaf ecmp {
        type string;
      }
      leaf-list leak-export {
        // NCS patched for predictable order
        ordered-by user;
        type string;
      }
      leaf leak-export-limit {
        type string;
      }
      leaf single-sfm-overload {
        type empty;
      }
      container segment-routing {
        container sr-policies {
          list static-policy {
            // NCS patched for predictable order
            ordered-by user;
            key "policy-id";
            leaf policy-id {
              type string;
            }
            leaf binding-sid {
              type string;
            }
            leaf color {
              type string;
            }
            leaf distinguisher {
              type string;
            }
            leaf endpoint {
              type string;
            }
            leaf head-end {
              type string;
            }
            list segment-list {
              // NCS patched for predictable order
              ordered-by user;
              key "id";
              leaf id {
                type string;
              }
              leaf weight {
                type string;
              }
              list segment {
                // NCS patched for predictable order
                ordered-by user;
                key "id";
                leaf id {
                  type string;
                }
                leaf mpls-label {
                  type string;
                }
              }
              leaf shutdown {
                type string;
              }
            }
            leaf shutdown {
              type string;
            }
          }
          leaf shutdown {
            type string;
          }
        }
      }
      container admin-tags {
        list admin-tag {
          // NCS patched for predictable order
          ordered-by user;
          tailf:cli-suppress-mode;
          key "tag";
          leaf tag {
            type ncs_compliance_template_string32;
          }
        }
        list route-admin-tag-policy {
          // NCS patched for predictable order
          ordered-by user;
          key "policy-name";
          leaf policy-name {
            type string;
          }
          list exclude {
            // NCS patched for predictable order
            ordered-by user;
            tailf:cli-suppress-mode;
            key "tag";
            leaf tag {
              type ncs_compliance_template_string32;
            }
          }
          list include {
            // NCS patched for predictable order
            ordered-by user;
            tailf:cli-suppress-mode;
            key "tag";
            leaf tag {
              type ncs_compliance_template_string32;
            }
          }
        }
      }
      leaf autonomous-system {
        type string;
      }
      leaf entropy-label {
        type empty;
      }
      leaf icmp-tunneling {
        type empty;
      }
      list interface {
        // NCS patched for predictable order
        ordered-by user;
        key "interface-name";
        leaf interface-name {
          type string;
        }
        leaf address {
          type string;
        }
        leaf description {
          type string;
        }
        leaf collect-stats {
          type empty;
        }
        container dhcp {
          leaf description {
            type string;
          }
          container gi-address {
            leaf gi-address-value {
              tailf:cli-drop-node-name;
              type string;
            }
            leaf src-ip-addr {
              type empty;
            }
          }
          uses ncs_compliance_template_dhcp-option-grouping {
            augment "option" {
              leaf circuit-id {
                type string;
              }
            }
            augment "option/vendor-specific-option" {
              leaf port-id {
                type empty;
              }
              leaf system-id {
                type empty;
              }
            }
          }
          leaf python-policy {
            type ncs_compliance_template_string32;
          }
          leaf relay-plain-bootp {
            type empty;
          }
          leaf-list server {
            // NCS patched for predictable order
            ordered-by user;
            type string;
          }
          leaf trusted {
            type empty;
          }
          leaf shutdown {
            type string;
          }
        }
        leaf dist-cpu-protection {
          type string;
        }
        container ldp-sync-timer {
          leaf ldp-sync-timer {
            tailf:cli-drop-node-name;
            type string;
          }
          leaf end-of-lib {
            type empty;
          }
        }
        container load-balancing {
          leaf lsr-load-balancing {
            type string;
          }
        }
        leaf local-dhcp-server {
          type string;
        }
        leaf cpu-protection {
          type string;
        }
        leaf loopback {
          type empty;
        }
        leaf enable-ingress-stats {
          type empty;
        }
        leaf unnumbered-mpls-tp {
          type empty;
        }
        leaf port {
          type string;
        }
        container egress {
          container filter {
            leaf ip {
              type ncs_compliance_template_filter-id;
            }
            leaf ipv6 {
              type ncs_compliance_template_filter-id;
            }
          }
          leaf queue-policy {
            type string;
          }
          container agg-rate-limit {
            leaf agg-rate {
              tailf:cli-drop-node-name;
              type string;
            }
            leaf cir {
              type string;
            }
          }
          leaf vlan-qos-policy {
            type string;
          }
          container agg-rate {
            container rate {
              leaf val {
                tailf:cli-drop-node-name;
                type string;
              }
              leaf cir {
                type string;
              }
            }
          }
          leaf egress-remark-policy {
            type string;
          }
        }
        container if-attribute {
          list admin-group {
            // NCS patched for predictable order
            ordered-by user;
            tailf:cli-suppress-mode;
            key "group-name";
            leaf group-name {
              type string;
            }
          }
          container delay {
            leaf static {
              type string;
            }
            leaf delay-selection {
              type string;
            }
            container dynamic {
              leaf measurement-template {
                type string;
              }
              container twamp-light {
                container ipv4 {
                  leaf source {
                    type string;
                  }
                  leaf destination {
                    type string;
                  }
                  leaf shutdown {
                    type string;
                  }
                }
                container ipv6 {
                  leaf source {
                    type string;
                  }
                  leaf destination {
                    type string;
                  }
                  leaf shutdown {
                    type string;
                  }
                }
              }
            }
          }
        }
        container ingress {
          container filter {
            leaf ip {
              type ncs_compliance_template_filter-id;
            }
            leaf ipv6 {
              type ncs_compliance_template_filter-id;
            }
          }
          leaf qos {
            type string;
          }
        }
        leaf lsr-load-balancing {
          type string;
        }
        uses ncs_compliance_template_interface-icmp-grouping;
        leaf ptp-hw-assist {
          type empty;
        }
        container urpf-check {
          leaf mode {
            type string;
          }
        }
        container ipv6 {
          leaf local-dhcp-server {
            type ncs_compliance_template_string32;
          }
          uses ncs_compliance_template_ipv6-grouping;
        }
        container bfd {
          uses ncs_compliance_template_bfd-grouping;
        }
        leaf autonomous-system {
          type string;
        }
        uses ncs_compliance_template_cflowd-params-grouping;
        container cflowd {
          leaf id {
            tailf:cli-drop-node-name;
            type string;
          }
          leaf direction {
            tailf:cli-drop-node-name;
            type string;
          }
        }
        container static-arp {
          leaf ip-address {
            tailf:cli-drop-node-name;
            type string;
          }
          leaf ieee-address {
            tailf:cli-drop-node-name;
            type ncs_compliance_template_ieee-mac;
          }
        }
        leaf tos-marking-state {
          type string;
        }
        container qos {
          leaf network-policy-id {
            tailf:cli-drop-node-name;
            type string;
          }
          leaf egress-port-redirect-group {
            type string;
          }
          leaf egress-instance {
            type string;
          }
          leaf ingress-fp-redirect-group {
            type string;
          }
          leaf ingress-instance {
            type string;
          }
        }
        leaf tcp-mss {
          type string;
        }
        leaf shutdown {
          type string;
        }
      }
      container tunnel-interface {
        list rsvp-p2mp {
          // NCS patched for predictable order
          ordered-by user;
          key "lsp-name";
          leaf lsp-name {
            type string;
          }
        }
      }
      container bgp {
        presence "present";
        uses ncs_compliance_template_router-bgp-add-paths-grouping;
        leaf initial-send-delay-zero {
          type empty;
        }
        container monitor {
          presence "true";
          leaf-list route-monitoring {
            // NCS patched for predictable order
            ordered-by user;
            type string;
          }
          leaf-list station {
            // NCS patched for predictable order
            ordered-by user;
            type string;
          }
          leaf shutdown {
            type string;
          }
        }
        leaf override-tunnel-elc {
          type empty;
        }
        leaf loop-detect-threshold {
          type string;
        }
        leaf-list advertise-external {
          // NCS patched for predictable order
          ordered-by user;
          type string;
        }
        leaf advertise-inactive {
          type empty;
        }
        leaf aggregator-id-zero {
          type empty;
        }
        leaf auth-keychain {
          type string;
        }
        uses ncs_compliance_template_prompted-authentication-key-grouping;
        leaf-list backup-path {
          // NCS patched for predictable order
          ordered-by user;
          type string;
        }
        uses ncs_compliance_template_bgp-best-path-selection-grouping;
        leaf bfd-enable {
          type empty;
        }
        container bgp-tunnel-metric {
          leaf metric {
            tailf:cli-drop-node-name;
            type string;
          }
          leaf prefer-aigp {
            type empty;
          }
        }
        leaf cluster {
          type string;
        }
        leaf connect-retry {
          type string;
        }
        leaf damping {
          type empty;
        }
        leaf description {
          type string;
        }
        leaf disable-4byte-asn {
          type empty;
        }
        leaf disable-client-reflect {
          type empty;
        }
        leaf-list disable-communities {
          // NCS patched for predictable order
          ordered-by user;
          type string;
        }
        leaf disable-fast-external-failover {
          type empty;
        }
        leaf disable-route-table-install {
          type empty;
        }
        leaf enable-inter-as-vpn {
          type empty;
        }
        leaf enable-peer-tracking {
          type empty;
        }
        leaf enable-rr-vpn-forwarding {
          type empty;
        }
        container error-handling {
          leaf update-fault-tolerance {
            type empty;
          }
        }
        leaf-list family {
          // NCS patched for predictable order
          ordered-by user;
          type ncs_compliance_template_family-names-type;
        }
        leaf flowspec-validate {
          type empty;
        }
        container flowspec {
          leaf validate-dest-prefix {
            type empty;
          }
        }
        leaf link-state-import-enable {
          type empty;
        }
        leaf link-state-export-enable {
          type empty;
        }
        uses ncs_compliance_template_bgp-graceful-restart-grouping;
        list group {
          // NCS patched for predictable order
          ordered-by user;
          key "id";
          leaf id {
            type string;
          }
          uses ncs_compliance_template_router-bgp-grouping;
          uses ncs_compliance_template_bgp-import-export-grouping;
          uses ncs_compliance_template_enable-origin-validation-grouping;
          container error-handling {
            leaf update-fault-tolerance {
              type empty;
            }
          }
          list neighbor {
            // NCS patched for predictable order
            ordered-by user;
            key "address";
            leaf address {
              type string;
            }
            uses ncs_compliance_template_router-bgp-grouping;
            uses ncs_compliance_template_enable-origin-validation-grouping;
            leaf-list advertise-label {
              // NCS patched for predictable order
              ordered-by user;
              type string;
            }
            uses ncs_compliance_template_bgp-import-export-grouping;
          }
          leaf-list next-hop-unchanged {
            // NCS patched for predictable order
            ordered-by user;
            type string;
          }
        }
        leaf ibgp-multipath {
          type empty;
        }
        container igp-shortcut {
          leaf value {
            tailf:cli-drop-node-name;
            type string;
          }
          leaf disallow-igp {
            type empty;
          }
        }
        uses ncs_compliance_template_bgp-import-export-grouping;
        uses ncs_compliance_template_bgp-common-grouping;
        uses ncs_compliance_template_bgp-local-as-grouping;
        leaf local-preference {
          type string;
        }
        leaf loop-detect {
          type string;
        }
        leaf med-out {
          type string;
        }
        leaf min-as-origination {
          type string;
        }
        leaf min-route-advertisement {
          type string;
        }
        leaf mp-bgp-keep {
          type empty;
        }
        leaf multihop {
          type string;
        }
        uses ncs_compliance_template_bgp-multipath-grouping;
        uses ncs_compliance_template_bgp-multi-path-grouping {
          augment "multi-path" {
            container label-ipv6 {
              uses ncs_compliance_template_max-paths-uneqcosts-grouping;
            }
          }
        }
        leaf mvpn-vrf-import-subtype-new {
          type empty;
        }
        uses ncs_compliance_template_bgp-next-hop-resolution-grouping;
        container outbound-route-filtering {
          container extended-community {
            leaf accept-orf {
              type empty;
            }
            container send-orf {
              presence "true";
              leaf-list send-orf {
                // NCS patched for predictable order
                ordered-by user;
                tailf:cli-drop-node-name;
                type string;
              }
            }
          }
        }
        container rib-management {
          container ipv4 {
            leaf-list leak-import {
              // NCS patched for predictable order
              ordered-by user;
              type string;
            }
          }
          container ipv6 {
            leaf-list leak-import {
              // NCS patched for predictable order
              ordered-by user;
              type string;
            }
            leaf route-table-import {
              type string;
            }
          }
          container label-ipv4 {
            leaf route-table-import {
              type string;
            }
          }
          container label-ipv6 {
            leaf route-table-import {
              type string;
            }
          }
        }
        leaf path-mtu-discovery {
          type empty;
        }
        leaf peer-tracking-policy {
          type string;
        }
        leaf purge-timer {
          type string;
        }
        leaf-list rapid-update {
          // NCS patched for predictable order
          ordered-by user;
          type string;
        }
        leaf rapid-withdrawal {
          type empty;
        }
        leaf-list remove-private {
          // NCS patched for predictable order
          ordered-by user;
          type string;
        }
        leaf-list route-target-list {
          // NCS patched for predictable order
          ordered-by user;
          type string;
        }
        leaf router-id {
          type string;
        }
        leaf selective-label-ipv4-install {
          type empty;
        }
        container segment-routing {
          presence "true";
          container prefix-sid-range {
            leaf global {
              type empty;
            }
          }
          leaf shutdown {
            type string;
          }
        }
        leaf split-horizon {
          type empty;
        }
        leaf transport-tunnel {
          type string;
        }
        leaf vpn-apply-export {
          type empty;
        }
        leaf vpn-apply-import {
          type empty;
        }
        leaf shutdown {
          type string;
        }
      }
      leaf ip-fast-reroute {
        type empty;
      }
      leaf fib-priority {
        type string;
      }
      container if-attribute {
        list admin-group {
          // NCS patched for predictable order
          ordered-by user;
          tailf:cli-suppress-mode;
          key "group-name";
          leaf group-name {
            type string;
          }
          leaf value {
            type string;
          }
        }
        list srlg-group {
          // NCS patched for predictable order
          ordered-by user;
          tailf:cli-suppress-mode;
          key "group-name";
          leaf group-name {
            type ncs_compliance_template_string32;
          }
          leaf value {
            type string;
          }
          leaf penalty-weight {
            type string;
          }
        }
      }
      container igmp {
        presence "present";

        grouping iface-grouping {
          leaf disable-router-alert-check {
            type empty;
          }
          leaf import {
            type string;
          }
          leaf max-groups {
            type string;
          }
          leaf max-grp-sources {
            type string;
          }
          leaf max-sources {
            type string;
          }
          uses ncs_compliance_template_mcac-grouping;
          leaf subnet-check {
            type string;
          }
          leaf version {
            type string;
          }
        }

        grouping igmp-common-grouping {
          leaf query-interval {
            type string;
          }
          leaf query-response-interval {
            type string;
          }
          container ssm-translate {
            list grp-range {
              // NCS patched for predictable order
              ordered-by user;
              key "start end";
              leaf start {
                type string;
              }
              leaf end {
                type string;
              }
              list source {
                // NCS patched for predictable order
                ordered-by user;
                tailf:cli-suppress-mode;
                key "ip-address";
                leaf ip-address {
                  type string;
                }
              }
            }
          }
        }
        list group-interface {
          // NCS patched for predictable order
          ordered-by user;
          key "ip-int-name";
          leaf ip-int-name {
            type string;
          }
          uses iface-grouping;
          leaf query-src-ip {
            type string;
          }
          leaf sub-hosts-only {
            type empty;
          }
          leaf shutdown {
            type string;
          }
        }
        leaf grp-if-query-src-ip {
          type string;
        }
        list interface {
          // NCS patched for predictable order
          ordered-by user;
          key "ip-int-name";
          leaf ip-int-name {
            type string;
          }
          uses iface-grouping;
          leaf query-last-listener-interval {
            type string;
          }
          leaf redundant-multicast {
            type empty;
          }
          uses igmp-common-grouping;
          uses ncs_compliance_template_igmp-static-grouping;
          leaf shutdown {
            type string;
          }
        }
        uses igmp-common-grouping;
        leaf query-last-member-interval {
          type string;
        }
        leaf robust-count {
          type string;
        }
        container tunnel-interface {
          list rsvp-p2mp {
            // NCS patched for predictable order
            ordered-by user;
            key "lsp-name";
            leaf lsp-name {
              type string;
            }
            uses ncs_compliance_template_igmp-static-grouping;
            leaf shutdown {
              type string;
            }
          }
        }
        leaf shutdown {
          type string;
        }
      }
      leaf router-id {
        type string;
      }
      list static-route {
        // NCS patched for predictable order
        ordered-by user;
        tailf:cli-suppress-mode;
        key "route";
        leaf route {
          type string;
        }
        choice nh {
          list next-hop {
            // NCS patched for predictable order
            ordered-by user;
            tailf:cli-suppress-mode;
            key "address";
            leaf address {
              type string;
            }
            uses ncs_compliance_template_static-route-extras-grouping;
          }
          leaf indirect {
            type string;
          }
          leaf black-hole {
            type empty;
          }
        }
        uses ncs_compliance_template_static-route-extras-grouping;
        choice rsvp-ldp {
          leaf rsvp-te {
            type empty;
          }
          leaf ldp {
            type empty;
          }
        }
        leaf disallow-igp {
          type empty;
        }
      }
      list static-route-entry {
        // NCS patched for predictable order
        ordered-by user;
        key "route";
        leaf route {
          type string;
        }
        list next-hop {
          // NCS patched for predictable order
          ordered-by user;
          key "address";
          leaf address {
            type string;
          }
          uses ncs_compliance_template_static-route-entry-nh-grouping;
        }
        list indirect {
          // NCS patched for predictable order
          ordered-by user;
          key "address";
          leaf address {
            type string;
          }
          uses ncs_compliance_template_static-route-entry-nh-grouping;
        }
        container black-hole {
          presence "true";
          uses ncs_compliance_template_static-route-entry-nh-grouping;
          container prefix-list {
            leaf name {
              tailf:cli-drop-node-name;
              type string;
            }
            leaf modifyer {
              tailf:cli-drop-node-name;
              type string;
            }
          }
        }
        leaf tag {
          type string;
        }
      }
      uses ncs_compliance_template_router-aggregate-grouping;

      grouping router-isis-grouping {
        leaf advertise-passive-only {
          type empty;
        }
        leaf prefix-attributes-tlv {
          type empty;
        }
        container entropy-label {
          leaf override-tunnel-elc {
            type empty;
          }
        }
        container database-export {
          leaf identifier {
            type string;
          }
          leaf bgp-ls-identifier {
            type string;
          }
        }
        leaf advertise-router-capability {
          type string;
        }
        container igp-shortcut {

          grouping res-filter-grouping {
            leaf resolution {
              type string;
            }
            container resolution-filter {
              list filter {
                // NCS patched for predictable order
                ordered-by user;
                tailf:cli-suppress-mode;
                tailf:cli-drop-node-name;
                key "filter";
                leaf filter {
                  type string;
                }
              }
            }
          }
          container tunnel-next-hop {
            // NCS drop config false container family
            container family-ipv4 {
              uses res-filter-grouping;
            }
            container family-ipv6 {
              uses res-filter-grouping;
            }
            container family-srv4 {
              uses res-filter-grouping;
            }
            container family-srv6 {
              uses res-filter-grouping;
            }
          }
          leaf shutdown {
            type string;
          }
        }
        leaf advertise-tunnel-link {
          type empty;
        }
        leaf all-l1isis {
          type string;
        }
        leaf all-l2isis {
          type string;
        }
        list area-id {
          // NCS patched for predictable order
          ordered-by user;
          tailf:cli-suppress-mode;
          key "id";
          leaf id {
            type string;
          }
        }
        leaf auth-keychain {
          type string;
        }
        leaf authentication-check {
          type string;
        }
        uses ncs_compliance_template_prompted-authentication-key-grouping;
        leaf authentication-type {
          type string;
        }
        leaf csnp-authentication {
          type string;
        }
        leaf default-route-tag {
          type string;
        }
        leaf disable-ldp-sync {
          type empty;
        }
        leaf-list export {
          // NCS patched for predictable order
          ordered-by user;
          type string;
        }
        container export-limit {
          leaf number {
            tailf:cli-drop-node-name;
            type string;
          }
          leaf log {
            type string;
          }
        }
        container graceful-restart {
          presence "true";
          leaf helper-disable {
            type empty;
          }
        }
        leaf hello-authentication {
          type string;
        }
        leaf hello-padding {
          type string;
        }
        leaf ignore-attached-bit {
          type empty;
        }
        leaf ignore-lsp-errors {
          type empty;
        }
        leaf iid-tlv-enable {
          type empty;
        }
        leaf standard-multi-instance {
          type empty;
        }
        list interface {
          // NCS patched for predictable order
          ordered-by user;
          key "name";
          leaf name {
            type string;
          }
          list bfd-enable {
            // NCS patched for predictable order
            ordered-by user;
            tailf:cli-suppress-mode;
            key "bfd-enable";
            leaf bfd-enable {
              type string;
            }
            leaf include-bfd-tlv {
              type empty;
            }
          }
          container ipv4-adjacency-sid {
            leaf label {
              type string;
            }
          }
          container ipv6-adjacency-sid {
            leaf label {
              type string;
            }
          }
          container ipv6-node-sid {
            leaf index {
              type string;
            }
          }
          leaf csnp-interval {
            type string;
          }
          leaf hello-authentication {
            type string;
          }
          uses ncs_compliance_template_prompted-hello-authentication-key-grouping;
          leaf hello-authentication-type {
            type string;
          }
          leaf interface-type {
            type string;
          }
          leaf ipv4-multicast-disable {
            type empty;
          }
          leaf ipv6-multicast-disable {
            type empty;
          }
          leaf ipv6-unicast-disable {
            type empty;
          }
          list level {
            // NCS patched for predictable order
            ordered-by user;
            key "id";
            leaf id {
              type string;
            }
            uses ncs_compliance_template_prompted-hello-authentication-key-grouping;
            leaf hello-authentication-type {
              type string;
            }
            leaf hello-interval {
              type string;
            }
            leaf hello-multiplier {
              type string;
            }
            leaf ipv4-multicast-metric {
              type string;
            }
            leaf ipv6-multicast-metric {
              type string;
            }
            leaf ipv6-unicast-metric {
              type string;
            }
            leaf metric {
              type string;
            }
            leaf passive {
              type empty;
            }
            leaf priority {
              type string;
            }
            leaf sd-offset {
              type string;
            }
            leaf sf-offset {
              type string;
            }
          }
          leaf level-capability {
            type string;
          }
          leaf loopfree-alternate-exclude {
            type empty;
          }
          leaf lsp-pacing-interval {
            type string;
          }
          leaf mesh-group {
            type string;
          }
          leaf passive {
            type empty;
          }
          leaf retransmit-interval {
            type string;
          }
          leaf tag {
            type string;
          }
          leaf shutdown {
            type string;
          }
        }
        leaf ipv4-multicast-routing {
          type string;
        }
        leaf ipv4-routing {
          type string;
        }
        leaf ipv6-routing {
          type string;
        }
        leaf ipv6-multicast-routing {
          type string;
        }
        leaf ldp-over-rsvp {
          type empty;
        }
        list level {
          // NCS patched for predictable order
          ordered-by user;
          key "id";
          leaf id {
            type string;
          }
          uses ncs_compliance_template_prompted-authentication-key-grouping;
          leaf authentication-type {
            type string;
          }
          leaf csnp-authentication {
            type string;
          }
          leaf default-ipv4-multicast-metric {
            type string;
          }
          leaf default-ipv6-multicast-metric {
            type string;
          }
          leaf default-ipv6-unicast-metric {
            type string;
          }
          leaf default-metric {
            type string;
          }
          leaf external-preference {
            type string;
          }
          leaf hello-authentication {
            type string;
          }
          leaf loopfree-alternate-exclude {
            type empty;
          }
          leaf preference {
            type string;
          }
          leaf psnp-authentication {
            type string;
          }
          leaf wide-metrics-only {
            type empty;
          }
        }
        leaf level-capability {
          type string;
        }
        list link-group {
          // NCS patched for predictable order
          ordered-by user;
          key "name";
          leaf name {
            type string;
          }
          list level {
            // NCS patched for predictable order
            ordered-by user;
            key "id";
            leaf id {
              type string;
            }
            leaf ipv6-unicast-metric-offset {
              type string;
            }
            leaf ipv4-unicast-metric-offset {
              type string;
            }
            leaf ipv6-multicast-metric-offset {
              type string;
            }
            leaf ipv4-multicast-metric-offset {
              type string;
            }
            list member {
              // NCS patched for predictable order
              ordered-by user;
              tailf:cli-suppress-mode;
              key "name";
              leaf name {
                type string;
              }
            }
            leaf revert-members {
              type string;
            }
            leaf oper-members {
              type string;
            }
          }
        }
        container loopfree-alternate {
          presence "true";
          leaf remote-lfa {
            type empty;
          }
          leaf max-pq-cost {
            type string;
          }
        }
        container loopfree-alternate-exclude {
          leaf-list prefix-policy {
            // NCS patched for predictable order
            ordered-by user;
            type string;
          }
        }
        leaf lsp-lifetime {
          type string;
        }
        leaf lsp-mtu-size {
          type string;
        }
        leaf lsp-refresh-interval {
          type string;
        }
        container multi-topology {
          leaf ipv6-unicast {
            type empty;
          }
        }
        leaf multicast-import {
          type string;
        }
        container overload {
          presence "true";
          leaf timeout {
            type string;
          }
          leaf max-metric {
            type empty;
          }
        }
        container overload-on-boot {
          presence "true";
          leaf timeout {
            type string;
          }
          leaf max-metric {
            type empty;
          }
        }
        leaf psnp-authentication {
          type string;
        }
        container reference-bandwidth {
          choice bandwidth {
            leaf bandwidth-in-kbps {
              tailf:cli-drop-node-name;
              type string;
            }
            leaf tbps {
              type string;
            }
            leaf gbps {
              type string;
            }
            leaf mbps {
              type string;
            }
            leaf kbps {
              type string;
            }
          }
        }
        leaf router-id {
          type string;
        }
        leaf rsvp-shortcut {
          type empty;
        }
        uses ncs_compliance_template_router-segment-routing-grouping;
        leaf strict-adjacency-check {
          type empty;
        }
        leaf suppress-attached-bit {
          type empty;
        }
        container timers {
          container spf-wait {
            leaf wait {
              tailf:cli-drop-node-name;
              type string;
            }
            leaf spf-initial-wait {
              type string;
            }
            leaf spf-second-wait {
              type string;
            }
          }
          container lsp-wait {
            leaf wait {
              tailf:cli-drop-node-name;
              type string;
            }
            leaf lsp-initial-wait {
              type string;
            }
            leaf lsp-second-wait {
              type string;
            }
          }
        }
        container spf-wait {
          leaf wait {
            tailf:cli-drop-node-name;
            type string;
          }
          leaf initial-wait {
            tailf:cli-drop-node-name;
            type string;
          }
          leaf second-wait {
            tailf:cli-drop-node-name;
            type string;
          }
        }
        container lsp-wait {
          leaf wait {
            tailf:cli-drop-node-name;
            type string;
          }
          leaf initial-wait {
            tailf:cli-drop-node-name;
            type string;
          }
          leaf second-wait {
            tailf:cli-drop-node-name;
            type string;
          }
        }
        leaf traffic-engineering {
          type empty;
        }
        container traffic-engineering-options {
          leaf advertise-delay {
            type empty;
          }
          container application-link-attributes {
            presence "true";
            leaf legacy {
              type empty;
            }
          }
          leaf ipv6 {
            type empty;
          }
        }
        leaf unicast-import-disable {
          type string;
        }
        leaf shutdown {
          type string;
        }
      }
      list isis-list {
        // NCS patched for predictable order
        ordered-by user;
        tailf:alt-name "isis";
        key "id";
        leaf id {
          type string;
        }
        leaf-list import {
          // NCS patched for predictable order
          ordered-by user;
          type string;
        }
        leaf system-id {
          type string;
        }
        uses router-isis-grouping {
          augment "interface" {
            container ipv4-node-sid {
              choice ipv4-node-sid {
                leaf index {
                  type string;
                }
                leaf label {
                  type string;
                }
              }
            }
          }
        }
        container alt-lsp-refresh-interval {
          tailf:alt-name "lsp-refresh-interval";
          leaf seconds {
            tailf:cli-drop-node-name;
            type string;
          }
          leaf half-lifetime {
            type ncs_compliance_template_enable-disable;
          }
        }
        container loopfree-alternates {
          container exclude {
            leaf-list prefix-policy {
              // NCS patched for predictable order
              ordered-by user;
              type string;
            }
          }
          container remote-lfa {
            presence "true";
            leaf max-pq-cost {
              type string;
            }
            container node-protect {
              presence "true";
              leaf max-pq-nodes {
                type string;
              }
            }
          }
          container ti-lfa {
            presence "true";
            leaf max-sr-frr-labels {
              type string;
            }
            leaf node-protect {
              type empty;
            }
          }
        }
        container rib-priority {
          container high {
            choice high-options {
              leaf prefix-list-name {
                tailf:cli-drop-node-name;
                type string;
              }
              leaf tag {
                type string;
              }
            }
          }
        }
      }
      container isis-container {
        tailf:alt-name "isis";
        presence "true";
        uses router-isis-grouping;
      }

      grouping router-ospf-grouping {
        leaf advertise-tunnel-link {
          type empty;
        }
        leaf advertise-router-capability {
          type string;
        }
        uses ncs_compliance_template_router-segment-routing-grouping;
        container loopfree-alternates {
          presence "true";
          container remote-lfa {
            presence "true";
          }
        }
        list area {
          // NCS patched for predictable order
          ordered-by user;
          key "area-id";
          uses ncs_compliance_template_ospf-area-id-grouping;

          grouping area-range-grouping {
            list area-range {
              // NCS patched for predictable order
              ordered-by user;
              tailf:cli-suppress-mode;
              key "ip-prefix-mask";
              leaf ip-prefix-mask {
                type string;
              }
              leaf adv-or-not {
                tailf:cli-drop-node-name;
                type string;
              }
            }
          }
          uses area-range-grouping;
          container nssa {
            uses area-range-grouping;
            leaf redistribute-external {
              type empty;
            }
            container originate-default-route {
              presence "true";
              leaf type-7 {
                type empty;
              }
              leaf no-adjancency {
                type empty;
              }
            }
            leaf summaries {
              type empty;
            }
          }
          list interface {
            // NCS patched for predictable order
            ordered-by user;
            key "name";
            leaf name {
              type string;
            }
            leaf secondary {
              type empty;
            }
            leaf bfd-enable {
              type empty;
            }
            leaf hello-interval {
              type string;
            }
            leaf dead-interval {
              type string;
            }
            leaf passive {
              type string;
            }
            list message-digest-key {
              // NCS patched for predictable order
              ordered-by user;
              tailf:cli-suppress-mode;
              key "key-id";
              leaf key-id {
                type string;
              }
              leaf md5 {
                type empty;
              }
              leaf hash-value {
                tailf:cli-drop-node-name;
                type string;
              }
              leaf scheme {
                tailf:cli-drop-node-name;
                type ncs_compliance_template_hash-method;
              }
            }
            leaf interface-type {
              type string;
            }
            leaf authentication-type {
              type string;
            }
            leaf metric {
              type string;
            }
            leaf mtu {
              type string;
            }
            container node-sid {
              leaf label {
                type string;
              }
            }
            leaf sid-protection {
              type string;
            }
            leaf shutdown {
              type string;
            }
          }
          container stub {
            leaf default-metric {
              type string;
            }
            leaf summaries {
              type string;
            }
          }
        }
        leaf asbr {
          type empty;
        }
        leaf compatible-rfc1583 {
          type empty;
        }
        leaf disable-ldp-sync {
          type empty;
        }
        leaf-list export {
          // NCS patched for predictable order
          ordered-by user;
          type string;
        }
        container export-limit {
          leaf limit {
            tailf:cli-drop-node-name;
            type string;
          }
          leaf log {
            type string;
          }
        }
        container external-db-overflow {
          leaf limit {
            tailf:cli-drop-node-name;
            type string;
          }
          leaf seconds {
            tailf:cli-drop-node-name;
            type string;
          }
        }
        leaf external-preference {
          type string;
        }
        container graceful-restart {
          leaf helper-disable {
            type empty;
          }
        }
        leaf ldp-over-rsvp {
          type empty;
        }
        leaf multicast-import {
          type empty;
        }
        leaf overload {
          type string;
        }
        container overload-alt {
          presence "true";
          tailf:alt-name "overload";
          leaf timeout {
            type string;
          }
        }
        leaf overload-include-stub {
          type empty;
        }
        container overload-on-boot {
          presence "true";
          leaf timeout {
            type string;
          }
        }
        leaf preference {
          type string;
        }
        leaf reference-bandwidth {
          type string;
        }
        leaf rsvp-shortcut {
          type empty;
        }
        container timers {
          leaf lsa-arrival {
            type string;
          }
        }
        leaf traffic-engineering {
          type empty;
        }
        leaf unicast-import-disable {
          type empty;
        }
        leaf shutdown {
          type string;
        }
      }
      list ospf-list {
        // NCS patched for predictable order
        ordered-by user;
        tailf:alt-name "ospf";
        key "ospf-instance";
        leaf ospf-instance {
          type string;
        }
        leaf router-id {
          tailf:cli-drop-node-name;
          type string;
        }
        uses router-ospf-grouping {
          augment "timers" {
            leaf lsa-accumulate {
              type string;
            }
            container lsa-generate {
              leaf max-lsa-wait {
                tailf:cli-drop-node-name;
                type string;
              }
              leaf lsa-initial-wait {
                tailf:cli-drop-node-name;
                type string;
              }
              leaf lsa-second-wait {
                tailf:cli-drop-node-name;
                type string;
              }
            }
            leaf redistribute-delay {
              type string;
            }
            container spf-wait {
              leaf max-spf-wait {
                tailf:cli-drop-node-name;
                type string;
              }
              leaf spf-initial-wait {
                tailf:cli-drop-node-name;
                type string;
              }
              leaf spf-second-wait {
                tailf:cli-drop-node-name;
                type string;
              }
            }
            container alt-lsa-generate {
              tailf:alt-name "lsa-generate";
              leaf max-lsa-wait {
                tailf:cli-drop-node-name;
                type string;
              }
              leaf lsa-initial-wait {
                type string;
              }
              leaf lsa-second-wait {
                type string;
              }
            }
            container alt-spf-wait {
              tailf:alt-name "spf-wait";
              leaf max-spf-wait {
                tailf:cli-drop-node-name;
                type string;
              }
              leaf spf-initial-wait {
                type string;
              }
              leaf spf-second-wait {
                type string;
              }
            }
            leaf incremental-spf-wait {
              type string;
            }
          }
        }
      }
      container ospf-container {
        tailf:alt-name "ospf";
        presence "true";
        leaf router-id {
          type string;
        }
        leaf router-id1 {
          tailf:cli-drop-node-name;
          type string;
        }
        uses router-ospf-grouping {
          augment "timers" {
            container lsa-generate {
              leaf max-lsa-wait {
                tailf:cli-drop-node-name;
                type string;
              }
              leaf lsa-initial-wait {
                tailf:cli-drop-node-name;
                type string;
              }
              leaf lsa-second-wait {
                tailf:cli-drop-node-name;
                type string;
              }
            }
            container spf-wait {
              leaf max-spf-wait {
                tailf:cli-drop-node-name;
                type string;
              }
              leaf spf-initial-wait {
                tailf:cli-drop-node-name;
                type string;
              }
              leaf spf-second-wait {
                tailf:cli-drop-node-name;
                type string;
              }
            }
          }
        }
      }

      grouping router-ospf3-grouping {
        list area {
          // NCS patched for predictable order
          ordered-by user;
          key "area-id";
          leaf area-id {
            type string;
          }
          list interface {
            // NCS patched for predictable order
            ordered-by user;
            key "interface-name";
            leaf interface-name {
              type string;
            }
            leaf interface-type {
              type string;
            }
            leaf passive {
              type empty;
            }
            leaf mtu {
              type string;
            }
            leaf metric {
              type string;
            }
            leaf shutdown {
              type string;
            }
          }
        }
        leaf shutdown {
          type string;
        }
      }
      list ospf3-list {
        // NCS patched for predictable order
        ordered-by user;
        tailf:alt-name "ospf3";
        key "ospf3-instance";
        leaf ospf3-instance {
          type string;
        }
        leaf router-id {
          tailf:cli-drop-node-name;
          type string;
        }
        uses router-ospf3-grouping;
      }
      container ospf3-container {
        tailf:alt-name "ospf3";
        presence "true";
        leaf router-id {
          type string;
        }
        uses router-ospf3-grouping;
      }
      container mcac {
        list policy {
          // NCS patched for predictable order
          ordered-by user;
          key "policy-name";
          leaf policy-name {
            type ncs_compliance_template_string32;
          }
          list bundle {
            // NCS patched for predictable order
            ordered-by user;
            key "bundle-name";
            leaf bundle-name {
              type ncs_compliance_template_string32;
            }
            leaf bandwidth {
              type string;
            }
            list channel {
              // NCS patched for predictable order
              ordered-by user;
              tailf:cli-suppress-mode;
              key "start-address end-address";
              leaf start-address {
                type string;
              }
              leaf end-address {
                type string;
              }
              leaf source {
                type string;
              }
              leaf bw {
                type string;
              }
              leaf class {
                type string;
              }
              leaf type {
                type string;
              }
            }
            leaf description {
              type string;
            }
            container mc-constraints {
              list lag-port-down {
                // NCS patched for predictable order
                ordered-by user;
                tailf:cli-suppress-mode;
                key "lag-id number-down";
                leaf lag-id {
                  type string;
                }
                leaf number-down {
                  type string;
                }
                leaf level {
                  type string;
                }
              }
              list level {
                // NCS patched for predictable order
                ordered-by user;
                tailf:cli-suppress-mode;
                key "level";
                leaf level {
                  type string;
                }
                leaf bw {
                  type string;
                }
              }
              leaf use-lag-port-weight {
                type empty;
              }
            }
            leaf shutdown {
              type string;
            }
          }
          leaf default-action {
            type string;
          }
          leaf description {
            type string;
          }
        }
      }
      container msdp {
        presence "present";
        leaf local-address {
          type string;
        }
        list group {
          // NCS patched for predictable order
          ordered-by user;
          key "group-name";
          leaf group-name {
            type string;
          }
          leaf mode {
            type string;
          }
          list peer {
            // NCS patched for predictable order
            ordered-by user;
            key "ip-address";
            leaf ip-address {
              type string;
            }
            leaf shutdown {
              type string;
            }
          }
          leaf shutdown {
            type string;
          }
        }
      }
      uses ncs_compliance_template_nat-pool-grouping;
      container l2tp {
        leaf local-address {
          type string;
        }
        leaf shutdown {
          type string;
        }
        list group {
          // NCS patched for predictable order
          ordered-by user;
          key "group-id";
          leaf group-id {
            type string;
          }
          leaf protocol {
            type string;
          }
          leaf local-address {
            type string;
          }
          list tunnel {
            // NCS patched for predictable order
            ordered-by user;
            key "tunnel-id";
            leaf tunnel-id {
              type string;
            }
            leaf local-name {
              type string;
            }
            leaf peer {
              type string;
            }
            leaf preference {
              type string;
            }
            container password {
              leaf id {
                tailf:cli-drop-node-name;
                type string;
              }
              leaf method {
                tailf:cli-drop-node-name;
                type ncs_compliance_template_hash-method;
              }
            }
            leaf remote-name {
              type string;
            }
            leaf load-balance-method {
              type string;
            }
            leaf shutdown {
              type string;
            }
          }
          leaf shutdown {
            type string;
          }
        }
      }
      container ldp {
        presence "present";
        container fast-reroute {
          presence "true";
          leaf backup-sr-tunnel {
            type empty;
          }
        }

        grouping router-ldp-hello-keepalive-grouping {
          container hello {
            leaf timeout {
              tailf:cli-drop-node-name;
              type string;
            }
            leaf factor {
              tailf:cli-drop-node-name;
              type string;
            }
          }
          container keepalive {
            leaf timeout {
              tailf:cli-drop-node-name;
              type string;
            }
            leaf factor {
              tailf:cli-drop-node-name;
              type string;
            }
          }
        }
        container aggregate-prefix-match {
          presence "present";
          leaf shutdown {
            type string;
          }
        }
        container egress-statistics {
          list fec-prefix {
            // NCS patched for predictable order
            ordered-by user;
            key "prefix";
            leaf prefix {
              type string;
            }
            leaf accounting-policy {
              type string;
            }
            leaf collect-stats {
              type empty;
            }
            leaf shutdown {
              type string;
            }
          }
        }
        leaf entropy-label-capability {
          type empty;
        }
        leaf-list export {
          // NCS patched for predictable order
          ordered-by user;
          type string;
        }
        list fec-originate {
          // NCS patched for predictable order
          ordered-by user;
          tailf:cli-suppress-mode;
          key "ip-prefix";
          leaf ip-prefix {
            type string;
          }
          leaf advertised-label {
            type string;
          }
          leaf pop {
            type empty;
          }
          leaf next-hop {
            type string;
          }
          leaf swap-label {
            type string;
          }
          leaf interface {
            type string;
          }
        }
        container graceful-restart {
          presence "true";
          leaf maximum-recovery-time {
            type string;
          }
        }
        container interface-parameters {
          list interface {
            // NCS patched for predictable order
            ordered-by user;
            key "name";
            leaf name {
              type string;
            }
            leaf dual-stack {
              type empty;
            }
            leaf bfd-enable {
              type empty;
            }
            leaf-list alt-bfd-enable {
              // NCS patched for predictable order
              ordered-by user;
              tailf:alt-name "bfd-enable";
              type string;
            }
            container ipv4 {
              uses router-ldp-hello-keepalive-grouping;
              container local-lsr-id {
                choice local-lsr-id-choice {
                  leaf local-lsr-id {
                    tailf:cli-drop-node-name;
                    type string;
                  }
                  leaf interface-name {
                    type string;
                  }
                }
              }
              container fec-type-capability {
                leaf p2mp-ipv4 {
                  type ncs_compliance_template_enable-disable;
                }
                leaf p2mp-ipv6 {
                  type ncs_compliance_template_enable-disable;
                }
                leaf prefix-ipv4 {
                  type ncs_compliance_template_enable-disable;
                }
                leaf prefix-ipv6 {
                  type ncs_compliance_template_enable-disable;
                }
              }
              leaf transport-address {
                type string;
              }
              leaf shutdown {
                type string;
              }
            }
            container ipv6 {
              uses router-ldp-hello-keepalive-grouping;
              leaf local-lsr-id {
                type string;
              }
              leaf transport-address {
                type string;
              }
              leaf shutdown {
                type string;
              }
            }
            leaf local-lsr-id {
              type string;
            }
            leaf multicast-traffic {
              type ncs_compliance_template_enable-disable;
            }
            leaf transport-address {
              type string;
            }
            leaf shutdown {
              type string;
            }
          }
          container ipv4 {
            uses router-ldp-hello-keepalive-grouping;
            leaf transport-address {
              type string;
            }
          }
          container ipv6 {
            leaf transport-address {
              type string;
            }
            uses router-ldp-hello-keepalive-grouping;
          }
          uses router-ldp-hello-keepalive-grouping;
        }
        container peer-parameters {
          list peer {
            // NCS patched for predictable order
            ordered-by user;
            key "addr";
            leaf addr {
              type string;
            }
            container authentication-key {
              leaf authentication-key {
                tailf:cli-drop-node-name;
                type string;
              }
              leaf scheme {
                tailf:cli-drop-node-name;
                type ncs_compliance_template_hash-method;
              }
            }
            leaf adv-adj-addr-only {
              type empty;
            }
            leaf export-prefixes {
              type string;
            }
          }
        }
        leaf prefer-tunnel-in-tunnel {
          type empty;
        }
        leaf shortcut-local-ttl-propagate {
          type string;
        }
        leaf shortcut-transit-ttl-propagate {
          type string;
        }
        container targeted-session {
          uses router-ldp-hello-keepalive-grouping;
          container ipv4 {
            uses router-ldp-hello-keepalive-grouping;
          }
          container ipv6 {
            uses router-ldp-hello-keepalive-grouping;
          }
          list peer {
            // NCS patched for predictable order
            ordered-by user;
            key "peer-address";
            leaf peer-address {
              type string;
            }
            leaf bfd-enable {
              type empty;
            }
            uses router-ldp-hello-keepalive-grouping;
            leaf local-lsr-id {
              type string;
            }
            container tunneling {
              presence "true";
              leaf lsp {
                type string;
              }
            }
            leaf shutdown {
              type string;
            }
          }
        }
        leaf-list export-tunnel-table {
          // NCS patched for predictable order
          ordered-by user;
          type string;
        }
        leaf implicit-null-label {
          type empty;
        }
        leaf label-withdrawal-delay {
          type string;
        }
        container session-parameters {
          list peer {
            // NCS patched for predictable order
            ordered-by user;
            key "ip-address";
            leaf ip-address {
              type string;
            }
            leaf adv-adj-addr-only {
              type empty;
            }
            leaf-list export-prefixes {
              // NCS patched for predictable order
              ordered-by user;
              type string;
            }
            container fec-type-capability {
              leaf prefix-ipv4 {
                type string;
              }
              leaf prefix-ipv6 {
                type string;
              }
            }
          }
        }
        container tcp-session-parameters {
          list peer-transport {
            // NCS patched for predictable order
            ordered-by user;
            key "ip-address";
            leaf ip-address {
              type string;
            }
            uses ncs_compliance_template_prompted-authentication-key-grouping;
            leaf path-mtu-discovery {
              type empty;
            }
            leaf ttl-security {
              type string;
            }
          }
        }
        container import-pmsi-routes {
          leaf mvpn {
            type empty;
          }
          leaf mvpn-no-export-community {
            type empty;
          }
        }
        leaf tunnel-table-pref {
          type string;
        }
        leaf shutdown {
          type string;
        }
      }
      container ldp-shortcut {
        presence "true";
        leaf value {
          tailf:cli-drop-node-name;
          type string;
        }
      }
      container dhcp {
        uses ncs_compliance_template_local-dhcp-server-grouping;
      }
      container dhcp6 {
        list local-dhcp-server {
          // NCS patched for predictable order
          ordered-by user;
          key "server-name";
          leaf server-name {
            type string;
          }
          leaf description {
            type string;
          }
          leaf user-ident {
            type string;
          }
          container use-link-address {
            presence "true";
            leaf scope {
              type string;
            }
          }
          container lease-hold-time {
            leaf days {
              type string;
            }
            leaf hrs {
              type string;
            }
            leaf min {
              type string;
            }
            leaf sec {
              type string;
            }
          }
          container lease-hold-time-for {
            leaf solicited-release {
              type empty;
            }
          }
          list pool {
            // NCS patched for predictable order
            ordered-by user;
            key "name";
            leaf name {
              type string;
            }
            leaf description {
              type string;
            }
            container delegated-prefix-length {
              leaf prefix-lenght {
                tailf:cli-drop-node-name;
                type string;
              }
              leaf minimum {
                type string;
              }
              leaf maximum {
                type string;
              }
            }
            container options {
              leaf-list dns-server {
                // NCS patched for predictable order
                ordered-by user;
                type string;
              }
              list custom-option {
                // NCS patched for predictable order
                ordered-by user;
                tailf:cli-suppress-mode;
                key "option-number";
                leaf option-number {
                  type string;
                }
                choice val {
                  leaf hex {
                    type string;
                  }
                  leaf string {
                    type string;
                  }
                }
              }
            }
            list prefix {
              // NCS patched for predictable order
              ordered-by user;
              key "address";
              leaf address {
                type string;
              }
              leaf pd {
                type empty;
              }
              leaf wan-host {
                type empty;
              }
              container preferred-lifetime {
                leaf days {
                  type string;
                }
                leaf hrs {
                  type string;
                }
                leaf min {
                  type string;
                }
                leaf sec {
                  type string;
                }
              }
              container rebind-timer {
                leaf days {
                  type string;
                }
                leaf hrs {
                  type string;
                }
                leaf min {
                  type string;
                }
                leaf sec {
                  type string;
                }
              }
              container renew-timer {
                leaf days {
                  type string;
                }
                leaf hrs {
                  type string;
                }
                leaf min {
                  type string;
                }
                leaf sec {
                  type string;
                }
              }
              container valid-lifetime {
                leaf days {
                  type string;
                }
                leaf hrs {
                  type string;
                }
                leaf min {
                  type string;
                }
                leaf sec {
                  type string;
                }
              }
            }
          }
          leaf use-pool-from-client {
            type empty;
          }
          leaf shutdown {
            type string;
          }
        }
      }
      container radius-server {
        uses ncs_compliance_template_radius-server-grouping;
      }
      container rip {
        list group {
          // NCS patched for predictable order
          ordered-by user;
          key "name";
          leaf name {
            type ncs_compliance_template_string32;
          }
          leaf description {
            type string;
          }
          leaf export {
            type string;
          }
          leaf metric-out {
            type string;
          }
          list neighbor {
            // NCS patched for predictable order
            ordered-by user;
            key "intf-id";
            leaf intf-id {
              type string;
            }
            container authentication-key {
              leaf key {
                tailf:cli-drop-node-name;
                type string;
              }
              leaf hash {
                tailf:cli-drop-node-name;
                type string;
              }
            }
            container timers {
              leaf update {
                tailf:cli-drop-node-name;
                type string;
              }
              leaf timeout {
                tailf:cli-drop-node-name;
                type string;
              }
              leaf flush {
                tailf:cli-drop-node-name;
                type string;
              }
            }
            leaf shutdown {
              type string;
            }
          }
          leaf shutdown {
            type string;
          }
        }
        leaf shutdown {
          type string;
        }
      }
      container mpls {
        presence "true";
        container auto-bandwidth-multipliers {
          leaf sample-multiplier {
            type string;
          }
          leaf adjust-multiplier {
            type string;
          }
        }
        leaf bypass-resignal-timer {
          type string;
        }
        leaf hold-timer {
          type string;
        }
        leaf cspf-on-loose-hop {
          type empty;
        }
        leaf p2mp-resignal-timer {
          type string;
        }
        leaf least-fill-reoptim-thd {
          type string;
        }
        leaf static-lsp-fast-retry {
          type string;
        }
        list path {
          // NCS patched for predictable order
          ordered-by user;
          key "name";
          leaf name {
            type string;
          }
          list hop {
            // NCS patched for predictable order
            ordered-by user;
            tailf:cli-suppress-mode;
            key "hop-number";
            leaf hop-number {
              type string;
            }
            leaf ip-address {
              tailf:cli-drop-node-name;
              type string;
            }
            leaf mode {
              tailf:cli-drop-node-name;
              type string;
            }
          }
          leaf shutdown {
            type string;
          }
        }
        container pce-report {
          leaf rsvp-te {
            type string;
          }
          leaf sr-te {
            type string;
          }
        }
        container sr-te-resignal {
          leaf resignal-timer {
            type string;
          }
          leaf resignal-on-igp-event {
            type empty;
          }
        }
        list admin-group {
          // NCS patched for predictable order
          ordered-by user;
          tailf:cli-suppress-mode;
          key "name";
          leaf name {
            type string;
          }
          leaf value {
            tailf:cli-drop-node-name;
            type string;
          }
        }
        leaf admin-group-frr {
          type empty;
        }
        leaf resignal-timer {
          type string;
        }
        container srlg-database {
          list router-id {
            // NCS patched for predictable order
            ordered-by user;
            key "ip-address";
            leaf ip-address {
              type string;
            }
            list interface {
              // NCS patched for predictable order
              ordered-by user;
              tailf:cli-suppress-mode;
              key "ip-address srlg-group";
              leaf ip-address {
                type string;
              }
              leaf srlg-group {
                type ncs_compliance_template_string32;
              }
            }
            leaf shutdown {
              type string;
            }
          }
        }
        container srlg-frr {
          presence "present";
          leaf strict {
            type empty;
          }
        }
        list srlg-group {
          // NCS patched for predictable order
          ordered-by user;
          key "name";
          leaf name {
            type string;
          }
          leaf value {
            type string;
          }
        }
        list interface {
          // NCS patched for predictable order
          ordered-by user;
          key "name";
          leaf name {
            type string;
          }
          leaf-list admin-group {
            // NCS patched for predictable order
            ordered-by user;
            type string;
          }
          list label-map {
            // NCS patched for predictable order
            ordered-by user;
            key "in-label";
            leaf in-label {
              type string;
            }
            leaf pop {
              type empty;
            }
            leaf shutdown {
              type string;
            }
          }
          leaf te-metric {
            type string;
          }
          list srlg-group {
            // NCS patched for predictable order
            ordered-by user;
            tailf:cli-suppress-mode;
            key "group-name";
            leaf group-name {
              type ncs_compliance_template_string32;
            }
          }
          leaf shutdown {
            type string;
          }
        }
        container pce-initiated-lsp {
          presence "true";
          container sr-te {
            leaf shutdown {
              type string;
            }
          }
        }
        list lsp-template {
          // NCS patched for predictable order
          ordered-by user;
          key "template";
          leaf template {
            type string;
          }
          leaf mode {
            tailf:cli-drop-node-name;
            type string;
          }
          leaf default-path {
            type string;
          }
          leaf path-computation-method {
            type string;
          }
          leaf label-stack-reduction {
            type empty;
          }
          container fast-reroute {
            leaf frr-method {
              tailf:cli-drop-node-name;
              type string;
            }
            leaf hop-limit {
              type string;
            }
          }
          leaf cspf {
            type empty;
          }
          container egress-statistics {
            leaf collect-stats {
              type empty;
            }
            leaf accounting-policy {
              type string;
            }
          }
          leaf template-id {
            type string;
          }
          container max-sr-labels {
            leaf label-stack-size {
              tailf:cli-drop-node-name;
              type string;
            }
            leaf additional-frr-labels {
              type string;
            }
          }
          leaf pce-report {
            type string;
          }
          leaf shutdown {
            type string;
          }
        }
        container auto-lsp {
          list lsp-template {
            // NCS patched for predictable order
            ordered-by user;
            tailf:cli-suppress-mode;
            key "template";
            leaf template {
              type string;
            }
            leaf-list policy {
              // NCS patched for predictable order
              ordered-by user;
              type string;
            }
          }
        }
        list lsp {
          // NCS patched for predictable order
          ordered-by user;
          key "name";
          leaf name {
            type string;
          }
          leaf label-stack-reduction {
            type empty;
          }
          leaf vprn-auto-bind {
            type string;
          }
          leaf bgp-transport-tunnel {
            type string;
          }
          leaf bgp-shortcut {
            type string;
          }
          leaf entropy-label {
            type string;
          }
          leaf metric {
            type string;
          }
          leaf metric-type {
            type string;
          }
          leaf bypass-only {
            type empty;
          }
          leaf p2mp-lsp {
            type empty;
          }
          leaf mpls-tp {
            type string;
          }
          leaf sr-te {
            type empty;
          }
          list admin-tag {
            // NCS patched for predictable order
            ordered-by user;
            tailf:cli-suppress-mode;
            key "tag";
            leaf tag {
              type ncs_compliance_template_string32;
            }
          }
          leaf to {
            type string;
          }
          leaf from {
            type string;
          }
          leaf-list exclude {
            // NCS patched for predictable order
            ordered-by user;
            type string;
          }
          container auto-bandwidth {
            container adjust-down {
              leaf percent {
                tailf:cli-drop-node-name;
                type string;
              }
              leaf bw {
                type string;
              }
            }
            container adjust-up {
              leaf percent {
                tailf:cli-drop-node-name;
                type string;
              }
              leaf bw {
                type string;
              }
            }
            list fc {
              // NCS patched for predictable order
              ordered-by user;
              tailf:cli-suppress-mode;
              key "fc-name";
              leaf fc-name {
                type ncs_compliance_template_fc-name;
              }
              leaf sampling-weight {
                type string;
              }
            }
            leaf max-bandwidth {
              type string;
            }
            leaf min-bandwidth {
              type string;
            }
            leaf monitor-bandwidth {
              type empty;
            }
            container multipliers {
              leaf sample-multiplier {
                type string;
              }
              leaf adjust-multiplier {
                type string;
              }
            }
            container overflow-limit {
              leaf number {
                tailf:cli-drop-node-name;
                type string;
              }
              leaf threshold {
                type string;
              }
              leaf bw {
                type string;
              }
            }
            container underflow-limit {
              leaf number {
                tailf:cli-drop-node-name;
                type string;
              }
              leaf threshold {
                type string;
              }
              leaf bw {
                type string;
              }
            }
          }
          container cspf {
            presence "true";
            leaf use-te-metric {
              type empty;
            }
          }
          container egress-statistics {
            leaf collect-stats {
              type empty;
            }
            leaf accounting-policy {
              type string;
            }
            leaf shutdown {
              type string;
            }
          }
          leaf adspec {
            type empty;
          }
          container fast-reroute {
            leaf frr-method {
              tailf:cli-drop-node-name;
              type string;
            }
            leaf hop-limit {
              type string;
            }
            leaf node-protect {
              type string;
            }
          }
          container igp-shortcut {
            leaf lfa {
              tailf:cli-drop-node-name;
              type string;
            }
            container relative-metric {
              presence "true";
              leaf offset {
                tailf:cli-drop-node-name;
                type string;
              }
            }
            leaf igp-shortcut {
              tailf:cli-drop-node-name;
              type string;
            }
          }
          list include {
            // NCS patched for predictable order
            ordered-by user;
            tailf:cli-suppress-mode;
            key "group";
            leaf group {
              type string;
            }
          }
          leaf least-fill {
            type empty;
          }
          container max-sr-labels {
            leaf label-stack-size {
              tailf:cli-drop-node-name;
              type string;
            }
            leaf additional-frr-labels {
              type string;
            }
          }
          leaf path-computation-method {
            type string;
          }
          leaf pce-control {
            type empty;
          }
          leaf pce-computation {
            type empty;
          }
          leaf pce-report {
            type string;
          }
          leaf propagate-admin-group {
            type empty;
          }

          grouping router-mpls-lsp-prim-sec-grouping {
            container bfd {
              leaf bfd-template {
                type string;
              }
              leaf bfd-enable {
                type empty;
              }
            }
            leaf path {
              type string;
            }
            leaf-list include {
              // NCS patched for predictable order
              ordered-by user;
              type string;
            }
            leaf-list exclude {
              // NCS patched for predictable order
              ordered-by user;
              type string;
            }
            leaf adaptive {
              type empty;
            }
            leaf bandwidth {
              type string;
            }
            leaf hop-limit {
              type string;
            }
            container priority {
              leaf setup-priority {
                tailf:cli-drop-node-name;
                type string;
              }
              leaf hold-priority {
                tailf:cli-drop-node-name;
                type string;
              }
            }
            leaf shutdown {
              type string;
            }
          }
          list primary {
            // NCS patched for predictable order
            ordered-by user;
            key "path";
            uses router-mpls-lsp-prim-sec-grouping;
          }
          list secondary {
            // NCS patched for predictable order
            ordered-by user;
            key "path";
            uses router-mpls-lsp-prim-sec-grouping;
            leaf standby {
              type empty;
            }
          }
          leaf retry-limit {
            type string;
          }
          leaf retry-timer {
            type string;
          }
          leaf shutdown {
            type string;
          }
        }
        list static-lsp {
          // NCS patched for predictable order
          ordered-by user;
          key "name";
          leaf name {
            type string;
          }
          container push {
            leaf label {
              tailf:cli-drop-node-name;
              type string;
            }
            leaf nexthop {
              type string;
            }
          }
          leaf to {
            type string;
          }
          leaf metric {
            type string;
          }
          leaf shutdown {
            type string;
          }
        }
        container ingress-statistics {
          list lsp {
            // NCS patched for predictable order
            ordered-by user;
            key "name";
            leaf name {
              type string;
            }
            leaf sender {
              type string;
            }
            leaf collect-stats {
              type empty;
            }
            leaf shutdown {
              type empty;
            }
          }
        }
        leaf p2p-active-path-fast-retry {
          type string;
        }
        leaf user-srlg-db {
          type ncs_compliance_template_enable-disable;
        }

        grouping entropy-label-grouping {
          container entropy-label {
            leaf rsvp-te {
              type string;
            }
            leaf sr-te {
              type string;
            }
          }
        }
        uses entropy-label-grouping;
        container tunnel-table-pref {
          leaf rsvp-te {
            type string;
          }
          leaf sr-te {
            type string;
          }
        }
        leaf shutdown {
          type string;
        }
      }
      container mpls-labels {
        leaf bgp-labels-hold-timer {
          type string;
        }
        container sr-labels {
          leaf start {
            type string;
          }
          leaf end {
            type string;
          }
        }
        leaf static-label-range {
          type string;
        }
        list reserved-label-block {
          // NCS patched for predictable order
          ordered-by user;
          key "name";
          leaf name {
            type string;
          }
          container start-label {
            leaf label {
              tailf:cli-drop-node-name;
              type string;
            }
            leaf end-label {
              type string;
            }
          }
        }
      }
      container origin-validation {
        list rpki-session {
          // NCS patched for predictable order
          ordered-by user;
          key "ip-address";
          leaf ip-address {
            type string;
          }
          leaf description {
            type string;
          }
          leaf port {
            type string;
          }
          leaf local-address {
            type string;
          }
          leaf shutdown {
            type string;
          }
        }
      }
      container rsvp {
        presence "present";
        leaf implicit-null-label {
          type empty;
        }
        list interface {
          // NCS patched for predictable order
          ordered-by user;
          key "name";
          leaf name {
            type string;
          }
          leaf bfd-enable {
            type empty;
          }
          leaf hello-interval {
            type string;
          }
          container refresh-reduction {
            leaf reliable-delivery {
              type empty;
            }
          }
          uses ncs_compliance_template_prompted-authentication-key-grouping;
          leaf subscription {
            type string;
          }
          leaf shutdown {
            type string;
          }
        }
        leaf node-id-in-rro {
          type string;
        }
        leaf refresh-reduction-over-bypass {
          type ncs_compliance_template_enable-disable;
        }
        leaf refresh-time {
          type string;
        }
        leaf shutdown {
          type string;
        }
      }
      container router-advertisement {
        list interface {
          // NCS patched for predictable order
          ordered-by user;
          key "ip-int-name";
          leaf ip-int-name {
            type string;
          }
          leaf current-hop-limit {
            type string;
          }
          leaf max-advertisement-interval {
            type string;
          }
          leaf min-advertisement-interval {
            type string;
          }
          leaf mtu {
            type string;
          }
          leaf managed-configuration {
            type empty;
          }
          leaf other-stateful-configuration {
            type empty;
          }
          list prefix {
            // NCS patched for predictable order
            ordered-by user;
            key "ipv6-prefix";
            leaf ipv6-prefix {
              type string;
            }
            leaf preferred-lifetime {
              type string;
            }
            leaf valid-lifetime {
              type string;
            }
          }
          leaf reachable-time {
            type string;
          }
          leaf retransmit-time {
            type string;
          }
          leaf router-lifetime {
            type string;
          }
          leaf use-virtual-mac {
            type empty;
          }
          leaf shutdown {
            type string;
          }
        }
      }
      container mld {
        list interface {
          // NCS patched for predictable order
          ordered-by user;
          key "ip-int-name";
          leaf ip-int-name {
            type string;
          }
          leaf shutdown {
            type string;
          }
        }
        leaf shutdown {
          type string;
        }
      }
      container pcep {
        container pcc {
          leaf keepalive {
            type string;
          }
          leaf dead-timer {
            type string;
          }
          leaf max-srte-pce-init-lsps {
            type string;
          }
          leaf redelegation-timer {
            type string;
          }
          container state-timer {
            leaf seconds {
              tailf:cli-drop-node-name;
              type string;
            }
            leaf action {
              type string;
            }
          }
          leaf local-address {
            type string;
          }
          list peer {
            // NCS patched for predictable order
            ordered-by user;
            key "address";
            leaf address {
              type string;
            }
            leaf preference {
              type string;
            }
            leaf route-preference {
              type string;
            }
            leaf shutdown {
              type string;
            }
          }
          leaf shutdown {
            type string;
          }
        }
      }
      container route-next-hop-policy {
        list template {
          // NCS patched for predictable order
          ordered-by user;
          key "template-name";
          leaf template-name {
            type string;
          }
          leaf protection-type {
            type string;
          }
          leaf nh-type {
            type string;
          }
          leaf srlg-enable {
            type empty;
          }
        }
      }
      container policy-options {
        list prefix-list {
          // NCS patched for predictable order
          ordered-by user;
          key "name";
          leaf name {
            type string;
          }
          list prefix {
            // NCS patched for predictable order
            ordered-by user;
            tailf:cli-suppress-mode;
            key "ip-prefix";
            leaf ip-prefix {
              type string;
            }
            leaf exact {
              type empty;
            }
            leaf longer {
              type empty;
            }
            leaf through {
              type string;
            }
            leaf prefix-length-range {
              type string;
            }
          }
        }
        list community {
          // NCS patched for predictable order
          ordered-by user;
          key "name";
          leaf name {
            type string;
          }
          leaf-list members {
            // NCS patched for predictable order
            ordered-by user;
            type string;
          }
          container expression {
            leaf expression {
              tailf:cli-drop-node-name;
              type string;
            }
            leaf exact {
              type empty;
            }
          }
        }
        list alt-community {
          // NCS patched for predictable order
          ordered-by user;
          tailf:cli-suppress-mode;
          tailf:alt-name "community";
          key "name";
          leaf name {
            type string;
          }
          leaf-list members {
            // NCS patched for predictable order
            ordered-by user;
            type string;
          }
          container expression {
            leaf expression {
              tailf:cli-drop-node-name;
              type string;
            }
            leaf exact {
              type empty;
            }
          }
        }
        list damping {
          // NCS patched for predictable order
          ordered-by user;
          key "name";
          leaf name {
            type string;
          }
          leaf half-life {
            type string;
          }
          leaf max-suppress {
            type string;
          }
          leaf reuse {
            type string;
          }
          leaf suppress {
            type string;
          }
        }
        list policy-statement {
          // NCS patched for predictable order
          ordered-by user;
          key "name";
          leaf name {
            type string;
          }
          leaf description {
            type string;
          }
          container default-action {
            uses ncs_compliance_template_policy-options-default-action-grouping;
          }
          list entry {
            // NCS patched for predictable order
            ordered-by user;
            key "id";
            leaf id {
              type string;
            }
            leaf description {
              type string;
            }
            container conditional-expression {
              presence "true";
              leaf route-exists {
                type string;
              }
            }
            container action {
              presence "true";
              leaf mode {
                tailf:cli-drop-node-name;
                type string;
              }
              uses ncs_compliance_template_policy-option-action-params-grouping;
              uses ncs_compliance_template_policy-options-action-fc-grouping;
            }
            leaf action-reject {
              type empty;
            }
            container from {
              presence "true";
              leaf area {
                type string;
              }
              leaf as-path {
                type string;
              }
              container as-path-length {
                leaf length {
                  tailf:cli-drop-node-name;
                  type string;
                }
                leaf operator {
                  tailf:cli-drop-node-name;
                  type string;
                }
              }
              leaf as-path-group {
                type string;
              }
              container community {
                leaf expression {
                  type empty;
                }
                leaf community {
                  tailf:cli-drop-node-name;
                  type string;
                }
              }
              container community-count {
                leaf count {
                  tailf:cli-drop-node-name;
                  type string;
                }
                leaf op {
                  tailf:cli-drop-node-name;
                  type string;
                }
                leaf val {
                  tailf:cli-drop-node-name;
                  type string;
                }
              }
              leaf external {
                type empty;
              }
              leaf evpn-type {
                type string;
              }
              container metric {
                leaf value {
                  tailf:cli-drop-node-name;
                  type string;
                }
                leaf comparator {
                  tailf:cli-drop-node-name;
                  type string;
                }
              }
              leaf next-hop {
                type string;
              }
              leaf-list family {
                // NCS patched for predictable order
                ordered-by user;
                type ncs_compliance_template_family-names-type;
              }
              leaf group-address {
                type string;
              }
              leaf host-ip {
                type string;
              }
              leaf interface {
                type string;
              }
              leaf level {
                type string;
              }
              container neighbor {
                choice a {
                  leaf ip-address {
                    tailf:cli-drop-node-name;
                    type string;
                  }
                  leaf prefix-list {
                    type string;
                  }
                }
              }
              leaf origin {
                type string;
              }
              leaf origin-validation-state {
                type string;
              }
              leaf path-type {
                type string;
              }
              leaf policy {
                type string;
              }
              leaf-list prefix-list {
                // NCS patched for predictable order
                ordered-by user;
                type string;
              }
              container protocol {
                leaf-list protocol {
                  // NCS patched for predictable order
                  ordered-by user;
                  tailf:cli-drop-node-name;
                  type ncs_compliance_template_policy-protocol;
                }
                choice instance-all {
                  leaf instance {
                    type string;
                  }
                  leaf all {
                    type empty;
                  }
                }
              }
              leaf source-address {
                type string;
              }
              leaf state {
                type string;
              }
              leaf tag {
                type ncs_compliance_template_policy-options-tag;
              }
              leaf type {
                type string;
              }
            }
            container to {
              presence "true";
              leaf level {
                type string;
              }
              leaf neighbor {
                type string;
              }
              leaf-list prefix-list {
                // NCS patched for predictable order
                ordered-by user;
                type string;
              }
              leaf-list protocol {
                // NCS patched for predictable order
                ordered-by user;
                type string;
              }
            }
          }
        }
        list as-path {
          // NCS patched for predictable order
          ordered-by user;
          key "name";
          leaf name {
            type string;
          }
          leaf expression {
            type string;
          }
        }
        list alt-as-path {
          // NCS patched for predictable order
          ordered-by user;
          tailf:cli-suppress-mode;
          tailf:alt-name "as-path";
          key "name";
          leaf name {
            type string;
          }
          leaf expression {
            type string;
          }
          leaf regexp {
            tailf:cli-drop-node-name;
            type string;
          }
        }
        list as-path-group {
          // NCS patched for predictable order
          ordered-by user;
          key "name";
          leaf name {
            type string;
          }
          list entry {
            // NCS patched for predictable order
            ordered-by user;
            tailf:cli-suppress-mode;
            key "entry-id";
            leaf entry-id {
              type string;
            }
            leaf expression {
              type string;
            }
          }
        }
      }
      container pim {
        list interface {
          // NCS patched for predictable order
          ordered-by user;
          key "ip-int-name";
          leaf ip-int-name {
            type string;
          }
          leaf assert-period {
            type string;
          }
          container bfd-enable {
            presence "true";
            leaf bfd-enable {
              tailf:cli-drop-node-name;
              type string;
            }
          }
          leaf bsm-check-rtr-alert {
            type empty;
          }
          leaf hello-interval {
            type string;
          }
          leaf hello-multiplier {
            type string;
          }
          leaf improved-assert {
            type string;
          }
          leaf instant-prune-echo {
            type empty;
          }
          leaf ipv4-multicast-disable {
            type string;
          }
          leaf ipv6-multicast-disable {
            type string;
          }
          leaf max-groups {
            type string;
          }
          uses ncs_compliance_template_mcac-grouping;
          leaf multicast-senders {
            type string;
          }
          leaf-list p2mp-ldp-tree-join {
            // NCS patched for predictable order
            ordered-by user;
            type string;
          }
          leaf priority {
            type string;
          }
          container sticky-dr {
            leaf priority {
              type string;
            }
            leaf three-way-hello {
              type empty;
            }
            leaf tracking-support {
              type empty;
            }
          }
          leaf shutdown {
            type string;
          }
        }
        leaf enable-mdt-spt {
          type empty;
        }
        leaf ipv4-multicast-disable {
          type string;
        }
        leaf ipv6-multicast-disable {
          type string;
        }
        leaf lag-usage-optimization {
          type empty;
        }
        leaf multicast-fast-failover {
          type empty;
        }
        leaf multicast6-fast-failover {
          type empty;
        }
        container rp {
          list anycast {
            // NCS patched for predictable order
            ordered-by user;
            key "rp-ip-address";
            leaf rp-ip-address {
              type string;
            }
            list rp-set-peer {
              // NCS patched for predictable order
              ordered-by user;
              tailf:cli-suppress-mode;
              key "ip-address";
              leaf ip-address {
                tailf:cli-drop-node-name;
                type string;
              }
            }
          }
          leaf-list bootstrap-import {
            // NCS patched for predictable order
            ordered-by user;
            type string;
          }
          leaf-list bootstrap-export {
            // NCS patched for predictable order
            ordered-by user;
            type string;
          }
          container static {
            list address {
              // NCS patched for predictable order
              ordered-by user;
              key "ip-address";
              leaf ip-address {
                type string;
              }
              list group-prefix {
                // NCS patched for predictable order
                ordered-by user;
                tailf:cli-suppress-mode;
                key "grp-ip-addr";
                leaf grp-ip-addr {
                  tailf:cli-drop-node-name;
                  type string;
                }
              }
              leaf override {
                type empty;
              }
            }
          }
          container bsr-candidate {
            leaf address {
              type string;
            }
            leaf hash-mask-len {
              type string;
            }
            leaf priority {
              type string;
            }
            leaf shutdown {
              type string;
            }
          }
          container rp-candidate {
            leaf address {
              type string;
            }
            list group-range {
              // NCS patched for predictable order
              ordered-by user;
              tailf:cli-suppress-mode;
              key "grp-ip-addr";
              leaf grp-ip-addr {
                type string;
              }
            }
            leaf holdtime {
              type string;
            }
            leaf priority {
              type string;
            }
            leaf shutdown {
              type string;
            }
          }
        }
        leaf rpf-table {
          type string;
        }
        uses ncs_compliance_template_pim-common-grouping;
        container ssm-groups {
          list group-range {
            // NCS patched for predictable order
            ordered-by user;
            tailf:cli-suppress-mode;
            key "prefix";
            leaf prefix {
              type string;
            }
          }
        }
        leaf shutdown {
          type string;
        }
      }
      container sgt-qos {
        list application {
          // NCS patched for predictable order
          ordered-by user;
          tailf:cli-suppress-mode;
          key "app-name";
          leaf app-name {
            type string;
          }
          choice choice {
            leaf dscp {
              type string;
            }
            leaf dot1p {
              type string;
            }
          }
        }
        list dscp {
          // NCS patched for predictable order
          ordered-by user;
          tailf:cli-suppress-mode;
          key "dscp-name";
          leaf dscp-name {
            type ncs_compliance_template_dscp-type;
          }
          leaf fc {
            type ncs_compliance_template_fc-name;
          }
        }
      }
      container ttl-propagate {
        leaf vprn-local {
          type string;
        }
        leaf vprn-transit {
          type string;
        }
      }
      container twamp-light {
        container reflector {
          presence "true";
          leaf description {
            type string;
          }
          leaf udp-port {
            type string;
          }
          leaf shutdown {
            type string;
          }
          list prefix {
            // NCS patched for predictable order
            ordered-by user;
            leaf description {
              type string;
            }
            key "ip-prefix";
            leaf ip-prefix {
              type string;
            }
          }
        }
      }
      container weighted-ecmp {
        presence "true";
        leaf strict {
          type empty;
        }
      }
    }
    container aaa {
      leaf radius-coa-port {
        type string;
      }
      list radius-script-policy {
        // NCS patched for predictable order
        ordered-by user;
        key "policy-name";
        leaf policy-name {
          type ncs_compliance_template_string32;
        }
        leaf description {
          type string;
        }
        container primary {
          leaf script-url {
            type string;
          }
          leaf shutdown {
            type string;
          }
        }
      }
      list radius-server-policy {
        // NCS patched for predictable order
        ordered-by user;
        key "policy-name";
        leaf policy-name {
          type ncs_compliance_template_string32;
        }
        leaf description {
          type string;
        }
        leaf acct-on-off {
          type empty;
        }
        leaf acct-request-script-policy {
          type ncs_compliance_template_string32;
        }
        leaf python-policy {
          type ncs_compliance_template_string32;
        }
        leaf accept-script-policy {
          type ncs_compliance_template_string32;
        }
        leaf auth-request-script-policy {
          type ncs_compliance_template_string32;
        }
        container servers {
          leaf access-algorithm {
            type string;
          }
          container buffering {

            grouping acct-grouping {
              leaf min {
                type string;
              }
              leaf max {
                type string;
              }
              leaf lifetime {
                type string;
              }
            }
            container acct-interim {
              uses acct-grouping;
            }
            container acct-start {
              uses acct-grouping;
            }
            container acct-stop {
              uses acct-grouping;
            }
          }
          container health-check {
            container down-timeout {
              leaf min {
                type string;
              }
              leaf sec {
                type string;
              }
            }
          }
          container hold-down-time {
            leaf sec {
              type string;
            }
            leaf min {
              type string;
            }
            leaf hrs {
              type string;
            }
            leaf days {
              type string;
            }
          }
          leaf retry {
            type string;
          }
          container timeout {
            leaf min {
              type string;
            }
            leaf sec {
              type string;
            }
          }
          leaf router {
            type string;
          }
          list server {
            // NCS patched for predictable order
            ordered-by user;
            tailf:cli-suppress-mode;
            key "server-index";
            leaf server-index {
              type string;
            }
            leaf name {
              type ncs_compliance_template_string32;
            }
          }
          leaf source-address {
            type string;
          }
        }
      }
      list diameter-peer-policy {
        // NCS patched for predictable order
        ordered-by user;
        key "peer-policy-name";
        leaf peer-policy-name {
          type ncs_compliance_template_string32;
        }
        leaf-list applications {
          // NCS patched for predictable order
          ordered-by user;
          type string;
        }
        leaf origin-host {
          type string;
        }
        leaf origin-realm {
          type string;
        }
        leaf source-address {
          type string;
        }
        list peer {
          // NCS patched for predictable order
          ordered-by user;
          key "name";
          leaf name {
            type ncs_compliance_template_string32;
          }
          leaf destination-host {
            type string;
          }
          leaf destination-realm {
            type string;
          }
          leaf address {
            type string;
          }
          container transport {
            leaf tcp {
              type empty;
            }
            leaf port {
              type string;
            }
          }
          leaf shutdown {
            type string;
          }
        }
      }
    }
    container system {
      container alarms {
        leaf max-cleared {
          type string;
        }
        leaf shutdown {
          type string;
        }
      }
      list alarm-contact-input {
        // NCS patched for predictable order
        ordered-by user;
        key "id";
        leaf id {
          type string;
        }
        leaf description {
          type string;
        }
        leaf alarm-output-severity {
          type string;
        }
        leaf trigger-alarm-msg {
          type string;
        }
        leaf shutdown {
          type string;
        }
      }
      container alarm-contact-output {
        presence "true";
        leaf shutdown {
          type string;
        }
      }
      container bluetooth {
        list module {
          // NCS patched for predictable order
          ordered-by user;
          key "name";
          leaf name {
            type string;
          }
        }
        leaf power {
          type string;
        }
        leaf advertising-timeout {
          type string;
        }
      }
      container fp {
        container options {
          container mpls {
            container entropy-label {
              leaf shutdown {
                type string;
              }
            }
          }
          container services {
            container vpls-evpn-mpls {
              leaf shutdown {
                type string;
              }
            }
          }
          container qos {
            container bum-policers {
              leaf shutdown {
                type string;
              }
            }
            container dscp-transparency {
              leaf shutdown {
                type string;
              }
            }
            container fc-4-profile {
              leaf shutdown {
                type string;
              }
            }
          }
          container router {
            container ecmp {
              leaf shutdown {
                type string;
              }
            }
          }
        }
      }
      container grpc {
        leaf allow-unsecure-connection {
          type empty;
        }
        container gnmi {
          leaf auto-config-save {
            type empty;
          }
          leaf shutdown {
            type string;
          }
        }
        container rib-api {
          leaf shutdown {
            type string;
          }
        }
        container md-cli {
          leaf shutdown {
            type string;
          }
        }
        container tcp-keepalive {
          leaf shutdown {
            type string;
          }
        }
        leaf tls-server-profile {
          type string;
        }
        leaf shutdown {
          type string;
        }
      }
      container satellite {
        list port-template {
          // NCS patched for predictable order
          ordered-by user;
          key "name";
          leaf name {
            type string;
          }
          leaf sat-type {
            // NCS drop mandatory statement
            type string;
          }
          list port {
            // NCS patched for predictable order
            ordered-by user;
            key "port-id";
            leaf port-id {
              type string;
            }
            leaf role {
              type string;
            }
          }
          leaf shutdown {
            type string;
          }
        }
        list eth-sat {
          // NCS patched for predictable order
          ordered-by user;
          key "id";
          leaf id {
            type string;
          }
          leaf description {
            type string;
          }
          leaf mac-address {
            type ncs_compliance_template_ieee-mac;
          }
          container sat-type {
            leaf type {
              tailf:cli-drop-node-name;
              type string;
            }
            container dynamic-uplink {
              leaf uplink-distribution {
                type string;
              }
            }
          }
          leaf client-down-delay {
            type string;
          }
          leaf feature {
            type string;
          }
          leaf enable-console-access {
            type string;
          }
          leaf software-repository {
            type string;
          }
          leaf sync-e {
            type empty;
          }
          leaf ptp-tc {
            type empty;
          }
          list port-map {
            // NCS patched for predictable order
            ordered-by user;
            tailf:cli-suppress-mode;
            key "client-port-id";
            leaf client-port-id {
              type string;
            }
            leaf primary {
              type string;
            }
            leaf secondary {
              type string;
            }
          }
          leaf shutdown {
            type string;
          }
        }
      }
      container port-topology {
        list port {
          // NCS patched for predictable order
          ordered-by user;
          tailf:cli-suppress-mode;
          // NCS drop tailf-common:cli-diff-create-before statement
          key "port-id";
          leaf port-id {
            type string;
          }
          leaf to {
            type string;
          }
        }
      }
      list power-shelf {
        // NCS patched for predictable order
        ordered-by user;
        key "power-shelf-id";
        leaf power-shelf-id {
          type string;
        }
        leaf description {
          type string;
        }
        leaf power-shelf-type {
          type string;
        }
        list power-module {
          // NCS patched for predictable order
          ordered-by user;
          key "power-module-id";
          leaf power-module-id {
            type string;
          }
          leaf power-module-type {
            type string;
          }
          leaf shutdown {
            type string;
          }
        }
        leaf shutdown {
          type string;
        }
      }
      container ip {
        leaf enforce-unique-if-index {
          type empty;
        }
      }
      list file-transmission-profile {
        // NCS patched for predictable order
        ordered-by user;
        key "name";
        leaf name {
          type ncs_compliance_template_string32;
        }
        leaf ipv4-source-address {
          type string;
        }
        container router {
          choice router {
            leaf router-name {
              tailf:cli-drop-node-name;
              type ncs_compliance_template_router-type;
            }
            leaf service {
              type string;
            }
          }
        }
      }
      container ptp {
        list alternate-profile {
          // NCS patched for predictable order
          ordered-by user;
          key "alternate-profile-name";
          leaf alternate-profile-name {
            type string;
          }
          leaf shutdown {
            type string;
          }
        }
        list clock {
          // NCS patched for predictable order
          ordered-by user;
          key "clock-id";
          leaf clock-id {
            type string;
          }
          leaf clock-mda {
            type string;
          }
          container clock-type {
            choice clock-type {
              leaf ordinary {
                type string;
              }
              leaf boundary {
                type empty;
              }
              leaf transparent-e2e {
                type empty;
              }
            }
          }
          leaf domain {
            type string;
          }
          leaf dynamic-peers {
            type empty;
          }
          leaf priority1 {
            type string;
          }
          leaf priority2 {
            type string;
          }
          leaf profile {
            type string;
          }
          leaf source-interface {
            type string;
          }
          list ptp-port {
            // NCS patched for predictable order
            ordered-by user;
            key "port-id";
            leaf port-id {
              type string;
            }
            leaf anno-rx-timeout {
              type string;
            }
            leaf log-anno-interval {
              type string;
            }
            leaf log-sync-interval {
              type string;
            }
            list peer {
              // NCS patched for predictable order
              ordered-by user;
              key "peer-id";
              leaf peer-id {
                type string;
              }
              leaf description {
                type string;
              }
              leaf ip-address {
                type string;
              }
            }
            leaf unicast-negotiate {
              type string;
            }
            leaf shutdown {
              type string;
            }
          }
          leaf shutdown {
            type string;
          }
        }
        container clock-type {
          leaf type {
            tailf:cli-drop-node-name;
            type string;
          }
          leaf role {
            tailf:cli-drop-node-name;
            type string;
          }
        }
        leaf domain {
          type string;
        }
        leaf domain-alt1 {
          tailf:alt-name "domain";
          type string;
        }
        leaf domain-alt2 {
          tailf:alt-name "domain";
          type string;
        }
        leaf domain-alt3 {
          tailf:alt-name "domain";
          type string;
        }
        leaf profile {
          type string;
        }
        list peer {
          // NCS patched for predictable order
          ordered-by user;
          key "ip-address";
          leaf ip-address {
            type string;
          }
          leaf local-priority {
            type string;
          }
          leaf shutdown {
            type string;
          }
        }
        list port {
          // NCS patched for predictable order
          ordered-by user;
          key "port-id";
          leaf port-id {
            type string;
          }
          leaf alternate-profile {
            type string;
          }
          leaf master-only {
            type string;
          }
          leaf address {
            type string;
          }
          leaf local-priority {
            type string;
          }
          leaf shutdown {
            type string;
          }
        }
        leaf shutdown {
          type string;
        }
      }
      container resource-profile {
        container ingress-internal-tcam {
          presence "true";
          list eth-cfm {
            // NCS patched for predictable order
            ordered-by user;
            key "id";
            leaf id {
              type string;
            }
            leaf down-mep {
              type string;
            }
          }
          leaf qos-sap-egress-resource {
            type string;
          }
          list qos-sap-ingress-resource {
            // NCS patched for predictable order
            ordered-by user;
            key "id";
            leaf id {
              type string;
            }
          }
          leaf qos-network-ingress-resource {
            type string;
          }
          list acl-sap-ingress {
            // NCS patched for predictable order
            ordered-by user;
            key "id";
            leaf id {
              type string;
            }
          }
          container qos {
            presence "true";
          }
        }
        container egress-internal-tcam {
          presence "true";
          list qos-sap-egress-resource {
            // NCS patched for predictable order
            ordered-by user;
            key "id";
            leaf id {
              type string;
            }
          }
          list qos-sap-ingress-resource {
            // NCS patched for predictable order
            ordered-by user;
            key "id";
            leaf id {
              type string;
            }
          }
          list acl-sap-egress {
            // NCS patched for predictable order
            ordered-by user;
            key "id";
            leaf id {
              type string;
            }
          }
        }
        leaf g8032-control-sap-tags {
          type string;
        }
        container router {
          presence "true";
        }
        container decommission {
          presence "true";
        }
      }
      container resource {
        list ecmp-profile {
          // NCS patched for predictable order
          ordered-by user;
          tailf:cli-suppress-mode;
          key "id";
          leaf id {
            type string;
          }
          leaf type {
            tailf:cli-drop-node-name;
            type string;
          }
          leaf links {
            type string;
          }
          leaf groups {
            type string;
          }
        }
      }
      container atm {
        leaf atm-location-id {
          type string;
        }
        container oam {
          leaf loopback-period {
            type string;
          }
          leaf retry-down {
            type string;
          }
          leaf retry-up {
            type string;
          }
        }
      }
      leaf boot-bad-exec {
        type string;
      }
      leaf boot-good-exec {
        type string;
      }
      list chassis-mode {
        // NCS patched for predictable order
        ordered-by user;
        key "chassis-mode";
        leaf chassis-mode {
          type string;
        }
        leaf force {
          type empty;
        }
        list power-supply {
          // NCS patched for predictable order
          ordered-by user;
          tailf:cli-suppress-mode;
          key "power-supply-id power-supply-type";
          leaf power-supply-id {
            type string;
          }
          leaf power-supply-type {
            type string;
          }
        }
      }
      leaf clli-code {
        type string;
      }
      leaf config-backup {
        type string;
      }
      leaf contact {
        type string;
      }
      leaf coordinates {
        type string;
      }
      container cron {
        uses ncs_compliance_template_cron-schedule-grouping;
      }
      container dns {
        container address-pref {
          choice choice {
            leaf ipv4-only {
              type empty;
            }
            leaf ipv6-first {
              type empty;
            }
          }
        }
      }
      leaf enable-icmp-vse {
        type empty;
      }
      container ethernet {
        container efm-oam {
          leaf grace-tx-enable {
            type empty;
          }
        }
        leaf new-qinq-untagged-sap {
          type empty;
        }
      }
      leaf l4-load-balancing {
        type empty;
      }
      leaf lacp-system-priority {
        type string;
      }
      container lldp {
        leaf message-fast-tx {
          type string;
        }
        leaf message-fast-tx-init {
          type string;
        }
        leaf reinit-delay {
          type string;
        }
        leaf tx-credit-max {
          type string;
        }
        leaf tx-hold-multiplier {
          type string;
        }
        leaf tx-interval {
          type string;
        }
        leaf notification-interval {
          type string;
        }
        leaf shutdown {
          type string;
        }
      }
      container load-balancing {
        leaf l4-load-balancing {
          type empty;
        }
        container hash-poly {
          leaf ecmp {
            type string;
          }
          leaf lag {
            type string;
          }
        }
        leaf lsr-load-balancing {
          type string;
        }
        leaf mc-enh-load-balancing {
          type empty;
        }
        leaf service-id-lag-hashing {
          type empty;
        }
        leaf system-ip-load-balancing {
          type empty;
        }
        container hash-algorithm {
          list polynomial {
            // NCS patched for predictable order
            ordered-by user;
            tailf:cli-suppress-mode;
            key "ptype";
            leaf ptype {
              type string;
            }
            leaf pval {
              tailf:cli-drop-node-name;
              type string;
            }
          }
        }
      }
      leaf location {
        type string;
      }
      container login-control {
        leaf exponential-backoff {
          type empty;
        }
        container ftp {
          leaf inbound-max-sessions {
            type string;
          }
        }
        leaf idle-timeout {
          type string;
        }
        leaf login-banner {
          type empty;
        }
        container motd {
          choice choice {
            leaf url {
              type string;
            }
            leaf text {
              type string;
            }
          }
        }
        container pre-login-message {
          presence "present";
          leaf login-text-string {
            tailf:cli-drop-node-name;
            type string;
          }
          leaf name {
            type empty;
          }
        }
        container ssh {
          leaf disable-graceful-shutdown {
            type empty;
          }
          leaf inbound-max-sessions {
            type string;
          }
          leaf outbound-max-sessions {
            type string;
          }
          leaf ttl-security {
            type string;
          }
        }
        container telnet {
          leaf enable-graceful-shutdown {
            type empty;
          }
          leaf inbound-max-sessions {
            type string;
          }
          leaf outbound-max-sessions {
            type string;
          }
          leaf ttl-security {
            type string;
          }
        }
      }
      container loopback-no-svc-port {
        leaf mac-swap {
          type empty;
        }
        leaf port-id {
          tailf:cli-drop-node-name;
          type string;
        }
      }
      container lsr-load-balancing {
        choice choice {
          leaf lbl-only {
            type empty;
          }
          leaf lbl-ip {
            type empty;
          }
          leaf ip-only {
            type empty;
          }
        }
      }
      container management-interface {
        container remote-management {
          leaf shutdown {
            type string;
          }
        }
        container cli {
          container classic-cli {
            leaf allow-immediate {
              type string;
            }
          }
          leaf-list cli-engine {
            // NCS patched for predictable order
            ordered-by user;
            type string;
          }
          container md-cli {
            leaf auto-config-save {
              type empty;
            }
            container environment {
              container command-completion {
                leaf enter {
                  type string;
                }
                leaf space {
                  type string;
                }
                leaf tab {
                  type string;
                }
              }
              container console {
                leaf length {
                  type string;
                }
                leaf width {
                  type string;
                }
              }
              container message-severity-level {
                leaf cli {
                  type string;
                }
              }
              leaf more {
                type string;
              }
              container progress-indicator {
                leaf delay {
                  type string;
                }
                leaf shutdown {
                  type string;
                }
              }
              container prompt {
                leaf context {
                  type string;
                }
                leaf newline {
                  type string;
                }
                leaf timestamp {
                  type empty;
                }
                leaf uncommitted-changes-indicator {
                  type string;
                }
              }
              leaf time-display {
                type string;
              }
            }
          }
        }
        leaf configuration-mode {
          type string;
        }
        leaf schema-path {
          type string;
        }
        container yang-modules {
          leaf base-r13-modules {
            type string;
          }
          leaf nokia-modules {
            type string;
          }
          leaf nokia-submodules {
            type string;
          }
          leaf nokia-combined-modules {
            type string;
          }
        }
      }
      leaf mc-enh-load-balancing {
        type empty;
      }
      leaf mixed-mode {
        type empty;
      }
      leaf name {
        type string;
      }
      container netconf {
        leaf auto-config-save {
          type empty;
        }
        container capabilities {
          leaf candidate {
            type string;
          }
          leaf writable-running {
            type empty;
          }
        }
        leaf shutdown {
          type string;
        }
      }
      container persistence {
        container ancp {
          leaf description {
            type string;
          }
          leaf location {
            type string;
          }
        }
        container application-assurance {
          leaf description {
            type string;
          }
          leaf location {
            type string;
          }
        }
        container dhcp-server {
          leaf description {
            type string;
          }
          leaf location {
            type string;
          }
        }
        container nat-port-forwarding {
          leaf description {
            type string;
          }
          leaf location {
            type string;
          }
        }
        container subscriber-mgmt {
          leaf description {
            type string;
          }
          leaf location {
            type string;
          }
        }
      }
      list power-module {
        // NCS patched for predictable order
        ordered-by user;
        key "power-module-id";
        leaf power-module-id {
          type string;
        }
        leaf power-module-type {
          type string;
        }
        leaf shutdown {
          type string;
        }
      }
      container power-management {
        list peq {
          // NCS patched for predictable order
          ordered-by user;
          key "id";
          leaf id {
            type string;
          }
          leaf chassis {
            type string;
          }
          leaf peq-type {
            type string;
          }
          leaf shutdown {
            type string;
          }
        }
        leaf mode {
          type string;
        }
        leaf power-safety-alert {
          type string;
        }
        leaf power-safety-level {
          type string;
        }
      }
      container script-control {
        list script {
          // NCS patched for predictable order
          ordered-by user;
          key "script-name";
          leaf script-name {
            type ncs_compliance_template_string32;
          }
          leaf owner {
            type ncs_compliance_template_string32;
          }
          leaf description {
            type string;
          }
          leaf location {
            type string;
          }
          leaf shutdown {
            type string;
          }
        }
        list script-policy {
          // NCS patched for predictable order
          ordered-by user;
          key "script-name";
          leaf script-name {
            type ncs_compliance_template_string32;
          }
          leaf owner {
            type ncs_compliance_template_string32;
          }
          leaf expire-time {
            type ncs_compliance_template_expire-time;
          }
          leaf lifetime {
            type ncs_compliance_template_expire-time;
          }
          leaf max-completed {
            type string;
          }
          leaf results {
            type string;
          }
          container script {
            leaf script-name {
              tailf:cli-drop-node-name;
              type ncs_compliance_template_string32;
            }
            leaf owner {
              type ncs_compliance_template_string32;
            }
          }
          leaf shutdown {
            type string;
          }
        }
      }
      container snmp {
        leaf engineID {
          type string;
        }
        leaf general-port {
          type string;
        }
        leaf packet-size {
          type string;
        }
        container streaming {
          leaf shutdown {
            type string;
          }
        }
        leaf shutdown {
          type string;
        }
      }
      container rollback {
        leaf local-max-checkpoints {
          type string;
        }
        leaf remote-max-checkpoints {
          type string;
        }
        leaf rescue-location {
          type string;
        }
        leaf rollback-location {
          type string;
        }
      }
      leaf system-ip-load-balancing {
        type empty;
      }
      container time {
        leaf prefer-local-time {
          type empty;
        }
        container ntp {
          leaf authentication-check {
            type string;
          }
          list authentication-key {
            // NCS patched for predictable order
            ordered-by user;
            tailf:cli-suppress-mode;
            key "key-id";
            leaf key-id {
              type string;
            }
            leaf key {
              type string;
            }
            leaf hash {
              tailf:cli-drop-node-name;
              type ncs_compliance_template_hash-method;
            }
            leaf type {
              type string;
            }
          }
          container ntp-server {
            presence "true";
            leaf authenticate {
              type empty;
            }
          }
          list server {
            // NCS patched for predictable order
            ordered-by user;
            tailf:cli-suppress-mode;
            key "address";
            leaf address {
              type string;
            }
            leaf key {
              type string;
            }
            leaf router {
              type ncs_compliance_template_router-type;
            }
            leaf version {
              type string;
            }
            leaf prefer {
              type empty;
            }
          }
          leaf shutdown {
            type string;
          }
        }
        container sntp {
          leaf broadcast-client {
            type empty;
          }
          list server-address {
            // NCS patched for predictable order
            ordered-by user;
            tailf:cli-suppress-mode;
            key "ip";
            leaf ip {
              type string;
            }
            leaf version {
              type string;
            }
            leaf mode {
              tailf:cli-drop-node-name;
              type string;
            }
            leaf interval {
              type string;
            }
          }
          leaf shutdown {
            type string;
          }
        }
        container zone {
          leaf name {
            tailf:cli-drop-node-name;
            type string;
          }
          leaf time {
            tailf:cli-drop-node-name;
            type string;
          }
        }
        list dst-zone {
          // NCS patched for predictable order
          ordered-by user;
          key "name";
          leaf name {
            type string;
          }
          container start {
            uses ncs_compliance_template_time-stamp;
          }
          container end {
            uses ncs_compliance_template_time-stamp;
          }
          leaf offset {
            type string;
          }
        }
      }
      container thresholds {
        container rmon {
          list alarm {
            // NCS patched for predictable order
            ordered-by user;
            tailf:cli-suppress-mode;
            key "rmon-alarm-id";
            leaf rmon-alarm-id {
              type string;
            }
            leaf variable-oid {
              type string;
            }
            leaf interval {
              type string;
            }
            leaf sample-type {
              tailf:cli-drop-node-name;
              type string;
            }
            leaf startup-alarm {
              type string;
            }
            leaf rising-event {
              type string;
            }
            leaf rising-threshold {
              type string;
            }
            leaf falling-event {
              type string;
            }
            leaf falling-threshold {
              type string;
            }
            leaf owner {
              type string;
            }
          }
          list event {
            // NCS patched for predictable order
            ordered-by user;
            tailf:cli-suppress-mode;
            key "rmon-event-id";
            leaf rmon-event-id {
              type string;
            }
            leaf event-type {
              tailf:cli-drop-node-name;
              type string;
            }
            leaf description {
              type string;
            }
            leaf owner {
              type string;
            }
          }
        }

        grouping memory-use-grouping {
          leaf rising-threshold {
            type string;
          }
          leaf falling-threshold {
            type string;
          }
          leaf interval {
            type string;
          }
          leaf rmon-event-type {
            tailf:cli-drop-node-name;
            type string;
          }
          leaf startup-alarm {
            type string;
          }
        }
        container memory-use-alarm {
          uses memory-use-grouping;
        }
        container memory-use-warn {
          uses memory-use-grouping;
        }

        grouping cflash-cap-grouping {
          leaf cflash-id {
            type string;
          }
          leaf rising-threshold {
            type string;
          }
          leaf falling-threshold {
            type string;
          }
          leaf interval {
            type string;
          }
          leaf rmon-event-type {
            tailf:cli-drop-node-name;
            type string;
          }
          leaf startup-alarm {
            type string;
          }
        }
        list cflash-cap-alarm {
          // NCS patched for predictable order
          ordered-by user;
          tailf:cli-suppress-mode;
          key "cflash-id";
          uses cflash-cap-grouping;
        }
        list cflash-cap-alarm-pct {
          // NCS patched for predictable order
          ordered-by user;
          tailf:cli-suppress-mode;
          key "cflash-id";
          uses cflash-cap-grouping;
        }
        list cflash-cap-warn {
          // NCS patched for predictable order
          ordered-by user;
          tailf:cli-suppress-mode;
          key "cflash-id";
          uses cflash-cap-grouping;
        }
        container kb-memory-use-alarm {
          leaf rising-threshold {
            type string;
          }
          leaf falling-threshold {
            type string;
          }
          leaf interval {
            type string;
          }
          leaf rmon-event-type {
            tailf:cli-drop-node-name;
            type string;
          }
          leaf startup-alarm {
            type string;
          }
        }
      }
      list power-supply {
        // NCS patched for predictable order
        ordered-by user;
        tailf:cli-suppress-mode;
        key "power-supply-id";
        leaf power-supply-id {
          type string;
        }
        leaf type {
          tailf:cli-drop-node-name;
          type string;
        }
        leaf ac_type {
          tailf:cli-drop-node-name;
          type string;
        }
      }
      container qos {

        grouping access-rate-grouping {
          leaf value {
            tailf:cli-drop-node-name;
            type string;
          }
          leaf unshaped-sap-cir {
            type string;
          }
        }
        container access-ingress-aggregate-rate {
          uses access-rate-grouping;
        }
        container network-ingress-aggregate-rate {
          uses access-rate-grouping;
        }
      }
      container vsd {
        leaf system-id {
          // NCS drop tailf-common:cli-diff-create-before statement
          type string;
        }
      }
      container xmpp {
        list server {
          // NCS patched for predictable order
          ordered-by user;
          key "name";
          leaf name {
            type string;
          }
          leaf domain-name {
            type string;
          }
          leaf router {
            type string;
          }
          leaf shutdown {
            type string;
          }
        }
      }
      container security {
        container management {
          leaf allow-ftp {
            type string;
          }
          leaf allow-grpc {
            type string;
          }
          leaf allow-netconf {
            type string;
          }
          leaf allow-ssh {
            type string;
          }
          leaf allow-telnet {
            type string;
          }
          leaf allow-telnet6 {
            type string;
          }
        }
        container hash-control {
          leaf read-version {
            type string;
          }
          leaf write-version {
            type string;
          }
        }
        list keychain {
          // NCS patched for predictable order
          ordered-by user;
          key "keychain-name";
          leaf keychain-name {
            type string;
          }
          container direction {
            container bi {
              list entry {
                // NCS patched for predictable order
                ordered-by user;
                key "id";
                leaf id {
                  type string;
                }
                leaf key {
                  type string;
                }
                leaf method {
                  tailf:cli-drop-node-name;
                  type ncs_compliance_template_hash-method;
                }
                leaf algorithm {
                  type string;
                }
                leaf begin-time {
                  type string;
                }
                leaf option {
                  type string;
                }
                leaf tolerance {
                  type string;
                }
                leaf shutdown {
                  type string;
                }
              }
            }
          }
          leaf description {
            type string;
          }
          leaf shutdown {
            type string;
          }
        }
        container management-interface {
          container classic-cli {
            leaf read-algorithm {
              type ncs_compliance_template_hash-hash2-all-hash;
            }
            leaf write-algorithm {
              type ncs_compliance_template_hash-hash2-cleartext;
            }
          }
          container grpc {
            leaf hash-algorithm {
              type ncs_compliance_template_hash-hash2-cleartext;
            }
          }
          container md-cli {
            leaf hash-algorithm {
              type ncs_compliance_template_hash-hash2-cleartext;
            }
          }
          container netconf {
            leaf hash-algorithm {
              type ncs_compliance_template_hash-hash2-cleartext;
            }
          }
        }
        container pki {
          container certificate-expiration-warning {
            leaf hours {
              tailf:cli-drop-node-name;
              type string;
            }
            leaf repeat {
              type string;
            }
          }
          container crl-expiration-warning {
            leaf hours {
              tailf:cli-drop-node-name;
              type string;
            }
            leaf repeat {
              type string;
            }
          }
          list ca-profile {
            // NCS patched for predictable order
            ordered-by user;
            key "name";
            leaf name {
              type ncs_compliance_template_string32;
            }
            leaf description {
              type string;
            }
            leaf cert-file {
              type string;
            }
            container cmpv2 {
              leaf accept-unprotected-errormsg {
                type empty;
              }
              leaf accept-unprotected-pkiconf {
                type empty;
              }
              leaf same-recipnonce-for-pollreq {
                type empty;
              }
              leaf always-set-sender-for-ir {
                type empty;
              }
              leaf http-response-timeout {
                type string;
              }
              container key-list {
                list key {
                  // NCS patched for predictable order
                  ordered-by user;
                  tailf:cli-suppress-mode;
                  key "reference";
                  leaf password {
                    tailf:cli-drop-node-name;
                    type string;
                  }
                  leaf hashing {
                    tailf:cli-drop-node-name;
                    type string;
                  }
                  leaf reference {
                    type string;
                  }
                }
              }
              leaf url {
                type string;
              }
              leaf response-signing-cert {
                type string;
              }
            }
            leaf crl-file {
              type string;
            }
            leaf revocation-check {
              type string;
            }
            container auto-crl-update {
              container pre-update-time {
                leaf days {
                  type string;
                }
                leaf hrs {
                  type string;
                }
              }
              leaf schedule-type {
                type string;
              }
              container crl-urls {
                list url-entry {
                  // NCS patched for predictable order
                  ordered-by user;
                  key "entry-id";
                  leaf entry-id {
                    type string;
                  }
                  leaf file-transmission-profile {
                    type ncs_compliance_template_string32;
                  }
                  leaf url {
                    type string;
                  }
                }
              }
              leaf shutdown {
                type string;
              }
            }
            leaf shutdown {
              type string;
            }
          }
        }
        list profile {
          // NCS patched for predictable order
          ordered-by user;
          key "name";
          leaf name {
            type string;
          }
          leaf default-action {
            type string;
          }
          list entry {
            // NCS patched for predictable order
            ordered-by user;
            key "entry-id";
            leaf entry-id {
              type string;
            }
            leaf action {
              type string;
            }
            leaf description {
              type string;
            }
            leaf match {
              type string;
            }
          }
          leaf li {
            type empty;
          }
          container netconf {
            container base-op-authorization {
              leaf action {
                type empty;
              }
              leaf cancel-commit {
                type empty;
              }
              leaf close-session {
                type empty;
              }
              leaf commit-op {
                type empty;
              }
              leaf commit {
                type empty;
              }
              leaf copy-config {
                type empty;
              }
              leaf create-subscription {
                type empty;
              }
              leaf delete-config {
                type empty;
              }
              leaf discard-changes {
                type empty;
              }
              leaf edit-config {
                type empty;
              }
              leaf get {
                type empty;
              }
              leaf get-config {
                type empty;
              }
              leaf get-data {
                type empty;
              }
              leaf get-schema {
                type empty;
              }
              leaf kill-session {
                type empty;
              }
              leaf lock {
                type empty;
              }
              leaf validate {
                type empty;
              }
            }
          }
          container grpc {
            container rpc-authorization {
              leaf gnoi-cert-mgmt-rotate {
                type string;
              }
              leaf gnoi-cert-mgmt-install {
                type string;
              }
              leaf gnoi-cert-mgmt-getcert {
                type string;
              }
              leaf gnoi-cert-mgmt-revoke {
                type string;
              }
              leaf gnoi-cert-mgmt-cangenerate {
                type string;
              }
              leaf gnoi-file-get {
                type string;
              }
              leaf gnoi-file-put {
                type string;
              }
              leaf gnoi-file-stat {
                type string;
              }
              leaf gnoi-file-remove {
                type string;
              }
              leaf gnoi-system-setpackage {
                type string;
              }
              leaf gnoi-system-switchcontrolprocessor {
                type string;
              }
              leaf gnoi-system-reboot {
                type string;
              }
              leaf gnoi-system-rebootstatus {
                type string;
              }
              leaf gnoi-system-cancelreboot {
                type string;
              }
              leaf gnmi-capabilities {
                type string;
              }
              leaf gnmi-get {
                type string;
              }
              leaf gnmi-set {
                type string;
              }
              leaf gnmi-subscribe {
                type string;
              }
              leaf md-cli-session {
                type string;
              }
              leaf rib-api-modify {
                type string;
              }
              leaf rib-api-getversion {
                type string;
              }
            }
          }
          leaf ssh-max-sessions {
            type string;
          }
        }
        container password {
          container admin-password {
            leaf password {
              tailf:cli-drop-node-name;
              type string;
            }
            leaf scheme {
              tailf:cli-drop-node-name;
              type ncs_compliance_template_hash-method;
            }
          }
          leaf aging {
            type string;
          }
          container complexity-rules {
            leaf minimum-length {
              type string;
            }
            container required {
              leaf lowercase {
                type string;
              }
              leaf uppercase {
                type string;
              }
              leaf numeric {
                type string;
              }
              leaf special-character {
                type string;
              }
            }
            leaf allow-user-name {
              type empty;
            }
          }
          container health-check {
            leaf interval {
              type string;
            }
            leaf no {
              type empty;
            }
          }
          container health-check-alt {
            tailf:alt-name "health-check";
            leaf interval {
              type string;
            }
          }
          leaf-list authentication-order {
            // NCS patched for predictable order
            ordered-by user;
            type string;
          }
          container attempts {
            leaf count {
              tailf:cli-drop-node-name;
              type string;
            }
            leaf time {
              type string;
            }
            leaf lockout {
              type string;
            }
          }
        }
        container radius {
          leaf authorization {
            type empty;
          }
          leaf accounting {
            type empty;
          }
          list server {
            // NCS patched for predictable order
            ordered-by user;
            tailf:cli-suppress-mode;
            key "server-index";
            leaf server-index {
              type string;
            }
            leaf address {
              // NCS drop mandatory statement
              type string;
            }
            leaf secret {
              // NCS drop mandatory statement
              type string;
            }
            leaf type {
              tailf:cli-drop-node-name;
              type ncs_compliance_template_hash-method;
            }
          }
          leaf shutdown {
            type string;
          }
        }
        container tech-support {
          leaf ts-location {
            type string;
          }
        }
        container tls {
          list cert-profile {
            // NCS patched for predictable order
            ordered-by user;
            key "profile-name";
            leaf profile-name {
              type string;
            }
            list entry {
              // NCS patched for predictable order
              ordered-by user;
              // NCS drop tailf-common:cli-diff-create-before statement
              key "entry-id";
              leaf entry-id {
                type string;
              }
              leaf cert {
                type string;
              }
              leaf key {
                type string;
              }
              container send-chain {
                list ca-profile {
                  // NCS patched for predictable order
                  ordered-by user;
                  tailf:cli-suppress-mode;
                  key "profile";
                  leaf profile {
                    type ncs_compliance_template_string32;
                  }
                }
              }
            }
            leaf shutdown {
              type string;
            }
          }
          list server-cipher-list {
            // NCS patched for predictable order
            ordered-by user;
            key "name";
            leaf name {
              type string;
            }
            list cipher {
              // NCS patched for predictable order
              ordered-by user;
              tailf:cli-suppress-mode;
              key "index";
              leaf index {
                type string;
              }
              leaf name {
                type string;
              }
            }
          }
          list server-tls-profile {
            // NCS patched for predictable order
            ordered-by user;
            key "name";
            leaf name {
              type string;
            }
            leaf cert-profile {
              type string;
            }
            leaf cipher-list {
              type string;
            }
            leaf shutdown {
              type string;
            }
          }
        }
        container tacplus {
          container accounting {
            presence "true";
            leaf record-type {
              type string;
            }
          }
          container authorization {
            presence "true";
            leaf use-prix-lvl {
              type empty;
            }
          }
          leaf interactive-authentication {
            type empty;
          }
          container priv-lvl-map {
            list priv-lvl {
              // NCS patched for predictable order
              ordered-by user;
              tailf:cli-suppress-mode;
              key "lvl";
              leaf lvl {
                type string;
              }
              leaf user-profile {
                tailf:cli-drop-node-name;
                type string;
              }
            }
          }
          leaf route-preference {
            type string;
          }
          list server {
            // NCS patched for predictable order
            ordered-by user;
            tailf:cli-suppress-mode;
            key "server-index";
            leaf server-index {
              type string;
            }
            leaf address {
              type string;
            }
            leaf secret {
              type string;
            }
            leaf hash {
              tailf:cli-drop-node-name;
              type ncs_compliance_template_hash-method;
            }
            leaf port {
              type string;
            }
          }
          leaf timeout {
            type string;
          }
          leaf use-default-template {
            type empty;
          }
          leaf shutdown {
            type string;
          }
        }
        leaf telnet-server {
          type empty;
        }
        leaf telnet6-server {
          type empty;
        }
        leaf ftp-server {
          type empty;
        }
        leaf per-peer-queuing {
          type empty;
        }
        container snmp {
          container access {
            list group {
              // NCS patched for predictable order
              ordered-by user;
              tailf:cli-suppress-mode;
              key "name security-model security-level";
              leaf name {
                type string;
              }
              leaf security-model {
                type string;
              }
              leaf security-level {
                type string;
              }
              container context {
                leaf context-name {
                  tailf:cli-drop-node-name;
                  type string;
                }
                leaf match {
                  tailf:cli-drop-node-name;
                  type string;
                }
                uses read-write-notify;
              }
              container read {
                tailf:cli-drop-node-name;
                uses read-write-notify;
              }

              grouping read-write-notify {
                leaf read {
                  type ncs_compliance_template_string32;
                }
                leaf write {
                  type ncs_compliance_template_string32;
                }
                leaf notify {
                  type ncs_compliance_template_string32;
                }
              }
            }
          }
          list src-access-list {
            // NCS patched for predictable order
            ordered-by user;
            key "list-name";
            leaf list-name {
              type ncs_compliance_template_string32;
            }
            list src-host {
              // NCS patched for predictable order
              ordered-by user;
              tailf:cli-suppress-mode;
              key "name";
              leaf name {
                type string;
              }
              leaf address {
                type string;
              }
            }
          }
          uses ncs_compliance_template_snmp-community-grouping;
          list usm-community {
            // NCS patched for predictable order
            ordered-by user;
            tailf:cli-suppress-mode;
            key "name type";
            leaf name {
              type string;
            }
            leaf type {
              tailf:cli-drop-node-name;
              type ncs_compliance_template_hash-method;
            }
            leaf group {
              type string;
            }
            leaf src-access-list {
              type ncs_compliance_template_string32;
            }
          }
          container attempts {
            leaf count {
              tailf:cli-drop-node-name;
              type string;
            }
            leaf time {
              type string;
            }
            leaf lockout {
              type string;
            }
          }
          list view {
            // NCS patched for predictable order
            ordered-by user;
            key "name subtree";
            leaf name {
              type ncs_compliance_template_string32;
            }
            leaf subtree {
              type string;
            }
            container mask {
              leaf mask-value {
                tailf:cli-drop-node-name;
                type string;
              }
              leaf type {
                type string;
              }
            }
          }
        }
        container source-address {
          list application {
            // NCS patched for predictable order
            ordered-by user;
            tailf:cli-suppress-mode;
            key "name";
            leaf name {
              type ncs_compliance_template_net-application;
            }
            leaf address {
              tailf:cli-drop-node-name;
              type string;
            }
          }
          list application6 {
            // NCS patched for predictable order
            ordered-by user;
            tailf:cli-suppress-mode;
            key "name";
            leaf name {
              type ncs_compliance_template_net-application;
            }
            leaf address {
              tailf:cli-drop-node-name;
              type string;
            }
          }
        }
        container ssh {
          leaf preserve-key {
            type empty;
          }
          leaf server-shutdown {
            type empty;
          }
          container key-re-exchange {
            container server {
              leaf mbytes {
                type string;
              }
              leaf minutes {
                type string;
              }
              leaf shutdown {
                type string;
              }
            }
            container client {
              leaf mbytes {
                type string;
              }
              leaf minutes {
                type string;
              }
              leaf shutdown {
                type string;
              }
            }
          }
          leaf permit-empty-passwords {
            type string;
          }
          leaf version {
            type string;
          }

          grouping cipher-list-grouping {
            list cipher {
              // NCS patched for predictable order
              ordered-by user;
              tailf:cli-suppress-mode;
              key "index";
              leaf index {
                type string;
              }
              leaf name {
                type string;
              }
            }
          }
          list client-cipher-list {
            // NCS patched for predictable order
            ordered-by user;
            key "protocol-version";
            uses cipher-list-grouping;
            leaf protocol-version {
              type string;
            }
          }
          container client-cipher-list-alt {
            tailf:alt-name "client-cipher-list";
            uses cipher-list-grouping;
          }
          list server-cipher-list {
            // NCS patched for predictable order
            ordered-by user;
            key "protocol-version";
            leaf protocol-version {
              type string;
            }
            uses cipher-list-grouping;
          }
          container server-cipher-list-alt {
            tailf:alt-name "server-cipher-list";
            uses cipher-list-grouping;
          }
          container server-kex-list {
            list kex {
              // NCS patched for predictable order
              ordered-by user;
              tailf:cli-suppress-mode;
              key "kex-id";
              unique "name";
              leaf kex-id {
                type string;
              }
              leaf name {
                type string;
              }
            }
          }
          container client-kex-list {
            list kex {
              // NCS patched for predictable order
              ordered-by user;
              tailf:cli-suppress-mode;
              key "kex-id";
              unique "name";
              leaf kex-id {
                type string;
              }
              leaf name {
                type string;
              }
            }
          }
          container server-mac-list {
            presence "true";
            list mac {
              // NCS patched for predictable order
              ordered-by user;
              tailf:cli-suppress-mode;
              key "index";
              leaf index {
                type string;
              }
              leaf name {
                type string;
              }
            }
          }
          container client-mac-list {
            presence "true";
            list mac {
              // NCS patched for predictable order
              ordered-by user;
              tailf:cli-suppress-mode;
              key "index";
              leaf index {
                type string;
              }
              leaf name {
                type string;
              }
            }
          }
        }
        list user-template {
          // NCS patched for predictable order
          ordered-by user;
          key "user-template-id";
          leaf user-template-id {
            type string;
          }
          leaf-list access {
            // NCS patched for predictable order
            ordered-by user;
            type string;
          }
          leaf profile {
            type string;
          }
        }
        list user {
          // NCS patched for predictable order
          ordered-by user;
          key "user-id";
          leaf user-id {
            type string;
          }
          leaf-list access {
            // NCS patched for predictable order
            ordered-by user;
            type string;
          }
          container console {
            leaf cannot-change-password {
              type empty;
            }
            leaf login-exec {
              type string;
            }
            container disable {
              leaf member {
                type string;
              }
            }
            list member {
              // NCS patched for predictable order
              ordered-by user;
              tailf:cli-suppress-mode;
              key "name";
              leaf name {
                type string;
              }
            }
            leaf new-password-at-login {
              type empty;
            }
          }
          leaf home-directory {
            type string;
          }
          container password {
            leaf id {
              tailf:cli-drop-node-name;
              type string;
            }
            leaf method {
              tailf:cli-drop-node-name;
              type ncs_compliance_template_hash-method;
            }
          }
          leaf restricted-to-home {
            type empty;
          }
          container public-keys {
            container rsa {
              list rsa-key {
                // NCS patched for predictable order
                ordered-by user;
                key "rsa-public-key-id";
                leaf rsa-public-key-id {
                  type string;
                }
                leaf description {
                  type string;
                }
                leaf key-value {
                  type string;
                }
              }
            }
            container ecdsa {
              list ecdsa-key {
                // NCS patched for predictable order
                ordered-by user;
                key "rsa-public-key-id";
                leaf rsa-public-key-id {
                  type string;
                }
                leaf description {
                  type string;
                }
                leaf key-value {
                  type string;
                }
              }
            }
          }
          list rsa-key {
            // NCS patched for predictable order
            ordered-by user;
            tailf:cli-suppress-mode;
            key "key-id";
            leaf key-id {
              type string;
            }
            leaf key {
              tailf:cli-drop-node-name;
              type string;
            }
          }
          container snmp {
            container authentication {
              leaf none {
                type empty;
              }
              leaf hash {
                type empty;
              }
              leaf hash2 {
                type empty;
              }
              leaf auth-type {
                tailf:cli-drop-node-name;
                type string;
              }
              leaf key-1 {
                tailf:cli-drop-node-name;
                type string;
              }
              leaf privacy {
                type string;
              }
              leaf key-2 {
                tailf:cli-drop-node-name;
                type string;
              }
              leaf hashval {
                tailf:cli-drop-node-name;
                type string;
              }
            }
            leaf group {
              type string;
            }
          }
        }
        container disable {
          leaf user {
            type string;
          }
        }
        container cpu-protection {
          leaf link-specific-rate {
            type string;
          }
          list policy {
            // NCS patched for predictable order
            ordered-by user;
            key "policy-id";
            leaf policy-id {
              type string;
            }
            leaf overall-rate {
              type string;
            }
            leaf out-profile-rate {
              type string;
            }
            leaf description {
              type string;
            }
            leaf per-source-rate {
              type string;
            }
          }
          container protocol-protection {
            presence "true";
            leaf allow-sham-links {
              type empty;
            }
            leaf block-pim-tunneled {
              type empty;
            }
          }
          leaf port-overall-rate {
            type string;
          }
        }
        container dist-cpu-protection {
          list policy {
            // NCS patched for predictable order
            ordered-by user;
            key "policy-id";
            leaf policy-id {
              type string;
            }
            leaf description {
              type string;
            }
            leaf type {
              type string;
            }
            list static-policer {
              // NCS patched for predictable order
              ordered-by user;
              key "policy-name";
              leaf policy-name {
                type string;
              }
              leaf description {
                type string;
              }
              container rate {
                choice rate {
                  container kbps {
                    leaf kilobits-per-second {
                      tailf:cli-drop-node-name;
                      type string;
                    }
                    leaf mbs {
                      type string;
                    }
                    leaf unit {
                      tailf:cli-drop-node-name;
                      type string;
                    }
                  }
                  container packets {
                    leaf ppi {
                      tailf:cli-drop-node-name;
                      type string;
                    }
                    leaf within {
                      type string;
                    }
                    leaf initial-delay {
                      type string;
                    }
                  }
                }
              }
              container exceed-action {

                grouping hold-down-grouping {
                  leaf hold-down {
                    type string;
                  }
                }
                choice exceed-action {
                  container discard {
                    presence "true";
                    uses hold-down-grouping;
                  }
                  container low-priority {
                    presence "true";
                    uses hold-down-grouping;
                  }
                }
              }
            }
            list protocol {
              // NCS patched for predictable order
              ordered-by user;
              key "name";
              leaf name {
                type string;
              }
              container enforcement {
                leaf policy-type {
                  tailf:cli-drop-node-name;
                  type string;
                }
                leaf policy-name {
                  tailf:cli-drop-node-name;
                  type string;
                }
              }
            }
          }
        }
        container cpm-filter {
          leaf default-action {
            type string;
          }
          container ip-filter {
            list entry {
              // NCS patched for predictable order
              ordered-by user;
              key "entry-id";
              leaf entry-id {
                type string;
              }
              container action {
                choice action-choice {
                  leaf drop {
                    type empty;
                  }
                  leaf accept {
                    type empty;
                  }
                  leaf queue {
                    type string;
                  }
                }
              }
              leaf description {
                type string;
              }
              leaf log {
                type string;
              }
              container match {
                presence "true";
                leaf protocol {
                  type ncs_compliance_template_protocol;
                }
                leaf dscp {
                  type ncs_compliance_template_dscp-type;
                }
                container dst-ip {
                  uses ncs_compliance_template_filter-match-ip-grouping;
                }
                container dst-port {
                  uses ncs_compliance_template_cpm-filter-match-port-grouping;
                }
                leaf fragment {
                  type string;
                }
                leaf icmp-code {
                  type string;
                }
                leaf icmp-type {
                  type ncs_compliance_template_icmp-type;
                }
                container ip-option {
                  leaf value {
                    tailf:cli-drop-node-name;
                    type string;
                  }
                  leaf mask {
                    tailf:cli-drop-node-name;
                    type string;
                  }
                }
                leaf multiple-option {
                  type string;
                }
                leaf option-present {
                  type string;
                }
                container port {
                  uses ncs_compliance_template_cpm-filter-match-port-grouping;
                }
                leaf router {
                  type string;
                }
                container src-ip {
                  uses ncs_compliance_template_filter-match-ip-grouping;
                }
                container src-port {
                  uses ncs_compliance_template_cpm-filter-match-port-grouping;
                }
                leaf tcp-ack {
                  type string;
                }
                leaf tcp-syn {
                  type string;
                }
              }
            }
            leaf shutdown {
              type string;
            }
          }
          container ipv6-filter {
            list entry {
              // NCS patched for predictable order
              ordered-by user;
              key "entry-id";
              leaf entry-id {
                type string;
              }
              container action {
                choice action-choice {
                  leaf drop {
                    type empty;
                  }
                  leaf accept {
                    type empty;
                  }
                  leaf queue {
                    type string;
                  }
                }
              }
              leaf description {
                type string;
              }
              leaf log {
                type string;
              }
              container match {
                presence "true";
                leaf fragment {
                  type string;
                }
                leaf next-header {
                  type ncs_compliance_template_protocol;
                }
                leaf dscp {
                  type ncs_compliance_template_dscp-type;
                }
                container dst-ip {
                  uses ncs_compliance_template_filter-match-ipv6-grouping;
                }
                container dst-port {
                  uses ncs_compliance_template_cpm-filter-match-port-grouping;
                }
                leaf flow-label {
                  type string;
                }
                leaf hop-by-hop-opt {
                  type string;
                }
                leaf icmp-code {
                  type string;
                }
                leaf icmp-type {
                  type ncs_compliance_template_icmpv6-type;
                }
                container port {
                  uses ncs_compliance_template_cpm-filter-match-port-grouping;
                }
                leaf router {
                  type string;
                }
                container src-ip {
                  uses ncs_compliance_template_filter-match-ipv6-grouping;
                }
                container src-port {
                  uses ncs_compliance_template_cpm-filter-match-port-grouping;
                }
                leaf tcp-ack {
                  type string;
                }
                leaf tcp-syn {
                  type string;
                }
              }
            }
            leaf shutdown {
              type string;
            }
          }
        }
        container cpm-queue {
          list queue {
            // NCS patched for predictable order
            ordered-by user;
            key "queue-id";
            leaf queue-id {
              type string;
            }
            leaf cbs {
              type string;
            }
            leaf mbs {
              type string;
            }
            container rate {
              leaf value {
                tailf:cli-drop-node-name;
                type string;
              }
              leaf cir {
                type string;
              }
            }
          }
        }
        container management-access-filter {
          container ip-filter {
            presence "true";
            leaf default-action {
              type ncs_compliance_template_filter-action;
            }
            list entry {
              // NCS patched for predictable order
              ordered-by user;
              key "entry-name";
              leaf entry-name {
                type string;
              }
              leaf action {
                type ncs_compliance_template_filter-action;
              }
              leaf description {
                type string;
              }
              leaf log {
                type empty;
              }
              container src-ip {
                choice format-choice {
                  container address-netmask {
                    tailf:cli-drop-node-name;
                    leaf address {
                      tailf:cli-drop-node-name;
                      type string;
                    }
                    leaf netmask {
                      tailf:cli-drop-node-name;
                      type string;
                    }
                  }
                  leaf ip-prefix-list {
                    type string;
                  }
                }
              }
              container dst-port {
                leaf port {
                  tailf:cli-drop-node-name;
                  type string;
                }
                leaf mask {
                  tailf:cli-drop-node-name;
                  type string;
                }
              }
              leaf src-port {
                type string;
              }
              container l4-src-port {
                leaf port {
                  tailf:cli-drop-node-name;
                  type string;
                }
                leaf mask {
                  tailf:cli-drop-node-name;
                  type string;
                }
              }
              leaf router {
                type ncs_compliance_template_router-type;
              }
              leaf protocol {
                type string;
              }
            }
            leaf shutdown {
              type string;
            }
          }
          container ipv6-filter {
            presence "true";
            leaf default-action {
              type ncs_compliance_template_filter-action;
            }
            list entry {
              // NCS patched for predictable order
              ordered-by user;
              key "entry-name";
              leaf entry-name {
                type string;
              }
              leaf action {
                type ncs_compliance_template_filter-action;
              }
              leaf description {
                type string;
              }
              container src-ip {
                choice format-choice {
                  leaf address {
                    tailf:cli-drop-node-name;
                    type string;
                  }
                  leaf ipv6-prefix-list {
                    type string;
                  }
                }
              }
              leaf src-port {
                type string;
              }
              container dst-port {
                leaf port {
                  tailf:cli-drop-node-name;
                  type string;
                }
                leaf mask {
                  tailf:cli-drop-node-name;
                  type string;
                }
              }
              leaf next-header {
                type string;
              }
              leaf log {
                type empty;
              }
              container l4-src-port {
                leaf port {
                  tailf:cli-drop-node-name;
                  type string;
                }
                leaf mask {
                  tailf:cli-drop-node-name;
                  type string;
                }
              }
              leaf router {
                type string;
              }
            }
            leaf shutdown {
              type string;
            }
          }
        }
        container vprn-aaa-server {
          leaf inband {
            type ncs_compliance_template_service-id;
          }
          leaf outband {
            type ncs_compliance_template_service-id;
          }
          leaf vprn {
            type ncs_compliance_template_service-id;
          }
        }
        container vprn-network-exceptions {
          presence "true";
          leaf number {
            tailf:cli-drop-node-name;
            type string;
          }
          leaf seconds {
            tailf:cli-drop-node-name;
            type string;
          }
        }
        container usb-port {
          presence "true";
          leaf shutdown {
            type string;
          }
        }
      }
      container sync-if-timing {
        leaf description {
          type string;
        }
        container gnss {
          leaf shutdown {
            type string;
          }
        }
        container ptp {
          leaf ql-override {
            type string;
          }
          leaf shutdown {
            type string;
          }
        }
        container bits {
          container input {
            leaf shutdown {
              type string;
            }
          }
        }
        container external {
          container input-interface {
            leaf type {
              type string;
            }
            leaf shutdown {
              type string;
            }
          }
        }
        leaf ql-selection {
          type empty;
        }
        container ref-order {

          typedef ref-order-type {
            type string;
          }
          leaf first {
            tailf:cli-drop-node-name;
            type ref-order-type;
          }
          leaf second {
            tailf:cli-drop-node-name;
            type ref-order-type;
          }
          leaf third {
            tailf:cli-drop-node-name;
            type ref-order-type;
          }
          leaf fourth {
            tailf:cli-drop-node-name;
            type ref-order-type;
          }
          leaf fifth {
            tailf:cli-drop-node-name;
            type ref-order-type;
          }
        }

        grouping ref-grouping {
          leaf ql-override {
            type string;
          }
          leaf source-port {
            type string;
          }
          leaf source-ptp-clock {
            type string;
          }
          leaf shutdown {
            type string;
          }
        }
        container ref1 {
          uses ref-grouping;
        }
        container ref2 {
          uses ref-grouping;
        }
        leaf revert {
          type empty;
        }
      }
      list software-repository {
        // NCS patched for predictable order
        ordered-by user;
        key "name";
        leaf name {
          type string;
        }
        leaf description {
          type string;
        }
        leaf primary-location {
          type string;
        }
        leaf secondary-location {
          type string;
        }
        leaf tertiary-location {
          type string;
        }
      }
      container telemetry {
        list destination-group {
          // NCS patched for predictable order
          ordered-by user;
          key "name";
          leaf name {
            type string;
          }
          leaf allow-unsecure-connection {
            type empty;
          }
          leaf description {
            type string;
          }
          list destination {
            // NCS patched for predictable order
            ordered-by user;
            key "address port";
            leaf address {
              type string;
            }
            leaf port {
              type string;
            }
            container router-instance {
              leaf router-id {
                tailf:cli-drop-node-name;
                type ncs_compliance_template_router-type;
              }
            }
          }
          container tcp-keepalive {
            leaf shutdown {
              type string;
            }
          }
        }
        container sensor-groups {
          list sensor-group {
            // NCS patched for predictable order
            ordered-by user;
            key "name";
            leaf name {
              type string;
            }
            leaf description {
              type string;
            }
            list path {
              // NCS patched for predictable order
              ordered-by user;
              key "path-string";
              leaf path-string {
                type string;
              }
            }
          }
        }
        container persistent-subscriptions {
          list subscription {
            // NCS patched for predictable order
            ordered-by user;
            key "name";
            leaf name {
              type string;
            }
            leaf description {
              type string;
            }
            leaf encoding {
              type string;
            }
            leaf sample-interval {
              type string;
            }
            leaf local-source-address {
              type string;
            }
            leaf destination-group {
              type string;
            }
            leaf mode {
              type string;
            }
            leaf sensor-group {
              type string;
            }
            leaf shutdown {
              type string;
            }
          }
        }
      }
    }
    container redundancy {
      container bgp-evpn-multi-homing {
        leaf boot-timer {
          type string;
        }
        leaf es-activation-timer {
          type string;
        }
      }
      container mgmt-ethernet {
        leaf revert {
          type string;
        }
      }
      container multi-chassis {
        list peer {
          // NCS patched for predictable order
          ordered-by user;
          key "address";
          leaf address {
            type string;
          }
          leaf description {
            type string;
          }
          leaf peer-name {
            type string;
          }
          container mc-lag {
            presence "true";
            leaf hold-on-neighbor-failure {
              type string;
            }
            leaf keep-alive-interval {
              type string;
            }
            list lag {
              // NCS patched for predictable order
              ordered-by user;
              tailf:cli-suppress-mode;
              key "lag-id";
              leaf lag-id {
                type string;
              }
              leaf lacp-key {
                type string;
              }
              leaf system-id {
                type ncs_compliance_template_ieee-mac;
              }
              leaf remote-lag {
                type string;
              }
              leaf system-priority {
                type string;
              }
              leaf source-bmac-lsb {
                type string;
              }
            }
            leaf shutdown {
              type string;
            }
          }
          leaf source-address {
            type string;
          }
          container sync {
            presence "true";
            list port {
              // NCS patched for predictable order
              ordered-by user;
              key "port-id";
              leaf port-id {
                type string;
              }
              list range {
                // NCS patched for predictable order
                ordered-by user;
                tailf:cli-suppress-mode;
                key "range-val";
                leaf range-val {
                  type string;
                }
                leaf sync-tag {
                  type string;
                }
              }
              leaf sync-tag {
                type string;
              }
            }
            leaf local-dhcp-server {
              type empty;
            }
            leaf python {
              type empty;
            }
            leaf srrp {
              type empty;
            }
            leaf-list sub-mgmt {
              // NCS patched for predictable order
              ordered-by user;
              type string;
            }
            leaf igmp {
              type empty;
            }
            leaf igmp-snooping {
              type empty;
            }
            leaf shutdown {
              type string;
            }
          }
          leaf shutdown {
            type string;
          }
        }
      }
      leaf rollback-sync {
        type empty;
      }
      leaf synchronize {
        type string;
      }
    }
    list connection-profile-vlan {
      // NCS patched for predictable order
      ordered-by user;
      // NCS drop tailf-common:cli-diff-create-before statement
      // NCS drop tailf-common:cli-diff-create-before statement
      // NCS drop tailf-common:cli-diff-create-before statement
      key "conn-prof-id";
      leaf conn-prof-id {
        type string;
      }
      leaf description {
        type string;
      }
      list vlan-range {
        // NCS patched for predictable order
        ordered-by user;
        key "from to";
        tailf:cli-suppress-mode;
        unique "from";
        leaf from {
          type string;
        }
        leaf to {
          type string;
        }
      }
    }
    list eth-ring {
      // NCS patched for predictable order
      ordered-by user;
      key "index";
      leaf index {
        type string;
      }
      leaf description {
        type string;
      }
      leaf revert-time {
        type string;
      }
      leaf rpl-node {
        type string;
      }
      list path {
        // NCS patched for predictable order
        ordered-by user;
        key "path-id";
        leaf path-id {
          type string;
        }
        leaf port {
          tailf:cli-drop-node-name;
          type string;
        }
        leaf raps-tag {
          type string;
        }
        leaf rpl-end {
          type empty;
        }
        container eth-cfm {
          uses ncs_compliance_template_eth-cfm {
            augment "mep" {
              leaf control-mep {
                type empty;
              }
            }
          }
        }
        leaf shutdown {
          type string;
        }
      }
      leaf shutdown {
        type string;
      }
    }
    container filter {
      list ip-filter {
        // NCS patched for predictable order
        ordered-by user;
        key "ip-filter-name";
        leaf ip-filter-name {
          type ncs_compliance_template_filter-id;
        }
        leaf name {
          type string;
        }
        leaf chain-to-system-filter {
          type empty;
        }
        list embed-filter {
          // NCS patched for predictable order
          ordered-by user;
          tailf:cli-suppress-mode;
          key "embed-filter-name";
          leaf embed-filter-name {
            type ncs_compliance_template_filter-id;
          }
          leaf router {
            type ncs_compliance_template_router-type;
          }
          leaf offset {
            type string;
          }
          leaf status {
            tailf:cli-drop-node-name;
            type string;
          }
        }
        leaf default-action {
          type string;
        }
        leaf filter-name {
          type string;
        }
        leaf scope {
          type string;
        }
        leaf description {
          type string;
        }
        list entry {
          // NCS patched for predictable order
          ordered-by user;
          uses ncs_compliance_template_ip-filter-entry-grouping;
          key "entry-name";
          leaf pbr-down-action-override {
            type string;
          }

          grouping ip-filter-entry-action-grouping-old {
            choice action-choice {
              container drop {
                presence "true";
                container packet-length {
                  leaf rule {
                    tailf:cli-drop-node-name;
                    type string;
                  }
                  leaf length {
                    tailf:cli-drop-node-name;
                    type string;
                  }
                }
              }
              leaf nat {
                type empty;
              }
              leaf http-redirect {
                type string;
              }
              container forward {
                presence "true";
                container next-hop {
                  choice next-hop-choice {
                    case na {
                      leaf ip-address {
                        tailf:cli-drop-node-name;
                        type string;
                      }
                    }
                    case nb {
                      leaf indirect {
                        type string;
                      }
                    }
                    case nc {
                      leaf interface {
                        type string;
                      }
                    }
                  }
                }
                leaf router {
                  type ncs_compliance_template_router-type;
                }
                leaf sap {
                  type string;
                }
                leaf sdp {
                  type string;
                }
                leaf redirect-policy {
                  type string;
                }
              }
            }
          }

          grouping ip-filter-entry-action-grouping-new {
            choice action-choice {
              container drop {
                presence "true";
                container packet-length {
                  choice rule-range {
                    container rule {
                      tailf:cli-drop-node-name;
                      leaf rule {
                        tailf:cli-drop-node-name;
                        type string;
                      }
                      leaf length {
                        tailf:cli-drop-node-name;
                        type string;
                      }
                    }
                    container range {
                      leaf start {
                        tailf:cli-drop-node-name;
                        type string;
                      }
                      leaf end {
                        tailf:cli-drop-node-name;
                        type string;
                      }
                    }
                  }
                }
              }
              leaf nat {
                type empty;
              }
              leaf http-redirect {
                type string;
              }
              container forward {
                presence "true";
                container vprn-target {
                  leaf bgp-nh {
                    type string;
                  }
                }
                container next-hop {
                  choice next-hop-choice {
                    case na {
                      leaf ip-address {
                        tailf:cli-drop-node-name;
                        type string;
                      }
                    }
                    case nb {
                      leaf indirect {
                        type string;
                      }
                    }
                    case nc {
                      leaf interface {
                        type string;
                      }
                    }
                  }
                }
                leaf router {
                  type ncs_compliance_template_service-id;
                }
                leaf lsp {
                  type string;
                }
                leaf sap {
                  type string;
                }
                leaf sdp {
                  type string;
                }
                leaf redirect-policy {
                  type string;
                }
              }
              leaf rate-limit {
                type string;
              }
            }
          }
          container action-flat {
            tailf:alt-name "action";
            uses ip-filter-entry-action-grouping-old;
          }
          container action {
            presence "true";
            uses ip-filter-entry-action-grouping-new;
          }
          leaf egress-pbr {
            type string;
          }
        }
      }
      list ipv6-filter {
        // NCS patched for predictable order
        ordered-by user;
        key "ip-filter-name";
        leaf ip-filter-name {
          type ncs_compliance_template_filter-id;
        }
        leaf name {
          type string;
        }
        leaf chain-to-system-filter {
          type empty;
        }
        leaf default-action {
          type string;
        }
        leaf filter-name {
          type string;
        }
        list embed-filter {
          // NCS patched for predictable order
          ordered-by user;
          tailf:cli-suppress-mode;
          key "embed-filter-name";
          leaf embed-filter-name {
            type ncs_compliance_template_filter-id;
          }
          leaf router {
            type ncs_compliance_template_router-type;
          }
          leaf offset {
            type string;
          }
          leaf status {
            tailf:cli-drop-node-name;
            type string;
          }
        }
        leaf scope {
          type string;
        }
        leaf description {
          type string;
        }
        list entry {
          // NCS patched for predictable order
          ordered-by user;
          uses ncs_compliance_template_ipv6-filter-entry-grouping;
          key "entry-name";
          leaf log {
            type string;
          }
          leaf action {
            type string;
          }
          container action-mode {
            tailf:alt-name "action";
            presence "true";
            leaf action {
              tailf:cli-drop-node-name;
              type string;
            }
            container rate-limit {
              leaf value {
                tailf:cli-drop-node-name;
                type string;
              }
            }
          }
        }
      }
      list mac-filter {
        // NCS patched for predictable order
        ordered-by user;
        key "mac-filter-name";
        leaf mac-filter-name {
          type ncs_compliance_template_filter-id;
        }
        leaf name {
          type string;
        }
        leaf default-action {
          type string;
        }
        leaf scope {
          type string;
        }
        leaf description {
          type string;
        }
        leaf filter-name {
          type string;
        }
        list entry {
          // NCS patched for predictable order
          ordered-by user;
          key "entry-name";
          leaf entry-name {
            type string;
          }
          leaf description {
            type string;
          }
          container match {
            container dot1p {
              leaf dot1p-value {
                tailf:cli-drop-node-name;
                type string;
              }
              leaf dot1p-mask {
                tailf:cli-drop-node-name;
                type string;
              }
            }
            container dst-mac {
              leaf mac {
                tailf:cli-drop-node-name;
                type string;
              }
              leaf mask {
                tailf:cli-drop-node-name;
                type string;
              }
            }
            container src-mac {
              leaf mac {
                tailf:cli-drop-node-name;
                type string;
              }
              leaf mask {
                tailf:cli-drop-node-name;
                type string;
              }
            }
            leaf frame-type {
              type string;
            }
            leaf etype {
              type string;
            }
          }
          container action-flat {
            tailf:alt-name "action";
            choice choice {
              case drop {
                leaf drop {
                  type empty;
                }
              }
              case forward {
                leaf forward {
                  type empty;
                }
                leaf sap {
                  type string;
                }
              }
            }
          }
          container action {
            choice choice {
              case drop {
                leaf drop {
                  type empty;
                }
              }
              case forward {
                leaf forward {
                  type empty;
                }
                leaf sap {
                  type string;
                }
              }
            }
          }
          leaf log {
            type string;
          }
        }
      }
      container match-list {

        grouping apply-path-grouping {
          container apply-path {
            list bgp-peers {
              // NCS patched for predictable order
              ordered-by user;
              tailf:cli-suppress-mode;
              key "id";
              leaf id {
                type string;
              }
              leaf router {
                type ncs_compliance_template_router-type;
              }
              leaf group {
                type string;
              }
              leaf neighbor {
                type string;
              }
            }
          }
        }
        list ip-prefix-list {
          // NCS patched for predictable order
          ordered-by user;
          key "name";
          leaf name {
            type string;
          }
          leaf description {
            type string;
          }
          list prefix {
            // NCS patched for predictable order
            ordered-by user;
            tailf:cli-suppress-mode;
            key "pfx";
            leaf pfx {
              type string;
            }
          }
          list prefix-exclude {
            // NCS patched for predictable order
            ordered-by user;
            tailf:cli-suppress-mode;
            key "address";
            leaf address {
              type string;
            }
          }
          uses apply-path-grouping;
        }
        list ipv6-prefix-list {
          // NCS patched for predictable order
          ordered-by user;
          key "name";
          leaf name {
            type string;
          }
          leaf description {
            type string;
          }
          list prefix {
            // NCS patched for predictable order
            ordered-by user;
            tailf:cli-suppress-mode;
            key "pfx";
            leaf pfx {
              type string;
            }
          }
          uses apply-path-grouping;
        }
        list port-list {
          // NCS patched for predictable order
          ordered-by user;
          key "port-list-name";
          leaf port-list-name {
            type ncs_compliance_template_string32;
          }
          leaf description {
            type string;
          }
          container port {
            list port {
              // NCS patched for predictable order
              ordered-by user;
              tailf:cli-drop-node-name;
              tailf:cli-suppress-mode;
              key "port-number";
              leaf port-number {
                type string;
              }
            }
            list range {
              // NCS patched for predictable order
              ordered-by user;
              tailf:cli-suppress-mode;
              key "start end";
              leaf start {
                type string;
              }
              leaf end {
                type string;
              }
            }
          }
        }
      }
      list log {
        // NCS patched for predictable order
        ordered-by user;
        key "log-id";
        leaf log-id {
          type string;
        }
        leaf description {
          type string;
        }
        container destination {
          choice choice {
            leaf memory {
              type string;
            }
            leaf syslog {
              type string;
            }
          }
        }
        leaf wrap-around {
          type string;
        }
        leaf shutdown {
          type string;
        }
      }
      list redirect-policy {
        // NCS patched for predictable order
        ordered-by user;
        key "redirect-policy-name";
        leaf redirect-policy-name {
          type string;
        }
        leaf description {
          type string;
        }
        list destination {
          // NCS patched for predictable order
          ordered-by user;
          key "ip-address";
          leaf ip-address {
            type string;
          }
          leaf description {
            type string;
          }
          container ping-test {
            presence "true";
            container drop-count {
              leaf consecutive-failures {
                tailf:cli-drop-node-name;
                type string;
              }
              leaf hold-down {
                type string;
              }
            }
            leaf interval {
              type string;
            }
            leaf timeout {
              type string;
            }
          }
          leaf priority {
            type string;
          }
          leaf shutdown {
            type string;
          }
        }
        leaf shutdown {
          type string;
        }
      }
      container system-filter {
        leaf ip {
          type ncs_compliance_template_filter-id;
        }
        leaf ipv6 {
          type ncs_compliance_template_filter-id;
        }
      }
    }
    container test-oam {
      container link-measurement {
        list measurement-template {
          // NCS patched for predictable order
          ordered-by user;
          key "template-name";
          leaf template-name {
            type string;
          }
          container aggregate-sample-window {
            leaf multiplier {
              type string;
            }
            leaf window-integrity {
              type string;
            }
            container threshold {
              leaf absolute {
                type string;
              }
              leaf relative {
                type string;
              }
            }
          }
          leaf delay {
            type string;
          }
          leaf description {
            type string;
          }
          leaf interval {
            type string;
          }
          container twamp-light {
            leaf dest-udp-port {
              type string;
            }
            leaf dscp {
              type ncs_compliance_template_dscp-type;
            }
            leaf fc {
              type ncs_compliance_template_fc-name;
            }
          }
          leaf shutdown {
            type string;
          }
        }
      }
      container twamp {
        container twamp-test-pdu {
          leaf ipv4-timestamping {
            type string;
          }
          leaf ipv6-timestamping {
            type string;
          }
        }
        container server {
          leaf inactivity-timeout {
            type string;
          }
          leaf max-conn-server {
            type string;
          }
          leaf max-sess-server {
            type string;
          }
          list prefix {
            // NCS patched for predictable order
            ordered-by user;
            key "ip-prefix";
            leaf ip-prefix {
              type string;
            }
            leaf description {
              type string;
            }
            leaf max-conn-prefix {
              type string;
            }
            leaf max-sess-prefix {
              type string;
            }
          }
          leaf shutdown {
            type string;
          }
        }
      }
    }
    container mirror {
      list mirror-dest {
        // NCS patched for predictable order
        ordered-by user;
        key "service-id";
        uses ncs_compliance_template_service-id-grouping;
        leaf name {
          type string;
        }
        list pcap {
          // NCS patched for predictable order
          ordered-by user;
          key "name";
          leaf name {
            type string;
          }
          leaf file-url {
            type string;
          }
        }
        leaf mirror-type {
          type string;
        }
        leaf type {
          type string;
        }
        leaf description {
          type string;
        }
        leaf enable-port-id {
          type empty;
        }
        container encap {
          list layer-3-encap {
            // NCS patched for predictable order
            ordered-by user;
            key "encap";
            leaf encap {
              type string;
            }
            leaf direction-bit {
              type empty;
            }
            container gateway {
              container ip {
                leaf src {
                  type string;
                }
                leaf dest {
                  type string;
                }
              }
              container udp {
                leaf src {
                  type string;
                }
                leaf dest {
                  type string;
                }
              }
            }
          }
        }
        list endpoint {
          // NCS patched for predictable order
          ordered-by user;
          key "endpoint-name";
          leaf endpoint-name {
            type ncs_compliance_template_string32;
          }
          leaf description {
            type string;
          }
          leaf revert-time {
            type string;
          }
        }
        leaf fc {
          type ncs_compliance_template_fc-name;
        }
        container isa-aa-group {
          leaf aa-group-id {
            tailf:cli-drop-node-name;
            type string;
          }
          leaf traffic-direction {
            tailf:cli-drop-node-name;
            type string;
          }
        }
        container remote-source {
          presence "true";
          leaf far-end {
            type string;
          }
          list spoke-sdp {
            // NCS patched for predictable order
            ordered-by user;
            key "sdp-id vc-id";
            leaf sdp-id {
              type string;
            }
            leaf vc-id {
              type string;
            }
            leaf endpoint {
              type ncs_compliance_template_string32;
            }
            leaf vc-type {
              type string;
            }
            leaf shutdown {
              type string;
            }
          }
        }
        list sap {
          // NCS patched for predictable order
          ordered-by user;
          key "sap-id";
          leaf sap-id {
            type string;
          }
          container cem {
            container packet {
              choice packet {
                leaf jitter-buffer {
                  type string;
                }
                leaf bytes {
                  type string;
                }
              }
            }
            leaf rtp-header {
              type empty;
            }
          }
          container egress {
            container ip-mirror {
              container sa-mac {
                leaf sa-mac {
                  tailf:cli-drop-node-name;
                  type ncs_compliance_template_ieee-mac;
                }
                leaf da-mac {
                  type ncs_compliance_template_ieee-mac;
                }
              }
            }
            leaf qos {
              type string;
            }
          }
        }
        leaf service-name {
          type string;
        }
        leaf shutdown {
          type string;
        }
        leaf slice-size {
          type string;
        }
        list spoke-sdp {
          // NCS patched for predictable order
          ordered-by user;
          key "sdp-id vc-id";
          leaf sdp-id {
            type string;
          }
          leaf vc-id {
            type string;
          }
          leaf endpoint {
            type ncs_compliance_template_string32;
          }
          leaf vc-type {
            type string;
          }
          leaf control-word {
            type empty;
          }
          leaf precedence {
            type string;
          }
          container egress {
            container l2tpv3 {
              leaf cookie {
                type string;
              }
            }
            leaf vc-label {
              type string;
            }
          }
          container ingress {
            leaf vc-label {
              type string;
            }
          }
          leaf shutdown {
            type string;
          }
        }
      }
      list mirror-source {
        // NCS patched for predictable order
        ordered-by user;
        key "service-id";
        leaf service-id {
          type ncs_compliance_template_service-id;
        }
        list port {
          // NCS patched for predictable order
          ordered-by user;
          tailf:cli-suppress-mode;
          key "name";
          leaf name {
            type string;
          }
          leaf egress {
            type empty;
          }
          leaf ingress {
            type empty;
          }
        }
        list sap {
          // NCS patched for predictable order
          ordered-by user;
          tailf:cli-suppress-mode;
          key "sap-id";
          leaf sap-id {
            type string;
          }
          leaf egress {
            type empty;
          }
          leaf ingress {
            type empty;
          }
        }
        leaf shutdown {
          type string;
        }
      }
    }
    container saa {
      list test {
        // NCS patched for predictable order
        ordered-by user;
        key "test-name";
        leaf test-name {
          type string;
        }
        leaf owner {
          type string;
        }
        leaf accounting-policy {
          type string;
        }
        leaf continuous {
          type empty;
        }
        leaf description {
          type string;
        }

        grouping saa-test-event-grouping {
          leaf rising-threshold {
            type string;
          }
          leaf falling-threshold {
            type string;
          }
          leaf direction {
            type string;
          }
        }
        list jitter-event {
          // NCS patched for predictable order
          ordered-by user;
          tailf:cli-suppress-mode;
          key "direction";
          uses saa-test-event-grouping;
        }
        list latency-event {
          // NCS patched for predictable order
          ordered-by user;
          tailf:cli-suppress-mode;
          key "direction";
          uses saa-test-event-grouping;
        }
        list loss-event {
          // NCS patched for predictable order
          ordered-by user;
          tailf:cli-suppress-mode;
          key "direction";
          uses saa-test-event-grouping;
        }
        container type {
          presence "true";
          container cpe-ping {
            leaf service {
              type ncs_compliance_template_service-id;
            }
            leaf destination {
              type string;
            }
            leaf source {
              type string;
            }
            leaf source-mac {
              type ncs_compliance_template_ieee-mac;
            }
            leaf fc {
              type ncs_compliance_template_fc-name;
            }
            leaf profile {
              type string;
            }
            leaf ttl {
              type string;
            }
            leaf count {
              type string;
            }
            leaf send-control {
              type empty;
            }
            leaf return-control {
              type empty;
            }
            leaf interval {
              type string;
            }
          }
          container icmp-ping {
            leaf ip-address {
              tailf:cli-drop-node-name;
              type string;
            }
            leaf size {
              type string;
            }
            leaf source {
              type string;
            }
            leaf interval {
              type string;
            }
            leaf count {
              type string;
            }
            leaf router {
              type string;
            }
            leaf router-instance {
              type string;
            }
          }
          container dns {
            leaf target-addr {
              type string;
            }
            leaf name-server {
              type string;
            }
            leaf source {
              type string;
            }
            leaf count {
              type string;
            }
            leaf timeout {
              type string;
            }
            leaf interval {
              type string;
            }
            leaf record-type {
              type string;
            }
          }
          container eth-cfm-two-way-delay {
            leaf mac-address {
              tailf:cli-drop-node-name;
              type ncs_compliance_template_ieee-mac;
            }
            leaf mep {
              type string;
            }
            leaf domain {
              type string;
            }
            leaf association {
              type string;
            }
            leaf fc {
              type ncs_compliance_template_fc-name;
            }
            leaf profile {
              type string;
            }
            leaf count {
              type string;
            }
            leaf timeout {
              type string;
            }
            leaf interval {
              type string;
            }
          }
          container lsp-ping {
            leaf lsp-name {
              tailf:cli-drop-node-name;
              type string;
            }
            leaf path {
              type string;
            }
            leaf fc {
              type ncs_compliance_template_fc-name;
            }
            leaf profile {
              type string;
            }
            leaf interval {
              type string;
            }
            leaf send-count {
              type string;
            }
            leaf size {
              type string;
            }
            leaf src-ip-address {
              type string;
            }
            leaf timeout {
              type string;
            }
            leaf ttl {
              type string;
            }
          }
          container sdp-ping {
            leaf orig-sdp-id {
              tailf:cli-drop-node-name;
              type string;
            }
            leaf resp-sdp {
              type string;
            }
            leaf fc {
              type ncs_compliance_template_fc-name;
            }
            leaf profile {
              type string;
            }
            leaf size {
              type string;
            }
            leaf count {
              type string;
            }
            leaf timeout {
              type string;
            }
            leaf interval {
              type string;
            }
          }
          container vprn-ping {
            leaf service-id {
              tailf:cli-drop-node-name;
              type ncs_compliance_template_service-id;
            }
            leaf source {
              type string;
            }
            leaf destination {
              type string;
            }
            leaf fc {
              type ncs_compliance_template_fc-name;
            }
            leaf profile {
              type string;
            }
            leaf size {
              type string;
            }
            leaf ttl {
              type string;
            }
            leaf count {
              type string;
            }
            leaf return-control {
              type empty;
            }
            leaf timeout {
              type string;
            }
            leaf interval {
              type string;
            }
          }
        }
        container trap-gen {
          leaf probe-fail-enable {
            type empty;
          }
          leaf probe-fail-threshold {
            type string;
          }
          leaf test-completion-enable {
            type empty;
          }
          leaf test-fail-enable {
            type empty;
          }
          leaf test-fail-threshold {
            type string;
          }
        }
        leaf probe-history {
          type string;
        }
        leaf shutdown {
          type string;
        }
      }
    }
    container subscriber-mgmt {
      list category-map {
        // NCS patched for predictable order
        ordered-by user;
        key "name";
        leaf name {
          type string;
        }
        leaf description {
          type string;
        }
        leaf gx-session-level-usage {
          type string;
        }
        list category {
          // NCS patched for predictable order
          ordered-by user;
          key "name";
          leaf name {
            type string;
          }
          leaf credit-type-override {
            type string;
          }
          leaf rating-group {
            type string;
          }
          list queue {
            // NCS patched for predictable order
            ordered-by user;
            tailf:cli-suppress-mode;
            key "id";
            leaf id {
              type string;
            }
            leaf type {
              tailf:cli-drop-node-name;
              type string;
            }
          }
          list policer {
            // NCS patched for predictable order
            ordered-by user;
            tailf:cli-suppress-mode;
            key "id";
            leaf id {
              type string;
            }
            leaf type {
              tailf:cli-drop-node-name;
              type string;
            }
          }
        }
      }
      list credit-control-policy {
        // NCS patched for predictable order
        ordered-by user;
        key "policy-name";
        leaf policy-name {
          type string;
        }
        leaf description {
          type string;
        }
        container credit-control-server {
          leaf diameter {
            type string;
          }
        }
        leaf default-category-map {
          type string;
        }
      }
      list diameter-application-policy {
        // NCS patched for predictable order
        ordered-by user;
        key "name";
        leaf name {
          type string;
        }
        leaf application {
          type string;
        }
        leaf diameter-peer-policy {
          type ncs_compliance_template_string32;
        }
        container on-failure {
          leaf failover {
            type string;
          }
          leaf handling {
            type string;
          }
        }
        container gy {
          container avp-subscription-id {
            leaf origin {
              tailf:cli-drop-node-name;
              type string;
            }
            leaf type {
              type string;
            }
          }
          container extended-failure-handling {
            leaf shutdown {
              type string;
            }
            container interim-credit {
              leaf max-attempts {
                type string;
              }
              leaf reporting {
                type empty;
              }
            }
          }
        }
      }
      list local-user-db {
        // NCS patched for predictable order
        ordered-by user;
        key "name";
        leaf name {
          type string;
        }
        container ipoe {
          leaf-list match-list {
            // NCS patched for predictable order
            ordered-by user;
            type string;
          }
          list host {
            // NCS patched for predictable order
            ordered-by user;
            key "host-name";
            leaf host-name {
              type string;
            }
            leaf auth-policy {
              type string;
            }
            list identification-strings {
              // NCS patched for predictable order
              ordered-by user;
              key "option-number";
              leaf option-number {
                type string;
              }
              leaf sla-profile-string {
                type string;
              }
              leaf sub-profile-string {
                type string;
              }
            }
            container msap-defaults {
              leaf group-interface {
                type string;
              }
              leaf policy {
                type string;
              }
              leaf service {
                type string;
              }
            }
            leaf ipv6-wan-address-pool {
              type string;
            }
            leaf ipv6-delegated-prefix-pool {
              type string;
            }
            container options {
              leaf subnet-mask {
                type string;
              }
              leaf default-router {
                type string;
              }
            }
            leaf server {
              type string;
            }
            container host-identification {
              container option60 {
                leaf string {
                  type string;
                }
              }
              container circuit-id {
                leaf string {
                  type string;
                }
              }
              leaf sap-id {
                type string;
              }
            }
            container address {
              leaf pool {
                type string;
              }
            }
            leaf shutdown {
              type string;
            }
          }
        }
        container ppp {
          leaf-list match-list {
            // NCS patched for predictable order
            ordered-by user;
            type string;
          }
          list host {
            // NCS patched for predictable order
            ordered-by user;
            key "host-name";
            leaf host-name {
              type string;
            }
            leaf auth-policy {
              type string;
            }
            leaf pre-auth-policy {
              type string;
            }
            container host-identification {
              container username {
                leaf name {
                  tailf:cli-drop-node-name;
                  type string;
                }
                leaf domain {
                  tailf:cli-drop-node-name;
                  type string;
                }
              }
            }
            container password {
              leaf ignore {
                type empty;
              }
            }
            container l2tp {
              container group {
                leaf name {
                  tailf:cli-drop-node-name;
                  type string;
                }
              }
            }
            container address {
              leaf pool {
                type string;
              }
            }
            leaf shutdown {
              type string;
            }
          }
        }
        leaf shutdown {
          type string;
        }
      }

      grouping radius-attributes-grouping {
        leaf access-loop-options {
          type empty;
        }
        leaf calling-station-id {
          type string;
        }
        leaf circuit-id {
          type empty;
        }
        leaf dhcp-vendor-class-id {
          type empty;
        }
        leaf mac-address {
          type empty;
        }
        leaf nas-port {
          type string;
        }
        container nas-port-id {
          presence "true";
          leaf prefix-string {
            type string;
          }
          leaf suffix {
            type string;
          }
        }
        container nas-port-type {
          presence "true";
          leaf port-type {
            tailf:cli-drop-node-name;
            type string;
          }
        }
        leaf nas-identifier {
          type empty;
        }
        leaf remote-id {
          type empty;
        }
        leaf tunnel-server-attrs {
          type empty;
        }
        leaf wifi-num-attached-ues {
          type empty;
        }
        leaf wifi-ssid-vlan {
          type empty;
        }
      }
      container auto-sub-id-key {
        leaf-list ppp-sub-id-key {
          // NCS patched for predictable order
          ordered-by user;
          type string;
        }
        leaf-list ipoe-sub-id-key {
          // NCS patched for predictable order
          ordered-by user;
          type string;
        }
      }
      list authentication-policy {
        // NCS patched for predictable order
        ordered-by user;
        key "name";
        leaf name {
          type string;
        }
        leaf description {
          type string;
        }
        container fallback-action {
          leaf accept {
            type empty;
          }
          leaf user-db {
            type ncs_compliance_template_string32;
          }
          leaf force-probing {
            type empty;
          }
        }
        container include-radius-attribute {
          container acct-session-id {
            presence "true";
            leaf session {
              tailf:cli-drop-node-name;
              type string;
            }
          }
          leaf called-station-id {
            type empty;
          }
          leaf dhcp-options {
            type empty;
          }
          leaf dhcp6-options {
            type empty;
          }
          leaf pppoe-service-name {
            type empty;
          }
          uses radius-attributes-grouping;
        }
        leaf re-authentication {
          type empty;
        }
        leaf radius-server-policy {
          type ncs_compliance_template_string32;
        }
        leaf-list send-acct-stop-on-fail {
          // NCS patched for predictable order
          ordered-by user;
          type string;
        }
        container password {
          leaf pw {
            tailf:cli-drop-node-name;
            type string;
          }
          leaf hashing-scheme {
            tailf:cli-drop-node-name;
            type ncs_compliance_template_hash-method;
          }
        }
        leaf pppoe-access-method {
          type string;
        }
        container user-name-format {
          leaf format {
            tailf:cli-drop-node-name;
            type string;
          }
        }
      }
      list host-lockout-policy {
        // NCS patched for predictable order
        ordered-by user;
        key "policy-name";
        leaf policy-name {
          type ncs_compliance_template_string32;
        }
        leaf description {
          type string;
        }
        leaf lockout-reset-time {
          type string;
        }
        container lockout-time {
          leaf min {
            type string;
          }
          leaf max {
            type string;
          }
        }
        leaf max-lockout-hosts {
          type string;
        }
        leaf host-key {
          type string;
        }
      }
      list msap-policy {
        // NCS patched for predictable order
        ordered-by user;
        key "msap-policy-name";
        leaf msap-policy-name {
          type ncs_compliance_template_string32;
        }
        container cpu-protection {
          leaf policy-id {
            tailf:cli-drop-node-name;
            type string;
          }
          leaf monitoring {
            tailf:cli-drop-node-name;
            type string;
          }
        }
        leaf dist-cpu-protection {
          type string;
        }
        leaf description {
          type string;
        }
        container sub-sla-mgmt {
          container def-sub-id {
            choice def-sub-id {
              leaf use-sap-id {
                type empty;
              }
              leaf use-auto-id {
                type empty;
              }
              leaf string {
                type string;
              }
            }
          }
          container def-inter-dest-id {
            leaf type {
              tailf:cli-drop-node-name;
              type string;
            }
          }
          leaf def-sub-profile {
            type string;
          }
          leaf def-sla-profile {
            type string;
          }
          leaf sub-ident-policy {
            type string;
          }
          container single-sub-parameters {
            leaf profiled-traffic-only {
              type empty;
            }
          }
        }
        container ies-vprn-only-sap-parameters {
          leaf anti-spoof {
            type string;
          }
          container ingress {
            container qos {
              tailf:cli-drop-node-name;
              leaf qos {
                type string;
              }
              leaf queueing {
                tailf:cli-drop-node-name;
                type string;
              }
            }
          }
          container egress {
            leaf qos {
              type string;
            }
          }
        }
      }
      list ipoe-session-policy {
        // NCS patched for predictable order
        ordered-by user;
        key "policy-name";
        leaf policy-name {
          type ncs_compliance_template_string32;
        }
        leaf description {
          type string;
        }
        container session-key {
          leaf sap {
            type empty;
          }
          leaf mac {
            type empty;
          }
          leaf cid {
            type empty;
          }
          leaf rid {
            type empty;
          }
        }
      }
      list ppp-policy {
        // NCS patched for predictable order
        ordered-by user;
        key "ppp-policy-name";
        leaf ppp-policy-name {
          type ncs_compliance_template_string32;
        }
        leaf description {
          type string;
        }
        leaf ppp-mtu {
          type string;
        }
        container default-pap-password {
          leaf password {
            tailf:cli-drop-node-name;
            type string;
          }
          leaf method {
            tailf:cli-drop-node-name;
            type ncs_compliance_template_hash-method;
          }
        }
        leaf default-user-name {
          type string;
        }
        container keepalive {
          leaf seconds {
            tailf:cli-drop-node-name;
            type string;
          }
          leaf hold-up-multiplier {
            type string;
          }
        }
        container max-sessions-per-mac {
          leaf sessions {
            tailf:cli-drop-node-name;
            type string;
          }
          leaf allow-same-circuit-id-for-dhcp {
            type empty;
          }
        }
        leaf ppp-authentication {
          type string;
        }
        leaf session-timeout {
          type string;
        }
      }
      list radius-accounting-policy {
        // NCS patched for predictable order
        ordered-by user;
        key "name";
        leaf name {
          type ncs_compliance_template_string32;
        }
        leaf delay-start-time {
          type string;
        }
        leaf queue-instance-accounting {
          type string;
        }
        container session-accounting {
          presence "true";
          leaf-list keywords {
            // NCS patched for predictable order
            ordered-by user;
            tailf:cli-drop-node-name;
            type string;
          }
        }
        leaf description {
          type string;
        }
        container host-accounting {
          presence "true";
          leaf interim-update {
            type empty;
          }
        }
        container include-radius-attribute {
          uses radius-attributes-grouping;
          leaf detailed-acct-attributes {
            type string;
          }
          leaf acct-authentic {
            type empty;
          }
          leaf acct-delay-time {
            type empty;
          }
          leaf alc-acct-triggered-reason {
            type empty;
          }
          leaf alc-error-code {
            type empty;
          }
          leaf all-authorized-session-addresses {
            type empty;
          }
          leaf brg-num-active-sessions {
            type empty;
          }
          leaf delegated-ipv6-prefix {
            type empty;
          }
          leaf framed-interface-id {
            type empty;
          }
          leaf framed-ip-netmask {
            type empty;
          }
          leaf framed-ipv6-route {
            type empty;
          }
          leaf framed-route {
            type empty;
          }
          leaf framed-ip-addr {
            type empty;
          }
          leaf framed-ipv6-prefix {
            type empty;
          }
          leaf ipv6-address {
            type empty;
          }
          leaf nat-port-range {
            type empty;
          }
          leaf std-acct-attributes {
            type empty;
          }
          leaf tunnel-client-attrs {
            type empty;
          }
          leaf steering-profile {
            type empty;
          }
          leaf sub-profile {
            type empty;
          }
          leaf sla-profile {
            type empty;
          }
          leaf subscriber-id {
            type empty;
          }
          leaf user-name {
            type empty;
          }
          leaf v6-aggregate-stats {
            type empty;
          }
          leaf wifi-rssi {
            type empty;
          }
        }
        leaf radius-server-policy {
          type ncs_compliance_template_string32;
        }
        leaf session-id-format {
          type string;
        }
        leaf update-interval {
          type string;
        }
      }
      list shcv-policy {
        // NCS patched for predictable order
        ordered-by user;
        key "shcv-policy-name";
        leaf shcv-policy-name {
          type string;
        }
        leaf description {
          type string;
        }
        container layer-3 {
          leaf source-ip-origin {
            type string;
          }
        }
        container periodic {
          leaf action {
            type string;
          }
          leaf interval {
            type string;
          }
          leaf retry-count {
            type string;
          }
          leaf timeout {
            type string;
          }
          leaf shutdown {
            type string;
          }
        }
        container trigger {

          grouping trigger-grouping {
            leaf shutdown {
              type string;
            }
            leaf retry-count {
              type string;
            }
            leaf timeout {
              type string;
            }
          }
          container ip-conflict {
            uses trigger-grouping;
          }
          container host-limit-exceeded {
            uses trigger-grouping;
          }
          container inactivity {
            // NCS expand uses statement
            leaf shutdown {
              type string;
            }
            leaf retry-count {
              type string;
            }
            leaf timeout {
              type string;
            }
          }
          container mobility {
            uses trigger-grouping;
          }
          container mac-learning {
            // NCS expand uses statement
            leaf shutdown {
              type string;
            }
            leaf retry-count {
              type string;
            }
            leaf timeout {
              type string;
            }
          }
        }
        container vpls {
          leaf source-ip {
            type string;
          }
          leaf source-mac {
            type ncs_compliance_template_ieee-mac;
          }
        }
      }
      list sla-profile {
        // NCS patched for predictable order
        ordered-by user;
        key "sla-profile-name";
        leaf sla-profile-name {
          type string;
        }
        leaf description {
          type string;
        }
        leaf credit-control-policy {
          type string;
        }
        container host-limit {
          leaf max-number-of-hosts {
            tailf:cli-drop-node-name;
            type string;
          }
          leaf remove-oldest {
            type empty;
          }
        }
        container host-limits {
          leaf ipv4-overall {
            type string;
          }
          leaf ipv4-dhcp {
            type string;
          }
          leaf ipv6-pd-ipoe-dhcp {
            type string;
          }
          leaf ipv6-wan-ipoe-dhcp {
            type string;
          }
          leaf ipv6-overall {
            type string;
          }
          leaf overall {
            type string;
          }
        }
        container ingress {
          list qos {
            // NCS patched for predictable order
            ordered-by user;
            key "id";
            leaf id {
              type string;
            }
            leaf queuing {
              tailf:cli-drop-node-name;
              type string;
            }
            list queue {
              // NCS patched for predictable order
              ordered-by user;
              key "queue-id";
              leaf queue-id {
                type string;
              }
              leaf stat-mode {
                type string;
              }
            }
            list policer {
              // NCS patched for predictable order
              ordered-by user;
              key "policer-id";
              leaf policer-id {
                type string;
              }
              leaf stat-mode {
                type ncs_compliance_template_policer-stat-mode;
              }
            }
          }
          leaf ip-filter {
            type ncs_compliance_template_filter-id;
          }
          leaf ipv6-filter {
            type ncs_compliance_template_filter-id;
          }
        }
        container egress {
          list qos {
            // NCS patched for predictable order
            ordered-by user;
            key "id";
            leaf id {
              type string;
            }
            leaf multipoint-shared {
              type empty;
            }
            leaf vport-scheduler {
              type empty;
            }
            list queue {
              // NCS patched for predictable order
              ordered-by user;
              key "queue-id";
              leaf queue-id {
                type string;
              }
              leaf stat-mode {
                type string;
              }
            }
            list policer {
              // NCS patched for predictable order
              ordered-by user;
              key "policer-id";
              leaf policer-id {
                type string;
              }
              leaf stat-mode {
                type ncs_compliance_template_policer-stat-mode;
              }
            }
          }
          leaf ip-filter {
            type ncs_compliance_template_filter-id;
          }
          leaf ipv6-filter {
            type ncs_compliance_template_filter-id;
          }
          leaf qos-marking-from-sap {
            type string;
          }
          list scheduler-policy {
            // NCS patched for predictable order
            ordered-by user;
            key "scheduler-policy-name";
            leaf scheduler-policy-name {
              type string;
            }
            list scheduler {
              // NCS patched for predictable order
              ordered-by user;
              tailf:cli-suppress-mode;
              key "scheduler-name";
              leaf scheduler-name {
                type string;
              }
              leaf rate {
                type ncs_compliance_template_rate-type;
              }
              leaf cir {
                type ncs_compliance_template_rate-type-with-sum;
              }
            }
          }
        }
      }
      list sub-ident-policy {
        // NCS patched for predictable order
        ordered-by user;
        key "sub-ident-policy-name";
        leaf sub-ident-policy-name {
          type string;
        }
        leaf description {
          type string;
        }
        container app-profile-map {
          leaf use-direct-map-as-default {
            type empty;
          }
        }
        leaf strings-from-option {
          type string;
        }
        container sub-profile-map {
          leaf use-direct-map-as-default {
            type empty;
          }
        }
        container sla-profile-map {
          leaf use-direct-map-as-default {
            type empty;
          }
        }
      }
      list igmp-policy {
        // NCS patched for predictable order
        ordered-by user;
        key "name";
        leaf name {
          type string;
        }
        leaf per-host-replication {
          type empty;
        }
        container static {
          list group {
            // NCS patched for predictable order
            ordered-by user;
            key "ip-address";
            leaf ip-address {
              type string;
            }
            leaf starg {
              type empty;
            }
          }
        }
      }
      list sub-profile {
        // NCS patched for predictable order
        ordered-by user;
        key "sub-profile-name";
        leaf sub-profile-name {
          type string;
        }
        leaf description {
          type string;
        }
        leaf igmp-policy {
          type string;
        }
        leaf accounting-policy {
          type string;
        }
        leaf nat-policy {
          type string;
        }
        leaf collect-stats {
          type empty;
        }
        container radius-accounting {
          leaf-list policy {
            // NCS patched for predictable order
            ordered-by user;
            type ncs_compliance_template_string32;
          }
        }
        container radius-accounting-policy {
          leaf acct-policy-name {
            tailf:cli-drop-node-name;
            type ncs_compliance_template_string32;
          }
          leaf duplicate {
            type ncs_compliance_template_string32;
          }
        }
        container sla-profile-map {
          leaf use-direct-map-as-default {
            type empty;
          }
          list entry {
            // NCS patched for predictable order
            ordered-by user;
            tailf:cli-suppress-mode;
            key "key";
            leaf key {
              type string;
            }
            leaf sla-profile {
              type string;
            }
          }
        }
        container egress {
          container scheduler-policy {
            leaf scheduler-policy-id {
              tailf:cli-drop-node-name;
              type string;
            }
            list scheduler {
              // NCS patched for predictable order
              ordered-by user;
              tailf:cli-suppress-mode;
              key "scheduler-id";
              leaf scheduler-id {
                type string;
              }
              leaf rate {
                type string;
              }
              leaf cir {
                type string;
              }
            }
          }
          container agg-rate-limit {
            leaf agg-rate {
              tailf:cli-drop-node-name;
              type string;
            }
            leaf queue-frame-based-accounting {
              type empty;
            }
          }
        }
      }
    }
    container vrrp {
      list policy {
        // NCS patched for predictable order
        ordered-by user;
        key "policy-id";
        leaf policy-id {
          type string;
        }
        leaf context {
          type ncs_compliance_template_service-id;
        }
        leaf delta-in-use-limit {
          type string;
        }
        leaf description {
          type string;
        }
        container priority-event {

          grouping priority-event-grouping {
            leaf hold-set {
              type string;
            }
            leaf hold-clear {
              type string;
            }
            container priority {
              leaf priority-level {
                tailf:cli-drop-node-name;
                type string;
              }
              leaf keyword {
                tailf:cli-drop-node-name;
                type string;
              }
            }
          }
          list host-unreachable {
            // NCS patched for predictable order
            ordered-by user;
            key "address";
            leaf address {
              type string;
            }
            uses priority-event-grouping;
            leaf drop-count {
              type string;
            }
            leaf interval {
              type string;
            }
            leaf padding-size {
              type string;
            }
            leaf timeout {
              type string;
            }
          }
          list lag-port-down {
            // NCS patched for predictable order
            ordered-by user;
            key "lag-id";
            leaf lag-id {
              type string;
            }
            uses priority-event-grouping;
            list number-down {
              // NCS patched for predictable order
              ordered-by user;
              key "number-of-lag-ports-down";
              leaf number-of-lag-ports-down {
                type string;
              }
              container priority {
                leaf priority-level {
                  tailf:cli-drop-node-name;
                  type string;
                }
                leaf keyword {
                  tailf:cli-drop-node-name;
                  type string;
                }
              }
            }
          }
          list mc-ipsec-non-forwarding {
            // NCS patched for predictable order
            ordered-by user;
            key "tunnel-grp-id";
            leaf tunnel-grp-id {
              type string;
            }
            uses priority-event-grouping;
          }
          list port-down {
            // NCS patched for predictable order
            ordered-by user;
            key "port-id";
            leaf port-id {
              type string;
            }
            uses priority-event-grouping;
          }
          list route-unknown {
            // NCS patched for predictable order
            ordered-by user;
            key "prefix";
            leaf prefix {
              type string;
            }
            uses priority-event-grouping;
            container less-specific {
              presence "true";
              leaf allow-default {
                type empty;
              }
            }
            list next-hop {
              // NCS patched for predictable order
              ordered-by user;
              tailf:cli-suppress-mode;
              key "address";
              leaf address {
                type string;
              }
            }
            list protocol {
              // NCS patched for predictable order
              ordered-by user;
              tailf:cli-suppress-mode;
              key "protocol";
              leaf protocol {
                type string;
              }
            }
          }
        }
      }
    }
    container bof {

      grouping bof-address-grouping {
        leaf address {
          type string;
        }
        leaf type {
          tailf:cli-drop-node-name;
          type string;
        }
      }
      list address {
        // NCS patched for predictable order
        ordered-by user;
        tailf:cli-suppress-mode;
        key "address";
        uses bof-address-grouping;
      }
      container auto-discover {
        presence "true";
        leaf id {
          type string;
        }
        leaf vlan {
          type string;
        }
      }
      leaf autonegotiate {
        type empty;
      }
      leaf console-speed {
        type string;
      }
      leaf dns-domain {
        type string;
      }
      leaf duplex {
        type string;
      }
      leaf fips-140-2 {
        type string;
      }
      leaf ip-mtu {
        type string;
      }
      leaf li-local-save {
        type string;
      }
      leaf li-separate {
        type string;
      }
      leaf persist {
        type string;
      }
      leaf primary-config {
        type string;
      }
      leaf primary-dns {
        type string;
      }
      leaf primary-image {
        type string;
      }
      leaf secondary-config {
        type string;
      }
      leaf secondary-dns {
        type string;
      }
      leaf secondary-image {
        type string;
      }
      leaf speed {
        type string;
      }

      grouping bof-static-route-grouping {
        leaf prefix {
          type string;
        }
        leaf next-hop {
          type string;
        }
      }
      list static-route {
        // NCS patched for predictable order
        ordered-by user;
        tailf:cli-suppress-mode;
        key "prefix";
        uses bof-static-route-grouping;
      }
      leaf tertiary-config {
        type string;
      }
      leaf tertiary-dns {
        type string;
      }
      leaf tertiary-image {
        type string;
      }
      leaf wait {
        type string;
      }
      leaf console-disabled {
        type string;
      }
      list eth-mgmt-address {
        // NCS patched for predictable order
        ordered-by user;
        tailf:cli-suppress-mode;
        key "address";
        uses bof-address-grouping;
      }
      leaf eth-mgmt-autoneg {
        type string;
      }
      leaf eth-mgmt-disabled {
        type string;
      }
      leaf eth-mgmt-duplex {
        type string;
      }
      list eth-mgmt-route {
        // NCS patched for predictable order
        ordered-by user;
        tailf:cli-suppress-mode;
        key "prefix";
        uses bof-static-route-grouping;
      }
      leaf eth-mgmt-speed {
        type string;
      }
      leaf uplinkA-address {
        type string;
      }
      leaf uplinkA-port {
        type string;
      }
      list uplinkA-route {
        // NCS patched for predictable order
        ordered-by user;
        tailf:cli-suppress-mode;
        key "prefix";
        uses bof-static-route-grouping;
      }
      leaf uplinkA-vlan {
        type string;
      }
      leaf uplinkA-autoneg {
        type empty;
      }
      leaf uplinkA-duplex {
        type string;
      }
      leaf uplinkA-speed {
        type string;
      }
      leaf uplinkB-address {
        type string;
      }
      leaf uplinkB-port {
        type string;
      }
      list uplinkB-route {
        // NCS patched for predictable order
        ordered-by user;
        tailf:cli-suppress-mode;
        key "prefix";
        uses bof-static-route-grouping;
      }
      leaf uplinkB-vlan {
        type string;
      }
      leaf uplinkB-autoneg {
        type empty;
      }
      leaf uplinkB-duplex {
        type string;
      }
      leaf uplinkB-speed {
        type string;
      }
      leaf uplink-mode {
        type string;
      }
      leaf usb-port-key {
        type string;
      }
      leaf license-file {
        type string;
      }
    }
    container debug {
      container lag {
        list lag-id {
          // NCS patched for predictable order
          ordered-by user;
          tailf:cli-suppress-mode;
          key "id";
          leaf id {
            type string;
          }
          container items {
            tailf:cli-drop-node-name;
            leaf-list debug-item {
              // NCS patched for predictable order
              ordered-by user;
              tailf:cli-drop-node-name;
              type string;
            }
            leaf-list port {
              // NCS patched for predictable order
              ordered-by user;
              type string;
            }
          }
        }
      }
      list mirror-source {
        // NCS patched for predictable order
        ordered-by user;
        key "service-id";
        leaf service-id {
          type ncs_compliance_template_service-id;
        }
        list ingress-label {
          // NCS patched for predictable order
          ordered-by user;
          tailf:cli-suppress-mode;
          key "label";
          leaf label {
            type string;
          }
        }
        list ip-filter {
          // NCS patched for predictable order
          ordered-by user;
          tailf:cli-suppress-mode;
          key "ip-filter-name";
          leaf ip-filter-name {
            type ncs_compliance_template_filter-id;
          }
          leaf-list entry {
            // NCS patched for predictable order
            ordered-by user;
            type string;
          }
        }
        list mac-filter {
          // NCS patched for predictable order
          ordered-by user;
          tailf:cli-suppress-mode;
          key "mac-filter-name";
          leaf mac-filter-name {
            type ncs_compliance_template_filter-id;
          }
          leaf-list entry {
            // NCS patched for predictable order
            ordered-by user;
            type string;
          }
        }
        list port {
          // NCS patched for predictable order
          ordered-by user;
          tailf:cli-suppress-mode;
          key "port-id";
          leaf lag {
            type empty;
          }
          leaf port-id {
            type string;
          }
          leaf ingress {
            type empty;
          }
          leaf egress {
            type empty;
          }
        }
        list sap {
          // NCS patched for predictable order
          ordered-by user;
          tailf:cli-suppress-mode;
          key "sap-id";
          leaf sap-id {
            type string;
          }
          leaf ingress {
            type empty;
          }
          leaf egress {
            type empty;
          }
        }
        list subscriber {
          // NCS patched for predictable order
          ordered-by user;
          tailf:cli-suppress-mode;
          key "sub-ident-string";
          leaf sub-ident-string {
            type string;
          }
          leaf sap {
            type string;
          }
          leaf ip {
            type string;
          }
          leaf mac {
            type ncs_compliance_template_ieee-mac;
          }
          leaf sla-profile-name {
            tailf:alt-name "sla-profile";
            type string;
          }
          leaf fc {
            type ncs_compliance_template_fc-name;
          }
          leaf ingress {
            type empty;
          }
          leaf egress {
            type empty;
          }
        }
        leaf shutdown {
          type string;
        }
      }

      grouping debug-router-grouping {
        container bgp {

          grouping neighbor-grouping {
            choice zzz {
              leaf neighbor {
                type string;
              }
              leaf group {
                type string;
              }
            }
          }
          container events {
            uses neighbor-grouping;
          }
          container packets {
            uses neighbor-grouping;
          }
        }
        container ip {
          leaf arp {
            type empty;
          }
          leaf icmp {
            type empty;
          }
          leaf icmp6 {
            type empty;
          }
        }
      }
      container router {
        list router-id {
          // NCS patched for predictable order
          ordered-by user;
          tailf:cli-drop-node-name;
          key "router-name";
          leaf router-name {
            type ncs_compliance_template_router-type;
          }
          // NCS expand uses statement
          container bgp {

            grouping neighbor-grouping {
              choice zzz {
                leaf neighbor {
                  type string;
                }
                leaf group {
                  type string;
                }
              }
            }
            container events {
              // NCS expand uses statement
              choice zzz {
                leaf neighbor {
                  type string;
                }
                leaf group {
                  type string;
                }
              }
            }
            container packets {
              // NCS expand uses statement
              choice zzz {
                leaf neighbor {
                  type string;
                }
                leaf group {
                  type string;
                }
              }
            }
          }
          container ip {
            leaf arp {
              type empty;
            }
            leaf icmp {
              type empty;
            }
            leaf icmp6 {
              type empty;
            }
          }
        }
        list service-name {
          // NCS patched for predictable order
          ordered-by user;
          key "name";
          leaf name {
            type string;
          }
          uses debug-router-grouping;
        }
      }
    }
    container external-alarms {
      list alarm {
        // NCS patched for predictable order
        ordered-by user;
        key "alarm-id";
        leaf alarm-id {
          type string;
        }
        leaf chassis-alarming {
          type string;
        }
        leaf description {
          type string;
        }
        leaf log {
          type string;
        }
        container thresholds {
          container analog {
            container level {
              leaf op {
                tailf:cli-drop-node-name;
                type string;
              }
              leaf millivolts {
                tailf:cli-drop-node-name;
                type string;
              }
            }
          }
        }
        container trigger {
          leaf type {
            tailf:cli-drop-node-name;
            type string;
          }
          leaf-list alarm-input {
            // NCS patched for predictable order
            ordered-by user;
            tailf:cli-drop-node-name;
            type string;
          }
        }
        leaf severity {
          type string;
        }
        leaf shutdown {
          type string;
        }
      }
    }
    container python {
      list python-policy {
        // NCS patched for predictable order
        ordered-by user;
        key "name";
        leaf name {
          type ncs_compliance_template_string32;
        }
        leaf description {
          type string;
        }
        list dhcp {
          // NCS patched for predictable order
          ordered-by user;
          tailf:cli-suppress-mode;
          key "type direction";
          leaf type {
            type string;
          }
          leaf direction {
            type string;
          }
          leaf script {
            type ncs_compliance_template_string32;
          }
        }
        list dhcp6 {
          // NCS patched for predictable order
          ordered-by user;
          tailf:cli-suppress-mode;
          key "type direction";
          leaf type {
            type string;
          }
          leaf direction {
            type string;
          }
          leaf script {
            type ncs_compliance_template_string32;
          }
        }
        list radius {
          // NCS patched for predictable order
          ordered-by user;
          tailf:cli-suppress-mode;
          key "type direction";
          leaf type {
            type string;
          }
          leaf direction {
            type string;
          }
          leaf script {
            type ncs_compliance_template_string32;
          }
        }
      }
      list python-script {
        // NCS patched for predictable order
        ordered-by user;
        key "name";
        leaf name {
          type ncs_compliance_template_string32;
        }
        leaf action-on-fail {
          type string;
        }
        leaf description {
          type string;
        }
        leaf primary-url {
          type string;
        }
        leaf shutdown {
          type string;
        }
      }
    }
    container commands {
      tailf:cli-drop-node-name;
    }
  }
}
