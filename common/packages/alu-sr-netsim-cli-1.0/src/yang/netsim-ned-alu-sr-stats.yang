module netsim-ned-alu-sr-stats {
  namespace "http://tail-f.com/ned/alu-sr/stats";
  prefix alu-stats;

  import tailf-common {
    prefix tailf;
  }
  import ietf-inet-types {
    prefix inet;
  }
  import ietf-yang-types {
    prefix yang;
  }

  typedef state {
    type enumeration {
      enum Up;
      enum Down;
      enum "Not configured";
    }
  }

  grouping hardware-data-common {
    leaf part-number {
      type string;
    }
    leaf clei-code {
      type string;
    }
    leaf serial-number {
      type string;
    }
    leaf manufacture-date {
      type string;
    }
    leaf manufacturing-deviations {
      type string;
    }
    leaf manufacturing-assembly-number {
      type string;
    }
    leaf last-boot {
      type yang:date-and-time;
    }
    leaf alarm-state {
      type string;
    }
  }

  grouping hardware-data-state {
    leaf oper-state {
      type string;
    }
    leaf admin-state {
      type string;
    }
  }

  grouping hardware-data-version {
    leaf software-version {
      type string;
    }
    leaf software-boot-version {
      type string;
    }
  }

  grouping hardware-data-temperature {
    leaf temperature {
      type string;
    }
    leaf temperature-threshold {
      type string;
    }
  }

  grouping provisioned-equipped-type {
    leaf provisioned-type {
      type string;
    }
    leaf equipped-type {
      type string;
    }
  }

  grouping packets-octets-grouping {
    leaf packets {
      type uint64;
    }
    leaf octets {
      type uint64;
    }
  }

  grouping allocated-grouping {
    leaf allocated {
      type uint64;
    }
  }

  grouping total-allocated-free-grouping {
    leaf total {
      type uint64;
    }
    uses allocated-grouping;
    leaf free {
      type uint64;
    }
  }

  list slot {
    config false;
    key "slot-id";
    leaf slot-id {
      type uint32;
    }
    list mda {
      key "mda-id";
      leaf mda-id {
        type uint32;
      }
      leaf ports-maximum {
        type uint32;
      }
      leaf ports-equipped {
        type uint32;
      }
      uses hardware-data-common;
      uses hardware-data-state;
      uses hardware-data-version;
      leaf firmware-version {
        type string;
      }
      uses hardware-data-temperature;
      uses provisioned-equipped-type;
    }
    tailf:alt-name "slot-stats";
  }
  list chassis {
    config false;
    key "chassis-id";
    leaf chassis-id {
      type uint32;
    }
    leaf status {
      type string;
    }
    leaf type {
      type string;
    }
    leaf over-temperature-state {
      type string;
    }
    leaf role {
      type string;
    }
    uses hardware-data-common;
    container environment {
      leaf number-of-fans {
        type uint32;
      }
      list fan-tray {
        key "fan-tray-id";
        leaf fan-tray-id {
          type uint32;
        }
        leaf status {
          type string;
        }
        leaf speed {
          type string;
        }
        uses hardware-data-common;
        uses hardware-data-state;
      }
    }
    container power {
      list power-supply-tray {
        key "power-supply-tray-id";
        leaf power-supply-tray-id {
          type uint32;
        }
        leaf status {
          type string;
        }
        leaf equipped-type {
          type string;
        }
        leaf provisioned-type {
          type string;
        }
        leaf power-zone {
          type uint32;
        }
        leaf input-feed-status {
          type string;
        }
        leaf input-power-mode {
          type string;
        }
        uses hardware-data-common;
        uses hardware-data-state;
      }
    }
    tailf:alt-name "chassis-stats";
  }
  list card {
    config false;
    key "card-id";
    leaf card-id {
      type string;
    }
    leaf mda-slots {
      type uint32;
    }
    leaf mda-installed {
      type uint32;
    }
    leaf generation {
      type string;
    }
    uses hardware-data-common;
    uses hardware-data-state;
    uses hardware-data-version;
    uses hardware-data-temperature;
    uses provisioned-equipped-type;
    tailf:alt-name "card-stats";
  }
  list sfm {
    config false;
    key "sfm-id";
    leaf sfm-id {
      type uint32;
    }
    uses hardware-data-common;
    uses hardware-data-state;
    uses hardware-data-temperature;
    uses provisioned-equipped-type;
    tailf:alt-name "sfm-stats";
  }
  container eth-cfm {
    list stack-table {
      config false;
      key "name";
      leaf name {
        type string;
      }
      leaf level {
        type string;
      }
      leaf dir {
        type string;
      }
      leaf md-index {
        type string;
      }
      leaf ma-index {
        type string;
      }
      leaf mep-id {
        type string;
      }
      leaf mac-address {
        type string;
      }
      leaf defect {
        type string;
      }
      leaf g {
        type string;
      }
    }
    tailf:alt-name "eth-cfm-stats";
  }
  list lag {
    config false;
    key "lag-id";
    leaf lag-id {
      type string;
    }
    leaf admin-state {
      type string;
    }
    leaf oper-state {
      type string;
    }
    leaf port-threshold {
      type string;
    }
    leaf up-link-count {
      type string;
    }
    leaf member-port-state {
      type string;
    }
    container details {
      config false;
      container thresholds {
        leaf exceeded-count {
          type string;
        }
        leaf port {
          type string;
        }
        leaf last-cleared {
          type string;
        }
        leaf port-action {
          type string;
        }
        leaf weight {
          type string;
        }
        leaf weight-action {
          type string;
        }
      }
      leaf dynamic-cost {
        type string;
      }
      leaf encap-type {
        type string;
      }
      leaf configured-address {
        type string;
      }
      leaf hardware-address {
        type string;
      }
      leaf lag-if-index {
        type string;
      }
      leaf adapt-qos {
        type string;
      }
      leaf hold-time-down {
        type string;
      }
      leaf port-type {
        type string;
      }
      leaf per-link-hash {
        type string;
      }
      leaf include-egress-hash-config {
        type string;
      }
      leaf forced {
        type string;
      }
      leaf per-fp-ingress-queuing {
        type string;
      }
      leaf per-fp-egress-queuing {
        type string;
      }
      leaf per-fp-sap-instance {
        type string;
      }
      container access {
        leaf bandwidth {
          type string;
        }
        leaf booking-factor {
          type string;
        }
        leaf available-bandwidth {
          type string;
        }
        leaf booked-bandwidth {
          type string;
        }
      }
      container lacp {
        leaf status {
          type string;
        }
        leaf mode {
          type string;
        }
        leaf transmit-Interval {
          type string;
        }
        leaf xmit-standby {
          type string;
        }
      }
      leaf selection-criteria {
        type string;
      }
      leaf slave-to-partner {
        type string;
      }
      leaf mux-control {
        type string;
      }
      container sub-group {
        leaf hold-time {
          type string;
        }
        leaf remaining-time {
          type string;
        }
        leaf selected {
          type string;
        }
        leaf count {
          type string;
        }
        leaf candidate {
          type string;
        }
      }
      leaf system-id {
        type string;
      }
      leaf system-priority {
        type string;
      }
      leaf admin-key {
        type string;
      }
      leaf oper-key {
        type string;
      }
      container prtr {
        leaf system-id {
          type string;
        }
        leaf system-prriority {
          type string;
        }
        leaf oper-key {
          type string;
        }
      }
      leaf standby-signaling {
        type string;
      }
      leaf port-weight-speed {
        type string;
      }
      leaf number-weight-up {
        type string;
      }
      list port {
        key "port-id";
        leaf port-id {
          type string;
        }
        leaf admin-state {
          type string;
        }
        leaf active-standby {
          type string;
        }
        leaf oper-state {
          type string;
        }
        leaf primary {
          type string;
        }
        leaf sub-group {
          type string;
        }
        leaf forced {
          type string;
        }
        leaf priority {
          type string;
        }
      }
      list role {
        key "port-id role";
        leaf port-id {
          type string;
        }
        leaf role {
          type string;
        }
        leaf exp {
          type string;
        }
        leaf def {
          type string;
        }
        leaf dist {
          type string;
        }
        leaf syn {
          type string;
        }
        leaf aggr {
          type string;
        }
        leaf timeout {
          type string;
        }
        leaf activity {
          type string;
        }
      }
    }
    container statistics {
      config false;
      list port {
        key "port-id";
        leaf port-id {
          type string;
        }
        container input {
          config false;
          leaf packets {
            type string;
          }
          leaf bytes {
            type string;
          }
          leaf errors {
            type string;
          }
        }
        container output {
          config false;
          leaf packets {
            type string;
          }
          leaf bytes {
            type string;
          }
          leaf errors {
            type string;
          }
        }
      }
    }
    tailf:alt-name "lag-stats";
  }
  list ports {
    config false;
    key "port-id";
    leaf port-id {
      type string;
    }
    leaf admin-state {
      type string;
    }
    leaf link {
      type boolean;
    }
    leaf port-state {
      type string;
    }
    leaf configured-mtu {
      type uint32;
    }
    leaf operational-mtu {
      type uint32;
    }
    leaf mode {
      type string;
    }
    leaf encap-type {
      type string;
    }
    leaf module-type {
      type string;
    }
    container transceiver-data {
      leaf last-state-change {
        type string;
      }
      container speed {
        container operational {
          leaf value {
            type uint32;
          }
          leaf unit {
            type string;
          }
        }
        container configured {
          leaf value {
            type uint32;
          }
          leaf unit {
            type string;
          }
        }
      }
      container duplex {
        container operational {
          leaf value {
            type string;
          }
        }
        container configured {
          leaf value {
            type string;
          }
        }
      }
      leaf transceiver-type {
        type string;
      }
      leaf model-number {
        type string;
      }
      leaf tx-laser-wavelength {
        type decimal64 {
          fraction-digits 3;
        }
        units "nm";
      }
      leaf diagnostics-capable {
        type string;
      }
      leaf connector-code {
        type string;
      }
      leaf vendor-oui {
        type string;
      }
      leaf manufacture-date {
        type string;
      }
      leaf media {
        type string;
      }
      leaf serial-number {
        type string;
      }
      leaf part-number {
        type string;
      }
      leaf optical-compliance {
        type string;
      }
      leaf link-length-support {
        type string;
      }
      container traffic-statistics {
        container input {
          config false;
          leaf octets {
            type uint64;
          }
          leaf packets {
            type uint64;
          }
          leaf errors {
            type uint64;
          }
          leaf utilization {
            type decimal64 {
              fraction-digits 2;
            }
          }
        }
        container output {
          config false;
          leaf octets {
            type uint64;
          }
          leaf packets {
            type uint64;
          }
          leaf errors {
            type uint64;
          }
          leaf utilization {
            type decimal64 {
              fraction-digits 2;
            }
          }
        }
      }
      list transceiver-digital-diagnostic-monitoring {
        key "name";
        leaf name {
          type string;
        }
        leaf value {
          type decimal64 {
            fraction-digits 2;
          }
        }
        leaf high-alarm {
          type decimal64 {
            fraction-digits 2;
          }
        }
        leaf high-warn {
          type decimal64 {
            fraction-digits 2;
          }
        }
        leaf low-warn {
          type decimal64 {
            fraction-digits 2;
          }
        }
        leaf low-alarm {
          type decimal64 {
            fraction-digits 2;
          }
        }
      }
      container coherent-optical-module {
        leaf present-rx-chan {
          type string;
        }
        leaf alarm-status {
          type string;
        }
        leaf defect-points {
          type string;
        }
        leaf rx-q-margin {
          type string;
        }
        leaf chromatic-dispersion {
          type int64;
          units "ps/nm";
        }
        leaf snr-x-polar {
          type decimal64 {
            fraction-digits 1;
          }
          units "dB";
        }
        leaf differential-group-delay {
          type int32;
          units "ps";
        }
        leaf snr-y-polar {
          type decimal64 {
            fraction-digits 1;
          }
          units "dB";
        }
        leaf pre-fec-ber {
          type string;
        }
        leaf module-state {
          type string;
        }
        leaf tx-turnup-states {
          type string;
        }
        leaf rx-turnup-states {
          type string;
        }
      }
      container otu-interface {
        leaf otu-status {
          type string;
        }
        leaf fec-mode {
          type string;
        }
        leaf async-mapping {
          type string;
        }
        leaf data-rate {
          type string;
        }
        leaf alarm-status {
          type string;
        }
        leaf sm-tti-tx {
          type string;
        }
        leaf sm-tti-rx {
          type string;
        }
        leaf otu-tim {
          type string;
        }
        leaf pm-tti-tx {
          type string;
        }
        leaf pm-tti-rx {
          type string;
        }
        leaf odu-tim {
          type string;
        }
        leaf psi-tti-tx {
          type string;
        }
        leaf psi-tti-rx {
          type string;
        }
        leaf opu-tim {
          type string;
        }
        leaf psi-pt-tx {
          type string;
        }
        leaf psi-pt-ex {
          type string;
        }
        leaf psi-pt-rx {
          type string;
        }
        leaf opu-plm {
          type string;
        }
      }
      container ethernet-statistics {
        leaf broadcast-packets {
          type uint64;
        }
        leaf multicast-packets {
          type uint64;
        }
        leaf undersize-packets {
          type uint64;
        }
        leaf oversize-packets {
          type uint64;
        }
        leaf collisions {
          type uint64;
        }
        leaf drop-events {
          type uint64;
        }
        leaf crc-align-errors {
          type uint64;
        }
        leaf fragments {
          type uint64;
        }
        leaf jabbers {
          type uint64;
        }
        leaf octets {
          type uint64;
        }
        leaf packets {
          type uint64;
        }
        leaf packets-of-octets-64 {
          type uint64;
        }
        leaf packets-of-octets-65-to-127 {
          type uint64;
        }
        leaf packets-of-octets-128-to-255 {
          type uint64;
        }
        leaf packets-of-octets-256-to-511 {
          type uint64;
        }
        leaf packets-to-octets-512-to-1023 {
          type uint64;
        }
        leaf packets-to-octets-1024-to-1518 {
          type uint64;
        }
        leaf packets-of-octets-1519-or-more {
          type uint64;
        }
      }
      container port-statistics {
        leaf unicast-packets-in {
          type uint64;
        }
        leaf unicast-packets-out {
          type uint64;
        }
        leaf multicast-packets-in {
          type uint64;
        }
        leaf multicast-packets-out {
          type uint64;
        }
        leaf broadcast-packets-in {
          type uint64;
        }
        leaf broadcast-packets-out {
          type uint64;
        }
        leaf discards-in {
          type uint64;
        }
        leaf discards-out {
          type uint64;
        }
      }
      list transceiver-lanes {
        key "id";
        leaf id {
          type uint16;
        }
        leaf temp {
          type decimal64 {
            fraction-digits 1;
          }
          units "C";
        }
        leaf tx-bias {
          type decimal64 {
            fraction-digits 1;
          }
          units "mA";
        }
        leaf tx-pwr {
          type decimal64 {
            fraction-digits 2;
          }
          units "dBm";
        }
        leaf rx-pwr {
          type decimal64 {
            fraction-digits 2;
          }
          units "dBm";
        }
      }
    }
    tailf:alt-name "ports-stats";
  }
  list router {
    config false;
    key "name";
    leaf name {
      type string;
    }
    list status {
      key "name";
      leaf name {
        type string;
      }
      leaf admin-state {
        type state;
      }
      leaf oper-state {
        type state;
      }
    }
    list bgp {
      key "neighbor";
      leaf neighbor {
        type union {
          type string;
        }
      }
      leaf description {
        type string;
      }
      leaf as {
        type uint32;
      }
      leaf packets-received {
        type uint64;
      }
      leaf in-queue {
        type uint64;
      }
      leaf up-down {
        type string;
      }
      leaf packets-sent {
        type uint64;
      }
      leaf out-queue {
        type uint64;
      }
      leaf state {
        type enumeration {
          enum Established;
          enum Idle;
          enum Connect;
          enum Active;
          enum OpenSent;
          enum OpenConfirm;
        }
      }
      list stats {
        key "protocol";
        leaf protocol {
          type string;
        }
        leaf rcv {
          type uint64;
        }
        leaf act {
          type uint64;
        }
        leaf sent {
          type uint64;
        }
      }
      container details {
        config false;
        leaf group {
          type string;
        }
        container peer {
          leaf as {
            type uint32;
          }
          leaf port {
            type uint32;
          }
          leaf address {
            type string;
          }
        }
        container local {
          leaf as {
            type uint32;
          }
          leaf port {
            type uint32;
          }
          leaf address {
            type string;
          }
        }
        leaf state {
          type string;
        }
        leaf last-state {
          type string;
        }
        leaf last-event {
          type string;
        }
        leaf last-error {
          type string;
        }
        leaf local-family {
          type string;
        }
        leaf remote-family {
          type string;
        }
      }
    }
    list interface {
      key "ip-int-name";
      leaf ip-int-name {
        type string;
      }
      list addresses {
        key "address";
        leaf address {
          type union {
            type string;
            type enumeration {
              enum -;
            }
          }
        }
        leaf state {
          type string;
        }
      }
      leaf admin-state {
        type state;
      }
      leaf oper-state-ipv4 {
        type state;
      }
      leaf oper-state-ipv6 {
        type state;
      }
      leaf mode {
        type string;
      }
      leaf port-or-sap-id {
        type string;
      }
    }
    container isis {
      list adjacency {
        key "system-id interface";
        leaf system-id {
          type string;
        }
        leaf interface {
          type string;
        }
        leaf usage {
          type string;
        }
        leaf state {
          type string;
        }
        leaf hold {
          type uint32;
        }
      }
    }
    container pim {
      container neighbor {
        container ipv6 {
          list interface {
            key "name neighbor";
            leaf name {
              type string;
            }
            leaf neighbor {
              type string;
            }
            leaf dr-priority {
              type uint32;
            }
            leaf up-time {
              type string;
            }
            leaf expiry-time {
              type string;
            }
            leaf hold-time {
              type uint32;
            }
          }
        }
      }
    }
    list neighbor {
      key "interface address";
      leaf interface {
        type string;
      }
      leaf address {
        type inet:ipv6-address;
      }
      leaf link-layer {
        type yang:mac-address;
      }
      leaf state {
        type enumeration {
          enum incomplete;
          enum reachable;
          enum stale;
          enum delay;
          enum probe;
        }
      }
      leaf origin {
        type enumeration {
          enum dynamic;
          enum static;
        }
      }
      leaf is-router {
        type enumeration {
          enum Yes;
          enum No;
        }
      }
    }
    tailf:alt-name "router-stats";
  }
  container service {
    config false;
    list id {
      key "service-id";
      leaf service-id {
        type uint32;
      }
      leaf service-type {
        type string;
      }
      leaf admin-state {
        type state;
      }
      leaf oper-state {
        type state;
      }
      leaf customer-id {
        type uint32;
      }
      leaf service-name {
        type string;
      }
      list fdb {
        config false;
        key "mac";
        leaf mac {
          type string;
        }
        leaf source-identifier {
          type string;
        }
        leaf type {
          type string;
        }
        leaf last-change {
          type string;
        }
      }
      list arp {
        config false;
        key "ip";
        leaf ip {
          type string;
        }
        leaf mac {
          type string;
        }
        leaf type {
          type string;
        }
        leaf expiry {
          type string;
        }
        leaf interface {
          type string;
        }
        leaf sap {
          type string;
        }
      }
    }
    list sap {
      key "id";
      leaf id {
        type string;
      }
      leaf service-id {
        type string;
      }
      leaf ingress-qos {
        type string;
      }
      leaf ingress-filter {
        type string;
      }
      leaf egress-qos {
        type string;
      }
      leaf egress-filter {
        type string;
      }
      leaf admin-state {
        type state;
      }
      leaf oper-state {
        type state;
      }
      container statistics {
        config false;
        leaf last-cleared-time {
          type string;
        }
        container cpm-ingress {
          container dropped {
            uses packets-octets-grouping;
          }
          container received-valid {
            uses packets-octets-grouping;
          }
          container offered-high-prio {
            uses packets-octets-grouping;
          }
          container offered-low-prio {
            uses packets-octets-grouping;
          }
          container offered-uncolor {
            uses packets-octets-grouping;
          }
          container offered-managed {
            uses packets-octets-grouping;
          }
        }
        container ingress-queueing-stats {
          leaf policy-id {
            type string;
          }
          container dropped-high-prio {
            uses packets-octets-grouping;
          }
          container dropped-low-prio {
            uses packets-octets-grouping;
          }
          container forwarded-in-profile {
            uses packets-octets-grouping;
          }
          container forwarded-out-profile {
            uses packets-octets-grouping;
          }
        }
        container egress-queueing-stats {
          leaf policy-id {
            type string;
          }
          container dropped-in-profile {
            uses packets-octets-grouping;
          }
          container dropped-out-profile {
            uses packets-octets-grouping;
          }
          container forwarded-in-profile {
            uses packets-octets-grouping;
          }
          container forwarded-out-profile {
            uses packets-octets-grouping;
          }
        }
      }
    }
    list sdp {
      key "id";
      leaf id {
        type uint32;
      }
      leaf admin-mtu {
        type uint32;
      }
      leaf oper-mtu {
        type uint32;
      }
      leaf ip-address {
        type union {
          type string;
        }
      }
      leaf admin-state {
        type state;
      }
      leaf oper-state {
        type state;
      }
      leaf deliver {
        type string;
      }
      leaf lsp {
        type string;
      }
      leaf signal {
        type string;
      }
    }
    container active-subscribers {
      container summary {
        leaf total-count {
          type uint32;
        }
      }
    }
    list fdb-info {
      config false;
      key "service-id";
      leaf service-id {
        type string;
      }
      container mac-move {
        leaf status {
          type string;
        }
        leaf rate {
          type string;
        }
        leaf timeout {
          type string;
        }
        leaf retries {
          type string;
        }
      }
      container factor {
        leaf primary {
          type string;
        }
        leaf secondary {
          type string;
        }
      }
      leaf table-size {
        type string;
      }
      leaf allocated-count {
        type string;
      }
      leaf total-in-use {
        type string;
      }
      container counters {
        leaf learned {
          type string;
        }
        leaf static {
          type string;
        }
        leaf oam-mac {
          type string;
        }
        leaf dhcp-mac {
          type string;
        }
        leaf host-mac {
          type string;
        }
        leaf interface-mac {
          type string;
        }
        leaf spb {
          type string;
        }
        leaf cond-mac {
          type string;
        }
        leaf bgp-evpn {
          type string;
        }
        leaf evpn-static {
          type string;
        }
        leaf evpn-duplicate-detect {
          type string;
        }
      }
      container age {
        leaf local {
          type string;
        }
        leaf remote {
          type string;
        }
      }
      container watermark {
        leaf low {
          type string;
        }
        leaf high {
          type string;
        }
      }
      leaf mac-learning {
        type string;
      }
      leaf discard-unknown {
        type string;
      }
      leaf mac-aging {
        type string;
      }
      leaf relearn-only {
        type string;
      }
      leaf mac-subnet-length {
        type string;
      }
      leaf self-learned-fdb {
        type string;
      }
    }
    tailf:alt-name "service-stats";
  }
  container system {
    config false;
    container lldp {
      list neighbor {
        key "port";
        leaf port {
          type string;
        }
        leaf scope {
          type enumeration {
            enum NB;
            enum NTPMR;
            enum NC;
          }
        }
        leaf remote-chassis-id {
          type string;
        }
        leaf index {
          type uint32;
        }
        leaf port-id {
          type string;
        }
        leaf remote-system-name {
          type string;
        }
      }
    }
    container information {
      leaf system-name {
        type string;
      }
      leaf chassis-type {
        type string;
      }
      leaf software-version {
        type string;
      }
      leaf system-up-time {
        type string;
      }
      leaf last-time-configuration-saved {
        type string;
      }
      leaf last-user-to-modify-configuration {
        type string;
      }
      leaf snmp-engine-id {
        type string;
      }
    }
    tailf:alt-name "system-stats";
  }
  container resource-usage {
    list card {
      config false;
      key "card-id";
      leaf card-id {
        type uint32;
      }
      container qos-user-schedulers {
        uses total-allocated-free-grouping;
      }
      container qos-user-scheduler-overrides {
        uses total-allocated-free-grouping;
      }
      container subscriber-sla-profile-instances {
        uses total-allocated-free-grouping;
      }
      container subscriber-sla-profile-instances-qos-overrides {
        uses total-allocated-free-grouping;
      }
      container hsmda-queue-overrides {
        uses total-allocated-free-grouping;
      }
      container egress-port-qgroup-instances {
        uses total-allocated-free-grouping;
      }
      container egress-access-port-queue-group-instances {
        uses total-allocated-free-grouping;
      }
      container egress-network-port-queue-group-instances {
        uses total-allocated-free-grouping;
      }
      container ingress-fp-queue-group-instances {
        uses total-allocated-free-grouping;
      }
      container egress-port-vport {
        uses total-allocated-free-grouping;
      }
      container subscriber-categories {
        uses total-allocated-free-grouping;
      }
      container qos-intermediate-arbiters {
        uses total-allocated-free-grouping;
      }
      container qos-intermediate-overrides {
        uses total-allocated-free-grouping;
      }
      list fp {
        key "fp-id";
        leaf fp-id {
          type uint32;
        }
        container sap-ingress-qos-policies {
          uses total-allocated-free-grouping;
        }
        container dynamic-egress-classification {
          uses total-allocated-free-grouping;
        }
        container dynamic-egress-in-use-by-sap-egress {
          uses allocated-grouping;
        }
        container dynamic-egress-in-use-by-network-egress {
          uses allocated-grouping;
        }
        container ingress-queues {
          uses total-allocated-free-grouping;
        }
        container egress-queues {
          uses total-allocated-free-grouping;
        }
        container ingress-policers {
          uses total-allocated-free-grouping;
        }
        container ingress-policer-stats {
          uses total-allocated-free-grouping;
        }
        container egress-policers {
          uses total-allocated-free-grouping;
        }
        container egress-policer-stats {
          uses total-allocated-free-grouping;
        }
        container qos-ingress-root-arbiters {
          uses total-allocated-free-grouping;
        }
        container qos-egress-root-arbiters {
          uses total-allocated-free-grouping;
        }
        container egress-qos-bypass {
          uses total-allocated-free-grouping;
        }
        container dynamic-queues {
          uses total-allocated-free-grouping;
        }
        container dynamic-queues-in-use-by-ingress {
          uses allocated-grouping;
        }
        container dynamic-queues-in-use-by-egress {
          uses allocated-grouping;
        }
        container dynamic-policers {
          uses total-allocated-free-grouping;
        }
        container dynamic-policers-in-use-by-ingress {
          uses allocated-grouping;
        }
        container dynamic-policers-in-use-by-egress {
          uses allocated-grouping;
        }
        container dynamic-policer-stats {
          uses total-allocated-free-grouping;
        }
        container dynamic-policer-stats-in-use-by-ingress {
          uses allocated-grouping;
        }
        container dynamic-policer-stats-in-use-by-egress {
          uses allocated-grouping;
        }
        container ingress-acl-qos-entries {
          uses total-allocated-free-grouping;
        }
        container ingress-acl-entries {
          uses total-allocated-free-grouping;
        }
        container ingress-qos-entries {
          uses total-allocated-free-grouping;
        }
        container ingress-ipv6-acl-entries {
          uses total-allocated-free-grouping;
        }
        container ingress-ipv6-qos-entries {
          uses total-allocated-free-grouping;
        }
        container egress-acl-qos-entries {
          uses total-allocated-free-grouping;
        }
        container egress-acl-entries {
          uses total-allocated-free-grouping;
        }
        container egress-qos-entries {
          uses total-allocated-free-grouping;
        }
        container egress-ipv6-acl-entries {
          uses total-allocated-free-grouping;
        }
        container egress-ipv6-qos-entries {
          uses total-allocated-free-grouping;
        }
        container ingress-acl-filters {
          uses total-allocated-free-grouping;
        }
        container egress-acl-filters {
          uses total-allocated-free-grouping;
        }
        container ingress-ipv6-acl-filters {
          uses total-allocated-free-grouping;
        }
        container egress-ipv6-acl-filters {
          uses total-allocated-free-grouping;
        }
        container sap-ingress-queue-group-redirect-list-entries {
          uses total-allocated-free-grouping;
        }
        container dynamic-service-entries {
          uses total-allocated-free-grouping;
        }
        container subscriber-hosts {
          uses total-allocated-free-grouping;
        }
        container encap-group-members {
          uses total-allocated-free-grouping;
        }
        container egress-network-queue-group-mappings {
          uses total-allocated-free-grouping;
        }
        container sap-instances-egress-queue-group-redirect-list-entries {
          uses total-allocated-free-grouping;
        }
        container subscriber-sla-profile-instances {
          uses total-allocated-free-grouping;
        }
        container mac-forwarding-database-fdb-entries {
          uses total-allocated-free-grouping;
        }
        container dynamic-named-pools {
          uses total-allocated-free-grouping;
        }
        container dynamic-named-pools-in-use-by-ingress {
          uses allocated-grouping;
        }
        container dynamic-named-pools-in-use-by-egress {
          uses allocated-grouping;
        }
        container dynamic-wred-pools {
          uses total-allocated-free-grouping;
        }
        container sap-instances {
          uses total-allocated-free-grouping;
        }
        container egress-hs-turbo-queue-group {
          uses total-allocated-free-grouping;
        }
        container egress-hs-queue-group {
          uses total-allocated-free-grouping;
        }
        container hs-primary-shapers {
          uses total-allocated-free-grouping;
        }
        container hs-explicit-primary-shapers {
          uses allocated-grouping;
        }
        container qos-user-schedulers {
          uses allocated-grouping;
        }
        container hs-secondary-shapers {
          uses total-allocated-free-grouping;
        }
      }
      list mda {
        key "mda-id";
        leaf mda-id {
          type uint32;
        }
        container egress-hsdma-queue-group {
          uses total-allocated-free-grouping;
        }
        container egress-hsdma-secondary-shapers {
          uses total-allocated-free-grouping;
        }
        container sap-instances {
          uses total-allocated-free-grouping;
        }
      }
    }
    container system {
      container sap-ingress-qos-policies {
        uses total-allocated-free-grouping;
      }
      container sap-egress-qos-policies {
        uses total-allocated-free-grouping;
      }
      container ingress-queue-group-templates {
        uses total-allocated-free-grouping;
      }
      container egress-queue-group-templates {
        uses total-allocated-free-grouping;
      }
      container egress-port-queue-group-instances {
        uses total-allocated-free-grouping;
      }
      container ingress-fp-queue-group-instances {
        uses total-allocated-free-grouping;
      }
      container egress-port-vport {
        uses total-allocated-free-grouping;
      }
      container dynamic-services-next-hop-entries {
        uses total-allocated-free-grouping;
      }
      container ipsec-next-hop-entries {
        uses total-allocated-free-grouping;
      }
      container subscriber-next-hop-entries {
        uses total-allocated-free-grouping;
      }
      container sap-entries {
        uses total-allocated-free-grouping;
      }
    }
    tailf:alt-name "resource-usage-stats";
  }
  container exec {
    tailf:alt-name "exec-stats";
  }
}
