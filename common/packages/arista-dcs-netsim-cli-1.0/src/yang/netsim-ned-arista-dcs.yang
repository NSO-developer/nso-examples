module netsim-ned-arista-dcs {
  namespace "http://tail-f.com/ned/arista-dcs";
  prefix dcs;

  import tailf-common {
    prefix tailf;
  }
  import ietf-inet-types {
    prefix inet;
  }

  revision 2026-03-27;

  typedef ip-mask {
    type string;
  }

  typedef mac-address-type {
    type union {
      type string;
      type string;
      type string;
      type string;
    }
  }

  typedef mac-address-type2 {
    type union {
      type string;
      type string;
      type string;
      type string;
    }
  }

  typedef vlan-list-type {
    type uint16;
  }

  typedef vrf-member-type {
    type union {
      type string;
      type enumeration {
        enum management;
      }
    }
  }

  typedef logging-level-type {
    type enumeration {
      enum alerts;
      enum critical;
      enum debugging;
      enum emergencies;
      enum errors;
      enum informational;
      enum notifications;
      enum warnings;
    }
  }

  typedef aaa-group-type {
    type union {
      type string;
      type enumeration {
        enum radius;
        enum tacacs+;
      }
    }
  }

  typedef aaa-authorization-name-type {
    type enumeration {
      enum default;
    }
  }

  typedef aaa-accounting-name-type {
    type enumeration {
      enum default;
      enum console;
    }
  }

  typedef std-ip-acl-type {
    type union {
      type uint16;
      type uint16;
      type string;
    }
  }

  typedef authentication-level-type {
    type enumeration {
      enum level-1;
      enum level-2;
    }
  }

  typedef rd-type {
    type string;
  }

  typedef vpn-id-type {
    type string;
  }

  typedef host-type {
    type union {
      type inet:ip-address;
      type inet:domain-name;
    }
  }

  typedef asn-ip-type {
    type string;
  }

  typedef hhmm-type {
    type string;
  }

  typedef weekday-type {
    type enumeration {
      enum Mon;
      enum Tue;
      enum Wed;
      enum Thu;
      enum Fri;
      enum Sat;
      enum Sun;
    }
  }

  typedef month-type {
    type enumeration {
      enum Jan;
      enum Feb;
      enum Mar;
      enum Apr;
      enum May;
      enum Jun;
      enum Jul;
      enum Aug;
      enum Sep;
      enum Oct;
      enum Nov;
      enum Dec;
    }
  }

  typedef std-acl-type {
    type union {
      type uint16;
      type uint16;
      type string;
    }
  }

  typedef ext-acl-type {
    type union {
      type uint16;
      type uint16;
      type string;
    }
  }

  typedef exp-acl-type {
    type union {
      type uint16;
      type uint16;
      type string;
    }
  }

  typedef mdt-data-list-type {
    type union {
      type uint16;
      type uint16;
      type string;
    }
  }

  typedef ldp-discovery-address-type {
    type union {
      type enumeration {
        enum interface {
          tailf:code-name "ldp_interface";
        }
      }
      type inet:ipv4-address;
    }
  }

  typedef mst-cost-type {
    type union {
      type uint32;
      type enumeration {
        enum auto {
          tailf:code-name "mst_cost_type_auto";
        }
      }
    }
  }

  typedef spanning-tree-cost-type {
    type union {
      type uint32;
      type enumeration {
        enum auto {
          tailf:code-name "spanning-tree-cost-type-auto";
        }
      }
    }
  }

  typedef precedence-type {
    type union {
      type uint16;
      type enumeration {
        enum critical;
        enum flash;
        enum flash-override;
        enum immediate;
        enum internet {
          tailf:code-name "prec_internet";
        }
        enum network;
        enum priority {
          tailf:code-name "prec_priority";
        }
        enum routine;
      }
    }
  }

  typedef precedence-type2 {
    type union {
      type uint16;
      type enumeration {
        enum rsvp {
          tailf:code-name "prec_rsvp";
        }
      }
    }
  }

  typedef police-action-old-type {
    type enumeration {
      enum drop {
        tailf:code-name "police_drop";
      }
      enum set-clp-transmit;
      enum set-discard-class-transmit;
      enum set-dscp-transmit;
      enum set-frde-transmit;
      enum set-mpls-exp-imposition-transmit;
      enum set-mpls-exp-topmost-transmit;
      enum set-prec-transmit;
      enum set-qos-transmit;
      enum transmit {
        tailf:code-name "police_transmit";
      }
    }
  }

  typedef ipv4-prefix {
    type string;
  }

  typedef access-list-standard-id-type {
    type union {
      type default-access-list-standard-id-type;
      type string;
    }
  }

  typedef default-access-list-standard-id-type {
    type union {
      type uint8;
      type uint16;
    }
  }

  typedef access-list-in-out-type {
    type enumeration {
      enum in;
      enum out;
    }
  }

  typedef redist-ospf-external-type {
    type enumeration {
      enum 1;
      enum 2;
    }
  }

  typedef bgp-as-no-type {
    type union {
      type uint32;
      type string;
    }
  }

  grouping interface-grouping {
    choice interface-choice {
      leaf Ethernet {
        tailf:cli-allow-join-with-value;
        type string;
      }
      leaf Loopback {
        tailf:cli-allow-join-with-value;
        type uint16;
      }
      leaf Management {
        tailf:cli-allow-join-with-value;
        type string;
      }
      leaf Null0 {
        type empty;
      }
      leaf Port-Channel {
        tailf:cli-allow-join-with-value;
        type string;
      }
      leaf Vlan {
        tailf:cli-allow-join-with-value;
        type uint16;
      }
      leaf Vxlan {
        tailf:cli-allow-join-with-value;
        type uint16;
      }
    }
  }

  grouping interface-no-content-on-delete-grouping {
    choice interface-choice {
      leaf Ethernet {
        tailf:cli-allow-join-with-value;
        type string;
      }
      leaf Loopback {
        tailf:cli-allow-join-with-value;
        type uint16;
      }
      leaf Management {
        tailf:cli-allow-join-with-value;
        type string;
      }
      leaf Null0 {
        type empty;
      }
      leaf Port-Channel {
        tailf:cli-allow-join-with-value;
        type string;
      }
      leaf Vlan {
        tailf:cli-allow-join-with-value;
        type uint16;
      }
      leaf Vxlan {
        tailf:cli-allow-join-with-value;
        type uint16;
      }
    }
  }

  grouping ip-route-grouping {
    list ip-route-interface-list {
      tailf:cli-drop-node-name;
      tailf:cli-suppress-mode;
      tailf:cli-delete-when-empty;
      tailf:cli-compact-syntax;
      key "prefix interface forwarding-address";
      leaf prefix {
        type ip-mask;
      }
      leaf interface {
        type string;
      }
      leaf forwarding-address {
        type inet:ipv4-address;
      }
      uses ip-route-options-grouping;
    }
    list ip-route-list {
      tailf:cli-drop-node-name;
      tailf:cli-suppress-mode;
      tailf:cli-delete-when-empty;
      tailf:cli-compact-syntax;
      key "prefix forwarding-address";
      leaf prefix {
        type ip-mask;
      }
      leaf forwarding-address {
        type inet:ipv4-address;
      }
      uses ip-route-options-grouping;
    }
    list ip-route-list-interface-only {
      tailf:cli-drop-node-name;
      tailf:cli-suppress-mode;
      tailf:cli-delete-when-empty;
      tailf:cli-compact-syntax;
      key "prefix interface";
      leaf prefix {
        type ip-mask;
      }
      leaf interface {
        type string;
      }
      uses ip-route-options-grouping;
    }
  }

  grouping ip-community-list-standard-grouping {
    container deny {
      presence "Specify community to reject";
      list deny-list {
        tailf:cli-drop-node-name;
        tailf:cli-suppress-mode;
        key "expr";
        leaf expr {
          tailf:cli-multi-word-key;
          type string;
        }
      }
    }
    container permit {
      presence "Specify community to accept";
      list permit-list {
        tailf:cli-drop-node-name;
        tailf:cli-suppress-mode;
        key "expr";
        leaf expr {
          tailf:cli-multi-word-key;
          type string;
        }
      }
    }
  }

  grouping switchport-interface-grouping {
    container switchport {
      container mac {
        container address {
          leaf learning {
            type boolean;
          }
        }
      }
      container access {
        leaf vlan {
          type uint16;
        }
      }
      leaf block {
        type enumeration {
          enum multicast {
            tailf:code-name "switchport_block_multicast";
          }
          enum unicast {
            tailf:code-name "switchport_block_unicast";
          }
        }
      }
      leaf description {
        tailf:cli-multi-value;
        type string;
      }
      leaf host {
        type empty;
      }
      leaf mode {
        type union {
          type enumeration {
            enum access {
              tailf:code-name "switchport_mode_access";
            }
            enum fex-fabric;
            enum trunk {
              tailf:code-name "switchport_mode_trunk";
            }
            enum tap;
            enum tool;
          }
          type string;
        }
      }
      container mode-container {
        tailf:cli-drop-node-name;
        container mode {
          container trunk {
            leaf phone {
              type empty;
            }
          }
        }
      }
      container phone {
        leaf vlan {
          type uint16;
        }
        leaf trunk {
          type enumeration {
            enum tagged;
            enum untagged;
          }
        }
      }
      container port-security {
        leaf maximum {
          type uint16;
        }
        container mac-address {
          leaf maximum {
            type union {
              type enumeration {
                enum disabled;
              }
              type uint32;
            }
          }
        }
        container violation {
          tailf:cli-compact-syntax;
          tailf:cli-sequence-commands {
            tailf:cli-reset-siblings;
          }
          leaf mode {
            tailf:cli-drop-node-name;
            type enumeration {
              enum protect;
              enum shutdown;
            }
          }
          leaf log {
            type empty;
          }
        }
      }
      leaf monitor {
        type empty;
      }
      container tap {
        container allowed {
          leaf-list vlan {
            tailf:cli-range-list-syntax;
            type uint16;
          }
        }
        container default {
          leaf-list group {
            tailf:cli-flat-list-syntax;
            type string;
          }
        }
        leaf identity {
          type uint16;
        }
        container native {
          leaf vlan {
            type uint16;
          }
        }
      }
      container tool {
        leaf identity {
          type enumeration {
            enum dot1q;
          }
        }
        leaf-list group {
          tailf:cli-flat-list-syntax;
          type string;
        }
      }
      container trunk {
        container allowed {
          container vlan {
            choice vlan-choice {
              leaf-list ids {
                tailf:cli-drop-node-name;
                tailf:cli-range-list-syntax;
                type vlan-list-type;
              }
              leaf fixed {
                tailf:cli-drop-node-name;
                type enumeration {
                  enum all;
                  enum none;
                }
              }
              leaf-list except {
                tailf:cli-range-list-syntax;
                type vlan-list-type;
              }
            }
          }
        }
        list group {
          tailf:cli-suppress-mode;
          key "name";
          leaf name {
            type string;
          }
        }
        container native {
          container vlan {
            leaf vlan {
              tailf:cli-drop-node-name;
              type uint16;
            }
            leaf tag {
              type empty;
            }
          }
        }
      }
      container vlan {
        container mapping {
          list map {
            tailf:cli-drop-node-name;
            tailf:cli-suppress-mode;
            key "from to";
            leaf from {
              type uint16;
            }
            leaf to {
              type uint16;
            }
          }
        }
        container translation {
          list from-to {
            tailf:cli-suppress-mode;
            tailf:cli-compact-syntax;
            tailf:cli-drop-node-name;
            key "from";
            leaf from {
              type uint32;
            }
            leaf to {
              tailf:cli-drop-node-name;
              type uint32;
            }
          }
        }
      }
    }
    container no-switchport {
      tailf:cli-drop-node-name;
      leaf switchport {
        type boolean;
      }
    }
  }

  grouping interface-isis-grouping {
    container isis {
      leaf enable {
        type string;
      }
      leaf hello-interval {
        type uint16;
      }
      leaf hello-multiplier {
        type uint16;
      }
      leaf bfd {
        type boolean;
      }
      leaf circuit-type {
        type enumeration {
          enum level-1;
          enum level-1-2;
          enum level-2;
        }
      }
      container ipv6 {
        leaf metric {
          type union {
            type enumeration {
              enum maximum;
            }
            type uint32;
          }
        }
      }
      leaf metric {
        type uint32;
      }
      leaf network {
        type enumeration {
          enum point-to-point;
        }
      }
      leaf passive {
        type empty;
      }
      container authentication {
        container mode {
          container md5 {
            presence "true";
            leaf level {
              tailf:cli-drop-node-name;
              type authentication-level-type;
            }
          }
          container text {
            presence "true";
            leaf level {
              tailf:cli-drop-node-name;
              type authentication-level-type;
            }
          }
        }
        container key {
          tailf:cli-compact-syntax;
          tailf:cli-sequence-commands {
            tailf:cli-reset-siblings;
          }
          leaf encrypt {
            tailf:cli-drop-node-name;
            tailf:cli-optional-in-sequence;
            type enumeration {
              enum 0;
              enum 7;
            }
          }
          leaf string {
            tailf:cli-drop-node-name;
            type string;
          }
        }
      }
    }
  }

  grouping interface-ethernet-port-channel-common-grouping {
    container bfd {
      container interval {
        tailf:cli-compact-syntax;
        tailf:cli-sequence-commands {
          tailf:cli-reset-siblings;
        }
        leaf transmit-rate {
          tailf:cli-drop-node-name;
          type uint32;
        }
        choice min-rx-choice {
          leaf min_rx {
            type uint32;
          }
          leaf min-rx {
            type uint32;
          }
        }
        leaf multiplier {
          type uint8;
        }
      }
      leaf echo {
        type empty;
      }
    }
    container bgp {
      container session {
        leaf tracker {
          type string;
        }
      }
    }
    container evpn {
      container ethernet-segment {
        tailf:cli-add-mode;
        leaf identifier {
          type string;
        }
        container designated-forwarder {
          container election {
            container algorithm {
              leaf preference {
                type uint16;
              }
            }
          }
        }
        container route-target {
          leaf import {
            type string;
          }
        }
      }
    }
    uses interface-isis-grouping;
    container l2-protocol {
      container forwarding {
        leaf profile {
          type string;
        }
      }
    }
    container mpls {
      container ldp {
        leaf interface {
          type empty;
        }
        leaf igp {
          type enumeration {
            enum sync;
          }
        }
      }
    }
    container telemetry {
      container inband {
        container profile {
          choice telemetry-inband-profile-choice {
            leaf core {
              type string;
            }
            leaf edge {
              type string;
            }
          }
        }
      }
    }
    container ptp {
      leaf enable {
        type empty;
      }
      container announce {
        leaf interval {
          type int8;
        }
        leaf timeout {
          type uint8;
        }
      }
      container delay-req {
        leaf interval {
          type int8;
        }
      }
      leaf local-priority {
        type uint8;
      }
      leaf role {
        type enumeration {
          enum dynamic;
          enum master;
        }
      }
      leaf transport {
        type enumeration {
          enum ipv4;
          enum ipv6;
          enum layer2;
        }
      }
      container sync-message {
        leaf interval {
          type int8;
        }
      }
      leaf-list vlan {
        tailf:cli-range-list-syntax;
        type uint16;
      }
    }
    container qos {
      leaf cos {
        type uint8;
      }
      leaf trust {
        type enumeration {
          enum cos;
          enum dscp;
        }
      }
    }
    leaf service-profile {
      type string;
    }
    container sflow {
      leaf enable {
        type boolean;
      }
    }
    container shape {
      container rate {
        tailf:cli-compact-syntax;
        tailf:cli-sequence-commands;
        leaf value {
          tailf:cli-drop-node-name;
          type uint32;
        }
        container burst-size {
          tailf:cli-compact-syntax;
          tailf:cli-flatten-container;
          tailf:cli-sequence-commands {
            tailf:cli-reset-siblings;
          }
          leaf value {
            tailf:cli-drop-node-name;
            type union {
              type uint32;
              type uint16;
              type uint32;
            }
          }
          choice burst-size-choice {
            leaf kbytes {
              type empty;
            }
            leaf mbytes {
              type empty;
            }
            leaf bytes {
              type empty;
            }
          }
        }
      }
    }
    list tx-queue {
      key "id";
      leaf id {
        type uint8;
      }
      leaf priority {
        type enumeration {
          enum strict;
        }
      }
      container bandwidth {
        leaf percent {
          type uint8;
        }
      }
    }
    container vlan {
      leaf id {
        type uint16;
      }
    }
    uses interface-mac-grouping;
    uses interface-spanning-tree-grouping;
  }

  grouping interface-spanning-tree-grouping {
    container spanning-tree {
      leaf mode {
        type enumeration {
          enum backup;
          enum mstp;
          enum none;
          enum rapid-pvst;
          enum rstp;
        }
      }
      leaf bpdufilter {
        type enumeration {
          enum disable {
            tailf:code-name "bdufilter_disable";
          }
          enum enable {
            tailf:code-name "bdufilter_enable";
          }
        }
      }
      container bpduguard {
        leaf value {
          tailf:cli-drop-node-name;
          type enumeration {
            enum disable;
            enum enable;
          }
        }
        container rate-limit {
          leaf value {
            tailf:cli-drop-node-name;
            type enumeration {
              enum disable;
              enum enable;
            }
          }
          container count {
            tailf:cli-compact-syntax;
            tailf:cli-sequence-commands;
            leaf value {
              tailf:cli-drop-node-name;
              type uint16;
            }
            leaf interval {
              type uint8;
            }
          }
        }
      }
      leaf cost {
        type spanning-tree-cost-type;
      }
      leaf guard {
        type enumeration {
          enum loop;
          enum none;
          enum root;
        }
      }
      leaf link-type {
        type enumeration {
          enum point-to-point;
          enum shared;
        }
      }
      container mst {
        list port {
          tailf:cli-drop-node-name;
          tailf:cli-suppress-mode;
          key "range";
          leaf range {
            type string;
          }
          leaf cost {
            type mst-cost-type;
          }
          leaf port-priority {
            type uint8;
          }
        }
        leaf pre-standard {
          type empty;
        }
        container simulate {
          container pvst {
            presence "Enable PVST simulation";
            leaf disable {
              type empty;
            }
          }
        }
      }
      container port {
        tailf:cli-sequence-commands {
          tailf:cli-reset-siblings;
        }
        tailf:cli-compact-syntax;
        leaf type {
          type enumeration {
            enum edge;
            enum network;
            enum normal;
          }
        }
        leaf trunk {
          type empty;
        }
      }
      container portfast {
        tailf:cli-compact-syntax;
        presence "true";
        leaf portfast {
          tailf:cli-drop-node-name;
          type enumeration {
            enum auto;
            enum edge;
            enum network;
            enum normal;
          }
        }
      }
      leaf port-priority {
        type uint8;
      }
    }
  }

  grouping ethernet-settings-grouping {
    container bandwidth {
      tailf:cli-sequence-commands {
        tailf:cli-reset-siblings;
      }
      tailf:cli-compact-syntax;
      leaf inherit {
        tailf:cli-optional-in-sequence;
        type empty;
      }
      leaf bandwidth {
        tailf:cli-drop-node-name;
        type uint32;
      }
    }
    leaf beacon {
      type empty;
    }
    leaf description {
      tailf:cli-multi-value;
      type string;
    }
    leaf cdp {
      type enumeration {
        enum enable {
          tailf:code-name "ethernet-settings-grouping_cdp_enable";
        }
      }
    }
    uses interface-encapsulation-grouping;
    container channel-group {
      tailf:cli-sequence-commands {
        tailf:cli-reset-siblings;
      }
      tailf:cli-compact-syntax;
      leaf id {
        tailf:cli-drop-node-name;
        type uint16;
      }
      leaf mode {
        type enumeration {
          enum active;
          enum on;
          enum passive {
            tailf:code-name "mode_passive";
          }
        }
      }
    }
    leaf delay {
      type uint32;
    }
    container fex {
      leaf associate {
        type uint8;
      }
    }
    container flowcontrol {
      leaf receive {
        type enumeration {
          enum off {
            tailf:code-name "flowcontrol_off";
          }
          enum on {
            tailf:code-name "flowcontrol_on";
          }
        }
      }
      leaf send {
        type enumeration {
          enum off {
            tailf:code-name "send_off";
          }
          enum on {
            tailf:code-name "send_on";
          }
        }
      }
    }
    container inherit {
      leaf port-profile {
        type string;
      }
    }
    uses switchport-interface-grouping;
    container vrf {
      choice vrf-choice {
        leaf forwarding {
          type string;
        }
        leaf name {
          tailf:cli-drop-node-name;
          type string;
        }
      }
      leaf member {
        type vrf-member-type;
      }
    }
    container ip {
      uses interface-ip-address-grouping;
      container igmp-alone {
        tailf:cli-drop-node-name;
        leaf igmp {
          type empty;
        }
      }
      container igmp {
        leaf version {
          type uint8;
        }
        container static-group {
          list multicast {
            tailf:cli-drop-node-name;
            tailf:cli-suppress-mode;
            key "address";
            leaf address {
              type inet:ipv4-address;
            }
          }
          list acl {
            tailf:cli-suppress-mode;
            key "name";
            leaf name {
              type string;
            }
          }
        }
        leaf router-alert {
          type enumeration {
            enum mandatory;
            enum optional;
          }
        }
        container snooping {
          leaf filter {
            type string;
          }
        }
      }
      uses access-group-list-grouping;
      uses interface-ip-ospf-grouping;
      uses interface-ip-proxy-arp-grouping;
      uses interface-ip-nat-grouping;
      container pim {
        leaf bfd-insance {
          type empty;
        }
        leaf border-router {
          type empty;
        }
        leaf bsr-router {
          type empty;
        }
        uses interface-ip-pim-bsr-border;
        leaf sparse-mode {
          type empty;
        }
      }
      container port {
        container access-group {
          tailf:cli-sequence-commands;
          tailf:cli-compact-syntax;
          leaf name {
            tailf:cli-drop-node-name;
            type string;
          }
          leaf inout {
            tailf:cli-drop-node-name;
            type enumeration {
              enum in;
              enum out;
            }
          }
        }
      }
      uses ip-helper-address-grouping;
      uses ip-verify-grouping;
      container virtual-router {
        list address {
          tailf:cli-suppress-mode;
          key "ip";
          leaf ip {
            type inet:ipv4-address;
          }
        }
      }
    }
    container ipv6 {
      leaf enable {
        type empty;
      }
      choice ipv6-address-choice {
        list address {
          tailf:cli-suppress-mode;
          tailf:cli-delete-when-empty;
          key "prefix";
          leaf prefix {
            type tailf:ipv6-address-and-prefix-length;
          }
          leaf link-local {
            type empty;
          }
        }
        container address-auto-config {
          tailf:cli-drop-node-name;
          leaf address {
            type enumeration {
              enum auto-config;
            }
          }
        }
      }
      uses access-group-list-grouping;
      uses ipv6-nd-grouping;
      container port {
        container traffic-filter {
          tailf:cli-sequence-commands;
          tailf:cli-compact-syntax;
          leaf name {
            tailf:cli-drop-node-name;
            type string;
          }
          leaf inout {
            tailf:cli-drop-node-name;
            type enumeration {
              enum in;
            }
          }
        }
      }
    }
    uses interface-ethernet-port-channel-common-grouping;
    container link {
      container debounce {
        presence "Configure link debounce timer";
        leaf time {
          type uint16;
        }
      }
    }
    uses lldp-grouping;
    container load-interval {
      leaf interval {
        tailf:cli-drop-node-name;
        type uint16;
      }
      list counter {
        tailf:cli-suppress-mode;
        key "id";
        leaf id {
          type uint8;
        }
        leaf interval {
          tailf:cli-drop-node-name;
          type uint16;
        }
      }
    }
    uses logging-interface-grouping;
    leaf mac-address {
      type mac-address-type;
    }
    container multicast {
      container ipv4 {
        tailf:cli-compact-syntax;
        tailf:cli-sequence-commands {
          tailf:cli-reset-siblings;
        }
        leaf boundary {
          type union {
            type tailf:ipv4-address-and-prefix-length;
            type tailf:ipv6-address-and-prefix-length;
            type string;
          }
        }
        leaf out {
          type empty;
        }
      }
    }
    leaf mtu {
      type uint16;
    }
    container class-map {
      container type {
        list pbr {
          key "match-any";
          leaf match-any {
            tailf:cli-expose-key-name;
            type string;
          }
          list class {
            tailf:cli-drop-node-name;
            tailf:cli-suppress-mode;
            tailf:cli-sequence-commands {
              tailf:cli-reset-siblings;
            }
            key "access-group";
            leaf seq {
              tailf:cli-drop-node-name;
              tailf:cli-prefix-key;
              tailf:cli-optional-in-sequence;
              type uint32;
            }
            leaf match {
              tailf:cli-prefix-key;
              type empty;
            }
            leaf ip {
              tailf:cli-prefix-key;
              type empty;
            }
            leaf access-group {
              tailf:cli-expose-key-name;
              type string;
            }
          }
        }
      }
    }
    uses nexthop-group-grouping;
    container policy-map {
      container type {
        list pbr {
          key "name";
          leaf name {
            type string;
          }
          list class {
            tailf:cli-drop-node-name;
            key "class";
            leaf seq {
              tailf:cli-drop-node-name;
              tailf:cli-prefix-key;
              tailf:cli-optional-in-sequence;
              type uint32;
            }
            leaf class {
              tailf:cli-expose-key-name;
              type string;
            }
            container set {
              leaf nexthop-group {
                type string;
              }
            }
          }
        }
      }
    }
    container priority-flow-control {
      leaf mode {
        type enumeration {
          enum auto {
            tailf:code-name "prio_flow_control_auto";
          }
          enum off {
            tailf:code-name "prio_flow_off";
          }
          enum on {
            tailf:code-name "prio_flow_on";
          }
        }
      }
    }
    uses snmp-trap-link-status-grouping;
    container speed {
      choice speed-choice {
        leaf speed {
          tailf:cli-drop-node-name;
          type enumeration {
            enum 100full;
            enum 10full;
            enum auto;
            enum sfp-1000baset;
            enum 10half;
            enum 200g-4;
          }
        }
        leaf auto {
          type enumeration {
            enum 100full;
            enum 100gfull;
            enum 10full;
            enum 25gfull;
            enum 40gfull;
            enum 50gfull;
          }
        }
        leaf forced {
          type enumeration {
            enum 10000full;
            enum 1000full;
            enum 1000half;
            enum 100full;
            enum 10gfull;
            enum 100gfull;
            enum 100half;
            enum 10full;
            enum 10half;
            enum 40gfull;
            enum 25gfull;
            enum 50gfull;
          }
        }
      }
    }
    container error-correction {
      choice error-correction-encoding {
        container no-encoding {
          tailf:cli-drop-node-name;
          leaf encoding {
            type boolean;
          }
        }
        container encoding {
          leaf fire-code {
            type empty;
          }
          leaf reed-solomon {
            type empty;
          }
        }
      }
    }
    uses storm-control-grouping;
    container untagged {
      leaf cos {
        type uint8;
      }
    }
    leaf shutdown {
      type empty;
    }
  }

  grouping port-channel-settings-grouping {
    container bandwidth {
      tailf:cli-sequence-commands {
        tailf:cli-reset-siblings;
      }
      tailf:cli-compact-syntax;
      leaf inherit {
        tailf:cli-optional-in-sequence;
        type empty;
      }
      leaf bandwidth {
        tailf:cli-drop-node-name;
        type uint32;
      }
    }
    leaf delay {
      type uint32;
    }
    leaf description {
      tailf:cli-multi-value;
      type string;
    }
    uses interface-encapsulation-grouping;
    container load-interval {
      leaf interval {
        tailf:cli-drop-node-name;
        type uint16;
      }
      list counter {
        tailf:cli-suppress-mode;
        key "id";
        leaf id {
          type uint8;
        }
        leaf interval {
          tailf:cli-drop-node-name;
          type uint16;
        }
      }
    }
    leaf mtu {
      type uint16;
    }
    leaf duplex {
      type enumeration {
        enum auto {
          tailf:code-name "port-channel-settings-grouping-duplex_auto";
        }
        enum full;
        enum half;
      }
    }
    container fex {
      leaf associate {
        type uint8;
      }
    }
    container flowcontrol {
      leaf receive {
        type enumeration {
          enum off {
            tailf:code-name "flowcontrol_receive_off";
          }
          enum on {
            tailf:code-name "flowcontrol_receive_on";
          }
        }
      }
      leaf send {
        type enumeration {
          enum off {
            tailf:code-name "flowcontrol_send_off";
          }
          enum on {
            tailf:code-name "flowcontrol_send_on";
          }
        }
      }
    }
    container hardware {
      leaf multicast {
        type enumeration {
          enum hw-hash;
        }
      }
    }
    container inherit {
      leaf port-profile {
        type string;
      }
    }
    uses switchport-interface-grouping;
    leaf mlag {
      type uint16;
    }
    container ip {
      container port {
        container access-group {
          tailf:cli-sequence-commands;
          tailf:cli-compact-syntax;
          leaf name {
            tailf:cli-drop-node-name;
            type string;
          }
          leaf inout {
            tailf:cli-drop-node-name;
            type enumeration {
              enum in;
              enum out;
            }
          }
        }
      }
      uses interface-ip-address-grouping;
      uses access-group-list-grouping;
      uses interface-ip-ospf-grouping;
      uses ip-helper-address-grouping;
      uses ip-verify-grouping;
      container igmp {
        leaf version {
          type uint8;
        }
        container snooping {
          leaf filter {
            type string;
          }
        }
      }
      uses interface-ip-proxy-arp-grouping;
      container pim {
        leaf sparse-mode {
          type empty;
        }
        uses interface-ip-pim-bsr-border;
      }
    }
    container ipv6 {
      leaf enable {
        type empty;
      }
      list address {
        tailf:cli-suppress-mode;
        tailf:cli-delete-when-empty;
        key "prefix";
        leaf prefix {
          type tailf:ipv6-address-and-prefix-length;
        }
        leaf link-local {
          type empty;
        }
      }
      uses access-group-list-grouping;
      container port {
        container traffic-filter {
          tailf:cli-sequence-commands;
          tailf:cli-compact-syntax;
          leaf name {
            tailf:cli-drop-node-name;
            type string;
          }
          leaf inout {
            tailf:cli-drop-node-name;
            type enumeration {
              enum in;
            }
          }
        }
      }
    }
    container pim {
      container ipv4 {
        leaf sparse-mode {
          type empty;
        }
        leaf bfd {
          type empty;
        }
      }
    }
    uses interface-ethernet-port-channel-common-grouping;
    container port-channel {
      container lacp {
        container fallback {
          presence "true";
          leaf mode {
            tailf:cli-drop-node-name;
            type enumeration {
              enum individual;
              enum static;
            }
          }
          leaf timeout {
            type uint16;
          }
        }
        leaf loopback {
          type empty;
        }
      }
      leaf min-links {
        type uint8;
      }
    }
    container lacp-container {
      tailf:cli-drop-node-name;
      container lacp {
        leaf system-id {
          type string;
        }
      }
    }
    leaf lacp {
      type enumeration {
        enum graceful-convergence;
        enum suspend-individual;
      }
    }
    leaf link-state-trap {
      type empty;
    }
    uses logging-interface-grouping;
    leaf mac-address {
      type mac-address-type;
    }
    leaf medium {
      type enumeration {
        enum broadcast {
          tailf:code-name "medium_broadcast";
        }
        enum p2p;
      }
    }
    container priority-flow-control {
      leaf mode {
        type enumeration {
          enum auto {
            tailf:code-name "port-channel-settings-grouping_prio_flow_control_auto";
          }
          enum off {
            tailf:code-name "flowcontrol_mode_off";
          }
          enum on {
            tailf:code-name "flowcontrol_mode_on";
          }
        }
      }
    }
    leaf shutdown {
      type empty;
    }
    leaf speed {
      type enumeration {
        enum 100 {
          tailf:code-name "port_cahnnels-settings_grouping_speed_100";
        }
        enum 1000 {
          tailf:code-name "port_cahnnels-settings_grouping_speed_1000";
        }
        enum 10000;
        enum auto {
          tailf:code-name "port_cahnnels-settings_grouping_auto";
        }
      }
    }
    uses storm-control-grouping;
    container untagged {
      leaf cos {
        type uint8;
      }
    }
    container vrf {
      choice vrf-choice {
        leaf forwarding {
          type string;
        }
        leaf name {
          tailf:cli-drop-node-name;
          type string;
        }
      }
    }
  }

  grouping mgmt-settings-ipv6-grouping {
    list address {
      tailf:cli-suppress-mode;
      tailf:cli-delete-when-empty;
      key "prefix";
      leaf prefix {
        type tailf:ipv6-address-and-prefix-length;
      }
      leaf link-local {
        type empty;
      }
    }
    leaf enable {
      type empty;
    }
    list access-group {
      tailf:cli-suppress-mode;
      tailf:cli-compact-syntax;
      tailf:cli-sequence-commands;
      key "inout";
      leaf name {
        tailf:cli-drop-node-name;
        tailf:cli-prefix-key;
        type string;
      }
      leaf inout {
        type enumeration {
          enum in;
          enum out;
        }
      }
    }
    leaf link-local {
      type inet:ipv6-address;
    }
    uses ipv6-nd-grouping;
    container neighbor {
      tailf:cli-compact-syntax;
      tailf:cli-sequence-commands;
      leaf address {
        tailf:cli-drop-node-name;
        type inet:ipv6-address;
      }
      leaf mac {
        tailf:cli-drop-node-name;
        type union {
          type string;
          type string;
          type string;
          type string;
        }
      }
    }
    leaf redirects {
      type empty;
    }
    container port {
      container traffic-filter {
        tailf:cli-sequence-commands;
        tailf:cli-compact-syntax;
        leaf name {
          tailf:cli-drop-node-name;
          type string;
        }
        leaf inout {
          tailf:cli-drop-node-name;
          type enumeration {
            enum in;
          }
        }
      }
    }
  }

  grouping mgmt-settings-grouping {
    leaf autostate {
      type boolean;
    }
    leaf description {
      tailf:cli-multi-value;
      type string;
    }
    leaf cdp {
      type enumeration {
        enum enable {
          tailf:code-name "cdp_enable";
        }
      }
    }
    leaf duplex {
      type enumeration {
        enum auto {
          tailf:code-name "mgmt_duplex_auto";
        }
        enum full;
        enum half;
      }
    }
    leaf load-interval {
      type uint16;
    }
    container isis {
      leaf enable {
        type string;
      }
      leaf passive {
        type empty;
      }
    }
    container vrf {
      choice vrf-choice {
        leaf forwarding {
          type string;
        }
        leaf name {
          tailf:cli-drop-node-name;
          type string;
        }
      }
      leaf member {
        type vrf-member-type;
      }
    }
    container ip {
      list access-group {
        tailf:cli-suppress-mode;
        tailf:cli-compact-syntax;
        tailf:cli-sequence-commands;
        key "inout";
        leaf name {
          tailf:cli-drop-node-name;
          tailf:cli-prefix-key;
          type string;
        }
        leaf inout {
          type enumeration {
            enum in;
            enum out;
          }
        }
      }
      uses interface-ip-address-grouping;
      container arp {
        tailf:cli-sequence-commands;
        tailf:cli-compact-syntax;
        leaf address {
          tailf:cli-drop-node-name;
          type inet:ipv4-address;
        }
        leaf mac {
          tailf:cli-drop-node-name;
          type mac-address-type2;
        }
      }
      leaf directed-broadcast {
        type empty;
      }
      container igmp-alone {
        tailf:cli-drop-node-name;
        leaf igmp {
          type empty;
        }
      }
      container igmp {
        leaf version {
          type uint8;
        }
        container static-group {
          list multicast {
            tailf:cli-drop-node-name;
            tailf:cli-suppress-mode;
            key "address";
            leaf address {
              type inet:ipv4-address;
            }
          }
        }
      }
      uses interface-ip-proxy-arp-grouping;
      container ospf {
        leaf area {
          type ospf-area-type;
        }
      }
      container pim {
        leaf sparse-mode {
          type empty;
        }
      }
      leaf port-unreachable {
        type empty;
      }
      leaf redirects {
        type empty;
      }
      leaf unreachables {
        type empty;
      }
      container port {
        container access-group {
          tailf:cli-sequence-commands;
          tailf:cli-compact-syntax;
          leaf name {
            tailf:cli-drop-node-name;
            type string;
          }
          leaf inout {
            tailf:cli-drop-node-name;
            type enumeration {
              enum in;
              enum out;
            }
          }
        }
      }
      container virtual-router {
        list address {
          tailf:cli-suppress-mode;
          key "ip";
          leaf ip {
            type inet:ipv4-address;
          }
        }
      }
      uses ip-helper-address-grouping;
      uses ip-verify-grouping;
    }
    uses lldp-grouping;
    uses logging-interface-grouping;
    leaf mtu {
      type uint16;
    }
    container ntp {
      leaf serve {
        type empty;
      }
    }
    uses snmp-trap-link-status-grouping;
    leaf speed {
      type enumeration {
        enum 1000 {
          tailf:code-name "mgmt-settings-grouping-speed_1000";
        }
        enum auto {
          tailf:code-name "mgmt-settings-grouping-auto";
        }
      }
    }
    uses interface-vrrp-grouping;
    leaf shutdown {
      type empty;
    }
  }

  grouping loopback-settings-grouping {
    leaf description {
      tailf:cli-multi-value;
      type string;
    }
    leaf cdp {
      type enumeration {
        enum enable {
          tailf:code-name "cdp_enable";
        }
      }
    }
    leaf duplex {
      type enumeration {
        enum auto {
          tailf:code-name "mgmt_duplex_auto";
        }
        enum full;
        enum half;
      }
    }
    container ip {
      container access-group {
        tailf:cli-sequence-commands;
        tailf:cli-compact-syntax;
        leaf name {
          tailf:cli-drop-node-name;
          type string;
        }
        leaf inout {
          tailf:cli-drop-node-name;
          type enumeration {
            enum in;
            enum out;
          }
        }
      }
      uses interface-ip-address-grouping;
      container arp {
        tailf:cli-sequence-commands;
        tailf:cli-compact-syntax;
        leaf address {
          tailf:cli-drop-node-name;
          type inet:ipv4-address;
        }
        leaf mac {
          tailf:cli-drop-node-name;
          type mac-address-type2;
        }
      }
      leaf directed-broadcast {
        type empty;
      }
      leaf port-unreachable {
        type empty;
      }
      leaf redirects {
        type empty;
      }
      leaf unreachables {
        type empty;
      }
      container ospf {
        leaf area {
          type ospf-area-type;
        }
        leaf cost {
          type uint16;
        }
      }
      uses interface-ip-proxy-arp-grouping;
      container port {
        container access-group {
          tailf:cli-sequence-commands;
          tailf:cli-compact-syntax;
          leaf name {
            tailf:cli-drop-node-name;
            type string;
          }
          leaf inout {
            tailf:cli-drop-node-name;
            type enumeration {
              enum in;
              enum out;
            }
          }
        }
      }
      uses ip-helper-address-grouping;
    }
    container ipv6 {
      list address {
        tailf:cli-suppress-mode;
        tailf:cli-delete-when-empty;
        key "prefix";
        leaf prefix {
          type tailf:ipv6-address-and-prefix-length;
        }
        leaf link-local {
          type empty;
        }
      }
      leaf link-local {
        type inet:ipv6-address;
      }
      leaf nd {
        type enumeration {
          enum redirects;
        }
      }
      container neighbor {
        tailf:cli-compact-syntax;
        tailf:cli-sequence-commands;
        leaf address {
          tailf:cli-drop-node-name;
          type inet:ipv6-address;
        }
        leaf mac {
          tailf:cli-drop-node-name;
          type union {
            type string;
            type string;
            type string;
            type string;
          }
        }
      }
      leaf redirects {
        type empty;
      }
      container port {
        container traffic-filter {
          tailf:cli-sequence-commands;
          tailf:cli-compact-syntax;
          leaf name {
            tailf:cli-drop-node-name;
            type string;
          }
          leaf inout {
            tailf:cli-drop-node-name;
            type enumeration {
              enum in;
            }
          }
        }
      }
    }
    container logging {
      container event {
        leaf link-status {
          type enumeration {
            enum yes;
            enum no;
            enum use-global;
          }
        }
      }
    }
    uses interface-isis-grouping;
    uses lldp-grouping;
    container node-segment {
      container ipv4 {
        leaf index {
          type uint16;
        }
      }
    }
    leaf mtu {
      type uint16;
    }
    uses snmp-trap-link-status-grouping;
    leaf speed {
      type enumeration {
        enum 1000 {
          tailf:code-name "mgmt-settings-grouping-speed_1000";
        }
        enum auto {
          tailf:code-name "mgmt-settings-grouping-auto";
        }
      }
    }
    container vrf {
      choice vrf-choice {
        leaf forwarding {
          type string;
        }
        leaf name {
          tailf:cli-drop-node-name;
          type string;
        }
      }
      leaf member {
        type vrf-member-type;
      }
    }
    uses interface-vrrp-grouping;
    leaf shutdown {
      type empty;
    }
  }

  grouping switchport-grouping {
    container switchport {
      presence "Configure switchport parameters";
      leaf beacon {
        type empty;
      }
      container fcrxbbcredit {
        choice bbcredit-choice {
          container creds {
            tailf:cli-drop-node-name;
            leaf credit {
              tailf:cli-drop-node-name;
              type uint8;
            }
            container ecreds {
              tailf:cli-drop-node-name;
              tailf:cli-sequence-commands {
                tailf:cli-reset-siblings;
              }
              tailf:cli-compact-syntax;
              presence "true";
              leaf credit {
                tailf:cli-drop-node-name;
                type uint8;
              }
              leaf mode {
                type enumeration {
                  enum E;
                }
              }
            }
            container fcreds {
              tailf:cli-drop-node-name;
              tailf:cli-sequence-commands {
                tailf:cli-reset-siblings;
              }
              tailf:cli-compact-syntax;
              presence "true";
              leaf credit {
                tailf:cli-drop-node-name;
                type uint8;
              }
              leaf mode {
                type enumeration {
                  enum Fx;
                }
              }
            }
          }
          leaf default {
            type empty;
          }
        }
      }
      leaf description {
        tailf:cli-multi-value;
        type string;
      }
      container ignore {
        leaf bit-error {
          type empty;
        }
      }
      leaf mode {
        type enumeration {
          enum E;
          enum F;
          enum SD;
          enum auto {
            tailf:code-name "switchport-grouping_mode_auto";
          }
        }
      }
      leaf speed {
        type enumeration {
          enum 1000 {
            tailf:code-name "switchport-grouping_1000";
          }
          enum 2000;
          enum 4000;
          enum 8000;
          enum auto {
            tailf:code-name "switchport-grouping_speed_auto";
          }
        }
      }
      container trunk {
        container allowed {
          container vlan {
            choice vlan-choice {
              leaf-list ids {
                tailf:cli-drop-node-name;
                tailf:cli-range-list-syntax;
                type vlan-list-type;
              }
              leaf fixed {
                tailf:cli-drop-node-name;
                type enumeration {
                  enum all;
                  enum none;
                }
              }
              leaf-list except {
                tailf:cli-range-list-syntax;
                type vlan-list-type;
              }
            }
          }
        }
        container native {
          leaf vlan {
            type uint16;
          }
        }
      }
    }
  }

  grouping fc-settings-grouping {
    container channel-group {
      choice channel-group-choice {
        list port {
          tailf:cli-drop-node-name;
          tailf:cli-sequence-commands {
            tailf:cli-reset-siblings;
          }
          tailf:cli-compact-syntax;
          key "nr";
          leaf nr {
            type uint16;
          }
          leaf force {
            type empty;
          }
        }
        leaf auto {
          type empty;
        }
      }
    }
    container fcdomain {
      container rcf-reject {
        leaf vsan {
          type string;
        }
      }
    }
    container fspf {
      container cost {
        tailf:cli-sequence-commands {
          tailf:cli-reset-siblings;
        }
        tailf:cli-compact-syntax;
        leaf cost {
          tailf:cli-drop-node-name;
          type uint16;
        }
        leaf vsan {
          type string;
        }
      }
      container dead-interval {
        tailf:cli-sequence-commands {
          tailf:cli-reset-siblings;
        }
        tailf:cli-compact-syntax;
        leaf cost {
          tailf:cli-drop-node-name;
          type uint16;
        }
        leaf vsan {
          type string;
        }
      }
      container hello-interval {
        tailf:cli-sequence-commands {
          tailf:cli-reset-siblings;
        }
        tailf:cli-compact-syntax;
        leaf cost {
          tailf:cli-drop-node-name;
          type uint16;
        }
        leaf vsan {
          type string;
        }
      }
      container passive {
        leaf vsan {
          type string;
        }
      }
      container retransmit-interval {
        tailf:cli-sequence-commands {
          tailf:cli-reset-siblings;
        }
        tailf:cli-compact-syntax;
        leaf cost {
          tailf:cli-drop-node-name;
          type uint16;
        }
        leaf vsan {
          type string;
        }
      }
    }
    container out-of-service {
      presence "Put an interface out of service.";
      leaf force {
        type empty;
      }
    }
    leaf shutdown {
      type boolean;
    }
    uses switchport-grouping;
  }

  grouping san-settings-grouping {
    container channel {
      leaf mode {
        type enumeration {
          enum active;
        }
      }
    }
    container fcdomain {
      container rcf-reject {
        leaf vsan {
          type string;
        }
      }
    }
    container fspf {
      container cost {
        tailf:cli-sequence-commands {
          tailf:cli-reset-siblings;
        }
        tailf:cli-compact-syntax;
        leaf cost {
          tailf:cli-drop-node-name;
          type uint16;
        }
        leaf vsan {
          type string;
        }
      }
      container dead-interval {
        tailf:cli-sequence-commands {
          tailf:cli-reset-siblings;
        }
        tailf:cli-compact-syntax;
        leaf cost {
          tailf:cli-drop-node-name;
          type uint16;
        }
        leaf vsan {
          type string;
        }
      }
      container hello-interval {
        tailf:cli-sequence-commands {
          tailf:cli-reset-siblings;
        }
        tailf:cli-compact-syntax;
        leaf cost {
          tailf:cli-drop-node-name;
          type uint16;
        }
        leaf vsan {
          type string;
        }
      }
      container passive {
        leaf vsan {
          type string;
        }
      }
      container retransmit-interval {
        tailf:cli-sequence-commands {
          tailf:cli-reset-siblings;
        }
        tailf:cli-compact-syntax;
        leaf cost {
          tailf:cli-drop-node-name;
          type uint16;
        }
        leaf vsan {
          type string;
        }
      }
    }
    leaf shutdown {
      type boolean;
    }
    uses switchport-grouping;
  }

  grouping accounting-action-type-grouping {
    leaf action-type {
      tailf:cli-drop-node-name;
      type enumeration {
        enum none;
        enum start-stop;
        enum stop-only;
      }
    }
  }

  grouping router-bgp-route-map-grouping {
    leaf route-map {
      type string;
    }
  }

  grouping password-grouping {
    container password-container {
      tailf:cli-compact-syntax;
      tailf:cli-flatten-container;
      tailf:cli-sequence-commands;
      tailf:cli-drop-node-name;
      leaf encryption {
        tailf:cli-drop-node-name;
        tailf:cli-optional-in-sequence;
        type uint8;
      }
      leaf password {
        tailf:cli-drop-node-name;
        type string;
      }
    }
  }

  grouping distribute-list-grouping {
    container distribute-list {
      list accesslist {
        tailf:cli-drop-node-name;
        tailf:cli-compact-syntax;
        tailf:cli-suppress-mode;
        tailf:cli-delete-when-empty;
        tailf:cli-suppress-list-no;
        key "in-out";
        leaf in-out {
          type access-list-in-out-type;
        }
      }
      list accesslist-ifname {
        tailf:cli-drop-node-name;
        tailf:cli-compact-syntax;
        tailf:cli-suppress-mode;
        tailf:cli-delete-when-empty;
        tailf:cli-suppress-list-no;
        key "in-out interface";
        leaf in-out {
          type access-list-in-out-type;
        }
        leaf interface {
          tailf:cli-expose-key-name;
          type string;
        }
      }
      list accesslist-prefix-gateway {
        tailf:cli-drop-node-name;
        tailf:cli-compact-syntax;
        tailf:cli-suppress-mode;
        tailf:cli-delete-when-empty;
        tailf:cli-suppress-list-no;
        tailf:cli-sequence-commands;
        key "in-out";
        leaf prefix-gateway {
          tailf:cli-drop-node-name;
          mandatory true;
          tailf:cli-prefix-key;
          type enumeration {
            enum prefix;
            enum prefix-list;
            enum gateway;
          }
        }
        leaf name {
          tailf:cli-drop-node-name;
          mandatory true;
          tailf:cli-prefix-key;
          type string;
        }
        leaf in-out {
          type access-list-in-out-type;
        }
      }
      list accesslist-prefix-gateway-ifname {
        tailf:cli-drop-node-name;
        tailf:cli-compact-syntax;
        tailf:cli-suppress-mode;
        tailf:cli-delete-when-empty;
        tailf:cli-suppress-list-no;
        tailf:cli-sequence-commands;
        key "in-out interface";
        leaf prefix-gateway {
          tailf:cli-drop-node-name;
          mandatory true;
          tailf:cli-prefix-key;
          type enumeration {
            enum prefix;
            enum prefix-list;
            enum gateway;
          }
        }
        leaf name {
          tailf:cli-drop-node-name;
          mandatory true;
          tailf:cli-prefix-key;
          type string;
        }
        leaf in-out {
          type access-list-in-out-type;
        }
        leaf interface {
          tailf:cli-expose-key-name;
          type string;
        }
      }
    }
  }

  grouping common-interface-grouping {
    leaf interface {
      type string;
    }
  }

  grouping passive-interface-grouping {
    container passive-interface {
      uses common-interface-grouping;
    }
  }

  grouping vrf-route-target-export-import-grouping {
    list port {
      tailf:cli-drop-node-name;
      tailf:cli-suppress-mode;
      key "asn-ip";
      leaf asn-ip {
        type asn-ip-type;
      }
    }
  }

  grouping vrf-route-target-content-grouping {
    uses vrf-route-target-export-import-grouping;
    container vpn-ipv4 {
      uses vrf-route-target-export-import-grouping;
    }
    container evpn {
      uses vrf-route-target-export-import-grouping;
      leaf route-map {
        type string;
      }
    }
  }

  grouping vrf-route-target-grouping {
    container export {
      uses vrf-route-target-content-grouping;
    }
    container import {
      uses vrf-route-target-content-grouping;
    }
  }

  grouping police-action-choice-grouping {
    choice action-choice {
      leaf drop {
        tailf:cli-hide-in-submode;
        type empty;
      }
      leaf set-clp-transmit {
        tailf:cli-hide-in-submode;
        type empty;
      }
      leaf set-discard-class-transmit {
        tailf:cli-hide-in-submode;
        type uint8;
      }
      leaf set-dscp-transmit {
        tailf:cli-hide-in-submode;
        type string;
      }
      leaf set-frde-transmit {
        tailf:cli-hide-in-submode;
        type empty;
      }
      leaf set-mpls-exp-imposition-transmit {
        tailf:cli-hide-in-submode;
        type uint8;
      }
      leaf set-mpls-exp-topmost-transmit {
        tailf:cli-hide-in-submode;
        type uint8;
      }
      leaf set-prec-transmit {
        tailf:cli-hide-in-submode;
        type uint8;
      }
      leaf set-qos-transmit {
        tailf:cli-hide-in-submode;
        type uint8;
      }
      leaf transmit {
        tailf:cli-hide-in-submode;
        type empty;
      }
    }
  }

  grouping police-action-grouping {
    leaf drop {
      type empty;
    }
    leaf set-clp-transmit {
      type empty;
    }
    leaf set-discard-class-transmit {
      type uint8;
    }
    leaf set-dscp-transmit {
      type string;
    }
    leaf set-frde-transmit {
      type empty;
    }
    leaf set-mpls-exp-imposition-transmit {
      type uint8;
    }
    leaf set-mpls-exp-topmost-transmit {
      type uint8;
    }
    leaf set-prec-transmit {
      type uint8;
    }
    leaf set-qos-transmit {
      type uint8;
    }
    leaf transmit {
      type empty;
    }
  }

  grouping logging-severity-grouping {
    leaf severity {
      tailf:cli-drop-node-name;
      type enumeration {
        enum alerts;
        enum critical;
        enum debugging;
        enum emergencies;
        enum errors;
        enum informational;
        enum notifications;
        enum warnings;
      }
    }
  }

  grouping access-group-grouping {
    container access-group {
      tailf:cli-sequence-commands;
      tailf:cli-compact-syntax;
      leaf name {
        tailf:cli-drop-node-name;
        type string;
      }
      leaf inout {
        tailf:cli-drop-node-name;
        type enumeration {
          enum in;
        }
      }
    }
  }

  grouping access-group-vrf-grouping {
    container access-group {
      tailf:cli-sequence-commands;
      tailf:cli-compact-syntax;
      leaf name {
        tailf:cli-drop-node-name;
        tailf:cli-break-sequence-commands;
        type string;
      }
      leaf inout {
        tailf:cli-drop-node-name;
        type enumeration {
          enum in;
        }
      }
      leaf vrf {
        type string;
      }
    }
  }

  grouping access-list-grouping {
    container access-list {
      tailf:cli-compact-syntax;
      list acl {
        tailf:cli-drop-node-name;
        key "name";
        leaf name {
          type std-ip-acl-type;
        }
        leaf comment {
          tailf:cli-multi-value;
          type string;
        }
        choice statistics-counters-choice {
          container statistics {
            leaf per-entry {
              type empty;
            }
          }
          container counters {
            leaf per-entry {
              type empty;
            }
          }
        }
        list std-access-list-rule {
          tailf:cli-suppress-mode;
          tailf:cli-delete-when-empty;
          tailf:cli-drop-node-name;
          tailf:cli-compact-syntax;
          key "seq";
          leaf seq {
            tailf:cli-suppress-range;
            type uint32;
          }
          leaf rule {
            tailf:cli-multi-value;
            tailf:cli-drop-node-name;
            type string;
          }
        }
      }
      container standard {
        list std-named-acl {
          tailf:cli-drop-node-name;
          key "name";
          leaf name {
            type std-ip-acl-type;
          }
          container statistics {
            leaf per-entry {
              type empty;
            }
          }
          list std-access-list-rule {
            tailf:cli-suppress-mode;
            tailf:cli-delete-when-empty;
            tailf:cli-drop-node-name;
            tailf:cli-compact-syntax;
            ordered-by user;
            key "rule";
            leaf rule {
              tailf:cli-multi-word-key;
              type string;
            }
          }
        }
      }
    }
  }

  grouping nexthop-group-grouping {
    list nexthop-group {
      key "name";
      leaf name {
        type string;
      }
      leaf type {
        tailf:cli-hide-in-submode;
        type enumeration {
          enum gre;
          enum mpls;
        }
      }
      leaf size {
        type uint16;
      }
      leaf ttl {
        type uint8;
      }
      container tunnel-source {
        leaf address {
          tailf:cli-drop-node-name;
          type inet:ipv4-address;
        }
        container intf {
          uses interface-grouping;
        }
      }
      leaf tunnel-key {
        type enumeration {
          enum ingress-interface;
        }
      }
      list entry {
        tailf:cli-compact-syntax;
        tailf:cli-suppress-mode;
        key "id";
        leaf id {
          type uint16;
        }
        leaf tunnel-destination {
          type inet:ipv4-address;
        }
      }
    }
  }

  grouping access-group-list-grouping {
    list access-group {
      tailf:cli-suppress-mode;
      tailf:cli-delete-when-empty;
      tailf:cli-compact-syntax;
      tailf:cli-sequence-commands;
      key "direction";
      leaf direction {
        type enumeration {
          enum in;
          enum out;
        }
      }
      leaf access-list {
        tailf:cli-drop-node-name;
        tailf:cli-prefix-key;
        type string;
      }
    }
  }

  grouping snmp-server-group-grouping {
    leaf context {
      tailf:cli-optional-in-sequence;
      type string;
    }
    leaf read {
      tailf:cli-optional-in-sequence;
      type string;
    }
    leaf notify {
      tailf:cli-optional-in-sequence;
      type string;
    }
    leaf write {
      tailf:cli-optional-in-sequence;
      type string;
    }
  }

  grouping router-isis-af-redistribute-grouping {
    container redistribute {
      container isis {
        container level-1-into-level-2 {
          tailf:cli-drop-node-name;
          tailf:cli-compact-syntax;
          tailf:cli-sequence-commands {
            tailf:cli-reset-siblings;
          }
          leaf level-1 {
            type empty;
          }
          leaf into {
            type empty;
          }
          leaf level-2 {
            type empty;
          }
          leaf route-map {
            type string;
          }
        }
        container level-2-into-level-1 {
          tailf:cli-drop-node-name;
          tailf:cli-compact-syntax;
          tailf:cli-sequence-commands {
            tailf:cli-reset-siblings;
          }
          leaf level-2 {
            type empty;
          }
          leaf into {
            type empty;
          }
          leaf level-1 {
            type empty;
          }
          leaf route-map {
            type string;
          }
        }
      }
    }
  }

  grouping ip-verify-grouping {
    container verify {
      container unicast {
        container source {
          container reachable-via {
            leaf rx {
              type empty;
            }
          }
        }
      }
    }
  }

  grouping interface-ip-ospf-grouping {
    container ospf {
      leaf area {
        type ospf-area-type;
      }
      choice ip-ospf-authentication-choice {
        leaf authentication {
          type empty;
        }
        container authentication-md {
          tailf:cli-drop-node-name;
          container authentication {
            leaf message-digest {
              type empty;
            }
          }
        }
      }
      container authentication-key {
        leaf auth-type {
          tailf:cli-drop-node-name;
          type uint8;
        }
        leaf auth-key {
          tailf:cli-drop-node-name;
          type string;
        }
      }
      leaf cost {
        type uint32;
      }
      leaf dead-interval {
        type uint16;
      }
      leaf hello-interval {
        type uint16;
      }
      list message-digest-key {
        tailf:cli-suppress-mode;
        tailf:cli-compact-syntax;
        tailf:cli-sequence-commands {
          tailf:cli-reset-siblings;
        }
        key "id";
        leaf id {
          tailf:cli-suppress-range;
          type uint8;
        }
        container md5 {
          tailf:cli-compact-syntax;
          tailf:cli-sequence-commands {
            tailf:cli-reset-siblings;
          }
          leaf auth-type {
            tailf:cli-drop-node-name;
            tailf:cli-optional-in-sequence;
            type enumeration {
              enum 0;
              enum 7;
              enum 8a;
            }
          }
          leaf auth-key {
            tailf:cli-drop-node-name;
            type string;
          }
        }
      }
      leaf mtu-ignore {
        type empty;
      }
      leaf network {
        type enumeration {
          enum point-to-point;
        }
      }
      leaf priority {
        type uint8;
      }
      leaf retransmit-interval {
        type uint16;
      }
      leaf shutdown {
        type empty;
      }
      leaf transmit-delay {
        type uint16;
      }
    }
  }

  grouping ip-helper-address-grouping {
    list helper-address {
      tailf:cli-suppress-mode;
      key "name";
      leaf name {
        type string;
      }
    }
  }

  grouping interface-encapsulation-grouping {
    container encapsulation {
      container vlan {
        tailf:cli-add-mode;
        container client {
          choice encapsulation-vlan-client-choice {
            container dot1q {
              tailf:cli-compact-syntax;
              tailf:cli-sequence-commands {
                tailf:cli-reset-siblings;
              }
              choice encapsulation-vlan-client-dot1q-choice {
                container outer {
                  tailf:cli-compact-syntax;
                  tailf:cli-flatten-container;
                  tailf:cli-sequence-commands {
                    tailf:cli-reset-siblings;
                  }
                  leaf outer-vlan {
                    tailf:cli-drop-node-name;
                    type uint16;
                  }
                  leaf inner {
                    type uint16;
                  }
                }
                leaf vlan {
                  tailf:cli-drop-node-name;
                  type uint16;
                }
              }
              container network {
                tailf:cli-flatten-container;
                leaf client {
                  type empty;
                }
              }
            }
            container unmatched {
              presence "true";
            }
            leaf untagged {
              type empty;
            }
          }
        }
      }
      container dot1q {
        leaf vlan {
          type uint16;
        }
      }
    }
  }

  grouping interface-service-policy-grouping {
    list service-policy {
      tailf:cli-suppress-mode;
      tailf:cli-delete-when-empty;
      key "type";
      leaf type {
        tailf:cli-expose-key-name;
        type enumeration {
          enum pbr;
          enum qos;
          enum tapagg;
        }
      }
      leaf input {
        type string;
      }
    }
  }

  grouping default-originate-grouping {
    container default-originate {
      tailf:cli-delete-when-empty;
      presence "true";
      leaf route-map {
        type string;
      }
    }
  }

  grouping route-map-grouping {
    list route-map {
      tailf:cli-suppress-mode;
      key "inout";
      leaf inout {
        type enumeration {
          enum in {
            tailf:code-name "route_in";
          }
          enum out {
            tailf:code-name "route_out";
          }
        }
      }
      leaf route-map-name {
        tailf:cli-drop-node-name;
        tailf:cli-prefix-key;
        type string;
        mandatory true;
      }
    }
  }

  grouping arp-timeout-grouping {
    container arp {
      choice aging-timeout-choice {
        leaf timeout {
          type uint16;
        }
        container aging {
          leaf timeout {
            type uint16;
          }
        }
      }
    }
  }

  grouping interface-ip-address-grouping {
    container address {
      leaf address-primary {
        tailf:cli-drop-node-name;
        type ip-mask;
      }
      list address-secondary {
        tailf:cli-drop-node-name;
        tailf:cli-compact-syntax;
        tailf:cli-suppress-mode;
        tailf:cli-sequence-commands {
          tailf:cli-reset-siblings;
        }
        key "prefix";
        leaf prefix {
          type ip-mask;
        }
        leaf secondary {
          type empty;
        }
      }
    }
  }

  grouping lldp-grouping {
    container lldp {
      leaf receive {
        type boolean;
      }
      leaf transmit {
        type boolean;
      }
    }
  }

  grouping tacacs-server-key-grouping {
    container key {
      tailf:cli-flatten-container;
      tailf:cli-compact-syntax;
      tailf:cli-sequence-commands {
        tailf:cli-reset-siblings;
      }
      leaf encryption {
        tailf:cli-drop-node-name;
        tailf:cli-optional-in-sequence;
        type enumeration {
          enum 0;
          enum 7;
          enum 8a;
        }
      }
      leaf key {
        tailf:cli-drop-node-name;
        tailf:cli-multi-value;
        type string;
      }
    }
  }

  grouping ip-route-options-grouping {
    leaf admin-distance {
      tailf:cli-drop-node-name;
      type uint8;
    }
    leaf name {
      tailf:cli-optional-in-sequence;
      type string;
    }
    leaf permanent {
      tailf:cli-optional-in-sequence;
      type empty;
    }
    leaf tag {
      tailf:cli-optional-in-sequence;
      type uint32;
    }
    leaf track {
      tailf:cli-optional-in-sequence;
      type uint16;
    }
    leaf metric {
      tailf:cli-optional-in-sequence;
      type uint32;
    }
  }

  grouping router-bgp-local-as-grouping {
    container local-as {
      presence "Specify a local-as number";
      tailf:cli-compact-syntax;
      tailf:cli-sequence-commands {
        tailf:cli-reset-siblings;
      }
      leaf as-no {
        tailf:cli-drop-node-name;
        type uint16;
      }
      leaf no-prepend {
        type empty;
      }
      leaf replace-as {
        type empty;
      }
      leaf dual-as {
        type empty;
      }
    }
  }

  grouping interface-ip-pim-bsr-border {
    container bsr-border {
      presence "true";
      list address {
        tailf:cli-drop-node-name;
        tailf:cli-suppress-mode;
        key "prefix";
        leaf prefix {
          type inet:ipv4-prefix;
        }
      }
      list access-list {
        tailf:cli-suppress-mode;
        key "name";
        leaf name {
          type string;
        }
      }
    }
  }

  grouping logging-interface-grouping {
    container logging {
      container event {
        container port {
          container linkstatus {
            tailf:alt-name "link-status";
            presence "UPDOWN and CHANGE messages";
            leaf default {
              type empty;
            }
          }
          container trunk-status {
            presence "TRUNK status messages";
            leaf default {
              type empty;
            }
          }
        }
        leaf link-status {
          type enumeration {
            enum yes;
            enum no;
            enum use-global;
          }
        }
        container storm-control {
          leaf discards {
            type enumeration {
              enum yes;
              enum no;
              enum use-global;
            }
          }
        }
      }
    }
  }

  grouping management-ssh-access-group-grouping {
    list access-group {
      tailf:cli-suppress-mode;
      tailf:cli-compact-syntax;
      key "name";
      leaf name {
        type string;
      }
      leaf inout {
        tailf:cli-drop-node-name;
        type enumeration {
          enum in;
        }
      }
      list vrf {
        tailf:cli-suppress-mode;
        tailf:cli-compact-syntax;
        key "name";
        leaf name {
          type string;
        }
        leaf inout {
          tailf:cli-drop-node-name;
          type enumeration {
            enum in;
          }
        }
      }
    }
  }

  grouping interface-vrrp-grouping {
    list vrrp {
      tailf:cli-suppress-mode;
      tailf:cli-compact-syntax;
      key "id";
      leaf id {
        type uint8;
      }
      container authentication {
        tailf:cli-compact-syntax;
        leaf text {
          type string;
        }
      }
      container preempt {
        container delay {
          tailf:cli-compact-syntax;
          leaf minimum {
            type uint16;
          }
          leaf reload {
            type uint16;
          }
        }
      }
      container timers {
        container delay {
          leaf reload {
            type uint16;
          }
        }
      }
      choice vrrp-priority-choice {
        leaf priority {
          type uint8;
        }
        leaf priority-level {
          type uint8;
        }
      }
      container peer {
        container authentication {
          container ietf-md5 {
            tailf:cli-compact-syntax;
            tailf:cli-sequence-commands;
            container key-string {
              tailf:cli-compact-syntax;
              tailf:cli-sequence-commands;
              leaf encryption {
                tailf:cli-drop-node-name;
                tailf:cli-optional-in-sequence;
                type enumeration {
                  enum 0;
                  enum 7;
                }
              }
              leaf password {
                tailf:cli-drop-node-name;
                type string;
              }
            }
          }
        }
      }
      choice vrrp-ip-choice {
        container ip {
          leaf version {
            type uint8;
          }
          leaf primary {
            tailf:cli-drop-node-name;
            type inet:ipv4-address;
          }
          container secondary {
            tailf:cli-drop-node-name;
            tailf:cli-compact-syntax;
            tailf:cli-sequence-commands {
              tailf:cli-reset-siblings;
            }
            leaf address {
              tailf:cli-drop-node-name;
              type inet:ipv4-address;
            }
            leaf secondary {
              type empty;
            }
          }
        }
        container ipv4 {
          leaf version {
            type uint8;
          }
          leaf primary {
            tailf:cli-drop-node-name;
            type inet:ipv4-address;
          }
          list address-secondary {
            tailf:cli-drop-node-name;
            tailf:cli-compact-syntax;
            tailf:cli-suppress-mode;
            key "address";
            leaf address {
              type inet:ipv4-address;
            }
            leaf secondary {
              type empty;
            }
          }
        }
      }
      list ipv6 {
        tailf:cli-suppress-mode;
        key "address";
        leaf address {
          type inet:ipv6-address;
        }
      }
      list tracked-object {
        tailf:cli-suppress-mode;
        key "name";
        leaf name {
          type string;
        }
        leaf decrement {
          type uint8;
        }
        leaf shutdown {
          type empty;
        }
      }
    }
  }

  grouping snmp-trap-link-status-grouping {
    container snmp {
      container trap {
        choice trap-choice {
          leaf link-status {
            type boolean;
          }
          leaf link-change {
            type boolean;
          }
        }
      }
    }
  }

  grouping interface-ip-proxy-arp-grouping {
    leaf local-proxy-arp {
      type empty;
    }
    leaf proxy-arp {
      type empty;
    }
  }

  grouping storm-control-level-grouping {
    container level {
      choice storm-control-level-choice {
        leaf pps {
          type uint32;
        }
        leaf maximum-bandwidth {
          tailf:cli-drop-node-name;
          type decimal64 {
            fraction-digits 2;
          }
        }
      }
    }
  }

  grouping storm-control-grouping {
    container storm-control {
      container broadcast {
        presence "Broadcast";
        tailf:cli-delete-when-empty;
        uses storm-control-level-grouping;
      }
      container unicast {
        presence "Unicast";
        tailf:cli-delete-when-empty;
        uses storm-control-level-grouping;
      }
      container multicast {
        presence "Multicast";
        tailf:cli-delete-when-empty;
        uses storm-control-level-grouping;
      }
      container unknown-unicast {
        presence "Unknown-unicast";
        tailf:cli-delete-when-empty;
        uses storm-control-level-grouping;
      }
    }
  }

  grouping username-sshkey-grouping {
    leaf file {
      type string;
    }
    list secondary {
      tailf:cli-suppress-mode;
      key "name";
      leaf name {
        tailf:cli-multi-word-key;
        type string;
      }
    }
    leaf sshkey {
      tailf:cli-drop-node-name;
      tailf:cli-multi-value;
      type string;
    }
  }

  grouping snmp-server-auth-grouping {
    leaf auth {
      type enumeration {
        enum md5;
        enum sha;
        enum sha224;
        enum sha256;
        enum sha384;
        enum sha512;
      }
    }
    leaf auth-password {
      tailf:cli-drop-node-name;
      type string;
    }
    leaf priv {
      tailf:cli-optional-in-sequence;
      type enumeration {
        enum aes;
        enum des;
        enum aes192;
        enum aes256;
      }
    }
    leaf priv-password {
      tailf:cli-drop-node-name;
      type string;
    }
  }

  grouping snmp-server-user-grouping {
    choice security-model {
      leaf v1 {
        type empty;
      }
      leaf v2c {
        type empty;
      }
      case v3 {
        container v3 {
          tailf:cli-compact-syntax;
          tailf:cli-flatten-container;
          tailf:cli-sequence-commands {
            tailf:cli-reset-siblings;
          }
          leaf localized {
            tailf:cli-optional-in-sequence;
            type empty;
          }
          leaf engineID {
            tailf:cli-drop-node-name;
            tailf:cli-optional-in-sequence;
            type string;
          }
          uses snmp-server-auth-grouping;
        }
      }
    }
  }

  grouping control-plane-access-group-grouping {
    container access-group {
      container non-vrf {
        tailf:cli-drop-node-name;
        tailf:cli-compact-syntax;
        tailf:cli-sequence-commands;
        leaf name {
          tailf:cli-drop-node-name;
          type string;
        }
        leaf inout {
          tailf:cli-drop-node-name;
          type enumeration {
            enum in;
          }
        }
      }
      list vrf {
        tailf:cli-drop-node-name;
        tailf:cli-suppress-mode;
        tailf:cli-compact-syntax;
        tailf:cli-delete-when-empty;
        key "vrf";
        leaf name {
          tailf:cli-prefix-key;
          tailf:cli-drop-node-name;
          type string;
        }
        leaf vrf {
          tailf:cli-expose-key-name;
          type string;
        }
        leaf inout {
          tailf:cli-drop-node-name;
          type enumeration {
            enum in;
          }
        }
      }
    }
  }

  grouping logging-host-grouping {
    leaf port {
      tailf:cli-drop-node-name;
      type uint16;
    }
    leaf protocol {
      type enumeration {
        enum tcp;
        enum udp;
      }
    }
  }

  grouping router-bgp-aggregate-address-grouping {
    list aggregate-address {
      tailf:cli-suppress-mode;
      tailf:cli-compact-syntax;
      key "address";
      leaf address {
        type union {
          type inet:ipv4-address;
          type inet:ipv4-prefix;
          type inet:ipv6-prefix;
        }
      }
      leaf as-set {
        type empty;
      }
      leaf summary-only {
        type empty;
      }
      leaf attribute-map {
        type string;
      }
      leaf match-map {
        type string;
      }
    }
  }

  grouping ipv6-route-options-grouping {
    leaf name {
      type string;
    }
    leaf tag {
      type uint32;
    }
    leaf distance {
      tailf:cli-drop-node-name;
      type uint8;
    }
  }

  grouping ipv6-route-grouping {
    list ipv6-route-interface-destination-list {
      tailf:cli-drop-node-name;
      tailf:cli-suppress-mode;
      tailf:cli-delete-when-empty;
      tailf:cli-compact-syntax;
      key "prefix interface destination";
      leaf prefix {
        type tailf:ipv6-address-and-prefix-length;
      }
      leaf interface {
        type string;
      }
      leaf destination {
        type inet:ipv6-address;
      }
      uses ipv6-route-options-grouping;
    }
    list ipv6-route-destination-list {
      tailf:cli-drop-node-name;
      tailf:cli-suppress-mode;
      tailf:cli-delete-when-empty;
      tailf:cli-compact-syntax;
      key "prefix nexthop";
      leaf prefix {
        type tailf:ipv6-address-and-prefix-length;
      }
      leaf nexthop {
        type inet:ipv6-address;
      }
      uses ipv6-route-options-grouping;
    }
    list ipv6-route-interface-list {
      tailf:cli-drop-node-name;
      tailf:cli-suppress-mode;
      tailf:cli-delete-when-empty;
      tailf:cli-compact-syntax;
      key "prefix interface";
      leaf prefix {
        type tailf:ipv6-address-and-prefix-length;
      }
      leaf interface {
        type string;
      }
      uses ipv6-route-options-grouping;
    }
  }

  grouping interface-mac-grouping {
    container mac {
      container address {
        container learning {
          leaf disabled {
            type empty;
          }
        }
      }
      container port {
        leaf access-group {
          type string;
        }
      }
      uses access-group-list-grouping;
    }
  }

  grouping route-target-grouping {
    list rt {
      tailf:cli-suppress-mode;
      tailf:cli-drop-node-name;
      key "asn-ip";
      leaf asn-ip {
        type asn-ip-type;
      }
    }
  }

  grouping route-target-evpn-grouping {
    container evpn {
      uses route-target-grouping;
    }
  }

  grouping router-bgp-vrf-address-family-route-target-grouping {
    container route-target {
      container import {
        uses route-target-grouping;
        uses route-target-evpn-grouping;
      }
      container export {
        uses route-target-grouping;
        uses route-target-evpn-grouping;
      }
    }
  }

  grouping mpls-label-range-grouping {
    leaf start {
      tailf:cli-drop-node-name;
      type uint32;
    }
    leaf number {
      tailf:cli-drop-node-name;
      type uint32;
    }
  }

  grouping maximum-routes-grouping {
    container maximum-routes {
      tailf:cli-compact-syntax;
      tailf:cli-sequence-commands {
        tailf:cli-reset-siblings;
      }
      leaf number {
        tailf:cli-drop-node-name;
        type uint32;
      }
      choice neighbor-maximum-routes-choice {
        leaf warning-only {
          type empty;
        }
        container warning-limit {
          tailf:cli-flatten-container;
          choice warning-limit-choice {
            container number {
              tailf:cli-drop-node-name;
              tailf:cli-compact-syntax;
              tailf:cli-sequence-commands {
                tailf:cli-reset-siblings;
              }
              leaf number {
                tailf:cli-drop-node-name;
                type uint32;
              }
              leaf warning-only {
                type empty;
              }
            }
            container percentage {
              tailf:cli-drop-node-name;
              tailf:cli-compact-syntax;
              tailf:cli-sequence-commands {
                tailf:cli-reset-siblings;
              }
              leaf percentage {
                tailf:cli-drop-node-name;
                type uint8;
              }
              leaf percent {
                type empty;
              }
              leaf warning-only {
                type empty;
              }
            }
          }
        }
      }
    }
  }

  grouping router-bgp-network-grouping {
    list network {
      tailf:cli-suppress-mode;
      key "address";
      leaf address {
        type union {
          type inet:ipv4-prefix;
          type inet:ipv6-prefix;
        }
      }
      leaf route-map {
        type string;
      }
    }
  }

  grouping router-pim-sparse-mode-rp-grouping {
    container rp {
      container address {
        list address-range-prefix {
          tailf:cli-drop-node-name;
          tailf:cli-suppress-mode;
          tailf:cli-compact-syntax;
          key "ip prefix";
          leaf ip {
            type inet:ipv4-address;
          }
          leaf prefix {
            type inet:ipv4-prefix;
          }
        }
        list address {
          tailf:cli-drop-node-name;
          tailf:cli-suppress-mode;
          tailf:cli-compact-syntax;
          key "ip";
          leaf ip {
            type inet:ipv4-address;
          }
          leaf override {
            type empty;
          }
        }
        list address-acl {
          tailf:cli-drop-node-name;
          tailf:cli-suppress-mode;
          tailf:cli-compact-syntax;
          key "ip access-list";
          leaf ip {
            type inet:ipv4-address;
          }
          leaf access-list {
            tailf:cli-expose-key-name;
            type string;
          }
          leaf override {
            type empty;
          }
        }
      }
    }
  }

  grouping protocol-icmp-grouping {
    container icmp-code-all {
      tailf:cli-drop-node-name;
      tailf:cli-compact-syntax;
      leaf-list type {
        tailf:cli-flat-list-syntax;
        type string;
      }
      leaf code {
        type enumeration {
          enum all;
        }
      }
    }
  }

  grouping directflow-interface-grouping {
    container interface {
      list Et {
        tailf:cli-suppress-mode;
        tailf:cli-range-list-syntax;
        tailf:cli-allow-join-with-key;
        key "id";
        leaf id {
          type uint16;
        }
      }
    }
  }

  grouping router-bgp-neighbor-password-grouping {
    container password {
      tailf:cli-compact-syntax;
      tailf:cli-sequence-commands;
      leaf encryption {
        tailf:cli-drop-node-name;
        tailf:cli-optional-in-sequence;
        type enumeration {
          enum 0;
          enum 7;
        }
      }
      leaf password {
        tailf:cli-drop-node-name;
        type string;
      }
    }
  }

  grouping rib-in-pre-policy-retain-grouping {
    container rib-in {
      container pre-policy {
        tailf:cli-compact-syntax;
        tailf:cli-sequence-commands;
        leaf retain {
          type boolean;
        }
      }
    }
  }

  grouping monitor-session-interface-mirror-detection-grouping {
    leaf mirroring-direction {
      tailf:cli-drop-node-name;
      type enumeration {
        enum rx;
        enum tx;
        enum both;
      }
    }
  }

  grouping monitor-session-interface-grouping {
    list Ethernet {
      tailf:cli-suppress-mode;
      tailf:cli-delete-when-empty;
      tailf:cli-allow-join-with-key;
      key "name";
      leaf name {
        type string;
      }
      uses monitor-session-interface-mirror-detection-grouping;
    }
    list Port-Channel {
      tailf:cli-suppress-mode;
      tailf:cli-delete-when-empty;
      tailf:cli-allow-join-with-key;
      key "name";
      leaf name {
        type string;
      }
      uses monitor-session-interface-mirror-detection-grouping;
    }
  }

  grouping vlan-internal-order-range-grouping {
    container range {
      tailf:cli-compact-syntax;
      tailf:cli-sequence-commands {
        tailf:cli-reset-siblings;
      }
      leaf begin {
        tailf:cli-drop-node-name;
        type uint16;
      }
      leaf end {
        tailf:cli-drop-node-name;
        type uint16;
      }
    }
  }

  grouping monitor-telemetry-inband-profile-collection-grouping {
    container collection {
      container flow {
        leaf tracker {
          type string;
        }
      }
    }
  }

  grouping interface-ip-nat-static-grouping {
    list group {
      tailf:cli-drop-node-name;
      tailf:cli-suppress-mode;
      tailf:cli-compact-syntax;
      tailf:cli-sequence-commands {
        tailf:cli-reset-siblings;
      }
      key "group";
      leaf orig-address {
        tailf:cli-drop-node-name;
        tailf:cli-prefix-key;
        type inet:ipv4-address;
      }
      leaf tr-address {
        tailf:cli-drop-node-name;
        tailf:cli-prefix-key;
        type inet:ipv4-address;
      }
      leaf group {
        tailf:cli-expose-key-name;
        type uint16;
      }
      leaf comment {
        tailf:cli-multi-value;
        type string;
      }
    }
  }

  grouping interface-ip-nat-grouping {
    container nat {
      container destination {
        container static {
          uses interface-ip-nat-static-grouping;
        }
      }
      container source {
        container static {
          uses interface-ip-nat-static-grouping;
        }
      }
    }
  }

  grouping ipv6-nd-grouping {
    container nd {
      leaf managed-config-flag {
        type empty;
      }
      list prefix {
        tailf:cli-suppress-mode;
        tailf:cli-compact-syntax;
        key "address";
        leaf address {
          type tailf:ipv6-address-and-prefix-length;
        }
        choice ipv6-nd-prefix-choice {
          leaf infinite {
            type empty;
          }
          leaf no-advertise {
            type empty;
          }
          leaf no-autoconfig {
            type empty;
          }
          leaf no-onlink {
            type empty;
          }
        }
      }
      container ra {
        container disabled {
          presence "true";
          leaf all {
            type empty;
          }
        }
        list dns-server {
          tailf:cli-suppress-mode;
          key "address";
          leaf address {
            type union {
              type inet:ipv6-address;
              type string;
            }
          }
          leaf lifetime {
            type uint32;
          }
        }
        container interval {
          container msec {
            tailf:cli-compact-syntax;
            tailf:cli-sequence-commands {
              tailf:cli-reset-siblings;
            }
            leaf max {
              tailf:cli-drop-node-name;
              type uint32;
            }
            leaf min {
              tailf:cli-drop-node-name;
              type uint32;
            }
          }
        }
      }
      leaf redirects {
        type empty;
      }
      leaf router-preference {
        type enumeration {
          enum high;
          enum low;
          enum medium;
        }
      }
    }
  }

  grouping graceful-restart-grouping {
    container graceful-restart {
      leaf restart-time {
        type uint16;
      }
      leaf stalepath-time {
        type uint16;
      }
    }
  }

  grouping bgp-additional-paths-grouping {
    container additional-paths {
      container install {
        presence "true";
        leaf ecmp-primary {
          type empty;
        }
      }
      leaf receive {
        type empty;
      }
      container send {
        presence "true";
        choice additional-paths-choice {
          leaf any {
            type empty;
          }
          leaf backup {
            type empty;
          }
          container ecmp {
            presence "true";
            leaf limit {
              type uint8;
            }
          }
          leaf limit {
            type uint8;
          }
        }
      }
    }
  }

  leaf os-major {
    type uint32;
  }
  leaf os-minor {
    type uint32;
  }
  list alias {
    tailf:cli-suppress-mode;
    key "name";
    leaf name {
      tailf:cli-multi-word-key;
      type string;
    }
  }
  container hardware {
    container access-list {
      container resource {
        container sharing {
          container vlan {
            leaf ipv4 {
              type enumeration {
                enum out;
              }
            }
            leaf ipv6 {
              type enumeration {
                enum out;
              }
            }
          }
        }
      }
      leaf mechanism {
        type enumeration {
          enum algomatch;
          enum none;
          enum tcam;
        }
      }
    }
    container counter {
      container feature {
        container acl {
          leaf in {
            type boolean;
          }
        }
        container ip {
          leaf in {
            type empty;
          }
          container in-layer3 {
            tailf:cli-drop-node-name;
            tailf:cli-compact-syntax;
            tailf:cli-sequence-commands {
              tailf:cli-reset-siblings;
            }
            leaf in {
              type empty;
            }
            leaf layer3 {
              type empty;
            }
          }
          container out-layer3 {
            tailf:cli-drop-node-name;
            tailf:cli-compact-syntax;
            tailf:cli-sequence-commands {
              tailf:cli-reset-siblings;
            }
            leaf out {
              type empty;
            }
            leaf layer3 {
              type empty;
            }
          }
        }
        container subinterface {
          leaf in {
            type empty;
          }
          leaf out {
            type empty;
          }
          container in-layer2 {
            tailf:cli-drop-node-name;
            tailf:cli-compact-syntax;
            tailf:cli-sequence-commands {
              tailf:cli-reset-siblings;
            }
            leaf in {
              type empty;
            }
            leaf layer2 {
              type empty;
            }
          }
          container out-layer2 {
            tailf:cli-drop-node-name;
            tailf:cli-compact-syntax;
            tailf:cli-sequence-commands {
              tailf:cli-reset-siblings;
            }
            leaf out {
              type empty;
            }
            leaf layer2 {
              type empty;
            }
          }
        }
        container traffic-policy {
          leaf cpu {
            type empty;
          }
          leaf in {
            type empty;
          }
          leaf out {
            type empty;
          }
        }
      }
    }
    list speed-group {
      tailf:cli-suppress-mode;
      tailf:cli-allow-join-with-key;
      key "id";
      leaf id {
        type uint16;
      }
      leaf serdes {
        type enumeration {
          enum 10g;
          enum 25g;
          enum 50g;
        }
      }
    }
    container tcam-mode {
      tailf:cli-drop-node-name;
      container tcam {
        tailf:cli-add-mode;
        list profile {
          key "name";
          leaf name {
            type string;
          }
          list feature {
            key "name";
            leaf name {
              tailf:cli-multi-word-key;
              type string;
            }
            leaf sequence {
              type uint16;
            }
            container key {
              container size {
                leaf limit {
                  type enumeration {
                    enum 160;
                    enum 320;
                    enum 80;
                  }
                }
              }
              leaf-list field {
                tailf:cli-flat-list-syntax;
                type string;
              }
            }
            leaf-list action {
              tailf:cli-flat-list-syntax;
              type string;
            }
            container packet {
              list ipv4 {
                tailf:cli-suppress-mode;
                key "name";
                leaf name {
                  tailf:cli-multi-word-key;
                  type string;
                }
              }
              list ipv6 {
                tailf:cli-suppress-mode;
                key "name";
                leaf name {
                  tailf:cli-multi-word-key;
                  type string;
                }
              }
              list mpls {
                tailf:cli-suppress-mode;
                key "name";
                leaf name {
                  tailf:cli-multi-word-key;
                  type string;
                }
              }
              list non-ip {
                tailf:cli-suppress-mode;
                key "name";
                leaf name {
                  tailf:cli-multi-word-key;
                  type string;
                }
              }
            }
          }
        }
        container system {
          leaf profile {
            type string;
          }
        }
      }
    }
    container tcam {
      leaf profile {
        type union {
          type enumeration {
            enum default;
            enum mirroring-acl;
            enum mpls-evpn;
            enum pbr-match-nexthop-group;
            enum qos;
            enum tap-aggregation-default;
            enum tap-aggregation-extended;
            enum tc-counters;
            enum vxlan-routing;
          }
          type string;
        }
      }
    }
  }
  container bfd {
    container interval {
      tailf:cli-compact-syntax;
      tailf:cli-sequence-commands {
        tailf:cli-reset-all-siblings;
      }
      leaf tx {
        tailf:cli-drop-node-name;
        type uint16;
      }
      leaf min_rx {
        type uint16;
      }
      leaf multiplier {
        type uint8;
      }
      leaf default {
        type empty;
      }
    }
  }
  list daemon {
    key "name";
    leaf name {
      type string;
    }
    leaf exec {
      tailf:cli-multi-value;
      type string;
    }
    leaf shutdown {
      type boolean;
    }
  }
  list schedule {
    tailf:cli-suppress-mode;
    tailf:cli-compact-syntax;
    tailf:cli-delete-when-empty;
    key "name";
    leaf name {
      type string;
    }
    leaf interval {
      type uint16;
    }
    leaf timeout {
      type uint32;
    }
    leaf max-log-files {
      type uint16;
    }
    leaf command {
      tailf:cli-multi-value;
      type string;
    }
  }
  list track {
    tailf:cli-suppress-mode;
    key "name";
    leaf name {
      type string;
    }
    container interface {
      tailf:cli-compact-syntax;
      tailf:cli-sequence-commands {
        tailf:cli-reset-siblings;
      }
      uses interface-grouping;
      leaf line-protocol {
        type empty;
      }
    }
  }
  container transceiver {
    container dom-threshold {
      container file {
        leaf default {
          type empty;
        }
      }
    }
    container qsfp {
      leaf default-mode {
        type enumeration {
          enum 4x10G;
        }
      }
    }
  }
  container terminal {
    leaf length {
      type uint16;
    }
    leaf width {
      type uint16;
    }
  }
  container aaa {
    container group {
      container server {
        list tacacsplus {
          tailf:alt-name "tacacs+";
          key "name";
          leaf name {
            type string;
          }
          container server {
            list server-list {
              tailf:cli-drop-node-name;
              tailf:cli-suppress-mode;
              tailf:cli-delete-when-empty;
              key "name";
              leaf name {
                type inet:host;
              }
              list vrf {
                tailf:cli-suppress-mode;
                key "name";
                leaf name {
                  type string;
                }
              }
            }
          }
        }
        list radius {
          key "name";
          leaf name {
            type string;
          }
        }
      }
    }
    container authentication {
      list login {
        tailf:cli-suppress-mode;
        tailf:cli-delete-when-empty;
        tailf:cli-compact-syntax;
        key "name";
        leaf name {
          type enumeration {
            enum default;
            enum console;
          }
        }
        leaf group {
          type aaa-group-type;
        }
        leaf local {
          type empty;
        }
        leaf none {
          type empty;
        }
      }
      container enable {
        container default {
          tailf:cli-compact-syntax;
          choice local-group-choice {
            container local {
              tailf:cli-drop-node-name;
              tailf:cli-compact-syntax;
              tailf:cli-sequence-commands;
              leaf local {
                type empty;
              }
              leaf group {
                type aaa-group-type;
              }
            }
            container group {
              tailf:cli-drop-node-name;
              tailf:cli-compact-syntax;
              tailf:cli-sequence-commands;
              leaf group {
                type aaa-group-type;
              }
              leaf local {
                type empty;
              }
            }
          }
          leaf none {
            type empty;
          }
        }
      }
      container policy {
        container local {
          leaf allow-nopassword-remote-login {
            type empty;
          }
        }
      }
    }
    container authorization {
      leaf console {
        type empty;
      }
      leaf serial-console {
        type empty;
      }
      leaf config-commands {
        type empty;
      }
      list exec {
        tailf:cli-suppress-mode;
        tailf:cli-delete-when-empty;
        tailf:cli-compact-syntax;
        key "name";
        leaf name {
          type aaa-authorization-name-type;
        }
        leaf group {
          type aaa-group-type;
        }
        leaf local {
          type empty;
        }
        leaf none {
          type empty;
        }
      }
      list commands {
        tailf:cli-suppress-mode;
        tailf:cli-delete-when-empty;
        tailf:cli-compact-syntax;
        key "level name";
        leaf level {
          type union {
            type enumeration {
              enum all;
            }
            type string;
          }
        }
        leaf name {
          type aaa-authorization-name-type;
        }
        leaf group {
          type aaa-group-type;
        }
        leaf local {
          type empty;
        }
        leaf none {
          type empty;
        }
      }
      container policy {
        container local {
          leaf default-role {
            type string;
          }
        }
      }
    }
    container accounting {
      list commands {
        tailf:cli-suppress-mode;
        tailf:cli-delete-when-empty;
        tailf:cli-compact-syntax;
        key "level name";
        leaf level {
          tailf:cli-allow-range;
          type union {
            type enumeration {
              enum all;
            }
            type string;
          }
        }
        leaf name {
          type aaa-accounting-name-type;
        }
        uses accounting-action-type-grouping;
        leaf logging {
          type empty;
        }
        leaf group {
          type aaa-group-type;
        }
      }
      container system {
        container default {
          tailf:cli-compact-syntax;
          tailf:cli-delete-when-empty;
          presence "true";
          choice system-choice {
            leaf none {
              type empty;
            }
            container start-stop {
              leaf logging {
                type empty;
              }
              leaf group {
                type union {
                  type string;
                  type enumeration {
                    enum radius;
                    enum tacacs+;
                  }
                }
              }
            }
            container stop-only {
              leaf group {
                type union {
                  type string;
                  type enumeration {
                    enum radius;
                    enum tacacs+;
                  }
                }
              }
            }
          }
        }
      }
      list exec {
        tailf:cli-suppress-mode;
        tailf:cli-delete-when-empty;
        tailf:cli-compact-syntax;
        key "name";
        leaf name {
          type aaa-accounting-name-type;
        }
        uses accounting-action-type-grouping;
        leaf logging {
          type empty;
        }
        leaf group {
          type aaa-group-type;
        }
      }
    }
    container root {
      tailf:cli-delete-when-empty;
      presence "true";
      choice aaa-root-password-choice {
        leaf nopassword {
          type empty;
        }
        container secret {
          tailf:cli-compact-syntax;
          tailf:cli-flatten-container;
          tailf:cli-sequence-commands;
          leaf encryption {
            tailf:cli-optional-in-sequence;
            tailf:cli-drop-node-name;
            type enumeration {
              enum 0;
              enum sha512;
              enum 5;
            }
          }
          leaf secret {
            tailf:cli-drop-node-name;
            type string;
          }
        }
      }
    }
  }
  leaf version {
    type string;
  }
  leaf hostname {
    type string;
  }
  container ptp {
    leaf clock-accuracy {
      type uint16;
    }
    leaf clock-identity {
      type string;
    }
    leaf domain {
      type uint16;
    }
    container mode {
      tailf:cli-compact-syntax;
      choice ptp-mode-choice {
        container boundary {
          presence "true";
          leaf one-step {
            type empty;
          }
        }
        leaf options {
          tailf:cli-drop-node-name;
          type enumeration {
            enum disabled;
            enum e2etransparent;
            enum gptp;
            enum ordinarymaster;
            enum p2ptransparent;
          }
        }
      }
    }
    leaf local-priority {
      type uint16;
    }
    leaf profile {
      type enumeration {
        enum g8275.1;
        enum g8275.2;
      }
    }
    leaf priority1 {
      type uint16;
    }
    leaf priority2 {
      type uint16;
    }
    container skew {
      container sample {
        leaf size {
          type uint8;
        }
      }
    }
    leaf ttl {
      type uint8;
    }
    container monitor {
      leaf sequence-id {
        type empty;
      }
      container threshold {
        container mean-path-delay {
          leaf threshold {
            tailf:cli-drop-node-name;
            type uint32;
          }
          container drop {
            tailf:cli-drop-node-name;
            tailf:cli-compact-syntax;
            tailf:cli-sequence-commands {
              tailf:cli-reset-siblings;
            }
            leaf threshold {
              tailf:cli-drop-node-name;
              type uint32;
            }
            leaf nanoseconds {
              type empty;
            }
            leaf drop {
              type empty;
            }
          }
        }
        container offset-from-master {
          leaf threshold {
            tailf:cli-drop-node-name;
            type uint32;
          }
          container drop {
            tailf:cli-drop-node-name;
            tailf:cli-compact-syntax;
            tailf:cli-sequence-commands {
              tailf:cli-reset-siblings;
            }
            leaf threshold {
              tailf:cli-drop-node-name;
              type uint32;
            }
            leaf nanoseconds {
              type empty;
            }
            leaf drop {
              type empty;
            }
          }
        }
        container missing-message {
          container sync {
            tailf:cli-compact-syntax;
            tailf:cli-sequence-commands {
              tailf:cli-reset-siblings;
            }
            leaf number {
              tailf:cli-drop-node-name;
              type uint8;
            }
            leaf sequence-ids {
              type empty;
            }
          }
          container follow-up {
            tailf:cli-compact-syntax;
            tailf:cli-sequence-commands {
              tailf:cli-reset-siblings;
            }
            leaf number {
              tailf:cli-drop-node-name;
              type uint8;
            }
            leaf sequence-ids {
              type empty;
            }
          }
          container delay-resp {
            tailf:cli-compact-syntax;
            tailf:cli-sequence-commands {
              tailf:cli-reset-siblings;
            }
            leaf number {
              tailf:cli-drop-node-name;
              type uint8;
            }
            leaf sequence-ids {
              type empty;
            }
          }
          container announce {
            tailf:cli-compact-syntax;
            tailf:cli-sequence-commands {
              tailf:cli-reset-siblings;
            }
            leaf number {
              tailf:cli-drop-node-name;
              type uint8;
            }
            leaf sequence-ids {
              type empty;
            }
          }
        }
      }
    }
  }
  container errdisable {
    container detect {
      container cause {
        leaf link-flap {
          type boolean;
        }
      }
    }
    container recovery {
      leaf interval {
        type uint32;
      }
      container cause {
        leaf bpduguard {
          type empty;
        }
        leaf link-flap {
          type empty;
        }
        leaf no-internal-vlan {
          type empty;
        }
        leaf portchannelguard {
          type empty;
        }
        leaf portsec {
          type empty;
        }
        leaf tapagg {
          type empty;
        }
        leaf uplink-failure-detection {
          type empty;
        }
        leaf xcvr-unsupported {
          type empty;
        }
      }
    }
    container flap-setting {
      container cause {
        container link-flap {
          tailf:cli-compact-syntax;
          tailf:cli-sequence-commands;
          leaf max-flaps {
            type uint8;
          }
          leaf time {
            type uint16;
          }
        }
      }
    }
  }
  list event-handler {
    key "name";
    leaf name {
      type string;
    }
    container trigger {
      choice trigger-on-choice {
        leaf on-boot {
          type empty;
        }
        container on-logging {
          tailf:cli-add-mode;
          leaf regex {
            type string;
          }
        }
        case on-maintenance {
          container on-maintenance {
            choice on-maintenance-enter-exit-choice {
              leaf enter {
                tailf:cli-multi-value;
                type string;
              }
              leaf exit {
                tailf:cli-multi-value;
                type string;
              }
            }
          }
          container on-config {
            leaf disabled {
              type empty;
            }
          }
        }
      }
    }
    container action {
      leaf bash {
        type string;
      }
    }
    leaf delay {
      type uint32;
    }
    leaf timeout {
      type uint16;
    }
  }
  leaf event-monitor {
    type empty;
  }
  container boot {
    leaf system {
      type string;
    }
  }
  container arp {
    container aging {
      container timeout {
        leaf default {
          type uint32;
        }
      }
    }
  }
  container banner {
    leaf login {
      type string;
    }
    leaf motd {
      type string;
    }
  }
  container maintenance {
    tailf:cli-add-mode;
    presence "true";
    container profile {
      list bgp {
        key "name";
        leaf name {
          type string;
        }
        container initiator {
          list route-map {
            tailf:cli-suppress-mode;
            tailf:cli-sequence-commands;
            key "dir";
            leaf name {
              tailf:cli-drop-node-name;
              tailf:cli-prefix-key;
              type string;
            }
            leaf dir {
              type enumeration {
                enum inout;
                enum in;
                enum out;
              }
            }
          }
        }
      }
      container bgp-default {
        tailf:cli-drop-node-name;
        container bgp {
          tailf:cli-compact-syntax;
          tailf:cli-sequence-commands {
            tailf:cli-reset-siblings;
          }
          leaf name {
            tailf:cli-drop-node-name;
            type string;
          }
          leaf default {
            type empty;
          }
        }
      }
      container interface-default {
        tailf:cli-drop-node-name;
        container interface {
          tailf:cli-compact-syntax;
          tailf:cli-sequence-commands {
            tailf:cli-reset-siblings;
          }
          leaf name {
            tailf:cli-drop-node-name;
            type string;
          }
          leaf default {
            type empty;
          }
        }
      }
      list interface {
        key "name";
        leaf name {
          type string;
        }
        container rate-monitoring {
          leaf load-interval {
            type uint16;
          }
          leaf threshold {
            type uint32;
          }
        }
      }
      container unit-default {
        tailf:cli-drop-node-name;
        container unit {
          tailf:cli-compact-syntax;
          tailf:cli-sequence-commands {
            tailf:cli-reset-siblings;
          }
          leaf name {
            tailf:cli-drop-node-name;
            type string;
          }
          leaf default {
            type empty;
          }
        }
      }
      list unit {
        key "name";
        leaf name {
          type string;
        }
        container on-boot {
          leaf duration {
            type uint32;
          }
        }
      }
    }
    container unit {
      container System {
        tailf:cli-add-mode;
        presence "true";
      }
      list unit-list {
        tailf:cli-drop-node-name;
        key "name";
        leaf name {
          type string;
        }
      }
    }
  }
  container monitor {
    container telemetry {
      container inband {
        tailf:cli-add-mode;
        leaf disabled {
          type boolean;
        }
        leaf device-id {
          type string;
        }
        container profile {
          list core {
            key "name";
            leaf name {
              type string;
            }
            container egress {
              uses monitor-telemetry-inband-profile-collection-grouping;
            }
          }
          list edge {
            key "name";
            leaf name {
              type string;
            }
            container ingress {
              container sample {
                leaf rate {
                  type uint32;
                }
              }
            }
            container egress {
              uses monitor-telemetry-inband-profile-collection-grouping;
            }
          }
          list vxlan {
            key "name";
            leaf name {
              type string;
            }
            container ingress {
              uses monitor-telemetry-inband-profile-collection-grouping;
            }
          }
        }
      }
    }
    list session {
      tailf:cli-suppress-mode;
      tailf:cli-delete-when-empty;
      key "name";
      leaf name {
        type string;
      }
      container source {
        leaf Cpu {
          type empty;
        }
        uses monitor-session-interface-grouping;
      }
      container destination {
        leaf Cpu {
          type empty;
        }
        uses monitor-session-interface-grouping;
      }
    }
  }
  container management {
    container api {
      container http-commands {
        tailf:cli-add-mode;
        container cors {
          container allowed-origin {
            leaf all {
              type empty;
            }
          }
        }
        container qos {
          leaf dscp {
            type uint8;
          }
        }
        container protocol {
          container http-empty {
            tailf:cli-drop-node-name;
            leaf http {
              type empty;
            }
          }
          container https-empty {
            tailf:cli-drop-node-name;
            leaf https {
              type boolean;
            }
          }
          container https {
            leaf certificate {
              type string;
            }
            container ssl {
              leaf profile {
                type string;
              }
            }
            leaf port {
              type uint16;
            }
          }
          leaf unix-socket {
            type empty;
          }
        }
        leaf shutdown {
          type boolean;
        }
        list vrf {
          key "name";
          leaf name {
            type string;
          }
          leaf shutdown {
            type boolean;
          }
          container ip {
            uses access-group-grouping;
          }
          container ipv6 {
            uses access-group-grouping;
          }
        }
      }
      container gnmi {
        tailf:cli-add-mode;
        container transport {
          list grpc {
            key "name";
            leaf name {
              type string;
            }
            container ssl {
              leaf profile {
                type string;
              }
            }
            leaf port {
              type uint32;
            }
            leaf vrf {
              type string;
            }
          }
        }
      }
      container netconf {
        tailf:cli-add-mode;
        container transport {
          tailf:cli-add-mode;
          presence "true";
          leaf ssh {
            tailf:cli-hide-in-submode;
            type string;
          }
        }
      }
    }
    container console {
      tailf:cli-add-mode;
      leaf idle-timeout {
        type uint32;
      }
    }
    container defaults {
      tailf:cli-add-mode;
      container secret {
        leaf hash {
          type enumeration {
            enum md5;
            enum sha512;
          }
        }
      }
    }
    container security {
      tailf:cli-add-mode;
      container entropy {
        leaf source {
          type enumeration {
            enum hardware;
          }
        }
      }
      container password {
        container encryption {
          leaf reversible {
            type enumeration {
              enum aes-256-gcm;
            }
          }
        }
      }
      container ssl {
        list profile {
          key "name";
          leaf name {
            type string;
          }
          container certificate {
            container certificate-key {
              tailf:cli-drop-node-name;
              tailf:cli-compact-syntax;
              tailf:cli-sequence-commands {
                tailf:cli-reset-siblings;
              }
              choice certificate-key-choice {
                leaf name {
                  tailf:cli-drop-node-name;
                  type string;
                }
                leaf common-name {
                  type empty;
                }
                leaf policy {
                  type empty;
                }
                leaf requirement {
                  type empty;
                }
              }
              leaf key {
                type string;
              }
            }
          }
          container trust {
            container certificate {
              list certificate-name {
                tailf:cli-drop-node-name;
                tailf:cli-suppress-mode;
                key "name";
                leaf name {
                  type string;
                }
              }
            }
          }
        }
      }
    }
    container ssh {
      tailf:cli-add-mode;
      leaf-list cipher {
        tailf:cli-flat-list-syntax;
        type union {
          type enumeration {
            enum 3des-cbc;
            enum aes128-cbc;
            enum aes128-ctr;
            enum aes192-cbc;
            enum aes192-ctr;
            enum aes256-cbc;
            enum aes256-ctr;
            enum arcfour;
            enum arcfour128;
            enum arcfour256;
            enum blowfish-cbc;
            enum cast128-cbc;
          }
          type string;
        }
      }
      leaf-list key-exchange {
        tailf:cli-flat-list-syntax;
        type enumeration {
          enum curve25519-sha256@libssh.org;
          enum diffie-hellman-group-exchange-sha1;
          enum diffie-hellman-group-exchange-sha256;
          enum diffie-hellman-group1-sha1;
          enum diffie-hellman-group14-sha1;
          enum ecdh-sha2-nistp256;
          enum ecdh-sha2-nistp384;
          enum ecdh-sha2-nistp521;
        }
      }
      leaf-list mac {
        tailf:cli-flat-list-syntax;
        type enumeration {
          enum hmac-md5;
          enum hmac-md5-96;
          enum hmac-ripemd160;
          enum hmac-sha1;
          enum hmac-sha1-96;
          enum hmac-sha1-etm@openssh.com;
          enum hmac-sha2-256;
          enum hmac-sha2-256-etm@openssh.com;
          enum hmac-sha2-512;
          enum hmac-sha2-512-etm@openssh.com;
          enum umac-128-etm@openssh.com;
          enum umac-128@openssh.com;
        }
      }
      container hostkey {
        container client {
          leaf strict-checking {
            type empty;
          }
        }
        container server {
          leaf-list options {
            tailf:cli-drop-node-name;
            tailf:cli-flat-list-syntax;
            type enumeration {
              enum dsa;
              enum ecdsa-nistp256;
              enum ecdsa-nistp521;
              enum ed25519;
              enum rsa;
            }
          }
          leaf-list cert {
            tailf:cli-flat-list-syntax;
            type string;
          }
        }
      }
      leaf idle-timeout {
        type uint32;
      }
      container ip {
        uses management-ssh-access-group-grouping;
      }
      container ipv6 {
        uses management-ssh-access-group-grouping;
      }
      leaf log-level {
        type enumeration {
          enum debug;
          enum debug1;
          enum debug2;
          enum debug3;
          enum error;
          enum fatal;
          enum info;
          enum quiet;
          enum verbose;
        }
      }
      container login {
        leaf timeout {
          type uint16;
        }
      }
      container qos {
        leaf dscp {
          type uint8;
        }
      }
      leaf shutdown {
        type boolean;
      }
      container authentication {
        leaf mode {
          type enumeration {
            enum keyboard-interactive;
            enum password;
          }
        }
      }
      list vrf {
        key "name";
        leaf name {
          type string;
        }
        leaf shutdown {
          type empty;
        }
      }
    }
    container telnet {
      tailf:cli-add-mode;
      leaf idle-timeout {
        type uint32;
      }
      container ip {
        uses access-group-grouping;
      }
      container ipv6 {
        uses access-group-grouping;
      }
      leaf session-limit {
        type uint8;
      }
      leaf shutdown {
        type boolean;
      }
      list vrf {
        key "name";
        leaf name {
          type string;
        }
        leaf shutdown {
          type empty;
        }
      }
    }
  }
  container mac {
    container address-table {
      leaf aging-time {
        type uint32;
      }
      container static {
        tailf:cli-compact-syntax;
        tailf:cli-sequence-commands;
        list address-mac {
          tailf:cli-drop-node-name;
          tailf:cli-suppress-mode;
          tailf:cli-delete-when-empty;
          key "mac-addr vlan";
          leaf mac-addr {
            type string;
          }
          leaf vlan {
            tailf:cli-expose-key-name;
            type uint16;
          }
          leaf destination {
            tailf:cli-drop-node-name;
            tailf:cli-multi-value;
            type string;
          }
        }
      }
    }
    list access-list {
      key "name";
      leaf name {
        type string;
      }
      list access-list-rule {
        tailf:cli-suppress-mode;
        tailf:cli-delete-when-empty;
        tailf:cli-drop-node-name;
        tailf:cli-compact-syntax;
        ordered-by user;
        key "rule";
        leaf rule {
          tailf:cli-multi-word-key;
          type string;
        }
      }
    }
  }
  container mpls {
    leaf ip {
      type empty;
    }
    container ping {
      tailf:cli-add-mode;
      container ip {
        uses access-group-vrf-grouping;
      }
      container ipv6 {
        uses access-group-vrf-grouping;
      }
    }
    container label {
      container range {
        container static {
          tailf:cli-compact-syntax;
          tailf:cli-sequence-commands {
            tailf:cli-reset-siblings;
          }
          uses mpls-label-range-grouping;
        }
        container isis-sr {
          tailf:cli-compact-syntax;
          tailf:cli-sequence-commands {
            tailf:cli-reset-siblings;
          }
          uses mpls-label-range-grouping;
        }
      }
    }
    container ldp {
      tailf:cli-add-mode;
      container router-id {
        leaf ip {
          tailf:cli-drop-node-name;
          type inet:ipv4-address;
        }
        container interface {
          uses interface-grouping;
        }
      }
      container transport-address {
        container interface {
          uses interface-grouping;
        }
      }
      container password {
        tailf:cli-compact-syntax;
        leaf enctype {
          tailf:cli-drop-node-name;
          type uint8;
        }
        leaf text {
          tailf:cli-drop-node-name;
          tailf:cli-multi-value;
          type string;
        }
      }
      container pseudowires {
        tailf:cli-add-mode;
        presence "true";
        leaf mtu {
          type uint16;
        }
        list pseudowire {
          key "name";
          leaf name {
            type string;
          }
          leaf mtu {
            type uint16;
          }
          leaf neighbor {
            type inet:ipv4-address;
          }
          leaf pseudowire-id {
            type uint32;
          }
        }
      }
      container igp {
        container sync {
          container delay {
            presence "true";
            leaf time {
              tailf:cli-drop-node-name;
              type uint8;
            }
          }
          container holddown {
            presence "true";
            leaf time {
              tailf:cli-drop-node-name;
              type uint8;
            }
          }
        }
      }
      container ip {
        uses access-group-grouping;
      }
      list neighbor {
        tailf:cli-suppress-mode;
        key "ip";
        leaf ip {
          type inet:ipv4-address;
        }
        leaf targeted {
          type empty;
        }
      }
      container fec {
        container filter {
          leaf prefix-list {
            type string;
          }
        }
      }
      container discovery {
        container hello {
          leaf hold-time {
            type union {
              type enumeration {
                enum infinite;
              }
              type uint16;
            }
          }
          leaf interval {
            type uint16;
          }
        }
      }
      leaf shutdown {
        type boolean;
      }
    }
    container ldp-no-mode {
      tailf:cli-drop-node-name;
      container ldp {
        container pseudowires {
          tailf:cli-add-mode;
          leaf mtu {
            type uint16;
          }
          list pseudowire {
            key "name";
            leaf name {
              type string;
            }
            leaf mtu {
              type uint16;
            }
            leaf neighbor {
              type inet:ipv4-address;
            }
            leaf pseudowire-id {
              type uint32;
            }
          }
        }
      }
    }
  }
  container patch {
    container panel {
      tailf:cli-add-mode;
      list patch {
        key "name";
        leaf name {
          type string;
        }
        list connector {
          tailf:cli-suppress-mode;
          tailf:cli-delete-when-empty;
          key "name";
          leaf name {
            type string;
          }
          choice patch-connector-choice {
            container interface {
              tailf:cli-compact-syntax;
              tailf:cli-sequence-commands {
                tailf:cli-reset-siblings;
              }
              choice patch-interface-choice {
                leaf Ethernet {
                  tailf:cli-allow-join-with-value;
                  type string;
                }
                leaf Port-Channel {
                  tailf:cli-allow-join-with-value;
                  type string;
                }
              }
              leaf dot1q {
                type empty;
              }
              leaf vlan {
                type uint16;
              }
            }
            container pseudowire {
              leaf ldp {
                type string;
              }
            }
          }
        }
      }
    }
  }
  container clock {
    leaf timezone {
      type string;
    }
  }
  container EXEC {
    tailf:cli-drop-node-name;
    container exec;
  }
  container enable {
    container secret {
      tailf:cli-compact-syntax;
      tailf:cli-flatten-container;
      tailf:cli-sequence-commands;
      leaf encryption {
        tailf:cli-optional-in-sequence;
        tailf:cli-drop-node-name;
        type enumeration {
          enum 0;
          enum sha512;
          enum 5;
        }
      }
      leaf secret {
        tailf:cli-drop-node-name;
        type string;
      }
    }
    container password {
      tailf:cli-compact-syntax;
      tailf:cli-flatten-container;
      tailf:cli-sequence-commands;
      leaf encryption {
        tailf:cli-optional-in-sequence;
        tailf:cli-drop-node-name;
        type enumeration {
          enum 0;
          enum sha512;
          enum 5;
        }
      }
      leaf secret {
        tailf:cli-drop-node-name;
        type string;
      }
    }
  }
  list username {
    tailf:cli-suppress-mode;
    tailf:cli-delete-when-empty;
    tailf:cli-compact-syntax;
    key "name";
    leaf name {
      type string;
    }
    leaf privilege {
      type uint8;
    }
    leaf role {
      type union {
        type enumeration {
          enum network-admin;
          enum network-operator;
          enum priv-0;
          enum priv-1;
          enum priv-10;
          enum priv-11;
          enum priv-12;
          enum priv-13;
          enum priv-14;
          enum priv-15;
          enum priv-2;
          enum priv-3;
          enum priv-4;
          enum priv-5;
          enum priv-6;
          enum priv-7;
          enum priv-8;
          enum priv-9;
          enum san-admin;
          enum vdc-admin;
          enum vdc-operator;
        }
        type string;
      }
    }
    choice password-choice {
      leaf nopassword {
        type empty;
      }
      container secret {
        tailf:cli-compact-syntax;
        tailf:cli-flatten-container;
        tailf:cli-sequence-commands {
          tailf:cli-reset-siblings;
        }
        leaf encryption {
          tailf:cli-optional-in-sequence;
          tailf:cli-drop-node-name;
          type enumeration {
            enum 0;
            enum sha512;
            enum 5;
            enum *;
          }
        }
        leaf secret {
          tailf:cli-drop-node-name;
          type string;
        }
      }
    }
    container sshkey {
      uses username-sshkey-grouping;
    }
    container ssh-key {
      uses username-sshkey-grouping;
    }
    leaf expire {
      type string;
    }
  }
  container password {
    leaf strength-check {
      type boolean;
    }
  }
  container vrf {
    choice vrf-choice {
      list definition {
        key "name";
        leaf name {
          type string;
        }
        leaf description {
          tailf:cli-multi-value;
          type string;
        }
        leaf rd {
          type rd-type;
        }
      }
      list instance {
        key "name";
        leaf name {
          type string;
        }
        leaf description {
          tailf:cli-multi-value;
          type string;
        }
        leaf rd {
          type rd-type;
        }
      }
    }
    list context {
      key "name";
      leaf name {
        type union {
          type string;
          type enumeration {
            enum management;
          }
        }
      }
      leaf description {
        type string;
      }
    }
  }
  container ip {
    uses access-list-grouping;
    container address {
      container virtual {
        container source-nat {
          list vrf {
            tailf:cli-suppress-mode;
            tailf:cli-compact-syntax;
            key "name";
            leaf name {
              type string;
            }
            leaf address {
              type inet:ipv4-address;
            }
          }
        }
      }
    }
    container community-list {
      list standard {
        tailf:cli-suppress-mode;
        tailf:cli-compact-syntax;
        key "name";
        leaf name {
          type string;
        }
        uses ip-community-list-standard-grouping;
      }
      list expanded {
        tailf:cli-suppress-mode;
        tailf:cli-compact-syntax;
        key "name";
        leaf name {
          type string;
        }
        uses ip-community-list-standard-grouping;
      }
      list name {
        tailf:cli-drop-node-name;
        tailf:cli-suppress-mode;
        tailf:cli-compact-syntax;
        key "name";
        leaf name {
          type string;
        }
        uses ip-community-list-standard-grouping;
      }
      list regexp {
        tailf:cli-suppress-mode;
        tailf:cli-compact-syntax;
        key "name";
        leaf name {
          type string;
        }
        uses ip-community-list-standard-grouping;
      }
    }
    container as-path {
      leaf regex-mode {
        type enumeration {
          enum asn;
          enum string;
        }
      }
      list access-list {
        tailf:cli-suppress-mode;
        key "name permit-or-deny aspathre";
        leaf name {
          type string;
        }
        leaf permit-or-deny {
          type enumeration {
            enum permit;
            enum deny;
          }
        }
        leaf aspathre {
          type string;
        }
        leaf origin {
          tailf:cli-drop-node-name;
          type enumeration {
            enum any;
            enum egp;
            enum igp;
            enum incomplete;
          }
        }
      }
    }
    container dhcp {
      container relay {
        container information {
          leaf option {
            type empty;
          }
        }
        uses access-group-grouping;
      }
    }
    container domain {
      container lookup {
        list vrf {
          tailf:cli-compact-syntax;
          tailf:cli-suppress-mode;
          key "name";
          leaf name {
            type string;
          }
          container source-interface {
            tailf:cli-flatten-container;
            uses interface-grouping;
          }
        }
        container source-interface {
          uses interface-grouping;
        }
      }
    }
    leaf domain-list {
      type string;
    }
    leaf domain-lookup {
      type empty;
    }
    leaf domain-name {
      type string;
    }
    container fhrp {
      leaf accept-mode {
        type empty;
      }
    }
    container hardware {
      container fib {
        container optimize {
          leaf prefix-length {
            tailf:cli-multi-value;
            type string;
          }
        }
        container programmed {
          leaf monitor {
            type empty;
          }
        }
      }
    }
    container icmp {
      container source-interface {
        uses interface-grouping;
      }
    }
    container nat {
      list pool {
        key "name";
        leaf name {
          type string;
        }
        leaf prefix-length {
          tailf:cli-hide-in-submode;
          type uint8;
        }
        container range {
          tailf:cli-compact-syntax;
          tailf:cli-sequence-commands {
            tailf:cli-reset-all-siblings;
          }
          leaf first-address {
            tailf:cli-drop-node-name;
            type inet:ipv4-address;
          }
          leaf last-ip {
            tailf:cli-drop-node-name;
            type inet:ipv4-address;
          }
        }
      }
    }
    list name-server {
      tailf:cli-compact-syntax;
      tailf:cli-suppress-mode;
      key "server";
      leaf server {
        type union {
          type inet:ipv4-address;
          type inet:ipv6-address;
        }
      }
      leaf vrf {
        tailf:cli-prefix-key;
        type string;
      }
    }
    container igmp {
      list profile {
        key "name";
        leaf name {
          type string;
        }
        leaf permit-or-deny {
          tailf:cli-drop-node-name;
          type enumeration {
            enum deny;
            enum permit;
          }
        }
        list range {
          tailf:cli-suppress-mode;
          key "low high";
          leaf low {
            type inet:ipv4-address;
          }
          leaf high {
            type inet:ipv4-address;
          }
        }
      }
      container snooping-leaf {
        tailf:cli-drop-node-name;
        leaf snooping {
          type boolean;
        }
      }
      container snooping {
        list vlan {
          tailf:cli-suppress-mode;
          tailf:cli-range-list-syntax;
          tailf:cli-delete-when-empty;
          key "id";
          leaf id {
            type uint16;
          }
          list member {
            tailf:cli-suppress-mode;
            key "address interface";
            leaf address {
              type inet:ipv4-address;
            }
            leaf interface {
              tailf:cli-expose-key-name;
              type string;
            }
          }
          container querier-leaf {
            tailf:cli-drop-node-name;
            leaf querier {
              type empty;
            }
          }
          container querier {
            leaf address {
              type inet:ipv4-address;
            }
            leaf version {
              type uint8;
            }
          }
        }
      }
    }
    container pim {
      container ssm {
        leaf range {
          type union {
            type string;
            type enumeration {
              enum standard;
            }
          }
        }
      }
      leaf log-neighbor-changes {
        type empty;
      }
      container bsr {
        container listen {
          leaf forward {
            type empty;
          }
        }
      }
      leaf bsr-candidate {
        type string;
      }
      list anycast-rp {
        tailf:cli-suppress-mode;
        key "anycast anycast-other";
        leaf anycast {
          type union {
            type inet:ipv4-address;
          }
        }
        leaf anycast-other {
          type union {
            type inet:ipv4-address;
          }
        }
      }
      list rp-address {
        tailf:cli-suppress-mode;
        key "rp-addr";
        leaf rp-addr {
          type inet:ipv4-address;
        }
        list prefix {
          tailf:cli-suppress-mode;
          tailf:cli-drop-node-name;
          key "address";
          leaf address {
            type inet:ipv4-prefix;
          }
        }
        list access-list {
          tailf:cli-suppress-mode;
          key "name";
          leaf name {
            type string;
          }
          leaf override {
            type empty;
          }
        }
      }
    }
    container prefix-list {
      list prefixes {
        tailf:cli-drop-node-name;
        key "name";
        leaf name {
          type string;
        }
        leaf comment {
          tailf:cli-multi-value;
          type string;
        }
        list seq {
          tailf:cli-suppress-mode;
          tailf:cli-delete-when-empty;
          key "no";
          leaf no {
            type uint32;
          }
          container deny {
            tailf:cli-sequence-commands {
              tailf:cli-reset-all-siblings;
            }
            tailf:cli-compact-syntax;
            tailf:cli-flatten-container;
            leaf ip {
              tailf:cli-drop-node-name;
              type inet:ipv4-prefix;
            }
            choice gele-eq-choice {
              container ge-le {
                tailf:cli-drop-node-name;
                tailf:cli-compact-syntax;
                tailf:cli-flatten-container;
                leaf ge {
                  tailf:cli-break-sequence-commands;
                  type uint8;
                }
                leaf le {
                  type uint8;
                }
              }
              leaf eq {
                type uint8;
              }
            }
          }
          container permit {
            tailf:cli-sequence-commands {
              tailf:cli-reset-all-siblings;
            }
            tailf:cli-compact-syntax;
            tailf:cli-flatten-container;
            leaf ip {
              tailf:cli-drop-node-name;
              type inet:ipv4-prefix;
            }
            choice gele-eq-choice {
              container ge-le {
                tailf:cli-drop-node-name;
                tailf:cli-compact-syntax;
                tailf:cli-flatten-container;
                leaf ge {
                  tailf:cli-break-sequence-commands;
                  type uint8;
                }
                leaf le {
                  type uint8;
                }
              }
              leaf eq {
                type uint8;
              }
            }
          }
        }
      }
    }
    container routing {
      presence "true";
      list vrf {
        tailf:cli-suppress-mode;
        key "vrf-id";
        leaf vrf-id {
          type string;
        }
        leaf prefix {
          tailf:cli-prefix-key;
          tailf:cli-drop-node-name;
          type enumeration {
            enum no;
            enum enable;
          }
        }
      }
    }
    leaf multicast-routing {
      type empty;
    }
    container radius {
      container source-interface {
        uses interface-grouping;
      }
    }
    container route {
      uses ip-route-grouping;
      leaf profile {
        type empty;
      }
      container static {
        leaf adjust-time {
          type uint8;
        }
        leaf inter-vrf {
          type empty;
        }
      }
      list vrf {
        tailf:cli-suppress-mode;
        tailf:cli-compact-syntax;
        tailf:cli-delete-when-empty;
        key "name";
        leaf name {
          type string;
        }
        uses ip-route-grouping;
      }
    }
    container ssh {
      container client {
        container source-interface {
          tailf:cli-compact-syntax;
          uses interface-no-content-on-delete-grouping;
          leaf vrf {
            type string;
          }
        }
      }
    }
    container tacacs {
      container source-interface {
        uses interface-grouping;
      }
      list vrf {
        tailf:cli-suppress-mode;
        tailf:cli-compact-syntax;
        key "name";
        leaf name {
          type string;
        }
        container source-interface {
          uses interface-grouping;
        }
      }
    }
    container ftp {
      container client {
        container source-interface {
          tailf:cli-compact-syntax;
          uses interface-no-content-on-delete-grouping;
          leaf vrf {
            type string;
          }
        }
      }
    }
    container tftp {
      container client {
        container local-interface {
          uses interface-no-content-on-delete-grouping;
          leaf vrf {
            type string;
          }
        }
        container source-interface {
          tailf:cli-compact-syntax;
          uses interface-no-content-on-delete-grouping;
          leaf vrf {
            type string;
          }
        }
      }
    }
    container virtual-router {
      container mac-address {
        leaf address {
          tailf:cli-drop-node-name;
          type string;
        }
        leaf advertisement-interval {
          type uint32;
        }
      }
    }
  }
  list route-map {
    tailf:cli-compact-syntax;
    key "name sequence";
    leaf name {
      type string;
    }
    leaf sequence {
      tailf:cli-drop-node-name;
      type uint16;
    }
    leaf operation {
      tailf:cli-drop-node-name;
      tailf:cli-prefix-key {
        tailf:cli-before-key "2";
      }
      type enumeration {
        enum deny {
          tailf:code-name "op_deny";
        }
        enum permit {
          tailf:code-name "op_internet";
        }
      }
    }
    leaf comment {
      tailf:cli-multi-value;
      type string;
    }
    leaf description {
      tailf:cli-multi-value;
      type string;
    }
    container match {
      container community {
        leaf-list name {
          tailf:cli-drop-node-name;
          tailf:cli-flat-list-syntax;
          type string;
        }
      }
      leaf as-path {
        type string;
      }
      container ip {
        container address {
          leaf prefix-list {
            type string;
          }
          leaf access-list {
            type string;
          }
        }
      }
      container ipv6 {
        container address {
          leaf prefix-list {
            type string;
          }
        }
      }
      leaf source-protocol {
        type enumeration {
          enum bgp;
          enum connected;
          enum isis;
          enum ospf;
          enum rip;
          enum static;
        }
      }
      leaf local-preference {
        type uint32;
      }
      leaf route-type {
        type enumeration {
          enum confederation-external;
          enum external;
          enum internal;
          enum local;
          enum vpn;
        }
      }
    }
    leaf sub-route-map {
      type string;
    }
    container continue {
      presence "true";
      leaf seq-no {
        tailf:cli-drop-node-name;
        type uint32;
      }
    }
    container set {
      container as-path {
        container match {
          container all {
            container replacement {
              choice replacement-choice {
                leaf none {
                  type empty;
                }
                leaf-list as-number {
                  tailf:cli-drop-node-name;
                  tailf:cli-flat-list-syntax;
                  ordered-by user;
                  type union {
                    type enumeration {
                      enum auto;
                    }
                    type uint32;
                    type string;
                  }
                }
              }
            }
          }
        }
        container prepend {
          container as-container {
            tailf:cli-drop-node-name;
            leaf as-number {
              tailf:cli-drop-node-name;
              tailf:cli-multi-value;
              type string;
            }
          }
          container last-as-cont {
            tailf:cli-drop-node-name;
            leaf last-as {
              type uint16;
            }
          }
        }
        container tag {
          presence "tag";
        }
      }
      container comm-list {
        tailf:cli-sequence-commands;
        choice comm-list-choice {
          leaf comm-list-standard {
            tailf:cli-drop-node-name;
            type uint16;
          }
          leaf comm-list-expanded {
            tailf:cli-drop-node-name;
            type uint16;
          }
          leaf comm-list-name {
            tailf:cli-drop-node-name;
            type string;
          }
        }
        leaf delete {
          type empty;
        }
      }
      container extcommunity {
        leaf-list rt {
          tailf:cli-flat-list-syntax;
          type asn-ip-type;
        }
      }
      leaf metric {
        type string;
      }
      leaf origin {
        type enumeration {
          enum egp;
          enum igp;
          enum incomplete;
        }
      }
      container community {
        tailf:cli-compact-syntax;
        choice community-choice {
          leaf-list community-list {
            tailf:cli-flat-list-syntax;
            type string;
          }
          leaf-list community-number {
            tailf:cli-drop-node-name;
            tailf:cli-flat-list-syntax;
            ordered-by user;
            type union {
              type uint32;
              type enumeration {
                enum additive;
                enum delete;
                enum GSHUT;
                enum internet;
                enum local-as;
                enum no-advertise;
                enum no-export;
                enum none;
              }
              type string;
            }
          }
        }
      }
      container ip {
        leaf next-hop {
          type inet:ipv4-address;
        }
      }
      container ipv6 {
        leaf next-hop {
          type inet:ipv6-address;
        }
      }
      leaf local-preference {
        type uint32;
      }
    }
  }
  container system {
    container l1 {
      tailf:cli-add-mode;
      container unsupported {
        container speed {
          leaf action {
            type enumeration {
              enum error;
              enum warn;
            }
          }
        }
        container error-correction {
          leaf action {
            type enumeration {
              enum error;
              enum warn;
            }
          }
        }
      }
    }
    container control-plane {
      tailf:cli-add-mode;
      container ip {
        uses control-plane-access-group-grouping;
      }
      container ipv6 {
        uses control-plane-access-group-grouping;
      }
    }
  }
  container tcpdump {
    list session {
      tailf:cli-suppress-mode;
      tailf:cli-compact-syntax;
      key "name";
      leaf name {
        type string;
      }
      leaf file {
        type string;
      }
    }
  }
  list peer-filter {
    key "name";
    leaf name {
      type string;
    }
    list seq {
      tailf:cli-drop-node-name;
      tailf:cli-suppress-mode;
      key "index";
      leaf index {
        type uint32;
      }
      container match {
        tailf:cli-compact-syntax;
        tailf:cli-sequence-commands;
        leaf as-range {
          type string;
        }
        leaf result {
          type enumeration {
            enum accept;
            enum reject;
          }
        }
      }
    }
  }
  container tacacs-server {
    list host {
      tailf:cli-suppress-mode;
      tailf:cli-delete-when-empty;
      tailf:cli-compact-syntax;
      ordered-by user;
      key "name";
      leaf name {
        type host-type;
      }
      leaf port {
        type uint16;
      }
      leaf timeout {
        type uint16;
      }
      leaf single-connection {
        type empty;
      }
      uses tacacs-server-key-grouping;
      list vrf {
        tailf:cli-suppress-mode;
        tailf:cli-compact-syntax;
        key "name";
        leaf name {
          type string;
        }
        uses tacacs-server-key-grouping;
      }
    }
    container policy {
      container unknown-mandatory-attribute {
        leaf ignore {
          type empty;
        }
      }
    }
    leaf timeout {
      type uint16;
    }
    uses tacacs-server-key-grouping;
  }
  container tap {
    container aggregation {
      tailf:cli-add-mode;
      container mode {
        tailf:cli-compact-syntax;
        container exclusive {
          presence "true";
          container no-errdisable {
            list Ethernet {
              tailf:cli-allow-join-with-key;
              tailf:cli-suppress-mode;
              key "name";
              leaf name {
                type string;
              }
            }
            list Port-Channel {
              tailf:cli-suppress-mode;
              tailf:cli-allow-join-with-key;
              key "name";
              leaf name {
                type string;
              }
            }
          }
        }
      }
      container service-policy {
        container type {
          container tapagg {
            container mac {
              container access-list {
                container match {
                  leaf ip {
                    type empty;
                  }
                }
              }
            }
          }
        }
      }
    }
  }
  list fex {
    key "id";
    leaf id {
      type uint16;
    }
    container pinning {
      leaf max-links {
        type uint16;
      }
    }
    leaf description {
      tailf:cli-multi-value;
      type string;
    }
  }
  container vlan {
    container internal {
      container order {
        choice vlan-internal-order-choice {
          container ascending {
            presence "true";
            uses vlan-internal-order-range-grouping;
          }
          container descending {
            presence "true";
            uses vlan-internal-order-range-grouping;
          }
        }
      }
    }
    list vlan-list {
      tailf:cli-drop-node-name;
      tailf:cli-range-list-syntax;
      key "id";
      leaf id {
        type uint16;
      }
      leaf comment {
        tailf:cli-multi-value;
        type string;
      }
      container ip {
        container igmp {
          container snooping {
            presence "Configures IGMP Snooping";
            leaf explicit-tracking {
              type empty;
            }
            leaf fast-leave {
              type empty;
            }
            leaf last-member-query-interval {
              type uint8;
            }
            leaf link-local-groups-suppression {
              type empty;
            }
            container mrouter {
              container interface {
                list Ethernet {
                  tailf:cli-allow-join-with-key;
                  tailf:cli-suppress-mode;
                  key "name";
                  leaf name {
                    type string;
                  }
                }
                list port-channel {
                  tailf:cli-suppress-mode;
                  tailf:cli-allow-join-with-key;
                  key "name";
                  leaf name {
                    type string;
                  }
                }
              }
            }
            leaf static-group {
              type inet:ipv4-address;
            }
          }
        }
      }
      leaf name {
        tailf:cli-multi-value;
        type string;
      }
      container service-policy {
        container input-map {
          tailf:cli-drop-node-name;
          tailf:cli-sequence-commands;
          tailf:cli-compact-syntax;
          leaf type {
            tailf:cli-optional-in-sequence;
            type enumeration {
              enum qos {
                tailf:code-name "service_policy_input_map_qos";
              }
              enum network-qos {
                tailf:code-name "service_policy_input_map_network_qos";
              }
              enum queuing {
                tailf:code-name "service_policy_input_map_queuing";
              }
            }
          }
          leaf input {
            type string;
          }
          leaf no-stats {
            type empty;
          }
          leaf name {
            tailf:cli-drop-node-name;
            type string;
          }
        }
        container output-map {
          tailf:cli-drop-node-name;
          tailf:cli-sequence-commands;
          tailf:cli-compact-syntax;
          leaf type {
            tailf:cli-optional-in-sequence;
            type enumeration {
              enum qos {
                tailf:code-name "service_policy_output_map_qos";
              }
              enum network-qos {
                tailf:code-name "service_policy_output_map_network_qos";
              }
              enum queuing {
                tailf:code-name "service_policy_output_map_queuing";
              }
            }
          }
          leaf output {
            type string;
          }
          leaf no-stats {
            type empty;
          }
          leaf name {
            tailf:cli-drop-node-name;
            type string;
          }
        }
      }
      leaf shutdown {
        type boolean;
      }
      leaf state {
        type enumeration {
          enum active;
          enum suspend;
        }
      }
      container trunk {
        leaf group {
          type string;
        }
      }
    }
  }

  typedef dscp-type {
    type uint16;
  }

  grouping match-grouping {
    container access-group {
      leaf-list name {
        type string;
      }
    }
    leaf-list cos {
      tailf:cli-range-list-syntax;
      type uint16;
    }
    leaf-list dscp {
      tailf:cli-range-list-syntax;
      type dscp-type;
    }
    container ip {
      leaf access-group {
        type string;
      }
    }
    container ipv6 {
      leaf access-group {
        type string;
      }
    }
    leaf-list precedence {
      tailf:cli-flat-list-syntax;
      type uint8;
    }
    container protocol {
      leaf arp {
        type empty;
      }
      leaf clns_es {
        type empty;
      }
      leaf clns_is {
        type empty;
      }
      leaf dhcp {
        type empty;
      }
      leaf ldp {
        type empty;
      }
      leaf netbios {
        type empty;
      }
    }
    container vlan {
      choice policy-map-match-vlan-choice {
        leaf-list range {
          tailf:cli-drop-node-name;
          tailf:cli-range-list-syntax;
          type uint16;
        }
        leaf-list flat {
          ordered-by user;
          tailf:cli-drop-node-name;
          tailf:cli-flat-list-syntax;
          type string;
        }
      }
    }
  }

  container class-map {
    container type {
      list qos {
        key "name";
        leaf name {
          type string;
        }
        leaf prematch {
          tailf:cli-prefix-key;
          tailf:cli-drop-node-name;
          type enumeration {
            enum match-all;
            enum match-any;
          }
        }
        leaf description {
          tailf:cli-multi-value;
          type string;
        }
        container match {
          uses match-grouping;
        }
      }
      list pbr {
        key "name";
        leaf name {
          type string;
        }
        leaf prematch {
          tailf:cli-prefix-key;
          tailf:cli-drop-node-name;
          type enumeration {
            enum match-all;
            enum match-any;
          }
        }
        leaf description {
          tailf:cli-multi-value;
          type string;
        }
        list class {
          tailf:cli-drop-node-name;
          tailf:cli-suppress-mode;
          tailf:cli-sequence-commands {
            tailf:cli-reset-siblings;
          }
          key "access-group";
          leaf seq {
            tailf:cli-drop-node-name;
            tailf:cli-prefix-key;
            tailf:cli-optional-in-sequence;
            type uint32;
          }
          leaf match {
            tailf:cli-prefix-key;
            type empty;
          }
          leaf ip {
            tailf:cli-prefix-key;
            type empty;
          }
          leaf access-group {
            tailf:cli-expose-key-name;
            type string;
          }
        }
      }
      list tapagg {
        key "name";
        leaf name {
          type string;
        }
        leaf prematch {
          tailf:cli-prefix-key;
          tailf:cli-drop-node-name;
          type enumeration {
            enum match-any;
          }
        }
        choice match-type-choice {
          list ip {
            tailf:cli-drop-node-name;
            tailf:cli-suppress-mode;
            tailf:cli-sequence-commands {
              tailf:cli-reset-siblings;
            }
            key "access-group";
            leaf seq {
              tailf:cli-drop-node-name;
              tailf:cli-prefix-key;
              tailf:cli-optional-in-sequence;
              type uint32;
            }
            leaf match {
              tailf:cli-prefix-key;
              type empty;
            }
            leaf ip {
              tailf:cli-prefix-key;
              type empty;
            }
            leaf access-group {
              tailf:cli-expose-key-name;
              type string;
            }
          }
          list ipv6 {
            tailf:cli-drop-node-name;
            tailf:cli-suppress-mode;
            tailf:cli-sequence-commands {
              tailf:cli-reset-siblings;
            }
            key "access-group";
            leaf seq {
              tailf:cli-drop-node-name;
              tailf:cli-prefix-key;
              tailf:cli-optional-in-sequence;
              type uint32;
            }
            leaf match {
              tailf:cli-prefix-key;
              type empty;
            }
            leaf ipv6 {
              tailf:cli-prefix-key;
              type empty;
            }
            leaf access-group {
              tailf:cli-expose-key-name;
              type string;
            }
          }
          list mac {
            tailf:cli-drop-node-name;
            tailf:cli-suppress-mode;
            tailf:cli-sequence-commands {
              tailf:cli-reset-siblings;
            }
            key "access-group";
            leaf seq {
              tailf:cli-drop-node-name;
              tailf:cli-prefix-key;
              tailf:cli-optional-in-sequence;
              type uint32;
            }
            leaf match {
              tailf:cli-prefix-key;
              type empty;
            }
            leaf mac {
              tailf:cli-prefix-key;
              type empty;
            }
            leaf access-group {
              tailf:cli-expose-key-name;
              type string;
            }
          }
        }
      }
    }
  }

  typedef class-name-type {
    type union {
      type string;
      type enumeration {
        enum class-default;
      }
    }
  }

  grouping policy-map-class-qos-grouping {
    list class {
      ordered-by user;
      key "name";
      leaf name {
        type class-name-type;
      }
      container police {
        choice police-choice {
          container cir {
            tailf:cli-compact-syntax;
            tailf:cli-sequence-commands {
              tailf:cli-reset-siblings;
            }
            leaf value {
              tailf:cli-drop-node-name;
              type uint32;
            }
            leaf units {
              tailf:cli-optional-in-sequence;
              tailf:cli-drop-node-name;
              type enumeration {
                enum bps;
                enum kbps;
                enum mbps;
              }
            }
            leaf bc {
              type uint32;
            }
            leaf bc-units {
              tailf:cli-optional-in-sequence;
              tailf:cli-drop-node-name;
              type enumeration {
                enum bytes;
                enum kbytes;
                enum mbytes;
              }
            }
          }
          container rate {
            tailf:cli-compact-syntax;
            tailf:cli-sequence-commands {
              tailf:cli-reset-siblings;
            }
            leaf value {
              tailf:cli-drop-node-name;
              type uint32;
            }
            leaf units {
              tailf:cli-optional-in-sequence;
              tailf:cli-drop-node-name;
              type enumeration {
                enum bps;
                enum kbps;
                enum mbps;
              }
            }
            leaf burst-size {
              type uint32;
            }
            leaf bs-units {
              tailf:cli-optional-in-sequence;
              tailf:cli-drop-node-name;
              type enumeration {
                enum bytes;
                enum kbytes;
                enum mbytes;
              }
            }
          }
        }
      }
      container set {
        leaf dscp {
          type dscp-type;
        }
        leaf traffic-class {
          type uint8;
        }
      }
    }
  }

  grouping policy-map-class-network-qos-grouping {
    container class {
      container type {
        list network-qos {
          key "name";
          leaf name {
            type class-name-type;
          }
          leaf mtu {
            type uint16;
          }
          leaf multicast-optimize {
            type empty;
          }
          container pause {
            container no-drop {
              presence "Enable no-drop for the CoS";
              tailf:cli-sequence-commands {
                tailf:cli-reset-all-siblings;
              }
              tailf:cli-compact-syntax;
              leaf buffer-size {
                tailf:cli-optional-in-sequence;
                type uint32;
              }
              leaf pause-threshold {
                type uint32;
              }
              leaf resume-threshold {
                type uint32;
              }
              leaf-list pfc-cos {
                tailf:cli-range-list-syntax;
                type uint8;
              }
            }
          }
          container queue-limit {
            tailf:cli-sequence-commands;
            tailf:cli-compact-syntax;
            leaf count {
              tailf:cli-drop-node-name;
              type uint32;
              must '../bytes';
            }
            leaf bytes {
              type empty;
            }
          }
          container set {
            leaf qos {
              type uint8;
            }
          }
        }
      }
    }
  }

  grouping policy-map-class-queuing-grouping {
    container class {
      container type {
        list queuing {
          key "name";
          leaf name {
            type class-name-type;
          }
          container bandwidth {
            leaf percent {
              type uint8;
            }
          }
          leaf priority {
            type empty;
          }
        }
      }
    }
  }

  container control-plane {
    tailf:cli-add-mode;
    container ip {
      uses control-plane-access-group-grouping;
    }
    container ipv6 {
      uses control-plane-access-group-grouping;
    }
    container scale-factor {
      tailf:cli-compact-syntax;
      tailf:cli-sequence-commands {
        tailf:cli-reset-siblings;
      }
      leaf scale {
        tailf:cli-drop-node-name;
        type decimal64 {
          fraction-digits 2;
        }
      }
      leaf module {
        type uint8;
      }
    }
    container service-policy {
      leaf input {
        type string;
      }
    }
  }
  container ntp {
    container server {
      list name {
        tailf:cli-drop-node-name;
        tailf:cli-suppress-mode;
        tailf:cli-compact-syntax;
        key "id";
        leaf id {
          type string;
        }
        container source {
          tailf:cli-flatten-container;
          uses interface-grouping;
        }
        leaf burst {
          tailf:cli-hide-in-submode;
          type empty;
        }
        leaf iburst {
          tailf:cli-hide-in-submode;
          type empty;
        }
        leaf maxpoll {
          tailf:cli-hide-in-submode;
          type uint8;
        }
        leaf minpoll {
          tailf:cli-hide-in-submode;
          type uint8;
        }
        leaf prefer {
          tailf:cli-hide-in-submode;
          type empty;
        }
        leaf version {
          tailf:cli-hide-in-submode;
          type uint8;
        }
        leaf key {
          tailf:cli-hide-in-submode;
          type uint16;
        }
      }
      list vrf {
        tailf:cli-compact-syntax;
        tailf:cli-suppress-mode;
        key "name hostname";
        leaf name {
          type string;
        }
        leaf hostname {
          type string;
        }
        leaf prefer {
          type empty;
        }
        leaf iburst {
          type empty;
        }
        leaf version {
          type uint8;
        }
        leaf maxpoll {
          type uint8;
        }
        container source {
          tailf:cli-flatten-container;
          uses interface-grouping;
        }
      }
    }
    container serve {
      leaf all {
        type empty;
      }
    }
    container source {
      uses interface-grouping;
      container vrf {
        tailf:cli-compact-syntax;
        tailf:cli-sequence-commands {
          tailf:cli-reset-all-siblings;
        }
        leaf name {
          tailf:cli-drop-node-name;
          type string;
        }
        uses interface-grouping;
      }
    }
    container local-interface {
      uses interface-grouping;
      container vrf {
        tailf:cli-compact-syntax;
        tailf:cli-sequence-commands {
          tailf:cli-reset-all-siblings;
        }
        leaf name {
          tailf:cli-drop-node-name;
          type string;
        }
        uses interface-grouping;
      }
    }
  }

  grouping ip-router-ospf-grouping {
    leaf router-id {
      type inet:ipv4-address;
    }
  }

  grouping queue-depth-grouping {
    leaf options {
      tailf:cli-drop-node-name;
      type union {
        type uint32;
        type enumeration {
          enum unlimited;
        }
      }
    }
  }

  grouping ospf-redistribute-match-grouping {
    leaf metric {
      type uint32;
    }
    leaf subnets {
      type empty;
    }
    leaf route-map {
      type string;
    }
    leaf tag {
      type uint32;
    }
  }

  grouping ospf-iso-igrp-redistribute-grouping {
    leaf metric {
      type uint32;
    }
    leaf metric-type {
      type enumeration {
        enum 1;
        enum 2;
      }
    }
    leaf tag {
      type uint32;
    }
    leaf subnets {
      type empty;
    }
  }

  grouping ospf-redistribute-grouping {
    container redist-options {
      tailf:cli-drop-node-name;
      tailf:cli-compact-syntax;
      uses ospf-iso-igrp-redistribute-grouping;
      leaf route-map {
        type string;
      }
    }
  }

  grouping ospf-redistribute-bgp-grouping {
    leaf as-number {
      tailf:cli-drop-node-name;
      type inet:as-number;
    }
    uses ospf-redistribute-grouping;
  }

  typedef ospf-area-type {
    type union {
      type uint32;
      type inet:ipv4-address;
    }
  }

  typedef ospf-metric-type {
    type uint32;
  }

  typedef limit-dc-non-dc-type {
    type union {
      type uint32;
      type enumeration {
        enum disable;
      }
    }
  }

  typedef neighbor-id-type {
    type union {
      type inet:ipv4-address;
      type inet:ipv6-address;
      type string;
    }
  }

  grouping address-family-grouping {
    list neighbor {
      tailf:cli-suppress-mode;
      key "id";
      leaf id {
        type neighbor-id-type;
      }
      leaf description {
        tailf:cli-multi-value;
        type string;
      }
      leaf activate {
        type empty;
      }
      uses route-map-grouping;
      uses default-originate-grouping;
      list prefix-list {
        tailf:cli-suppress-mode;
        tailf:cli-compact-syntax;
        key "in-out";
        leaf name {
          tailf:cli-prefix-key;
          tailf:cli-drop-node-name;
          mandatory true;
          type string;
        }
        leaf in-out {
          type enumeration {
            enum in;
            enum out;
          }
        }
      }
    }
    container aggregate-address {
      tailf:cli-compact-syntax;
      tailf:cli-sequence-commands {
        tailf:cli-reset-all-siblings;
      }
      leaf address {
        tailf:cli-drop-node-name;
        type inet:ipv4-address;
      }
      leaf mask {
        tailf:cli-drop-node-name;
        type inet:ipv4-address;
      }
      leaf advertise-map {
        tailf:cli-break-sequence-commands;
        type string;
      }
      leaf as-set {
        type empty;
      }
      leaf attribute-map {
        type string;
      }
      leaf as-override {
        type empty;
      }
      leaf route-map {
        type string;
      }
      leaf summary-only {
        type empty;
      }
      leaf suppress-map {
        type string;
      }
    }
  }

  uses nexthop-group-grouping;
  container router {
    container bfd {
      tailf:cli-add-mode;
      container interval {
        tailf:cli-compact-syntax;
        tailf:cli-sequence-commands {
          tailf:cli-reset-siblings;
        }
        leaf rate {
          tailf:cli-drop-node-name;
          type uint32;
        }
        leaf min-rx {
          type uint32;
        }
        leaf multiplier {
          type uint8;
        }
        leaf default {
          type empty;
        }
      }
      container multihop {
        container interval {
          tailf:cli-compact-syntax;
          tailf:cli-sequence-commands {
            tailf:cli-reset-siblings;
          }
          leaf rate {
            tailf:cli-drop-node-name;
            type uint32;
          }
          leaf min-rx {
            type uint32;
          }
          leaf multiplier {
            type uint8;
          }
        }
      }
    }
    list bgp {
      key "id";
      leaf id {
        type bgp-as-no-type;
      }
      leaf router-id {
        type inet:ipv4-address;
      }
      uses router-bgp-aggregate-address-grouping;
      container graceful-restart-alone {
        tailf:cli-drop-node-name;
        leaf graceful-restart {
          type empty;
        }
      }
      uses graceful-restart-grouping;
      uses router-bgp-network-grouping;
      container ip {
        uses access-group-grouping;
      }
      container ipv6 {
        uses access-group-grouping;
      }
      list vlan {
        key "id";
        leaf id {
          type uint16;
        }
        container designated-forwarder {
          container election {
            container preference {
              leaf rule {
                type enumeration {
                  enum high;
                  enum low;
                }
              }
            }
          }
        }
        leaf rd {
          type union {
            type rd-type;
            type enumeration {
              enum auto;
            }
          }
        }
        container route-target {
          container export {
            leaf auto {
              type empty;
            }
            list export {
              tailf:cli-drop-node-name;
              tailf:cli-suppress-mode;
              key "asn-ip";
              leaf asn-ip {
                type asn-ip-type;
              }
            }
          }
          container import {
            list auto {
              tailf:cli-suppress-mode;
              key "asn-ip";
              leaf asn-ip {
                type string;
              }
            }
            list import {
              tailf:cli-drop-node-name;
              tailf:cli-suppress-mode;
              key "asn-ip";
              leaf asn-ip {
                type asn-ip-type;
              }
            }
          }
          list both {
            tailf:cli-suppress-mode;
            key "asn-ip";
            leaf asn-ip {
              type asn-ip-type;
            }
          }
        }
        leaf maximum-routes {
          type uint32;
        }
        container redistribute {
          leaf host-route {
            type empty;
          }
          leaf learned {
            type empty;
          }
          leaf router-mac {
            type empty;
          }
          leaf static {
            type empty;
          }
        }
      }
      list vrf {
        key "name";
        leaf name {
          type string;
        }
        leaf router-id {
          type inet:ipv4-address;
        }
        leaf rd {
          type rd-type;
        }
        container update {
          leaf wait-install {
            type empty;
          }
        }
        leaf local-as {
          type uint32;
        }
        container bgp {
          container listen {
            list range {
              tailf:cli-suppress-mode;
              tailf:cli-compact-syntax;
              tailf:cli-delete-when-empty;
              tailf:cli-sequence-commands {
                tailf:cli-reset-siblings;
              }
              key "address";
              leaf address {
                type inet:ip-prefix;
              }
              leaf peer-group {
                tailf:cli-break-sequence-commands;
                type string;
              }
              leaf peer-filter {
                type string;
              }
              leaf remote-as {
                type inet:as-number;
              }
            }
          }
        }
        container route-target {
          uses vrf-route-target-grouping;
        }
        uses router-bgp-aggregate-address-grouping;
        uses graceful-restart-grouping;
        uses router-bgp-network-grouping;
        list neighbor {
          tailf:cli-suppress-mode;
          key "id";
          leaf id {
            type neighbor-id-type;
          }
          leaf remote-as {
            type bgp-as-no-type;
          }
          container peer {
            leaf group {
              type neighbor-id-type;
            }
          }
          uses default-originate-grouping;
          leaf description {
            tailf:cli-multi-value;
            type string;
          }
          container bfd {
            presence "true";
          }
          container timers {
            tailf:cli-compact-syntax;
            container keepalive-hold {
              tailf:cli-drop-node-name;
              tailf:cli-compact-syntax;
              tailf:cli-flatten-container;
              tailf:cli-sequence-commands {
                tailf:cli-reset-siblings;
              }
              leaf keepalive-interval {
                tailf:cli-drop-node-name;
                type uint16;
              }
              leaf holdtime {
                tailf:cli-drop-node-name;
                type uint16;
              }
            }
            leaf min-hold-time {
              type uint16;
            }
          }
          uses route-map-grouping;
          uses maximum-routes-grouping;
          leaf next-hop-self {
            type empty;
          }
          container as-path {
            container remote-as {
              container replace {
                leaf out {
                  type empty;
                }
              }
            }
          }
          uses rib-in-pre-policy-retain-grouping;
          uses router-bgp-neighbor-password-grouping;
          container send-community {
            presence "true";
          }
          container update-source {
            uses interface-grouping;
          }
        }
        container redistribute {
          container connected {
            presence "true";
            uses router-bgp-route-map-grouping;
          }
          container dynamic {
            presence "true";
            uses router-bgp-route-map-grouping;
          }
          container static {
            presence "true";
            uses router-bgp-route-map-grouping;
          }
          container ospf {
            presence "true";
            choice redistribute-ospf-match-internal-route-map-choice {
              leaf route-map {
                type string;
              }
              container match {
                container internal {
                  presence "true";
                  uses router-bgp-route-map-grouping;
                }
              }
            }
            container match-external {
              tailf:cli-drop-node-name;
              container match {
                container external {
                  presence "true";
                  uses router-bgp-route-map-grouping;
                }
              }
            }
          }
        }
        container evpn {
          container multicast {
            tailf:cli-add-mode;
            presence "true";
            container gateway {
              container dr {
                container election {
                  container algorithm {
                    leaf preference {
                      type uint16;
                    }
                  }
                }
              }
            }
            container address-family {
              container ipv4 {
                tailf:cli-add-mode;
                presence "true";
                leaf disabled {
                  type empty;
                }
                leaf transit {
                  type empty;
                }
              }
            }
          }
        }
        container address-family {
          container ipv4 {
            tailf:cli-add-mode;
            list neighbor {
              tailf:cli-suppress-mode;
              key "id";
              leaf id {
                type neighbor-id-type;
              }
              leaf activate {
                type empty;
              }
              leaf graceful-restart {
                type empty;
              }
              uses route-map-grouping;
            }
            uses router-bgp-network-grouping;
            uses router-bgp-vrf-address-family-route-target-grouping;
          }
          container ipv6 {
            tailf:cli-add-mode;
            list neighbor {
              tailf:cli-suppress-mode;
              key "id";
              leaf id {
                type neighbor-id-type;
              }
              leaf activate {
                type empty;
              }
              uses route-map-grouping;
            }
            uses router-bgp-vrf-address-family-route-target-grouping;
          }
        }
      }
      container non-vrf {
        tailf:cli-drop-node-name;
        uses router-bgp-local-as-grouping;
        container confederation {
          leaf identifier {
            type uint16;
          }
          container peers {
            presence "Peer ASs in BGP confederation";
            leaf-list peers-as {
              tailf:cli-drop-node-name;
              tailf:cli-flat-list-syntax;
              type uint16;
            }
          }
        }
        container distance {
          container bgp {
            tailf:cli-compact-syntax;
            tailf:cli-sequence-commands;
            leaf extern-as {
              tailf:cli-drop-node-name;
              type uint16;
            }
            leaf internal-as {
              tailf:cli-drop-node-name;
              type uint16;
            }
            leaf local {
              tailf:cli-drop-node-name;
              type uint16;
            }
          }
        }
        container maximum-paths {
          tailf:cli-compact-syntax;
          tailf:cli-sequence-commands;
          leaf number-of-paths {
            tailf:cli-drop-node-name;
            type uint16;
          }
          leaf ecmp {
            type uint16;
          }
        }
        container bgp {
          container asn {
            leaf notation {
              type enumeration {
                enum asdot;
                enum asplain;
              }
            }
          }
          uses bgp-additional-paths-grouping;
          container default {
            leaf ipv4-unicast {
              type boolean;
            }
            leaf ipv6-unicast {
              type empty;
            }
          }
          container convergence {
            container slow-peer {
              leaf time {
                type uint16;
              }
            }
          }
          leaf always-compare-med {
            type empty;
          }
          container listen {
            list range {
              tailf:cli-suppress-mode;
              tailf:cli-compact-syntax;
              tailf:cli-delete-when-empty;
              tailf:cli-sequence-commands {
                tailf:cli-reset-siblings;
              }
              key "address";
              leaf address {
                type inet:ip-prefix;
              }
              leaf peer-group {
                tailf:cli-break-sequence-commands;
                type string;
              }
              leaf peer-filter {
                type string;
              }
              leaf remote-as {
                type inet:as-number;
              }
            }
          }
          leaf log-neighbor-changes {
            type boolean;
          }
        }
        list neighbor {
          tailf:cli-suppress-mode;
          must 'count(*) > 1';
          key "id";
          leaf id {
            type neighbor-id-type;
          }
          container allowas-in {
            presence "accept as-paths";
            leaf as-number {
              tailf:cli-drop-node-name;
              type uint8;
            }
          }
          leaf description {
            tailf:cli-multi-value;
            type string;
          }
          container ebgp-multihop {
            presence "Allow EBGP neighbors not on directly connected networks";
            leaf max-hop {
              tailf:cli-drop-node-name;
              type uint8;
            }
          }
          leaf export-localpref {
            type uint32;
          }
          choice fall-over-bfd-choice {
            case fall-over {
              leaf fall-over {
                type enumeration {
                  enum bfd;
                }
              }
            }
            case bfd {
              container bfd {
                presence "true";
              }
              container bfd-interval {
                tailf:cli-drop-node-name;
                container bfd {
                  container interval {
                    tailf:cli-compact-syntax;
                    tailf:cli-sequence-commands {
                      tailf:cli-reset-siblings;
                    }
                    leaf rate {
                      tailf:cli-drop-node-name;
                      type uint16;
                    }
                    leaf min-rx {
                      type uint16;
                    }
                    leaf multiplier {
                      type uint8;
                    }
                  }
                }
              }
            }
          }
          leaf local-v6-addr {
            type inet:ipv6-address;
          }
          leaf next-hop-self {
            type empty;
          }
          container peer {
            choice peer-group-choice {
              leaf group {
                type empty;
              }
              container group-name {
                tailf:cli-drop-node-name;
                leaf group {
                  type neighbor-id-type;
                }
              }
            }
          }
          container peer-group {
            presence "true";
            leaf name {
              tailf:cli-drop-node-name;
              type neighbor-id-type;
            }
          }
          leaf next-hop-unchanged {
            type empty;
          }
          leaf import-localpref {
            type uint32;
          }
          uses router-bgp-local-as-grouping;
          leaf remote-as {
            type bgp-as-no-type;
          }
          container remove-private-as {
            presence "true";
            tailf:cli-compact-syntax;
            tailf:cli-sequence-commands {
              tailf:cli-reset-siblings;
            }
            leaf all {
              type empty;
            }
            leaf replace-as {
              type empty;
            }
          }
          leaf out-delay {
            type uint16;
          }
          uses route-map-grouping;
          uses default-originate-grouping;
          uses router-bgp-neighbor-password-grouping;
          leaf route-reflector-client {
            type empty;
          }
          leaf graceful-restart {
            type empty;
          }
          container send-community {
            presence "Send Community attribute to this neighbor";
            leaf send-community-where {
              type string;
            }
            container extended {
              presence "true";
            }
          }
          leaf shutdown {
            type empty;
          }
          container soft-reconfiguration {
            leaf inbound {
              type enumeration {
                enum yes;
                enum no;
                enum all;
              }
            }
          }
          uses rib-in-pre-policy-retain-grouping;
          container timers {
            tailf:cli-compact-syntax;
            tailf:cli-sequence-commands {
              tailf:cli-reset-siblings;
            }
            leaf keepalive-interval {
              tailf:cli-drop-node-name;
              type uint16;
            }
            leaf holdtime {
              tailf:cli-drop-node-name;
              type uint16;
            }
            leaf minimum-neighbor-hold {
              tailf:cli-drop-node-name;
              type uint16;
            }
          }
          container transport {
            container connection-mode {
              leaf passive {
                type empty;
              }
            }
          }
          leaf update-source {
            type string;
          }
          leaf weight {
            type uint16;
          }
          leaf metric-out {
            type uint32;
          }
          uses maximum-routes-grouping;
          leaf enforce-first-as {
            type boolean;
          }
        }
        container redistribute {
          container connected {
            presence "true";
            uses router-bgp-route-map-grouping;
          }
          container dynamic {
            presence "true";
            uses router-bgp-route-map-grouping;
          }
          container isis {
            tailf:cli-compact-syntax;
            presence "true";
            leaf level {
              tailf:cli-drop-node-name;
              type enumeration {
                enum level-1;
                enum level-2;
                enum level-1-2;
              }
            }
            leaf route-map {
              type string;
            }
          }
          container ospf {
            presence "true";
            uses router-bgp-route-map-grouping;
          }
          container ospf3 {
            presence "true";
            uses router-bgp-route-map-grouping;
          }
          container rip {
            presence "true";
            uses router-bgp-route-map-grouping;
          }
          container static {
            presence "true";
            uses router-bgp-route-map-grouping;
          }
        }
        container session {
          list tracker {
            key "name";
            leaf name {
              type string;
            }
            container recovery {
              tailf:cli-compact-syntax;
              tailf:cli-sequence-commands {
                tailf:cli-reset-siblings;
              }
              leaf delay {
                type uint16;
              }
              leaf seconds {
                type empty;
              }
            }
          }
        }
        container address-family {
          container no-vrf {
            tailf:cli-drop-node-name;
            container evpn {
              tailf:cli-add-mode;
              presence "true";
              leaf graceful-restart {
                type boolean;
              }
              list neighbor {
                tailf:cli-suppress-mode;
                key "id";
                leaf id {
                  type neighbor-id-type;
                }
                leaf activate {
                  type empty;
                }
                uses route-map-grouping;
                container encapsulation {
                  container mpls {
                    presence "true";
                    container next-hop-self {
                      container source-interface {
                        uses interface-grouping;
                      }
                    }
                  }
                }
              }
              container route {
                container import {
                  container match-failure {
                    leaf action {
                      type enumeration {
                        enum discard;
                      }
                    }
                  }
                }
              }
            }
            container ipv4 {
              tailf:cli-add-mode;
              uses address-family-grouping;
              container bgp {
                uses bgp-additional-paths-grouping;
              }
              uses router-bgp-network-grouping;
              container redistribute {
                container direct {
                  leaf route-map {
                    type string;
                  }
                }
                container connected {
                  presence "true";
                  uses router-bgp-route-map-grouping;
                }
              }
            }
            container ipv6 {
              tailf:cli-add-mode;
              uses address-family-grouping;
              uses router-bgp-network-grouping;
            }
            container vpn-ipv4 {
              tailf:cli-add-mode;
              presence "true";
              leaf graceful-restart {
                type boolean;
              }
              list neighbor {
                tailf:cli-suppress-mode;
                key "id";
                leaf id {
                  type neighbor-id-type;
                }
                leaf activate {
                  type empty;
                }
              }
            }
          }
        }
      }
      list template {
        key "peer-policy peer";
        leaf peer-policy {
          type string;
        }
        leaf peer {
          type string;
        }
        leaf peer-session {
          type string;
        }
        container inherit {
          leaf peer-session {
            type string;
          }
        }
        leaf remote-as {
          type inet:as-number;
        }
        leaf description {
          tailf:cli-multi-value;
          type string;
        }
        container update-source {
          leaf update-source-name {
            tailf:cli-drop-node-name;
            tailf:cli-multi-value;
            type string;
          }
        }
        container send-community {
          presence "Send Community attribute to this neighbor";
          leaf send-community-where {
            tailf:cli-drop-node-name;
            type enumeration {
              enum both;
              enum extended;
              enum standard {
                tailf:code-name "send_standard";
              }
            }
          }
        }
        leaf next-hop-self {
          type empty;
        }
        container timers {
          tailf:cli-compact-syntax;
          tailf:cli-sequence-commands {
            tailf:cli-reset-siblings;
          }
          leaf keepalive-interval {
            tailf:cli-drop-node-name;
            type uint16;
          }
          leaf holdtime {
            tailf:cli-drop-node-name;
            type uint16;
          }
          leaf minimum-neighbor-hold {
            tailf:cli-drop-node-name;
            type uint16;
          }
        }
        container password {
          tailf:cli-compact-syntax;
          leaf enctype {
            tailf:cli-drop-node-name;
            type uint8;
          }
          leaf text {
            tailf:cli-drop-node-name;
            tailf:cli-multi-value;
            type string;
          }
        }
        container address-family {
          container no-vrf {
            tailf:cli-drop-node-name;
            list ipv4 {
              key "unicast-multicast";
              leaf unicast-multicast {
                type enumeration {
                  enum unicast {
                    tailf:code-name "ipv4_unicast";
                  }
                  enum multicast {
                    tailf:code-name "ipv4_multicast";
                  }
                  enum mdt;
                  enum tunnel;
                  enum labeled-unicast;
                }
              }
              container inherit {
                tailf:cli-sequence-commands;
                tailf:cli-compact-syntax;
                container peer-policy {
                  leaf policy-name {
                    tailf:cli-drop-node-name;
                    type string;
                  }
                  leaf seq-num {
                    tailf:cli-drop-node-name;
                    type uint16;
                  }
                }
              }
              list prefix-list {
                tailf:cli-suppress-mode;
                key "inout";
                leaf inout {
                  type enumeration {
                    enum in {
                      tailf:code-name "prefix_in";
                    }
                    enum out {
                      tailf:code-name "prefix_out";
                    }
                  }
                }
                leaf prefix-list-name {
                  tailf:cli-drop-node-name;
                  tailf:cli-prefix-key;
                  type string;
                  mandatory true;
                }
              }
              uses route-map-grouping;
              uses address-family-grouping;
            }
          }
        }
      }
      container timers {
        container bgp {
          tailf:cli-compact-syntax;
          tailf:cli-sequence-commands {
            tailf:cli-reset-siblings;
          }
          leaf keepalive {
            tailf:cli-drop-node-name;
            type uint16;
          }
          leaf holdtime {
            tailf:cli-drop-node-name;
            type uint16;
          }
        }
      }
      container update {
        leaf wait-for-convergence {
          type empty;
        }
        leaf wait-install {
          type empty;
        }
      }
      list vlan-aware-bundle {
        key "name";
        leaf name {
          tailf:cli-multi-word-key;
          type string;
        }
        leaf rd {
          type rd-type;
        }
        container route-target {
          list both {
            tailf:cli-suppress-mode;
            key "asn-ip";
            leaf asn-ip {
              type asn-ip-type;
            }
          }
        }
        container redistribute {
          leaf learned {
            type empty;
          }
          leaf static {
            type empty;
          }
          leaf igmp {
            type empty;
          }
        }
        leaf vlan {
          type string;
        }
      }
    }
    container msdp {
      tailf:cli-add-mode;
      list peer {
        key "address";
        leaf address {
          type inet:ipv4-address;
        }
        container local-interface {
          uses interface-grouping;
        }
        list sa-filter {
          tailf:cli-suppress-mode;
          tailf:cli-compact-syntax;
          key "in-out";
          leaf in-out {
            type enumeration {
              enum in;
              enum out;
            }
          }
          leaf list {
            type string;
          }
        }
        leaf description {
          type string;
        }
      }
    }
    list ospf {
      key "id";
      leaf id {
        type uint16;
      }
      list vrf {
        key "name";
        leaf name {
          type string;
        }
      }
      container non-vrf {
        tailf:cli-drop-node-name;
        uses ip-router-ospf-grouping;
        list area {
          tailf:cli-suppress-mode;
          key "id";
          leaf id {
            tailf:cli-suppress-range;
            type ospf-area-type;
          }
          container authentication {
            presence "Enable authentication";
            leaf message-digest {
              type empty;
            }
          }
          leaf default-cost {
            type uint32;
          }
          list filter {
            tailf:cli-suppress-mode;
            tailf:cli-compact-syntax;
            key "in-out";
            leaf prefix {
              tailf:cli-prefix-key;
              mandatory true;
              type string;
            }
            leaf in-out {
              type enumeration {
                enum in;
                enum out;
              }
            }
          }
          container nssa {
            presence "Specify a NSSA area";
            container default-information-originate {
              tailf:cli-flatten-container;
              presence "Originate Type 7 default into NSSA area";
              leaf metric {
                type int32;
              }
              leaf metric-type {
                type ospf-metric-type;
              }
            }
            leaf no-ext-capability {
              type empty;
            }
            leaf no-redistribution {
              type empty;
            }
            leaf no-summary {
              type empty;
            }
            container translate {
              container type7 {
                leaf suppress-fa {
                  type empty;
                }
              }
            }
          }
          list range {
            tailf:cli-suppress-mode;
            key "ip mask";
            leaf ip {
              type inet:ipv4-address;
            }
            leaf mask {
              type inet:ipv4-address;
            }
            choice advertise-choice {
              leaf advertise {
                type empty;
              }
              leaf not-advertise {
                type empty;
              }
            }
            leaf cost {
              type uint32;
            }
          }
          list sham-link {
            tailf:cli-suppress-mode;
            key "source dest";
            leaf source {
              type inet:ipv4-address;
            }
            leaf dest {
              type inet:ipv4-address;
            }
            leaf cost {
              type uint16;
            }
          }
          container stub {
            presence "Specify a stub area";
            leaf no-ext-capability {
              type empty;
            }
            leaf no-summary {
              type empty;
            }
          }
          list virtual-link {
            must 'not(../nssa)' {
              error-message "The area is configured as NSSA area already";
            }
            must 'not(../stub)' {
              error-message "The area is configured as stub area already";
            }
            tailf:cli-suppress-mode;
            key "id";
            leaf id {
              type inet:ipv4-address;
            }
            leaf authentication {
              type empty;
            }
            container authentication-key {
              leaf auth-type {
                tailf:cli-drop-node-name;
                type uint8;
              }
              leaf auth-key {
                tailf:cli-drop-node-name;
                type string;
              }
            }
            leaf dead-interval {
              type uint16;
            }
            leaf hello-interval {
              type int32;
            }
            list message-digest-key {
              tailf:cli-suppress-mode;
              key "id";
              leaf id {
                tailf:cli-suppress-range;
                type uint8;
              }
              container md5 {
                tailf:cli-sequence-commands;
                leaf auth-type {
                  tailf:cli-drop-node-name;
                  tailf:cli-optional-in-sequence;
                  type uint8;
                }
                leaf auth-key {
                  tailf:cli-drop-node-name;
                  type string;
                }
              }
            }
            leaf retransmit-interval {
              type uint16;
            }
            leaf transmit-delay {
              type uint16;
            }
          }
        }
        container auto-cost {
          presence "Calculate OSPF interface cost according to bandwidth";
          leaf reference-bandwidth {
            type uint32;
          }
        }
        container bfd {
          leaf all-interfaces {
            type empty;
          }
        }
        container capability {
          leaf capability-type {
            tailf:cli-drop-node-name;
            type enumeration {
              enum lls;
              enum opaque;
              enum transit;
            }
          }
        }
        container compatible {
          leaf rfc1583 {
            type empty;
          }
        }
        container default-information {
          container originate {
            presence "Distribute a default route";
            leaf always {
              type empty;
            }
            leaf metric {
              type uint32;
            }
            leaf metric-type {
              type ospf-metric-type;
            }
            leaf route-map {
              type string;
            }
          }
        }
        leaf default-metric {
          type uint32;
        }
        container discard-route {
          presence "Enable or disable discard-route installation";
          tailf:cli-compact-syntax;
          leaf external {
            type uint32;
          }
          leaf internal {
            type uint32;
          }
        }
        container distance {
          tailf:cli-compact-syntax;
          container ospf-distance {
            tailf:cli-compact-syntax;
            tailf:cli-drop-node-name;
            leaf distance {
              tailf:cli-drop-node-name;
              type uint32;
            }
            tailf:cli-sequence-commands;
            leaf ip {
              tailf:cli-drop-node-name;
              type inet:ipv4-address;
            }
            leaf wildcard {
              tailf:cli-drop-node-name;
              type inet:ipv4-address;
            }
            leaf acl-name {
              tailf:cli-drop-node-name;
              type access-list-standard-id-type;
            }
          }
          container ospf {
            leaf external {
              type uint32;
            }
            leaf inter-area {
              type uint32;
            }
            leaf intra-area {
              type uint32;
            }
          }
        }
        uses distribute-list-grouping;
        container domain-id {
          choice domain-id-choice {
            leaf ip-format {
              tailf:cli-drop-node-name;
              type inet:ipv4-address;
            }
            container ip-format-secondary {
              tailf:cli-drop-node-name;
              tailf:cli-compact-syntax;
              tailf:cli-sequence-commands;
              leaf ip {
                tailf:cli-drop-node-name;
                type inet:ipv4-address;
              }
              leaf secondary {
                type empty;
              }
            }
            leaf Null {
              type empty;
            }
            container type {
              tailf:cli-sequence-commands;
              tailf:cli-compact-syntax;
              leaf type-leaf {
                tailf:cli-drop-node-name;
                type enumeration {
                  enum 0005;
                  enum 0105;
                  enum 0205;
                  enum 8005;
                }
              }
              leaf value {
                type string;
              }
            }
          }
        }
        leaf domain-tag {
          type uint32;
        }
        container ignore {
          container lsa {
            leaf mospf {
              type empty;
            }
          }
        }
        container interface-id {
          leaf snmp-if-index {
            type empty;
          }
        }
        leaf ispf {
          type empty;
        }
        container limit {
          tailf:cli-compact-syntax;
          container retransmissions {
            leaf non-dc {
              type limit-dc-non-dc-type;
            }
            leaf dc {
              type limit-dc-non-dc-type;
            }
          }
        }
        container local-rib-criteria {
          tailf:cli-compact-syntax;
          leaf forwarding-address {
            type empty;
          }
          leaf inter-area-summary {
            type empty;
          }
          leaf nssa-translation {
            type empty;
          }
        }
        container log-adjacency-changes {
          presence "Log changes in adjacency state";
          leaf detail {
            type empty;
          }
        }
        container max-lsa {
          tailf:cli-sequence-commands;
          leaf number {
            tailf:cli-drop-node-name;
            type uint32;
          }
          container options {
            tailf:cli-drop-node-name;
            tailf:cli-compact-syntax;
            leaf threshold-value {
              tailf:cli-drop-node-name;
              type uint32;
            }
            leaf ignore-count {
              type uint32;
            }
            leaf ignore-time {
              type uint32;
            }
            leaf reset-time {
              type uint32;
            }
            leaf warning-only {
              type empty;
            }
          }
        }
        container max-metric {
          container router-lsa {
            presence "Maximum metric in self-originated router-LSAs";
            container external-lsa {
              presence "Override external-lsa metric with max-metric value";
              tailf:cli-flatten-container;
              leaf metric {
                tailf:cli-drop-node-name;
                type uint32;
              }
            }
            leaf include-stub {
              type empty;
            }
            container on-startup {
              presence "Set maximum metric temporarily after reboot";
              tailf:cli-flatten-container;
              choice time-wait-for-bgp-choice {
                leaf time {
                  tailf:cli-drop-node-name;
                  type uint32;
                }
                leaf wait-for-bgp {
                  type empty;
                }
              }
            }
            container summary-lsa {
              presence "Override summary-lsa metric with max-metric value";
              tailf:cli-flatten-container;
              leaf metric {
                tailf:cli-drop-node-name;
                type uint32;
              }
            }
          }
        }
        leaf maximum-paths {
          type uint32;
        }
        container ip {
          uses access-group-grouping;
        }
        list network {
          tailf:cli-suppress-mode;
          key "ip";
          leaf ip {
            type union {
              type ip-mask;
            }
          }
          leaf area {
            type ospf-area-type;
          }
        }
        container passive-interface {
          leaf default {
            type empty;
          }
          list passive {
            tailf:cli-suppress-mode;
            tailf:cli-drop-node-name;
            key "id";
            leaf id {
              type string;
            }
          }
        }
        container disable {
          list passive-interface {
            tailf:cli-suppress-mode;
            tailf:cli-delete-when-empty;
            tailf:cli-compact-syntax;
            key "interface";
            leaf interface {
              tailf:cli-multi-word-key;
              type string;
            }
          }
        }
        container redistribute {
          uses ospf-redistribute-grouping;
          container bgp {
            uses ospf-redistribute-bgp-grouping;
          }
          container connected {
            presence "Connected";
            uses ospf-redistribute-grouping;
          }
          container rip {
            presence "Routing Information Protocol (RIP)";
            uses ospf-redistribute-grouping;
          }
          container static {
            presence "Static routes";
            uses ospf-redistribute-grouping;
          }
        }
        list summary-address {
          tailf:cli-suppress-mode;
          key "ip wildcard";
          leaf ip {
            type inet:ipv4-address;
          }
          leaf wildcard {
            type inet:ipv4-address;
          }
          choice tag-no-advertise-choice {
            leaf tag {
              type uint32;
            }
            leaf not-advertise {
              type empty;
            }
          }
        }
        container timers {
          container lsa-arrival {
            leaf arrival {
              tailf:cli-drop-node-name;
              type uint32;
            }
          }
          container throttle {
            container spf {
              tailf:cli-sequence-commands;
              tailf:cli-compact-syntax;
              leaf delay {
                tailf:cli-drop-node-name;
                type uint32;
              }
              leaf min-delay {
                tailf:cli-drop-node-name;
                type uint32;
              }
              leaf max-delay {
                tailf:cli-drop-node-name;
                type uint32;
              }
            }
          }
        }
      }
    }
    container ospf-vrf {
      tailf:cli-drop-node-name;
      list ospf {
        key "id";
        leaf id {
          type uint16;
        }
        leaf vrf {
          tailf:cli-hide-in-submode;
          type string;
        }
        container redistribute {
          container bgp {
            presence "true";
            container include {
              container leaked {
                presence "true";
                leaf route-map {
                  type string;
                }
              }
            }
            leaf route-map {
              type string;
            }
          }
          container ospf {
            container leaked {
              presence "true";
              leaf route-map {
                type string;
              }
            }
          }
        }
        list network {
          tailf:cli-suppress-mode;
          key "prefix";
          leaf prefix {
            type inet:ipv4-prefix;
          }
          leaf area {
            type ospf-area-type;
          }
        }
        container max-lsa {
          tailf:cli-sequence-commands;
          leaf number {
            tailf:cli-drop-node-name;
            type uint32;
          }
        }
      }
    }
    container pim {
      tailf:cli-add-mode;
      container ip {
        container pim {
          uses access-group-grouping;
        }
      }
    }
    container pim-bidirectional {
      tailf:cli-drop-node-name;
      container pim {
        container bidirectional {
          tailf:cli-add-mode;
          container ipv4 {
            tailf:cli-add-mode;
            leaf group-expiry-timer {
              type uint16;
            }
            uses router-pim-sparse-mode-rp-grouping;
          }
        }
      }
    }
    container pim-sparse-mode {
      tailf:cli-drop-node-name;
      container pim {
        container sparse-mode {
          tailf:cli-add-mode;
          container ipv4 {
            tailf:cli-add-mode;
            leaf bfd {
              type empty;
            }
            container spt {
              container threshold {
                leaf switch {
                  tailf:cli-drop-node-name;
                  type enumeration {
                    enum 0;
                    enum infinity;
                  }
                }
              }
            }
            uses router-pim-sparse-mode-rp-grouping;
            list anycast-rp {
              tailf:cli-suppress-mode;
              key "anycast anycast-other";
              leaf anycast {
                type inet:ipv4-address;
              }
              leaf anycast-other {
                type inet:ipv4-address;
              }
            }
            container ssm {
              leaf range {
                type string;
              }
            }
          }
          list vrf {
            key "name";
            leaf name {
              type string;
            }
            container ipv4 {
              tailf:cli-add-mode;
              leaf bfd {
                type empty;
              }
              uses router-pim-sparse-mode-rp-grouping;
            }
          }
        }
      }
    }
    container igmp {
      tailf:cli-add-mode;
      container ip {
        container igmp {
          uses access-group-grouping;
        }
      }
    }
    container general {
      tailf:cli-add-mode;
      container control-functions {
        tailf:cli-add-mode;
        leaf code {
          type string;
        }
      }
    }
    list isis {
      key "area-tag";
      leaf area-tag {
        type string;
      }
      list net {
        tailf:cli-suppress-mode;
        tailf:cli-delete-when-empty;
        key "tag";
        leaf tag {
          type string;
        }
      }
      container router-id {
        leaf ipv4 {
          type inet:ipv4-address;
        }
      }
      leaf is-type {
        type enumeration {
          enum level-1;
          enum level-1-2;
          enum level-2;
        }
      }
      leaf log-adjacency-changes {
        type empty;
      }
      leaf max-lsp-lifetime {
        type uint16;
      }
      container redistribute {
        container bgp {
          presence "true";
          leaf route-map {
            type string;
          }
        }
        container connected {
          presence "true";
          leaf route-map {
            type string;
          }
        }
        container ospf {
          container match {
            container external {
              presence "true";
              leaf route-map {
                type string;
              }
            }
            container internal {
              presence "true";
              leaf route-map {
                type string;
              }
            }
            container nssa-external {
              presence "true";
              leaf route-map {
                type string;
              }
            }
          }
        }
        container static {
          presence "true";
          leaf route-map {
            type string;
          }
        }
      }
      container segment-routing {
        container mpls {
          tailf:cli-add-mode;
          leaf router-id {
            type inet:ipv4-address;
          }
          leaf shutdown {
            type boolean;
          }
        }
      }
      container set-overload-bit {
        presence "true";
        container on-startup {
          choice on-startup-choice {
            container wait-for-bgp {
              presence "true";
              leaf timeout {
                type uint16;
              }
            }
            leaf time {
              tailf:cli-drop-node-name;
              type uint16;
            }
          }
        }
      }
      container spf-interval {
        tailf:cli-compact-syntax;
        tailf:cli-sequence-commands {
          tailf:cli-reset-siblings;
        }
        leaf interval {
          tailf:cli-drop-node-name;
          type uint16;
        }
        leaf initial-wait {
          tailf:cli-drop-node-name;
          type uint32;
        }
        leaf minimum-wait {
          tailf:cli-drop-node-name;
          type uint32;
        }
      }
      container authentication {
        container mode {
          container md5 {
            presence "true";
            leaf level {
              tailf:cli-drop-node-name;
              type authentication-level-type;
            }
          }
          container text {
            presence "true";
            leaf level {
              tailf:cli-drop-node-name;
              type authentication-level-type;
            }
          }
        }
        container key {
          tailf:cli-compact-syntax;
          tailf:cli-sequence-commands {
            tailf:cli-reset-siblings;
          }
          leaf encrypt {
            tailf:cli-drop-node-name;
            tailf:cli-optional-in-sequence;
            type enumeration {
              enum 0;
              enum 7;
            }
          }
          leaf string {
            tailf:cli-drop-node-name;
            type string;
          }
        }
      }
      container address-family {
        container ipv4 {
          tailf:cli-add-mode;
          leaf af {
            tailf:cli-drop-node-name;
            tailf:cli-hide-in-submode;
            type enumeration {
              enum unicast;
            }
          }
          leaf maximum-paths {
            type uint8;
          }
          uses router-isis-af-redistribute-grouping;
          leaf bfd {
            type enumeration {
              enum all-interfaces;
            }
          }
        }
        container ipv6 {
          tailf:cli-add-mode;
          leaf af {
            tailf:cli-drop-node-name;
            tailf:cli-hide-in-submode;
            type enumeration {
              enum unicast;
            }
          }
          leaf maximum-paths {
            type uint8;
          }
          leaf multi-topology {
            type empty;
          }
          uses router-isis-af-redistribute-grouping;
        }
      }
      container traffic-engineering {
        tailf:cli-add-mode;
        presence "true";
        leaf shutdown {
          type boolean;
        }
        leaf is-type {
          type enumeration {
            enum level-1;
            enum level-1-2;
            enum level-2;
          }
        }
      }
    }
    container rip {
      tailf:cli-add-mode;
      presence "true";
      leaf shutdown {
        type empty;
      }
      list network {
        tailf:cli-suppress-mode;
        key "prefix";
        leaf prefix {
          type tailf:ipv4-address-and-prefix-length;
        }
      }
    }
    container multicast {
      tailf:cli-add-mode;
      container ipv4 {
        tailf:cli-add-mode;
        container counters {
          container rate {
            container period {
              choice rate-period-choice {
                container decay {
                  tailf:cli-drop-node-name;
                  tailf:cli-compact-syntax;
                  tailf:cli-sequence-commands {
                    tailf:cli-reset-siblings;
                  }
                  leaf decay {
                    type uint16;
                  }
                  leaf units {
                    tailf:cli-drop-node-name;
                    type enumeration {
                      enum seconds;
                    }
                  }
                }
                container decay-default {
                  tailf:cli-drop-node-name;
                  tailf:cli-compact-syntax;
                  tailf:cli-sequence-commands {
                    tailf:cli-reset-siblings;
                  }
                  leaf decay {
                    type enumeration {
                      enum 300;
                    }
                  }
                  leaf units {
                    tailf:cli-drop-node-name;
                    type enumeration {
                      enum seconds;
                    }
                  }
                }
              }
            }
          }
        }
        container multipath {
          leaf none {
            type empty;
          }
        }
        leaf routing {
          type empty;
        }
        leaf software-forwarding {
          type enumeration {
            enum kernel;
            enum sfe;
          }
        }
        leaf software-forwarding-kernel {
          tailf:alt-name "software-forwarding";
          type enumeration {
            enum kernel;
            enum sfe;
          }
        }
        list route {
          tailf:cli-suppress-mode;
          tailf:cli-compact-syntax;
          tailf:cli-sequence-commands {
            tailf:cli-reset-siblings;
          }
          key "group-address source-address";
          leaf group-address {
            type inet:ipv4-address;
          }
          leaf source-address {
            type inet:ipv4-address;
          }
          container iif {
            tailf:cli-flatten-container;
            uses interface-grouping;
          }
          container oif {
            tailf:cli-flatten-container;
            uses interface-grouping;
          }
        }
      }
      container ipv6 {
        tailf:cli-add-mode;
        leaf routing {
          type empty;
        }
        leaf software-forwarding {
          type enumeration {
            enum kernel;
            enum sfe;
          }
        }
        leaf software-forwarding-kernel {
          tailf:alt-name "software-forwarding";
          type enumeration {
            enum kernel;
            enum sfe;
          }
        }
      }
      list vrf {
        key "name";
        leaf name {
          type string;
        }
        container ipv4 {
          tailf:cli-add-mode;
          leaf routing {
            type empty;
          }
        }
      }
    }
  }
  container lldp {
    container management-address {
      uses interface-grouping;
      leaf vrf {
        type string;
      }
    }
    leaf run {
      type boolean;
    }
    container timer {
      leaf period {
        tailf:cli-drop-node-name;
        type uint32;
      }
    }
  }
  container load-interval {
    leaf default {
      type uint16;
    }
  }
  list port-profile {
    tailf:cli-suppress-mode;
    key "id";
    leaf id {
      type union {
        type string;
        type enumeration {
          enum default;
        }
      }
    }
    leaf max-ports {
      type uint16;
    }
  }
  container policy-map {
    container type {
      list control-plane {
        key "name";
        leaf name {
          type string;
        }
        list class {
          key "name";
          leaf name {
            type class-name-type;
          }
          container police {
            tailf:cli-sequence-commands;
            tailf:cli-compact-syntax;
            leaf cir {
              type uint16;
            }
            leaf kbps {
              tailf:cli-optional-in-sequence;
              type empty;
            }
            leaf bc {
              type uint32;
            }
            leaf bytes {
              type empty;
            }
          }
        }
      }
      list copp {
        key "name";
        leaf name {
          type string;
        }
        list class {
          key "name";
          leaf name {
            type string;
          }
          container shape {
            leaf kbps {
              type uint32;
            }
          }
          container bandwidth {
            leaf kbps {
              type uint32;
            }
          }
        }
      }
      list qos {
        key "name";
        leaf name {
          type string;
        }
        leaf description {
          tailf:cli-multi-value;
          type string;
        }
        leaf comment {
          tailf:cli-multi-value;
          type string;
        }
        uses policy-map-class-qos-grouping;
      }
      list quality-of-service {
        key "name";
        leaf name {
          type string;
        }
        leaf description {
          tailf:cli-multi-value;
          type string;
        }
        leaf comment {
          tailf:cli-multi-value;
          type string;
        }
        uses policy-map-class-qos-grouping;
      }
      list pbr {
        key "name";
        leaf name {
          type string;
        }
        list class {
          tailf:cli-drop-node-name;
          key "class";
          leaf seq {
            tailf:cli-drop-node-name;
            tailf:cli-prefix-key;
            tailf:cli-optional-in-sequence;
            type uint32;
          }
          leaf class {
            tailf:cli-expose-key-name;
            type string;
          }
          container set {
            leaf nexthop-group {
              type string;
            }
          }
        }
      }
      list network-qos {
        key "name";
        leaf name {
          type string;
        }
        leaf description {
          tailf:cli-multi-value;
          type string;
        }
        uses policy-map-class-network-qos-grouping;
      }
      list queuing {
        key "name";
        leaf name {
          type string;
        }
        leaf description {
          tailf:cli-multi-value;
          type string;
        }
        uses policy-map-class-queuing-grouping;
      }
      list tapagg {
        key "name";
        leaf name {
          type string;
        }
        list class {
          tailf:cli-drop-node-name;
          key "class";
          leaf seq {
            tailf:cli-drop-node-name;
            tailf:cli-prefix-key;
            tailf:cli-optional-in-sequence;
            type uint32;
          }
          leaf class {
            tailf:cli-expose-key-name;
            type string;
          }
          leaf comment {
            tailf:cli-multi-value;
            type string;
          }
          container set {
            container aggregation-group {
              leaf-list group {
                tailf:cli-flat-list-syntax;
                type string;
              }
            }
          }
        }
      }
    }
  }
  container load-balance {
    container policies {
      tailf:cli-add-mode;
      container load-balance {
        container sand {
          list profile {
            key "name";
            leaf name {
              type string;
            }
          }
        }
      }
    }
  }
  container port-channel {
    container load-balance {
      container sand {
        leaf profile {
          type string;
        }
      }
    }
  }
  container platform {
    container trident {
      container forwarding-table {
        leaf partition {
          type enumeration {
            enum 0;
            enum 1;
            enum 2;
            enum 3;
            enum 4;
          }
        }
      }
    }
    container sand {
      container lag {
        leaf hardware-only {
          type empty;
        }
      }
    }
  }
  list role {
    key "name";
    leaf name {
      type string;
    }
    leaf comment {
      tailf:cli-multi-value;
      type string;
    }
    list role-list-rule {
      tailf:cli-suppress-mode;
      tailf:cli-delete-when-empty;
      tailf:cli-drop-node-name;
      tailf:cli-compact-syntax;
      key "seq";
      leaf seq {
        tailf:cli-suppress-range;
        type uint16;
      }
      leaf rule {
        tailf:cli-multi-value;
        tailf:cli-drop-node-name;
        type string;
      }
    }
  }
  container interface {
    list Ethernet {
      tailf:cli-allow-join-with-key;
      key "name";
      leaf name {
        type string;
      }
      uses ethernet-settings-grouping;
      uses interface-service-policy-grouping;
      uses arp-timeout-grouping;
      container pim {
        container ipv4 {
          container neighbor {
            leaf filter {
              type string;
            }
          }
          leaf bidirectional {
            type empty;
          }
          leaf border-router {
            type empty;
          }
          leaf sparse-mode {
            type empty;
          }
          leaf dr-priority {
            type uint32;
          }
          leaf bfd {
            type boolean;
          }
        }
      }
      uses interface-vrrp-grouping;
      container lacp {
        leaf port-priority {
          type uint16;
        }
        leaf rate {
          type enumeration {
            enum fast;
            enum normal;
          }
        }
        leaf timer {
          type enumeration {
            enum fast;
            enum normal;
          }
        }
      }
      container link-debounce {
        container time {
          tailf:cli-compact-syntax;
          tailf:cli-sequence-commands;
          leaf up-down {
            tailf:cli-drop-node-name;
            type uint16;
          }
          leaf down-only {
            tailf:cli-drop-node-name;
            type uint16;
          }
        }
      }
      container poe {
        leaf disabled {
          type empty;
        }
        container shutdown {
          leaf action {
            type enumeration {
              enum maintain;
              enum power-off;
            }
          }
        }
      }
      container transceiver {
        container power {
          leaf ignore {
            type empty;
          }
        }
        container application {
          leaf override {
            type union {
              type enumeration {
                enum 100gbase-srbd;
              }
              type uint8;
            }
          }
        }
        leaf frequency {
          type decimal64 {
            fraction-digits 3;
          }
        }
        container transmitter {
          leaf signal-power {
            type decimal64 {
              fraction-digits 2;
            }
          }
        }
      }
    }
    list Loopback {
      tailf:cli-allow-join-with-key;
      key "name";
      leaf name {
        type uint16;
      }
      uses loopback-settings-grouping;
      uses arp-timeout-grouping;
    }
    list Management {
      tailf:cli-allow-join-with-key;
      key "name";
      leaf name {
        type string;
      }
      uses mgmt-settings-grouping;
      container ipv6 {
        uses mgmt-settings-ipv6-grouping;
      }
      uses arp-timeout-grouping;
    }
    list Port-Channel {
      tailf:cli-allow-join-with-key;
      key "name";
      leaf name {
        type string;
      }
      leaf comment {
        tailf:cli-multi-value;
        type string;
      }
      uses port-channel-settings-grouping;
      uses interface-service-policy-grouping;
      uses arp-timeout-grouping;
      uses interface-vrrp-grouping;
    }
    list Vlan {
      tailf:cli-allow-join-with-key;
      key "id";
      leaf id {
        type uint16;
      }
      leaf name {
        type string;
      }
      container bfd {
        container interval {
          tailf:cli-compact-syntax;
          tailf:cli-sequence-commands {
            tailf:cli-reset-siblings;
          }
          leaf rate {
            tailf:cli-drop-node-name;
            type uint16;
          }
          leaf min-rx {
            type uint16;
          }
          leaf multiplier {
            type uint8;
          }
        }
      }
      uses mgmt-settings-grouping {
        augment "ip/address" {
          leaf virtual {
            type tailf:ipv4-address-and-prefix-length;
          }
        }
        augment "ip/pim" {
          leaf query-interval {
            type uint16;
          }
          leaf bfd-instance {
            type empty;
          }
        }
        augment "ip" {
          uses interface-ip-nat-grouping;
        }
        augment "ip/igmp" {
          container host-proxy {
            list group {
              tailf:cli-drop-node-name;
              tailf:cli-suppress-mode;
              key "address";
              leaf address {
                type inet:ipv4-address;
              }
              leaf disable {
                type empty;
              }
            }
          }
        }
      }
      container ospfv3 {
        container ipv6 {
          leaf area {
            type ospf-area-type;
          }
        }
        leaf passive-interface {
          type boolean;
        }
      }
      container pim {
        container ipv4 {
          container local-interface {
            uses interface-grouping;
          }
          container hello {
            leaf interval {
              type uint16;
            }
          }
          leaf sparse-mode {
            type empty;
          }
          leaf dr-priority {
            type uint32;
          }
          leaf bfd {
            type empty;
          }
        }
      }
      container rip {
        container authentication {
          container algorithm {
            container md5 {
              container key-id {
                tailf:cli-flatten-container;
                tailf:cli-sequence-commands;
                tailf:cli-compact-syntax;
                leaf value {
                  tailf:cli-drop-node-name;
                  type uint8;
                }
                container key {
                  tailf:cli-flatten-container;
                  tailf:cli-compact-syntax;
                  tailf:cli-sequence-commands;
                  leaf encryption {
                    tailf:cli-drop-node-name;
                    tailf:cli-optional-in-sequence;
                    type enumeration {
                      enum 0;
                      enum 7;
                    }
                  }
                  leaf password {
                    tailf:cli-drop-node-name;
                    type string;
                  }
                }
              }
            }
          }
        }
      }
      container ipv6 {
        uses mgmt-settings-ipv6-grouping;
        container address-virtual {
          tailf:cli-drop-node-name;
          container address {
            list virtual {
              tailf:cli-suppress-mode;
              key "prefix";
              leaf prefix {
                type tailf:ipv6-address-and-prefix-length;
              }
            }
          }
        }
        container dhcp {
          container relay {
            list destination {
              tailf:cli-suppress-mode;
              key "address";
              leaf address {
                type inet:ipv6-address;
              }
            }
          }
        }
        list virtual-router {
          tailf:cli-suppress-mode;
          key "address";
          leaf address {
            tailf:cli-expose-key-name;
            type inet:ipv6-address;
          }
        }
      }
      uses interface-service-policy-grouping;
      uses arp-timeout-grouping;
    }
    list Vxlan {
      tailf:cli-allow-join-with-key;
      key "id";
      leaf id {
        type uint16;
      }
      leaf description {
        tailf:cli-multi-value;
        type string;
      }
      container telemetry {
        container inband {
          container profile {
            leaf vxlan {
              type string;
            }
          }
        }
      }
      leaf shutdown {
        type empty;
      }
      container vxlan {
        leaf learn-restrict {
          type enumeration {
            enum any;
            enum flood;
            enum vtep;
          }
        }
        container multicast {
          container routing {
            leaf ipv4 {
              type empty;
            }
          }
        }
        leaf multicast-group {
          type inet:ipv4-address;
        }
        container source-interface {
          leaf Loopback {
            tailf:cli-drop-node-name;
            type string;
          }
        }
        leaf udp-port {
          type uint16;
        }
        container virtual-router {
          container encapsulation {
            container mac-address {
              choice encapsulation-mac-address-choice {
                leaf mlag-system-id {
                  type empty;
                }
                leaf ethernet-address {
                  tailf:cli-drop-node-name;
                  type string;
                }
              }
            }
          }
        }
        container vlan {
          list vlan-vni {
            tailf:cli-drop-node-name;
            tailf:cli-compact-syntax;
            tailf:cli-suppress-mode;
            tailf:cli-delete-when-empty;
            key "id";
            leaf id {
              type uint16;
            }
            leaf vni {
              mandatory true;
              type uint32;
            }
          }
          list vlan-list {
            tailf:cli-drop-node-name;
            tailf:cli-suppress-mode;
            tailf:cli-range-list-syntax;
            tailf:cli-delete-when-empty;
            key "id";
            leaf id {
              type uint16;
            }
            container flood {
              leaf-list vtep {
                tailf:cli-flat-list-syntax;
                type inet:ipv4-address;
              }
            }
            container multicast {
              leaf group {
                type inet:ipv4-address;
              }
            }
          }
        }
        list vrf {
          tailf:cli-suppress-mode;
          tailf:cli-delete-when-empty;
          key "name";
          leaf name {
            type string;
          }
          container multicast {
            container group {
              leaf ip {
                tailf:cli-drop-node-name;
                type inet:ipv4-address;
              }
              list overlay {
                tailf:cli-suppress-mode;
                tailf:cli-compact-syntax;
                tailf:cli-sequence-commands {
                  tailf:cli-reset-siblings;
                }
                key "address";
                leaf address {
                  type inet:ipv4-address;
                }
                leaf encap {
                  type inet:ipv4-address;
                }
                leaf immediate {
                  type empty;
                }
              }
            }
          }
          leaf vni {
            type uint32;
          }
        }
      }
    }
    container defaults {
      tailf:cli-add-mode;
      leaf mtu {
        type uint32;
      }
    }
  }
  container directflow {
    tailf:cli-add-mode;
    leaf shutdown {
      type boolean;
    }
    list flow {
      key "name";
      leaf name {
        type string;
      }
      container match {
        container input {
          uses directflow-interface-grouping;
        }
        container destination {
          leaf mac {
            type string;
          }
        }
      }
      container action {
        container output {
          uses directflow-interface-grouping;
        }
      }
    }
  }
  container ipv6 {
    uses access-list-grouping;
    container dhcp {
      container relay {
        uses access-group-grouping;
      }
    }
    container hardware {
      container fib {
        container optimize {
          leaf prefix-length {
            tailf:cli-multi-value;
            type string;
          }
        }
      }
    }
    container prefix-list {
      list prefixes {
        tailf:cli-drop-node-name;
        key "name";
        leaf name {
          type string;
        }
        leaf comment {
          tailf:cli-multi-value;
          type string;
        }
        list seq {
          tailf:cli-suppress-mode;
          key "no";
          leaf no {
            type uint32;
          }
          container deny {
            tailf:cli-compact-syntax;
            tailf:cli-flatten-container;
            tailf:cli-sequence-commands {
              tailf:cli-reset-all-siblings;
            }
            leaf ip {
              tailf:cli-drop-node-name;
              type inet:ipv6-prefix;
            }
            choice gele-eq-choice {
              container ge-le {
                tailf:cli-drop-node-name;
                tailf:cli-compact-syntax;
                tailf:cli-flatten-container;
                leaf ge {
                  tailf:cli-break-sequence-commands;
                  type uint8;
                }
                leaf le {
                  type uint8;
                }
              }
              leaf eq {
                type uint8;
              }
            }
          }
          container permit {
            tailf:cli-compact-syntax;
            tailf:cli-flatten-container;
            tailf:cli-sequence-commands {
              tailf:cli-reset-all-siblings;
            }
            leaf ip {
              tailf:cli-drop-node-name;
              type inet:ipv6-prefix;
            }
            choice gele-eq-choice {
              container ge-le {
                tailf:cli-drop-node-name;
                tailf:cli-compact-syntax;
                tailf:cli-flatten-container;
                leaf ge {
                  tailf:cli-break-sequence-commands;
                  type uint8;
                }
                leaf le {
                  type uint8;
                }
              }
              leaf eq {
                type uint8;
              }
            }
          }
        }
      }
    }
    list host {
      key "name ip";
      leaf name {
        type string;
      }
      leaf ip {
        type inet:ipv6-address;
      }
    }
    container route {
      list vrf {
        tailf:cli-suppress-mode;
        tailf:cli-delete-when-empty;
        tailf:cli-compact-syntax;
        key "name";
        leaf name {
          type string;
        }
        uses ipv6-route-grouping;
      }
      container no-vrf {
        tailf:cli-drop-node-name;
        uses ipv6-route-grouping;
      }
    }
    container unicast-routing {
      presence "true";
      leaf vrf {
        type string;
      }
    }
  }
  container logging {
    list host {
      tailf:cli-suppress-mode;
      tailf:cli-compact-syntax;
      key "id";
      leaf id {
        type string;
      }
      uses logging-host-grouping;
    }
    leaf relogging-interval {
      type uint16;
    }
    container buffered {
      tailf:cli-compact-syntax;
      presence "true";
      leaf size {
        tailf:cli-drop-node-name;
        type uint32;
      }
      uses logging-severity-grouping;
    }
    leaf trap {
      type logging-level-type;
    }
    leaf console {
      type logging-level-type;
    }
    container monitor {
      presence "true";
      uses logging-severity-grouping;
    }
    container format {
      leaf hostname {
        type enumeration {
          enum fqdn;
        }
      }
      container timestamp {
        choice logging-format-timestamp-choice {
          leaf high-resolution {
            type empty;
          }
          container traditional {
            tailf:cli-compact-syntax;
            leaf timezone {
              type empty;
            }
            leaf year {
              type empty;
            }
          }
        }
      }
      leaf sequence-numbers {
        type empty;
      }
    }
    leaf facility {
      type enumeration {
        enum auth;
        enum cron;
        enum daemon;
        enum kern;
        enum local0;
        enum local1;
        enum local2;
        enum local3;
        enum local4;
        enum local5;
        enum local6;
        enum local7;
        enum lpr;
        enum mail;
        enum news;
        enum sys10;
        enum sys11;
        enum sys12;
        enum sys13;
        enum sys14;
        enum sys9;
        enum syslog;
        enum user;
        enum uucp;
      }
    }
    container source-interface {
      uses interface-grouping;
    }
    list vrf {
      tailf:cli-suppress-mode;
      tailf:cli-compact-syntax;
      key "name";
      leaf name {
        type string;
      }
      list host {
        tailf:cli-suppress-mode;
        tailf:cli-compact-syntax;
        key "hostname";
        leaf hostname {
          type string;
        }
        uses logging-host-grouping;
      }
      container source-interface {
        uses interface-grouping;
      }
    }
  }
  container dns {
    leaf domain {
      type string;
    }
  }
  container sflow {
    container extension {
      leaf bgp {
        type empty;
      }
    }
    grouping sflow-destination-grouping {
      list destination {
        tailf:cli-suppress-mode;
        tailf:cli-compact-syntax;
        key "id";
        leaf id {
          type string;
        }
        leaf port {
          tailf:cli-drop-node-name;
          type uint16;
        }
      }
    }

    leaf polling-interval {
      type uint16;
    }
    container sample {
      choice sflow-sample-choice {
        leaf dangerous {
          type uint32;
        }
        leaf rate {
          tailf:cli-drop-node-name;
          type uint32;
        }
      }
      container input {
        leaf subinterface {
          type empty;
        }
      }
      leaf rewrite {
        type enumeration {
          enum dscp;
        }
      }
    }
    grouping sflow-source-grouping {
      leaf source {
        type string;
      }
      container source-interface {
        uses interface-grouping;
      }
    }

    uses sflow-destination-grouping;
    uses sflow-source-grouping;
    container vrf {
      uses sflow-destination-grouping;
      uses sflow-source-grouping;
      list vrf {
        tailf:cli-drop-node-name;
        tailf:cli-suppress-mode;
        key "name";
        leaf name {
          type string;
        }
        uses sflow-destination-grouping;
        uses sflow-source-grouping;
      }
    }
    leaf run {
      type empty;
    }
  }
  container l2-protocol {
    tailf:cli-add-mode;
    container forwarding {
      list profile {
        key "name";
        leaf name {
          type string;
        }
        container lacp {
          leaf forward {
            type empty;
          }
        }
        container lldp {
          leaf forward {
            type empty;
          }
        }
        container stp {
          leaf forward {
            type empty;
          }
        }
      }
    }
  }
  container queue-monitor {
    container default-length {
      tailf:cli-drop-node-name;
      leaf length {
        type boolean;
      }
    }
    container length {
      leaf update-interval {
        type uint32;
      }
      leaf notifying {
        type empty;
      }
    }
    container streaming {
      tailf:cli-add-mode;
      leaf shutdown {
        type boolean;
      }
      container ip {
        uses access-group-grouping;
      }
      container ipv6 {
        uses access-group-grouping;
      }
    }
  }
  container radius-server {
    leaf deadtime {
      type uint16;
    }
    leaf directed-request {
      type empty;
    }
    list host {
      tailf:cli-suppress-mode;
      tailf:cli-delete-when-empty;
      tailf:cli-compact-syntax;
      ordered-by user;
      key "id";
      leaf id {
        type union {
          type inet:ip-address;
          type string;
        }
      }
      leaf auth-port {
        type uint16;
      }
      leaf acct-port {
        type uint16;
      }
      container key {
        tailf:cli-flatten-container;
        tailf:cli-compact-syntax;
        tailf:cli-sequence-commands;
        leaf encryption {
          tailf:cli-drop-node-name;
          tailf:cli-optional-in-sequence;
          type enumeration {
            enum 0;
            enum 7;
          }
        }
        leaf password {
          tailf:cli-drop-node-name;
          type string;
        }
      }
      leaf authentication {
        type empty;
      }
      leaf accounting {
        type empty;
      }
      leaf retransmit {
        type uint8;
      }
      leaf timeout {
        type uint8;
      }
    }
    container key {
      tailf:cli-compact-syntax;
      tailf:cli-sequence-commands;
      leaf encryption {
        tailf:cli-drop-node-name;
        tailf:cli-optional-in-sequence;
        type enumeration {
          enum 0;
          enum 7;
        }
      }
      leaf password {
        tailf:cli-drop-node-name;
        type string;
      }
    }
    leaf retransmit {
      type uint8;
    }
    leaf timeout {
      type uint16;
    }
  }
  container snmp-server {
    leaf chassis-id {
      type string;
    }
    container enable {
      choice enable-choice {
        list traps {
          tailf:cli-suppress-mode;
          tailf:cli-delete-when-empty;
          key "name";
          leaf name {
            tailf:cli-multi-word-key;
            type string;
          }
          leaf prefix {
            tailf:cli-drop-node-name;
            tailf:cli-prefix-key;
            type enumeration {
              enum enable;
              enum no;
              enum default;
            }
          }
        }
      }
    }
    container engineID {
      leaf local {
        type string;
      }
    }
    list view {
      tailf:cli-suppress-mode;
      tailf:cli-delete-when-empty;
      tailf:cli-compact-syntax;
      key "name mib";
      leaf name {
        type string;
      }
      leaf mib {
        type string;
      }
      leaf included-excluded {
        tailf:cli-drop-node-name;
        type enumeration {
          enum excluded;
          enum included;
        }
      }
    }
    list user {
      tailf:cli-suppress-mode;
      tailf:cli-delete-when-empty;
      tailf:cli-compact-syntax;
      tailf:cli-sequence-commands {
        tailf:cli-reset-siblings;
      }
      key "name";
      leaf name {
        type string;
      }
      leaf group {
        tailf:cli-drop-node-name;
        type string;
      }
      uses snmp-server-user-grouping;
    }
    list community {
      tailf:cli-suppress-mode;
      tailf:cli-compact-syntax;
      key "id";
      leaf id {
        type string;
      }
      leaf mode {
        tailf:cli-drop-node-name;
        type enumeration {
          enum ro;
          enum rw;
          enum view;
        }
      }
      leaf ipv6 {
        type string;
      }
      leaf access-list {
        tailf:cli-drop-node-name;
        type string;
      }
    }
    list group {
      tailf:cli-suppress-mode;
      tailf:cli-delete-when-empty;
      tailf:cli-compact-syntax;
      tailf:cli-sequence-commands;
      key "name";
      leaf name {
        type string;
      }
      choice security-model {
        container v1 {
          tailf:cli-compact-syntax;
          tailf:cli-sequence-commands {
            tailf:cli-reset-siblings;
          }
          uses snmp-server-group-grouping;
        }
        container v2c {
          tailf:cli-compact-syntax;
          tailf:cli-sequence-commands {
            tailf:cli-reset-siblings;
          }
          uses snmp-server-group-grouping;
        }
        container v3 {
          tailf:cli-compact-syntax;
          tailf:cli-sequence-commands {
            tailf:cli-reset-siblings;
          }
          leaf security-level {
            tailf:cli-drop-node-name;
            type enumeration {
              enum auth;
              enum noauth;
              enum priv;
            }
          }
          uses snmp-server-group-grouping;
        }
      }
    }
    leaf contact {
      tailf:cli-multi-value;
      type string;
    }
    container source-interface {
      uses interface-grouping;
    }
    container local-interface {
      uses interface-grouping;
    }
    container ipv4 {
      leaf access-list {
        type string;
      }
      container access-list-vrf {
        tailf:cli-drop-node-name;
        list access-list {
          tailf:cli-suppress-mode;
          tailf:cli-sequence-commands;
          key "vrf";
          leaf name {
            tailf:cli-drop-node-name;
            tailf:cli-prefix-key;
            type string;
          }
          leaf vrf {
            tailf:cli-expose-key-name;
            type string;
          }
        }
      }
    }
    list host {
      tailf:cli-suppress-mode;
      tailf:cli-delete-when-empty;
      tailf:cli-compact-syntax;
      tailf:cli-sequence-commands {
        tailf:cli-reset-all-siblings;
      }
      key "ip-address";
      leaf ip-address {
        tailf:cli-case-sensitive;
        type host-type;
      }
      leaf message-type {
        tailf:cli-optional-in-sequence;
        tailf:cli-drop-node-name;
        type enumeration {
          enum informs;
          enum traps;
        }
      }
      container version {
        tailf:cli-optional-in-sequence;
        tailf:cli-flatten-container;
        tailf:cli-compact-syntax;
        leaf version {
          tailf:cli-drop-node-name;
          type enumeration {
            enum 1;
            enum 2c;
            enum 3;
          }
        }
        leaf security-level {
          tailf:cli-drop-node-name;
          type enumeration {
            enum auth;
            enum noauth;
            enum priv;
          }
        }
      }
      leaf community-string {
        tailf:cli-drop-node-name;
        type string;
      }
    }
    container host-vrf {
      tailf:cli-drop-node-name;
      list host {
        tailf:cli-suppress-mode;
        tailf:cli-delete-when-empty;
        tailf:cli-compact-syntax;
        key "ip-address vrf message-type";
        leaf ip-address {
          type inet:host;
        }
        leaf vrf {
          tailf:cli-expose-key-name;
          type string;
        }
        leaf message-type {
          type enumeration {
            enum informs;
            enum traps;
          }
        }
        list version {
          tailf:cli-suppress-mode;
          tailf:cli-compact-syntax;
          key "name community";
          leaf name {
            type enumeration {
              enum 1;
              enum 2c;
              enum 3;
            }
          }
          leaf community {
            type string;
          }
          list udp-port {
            tailf:cli-suppress-mode;
            tailf:cli-compact-syntax;
            key "port";
            leaf port {
              type uint16;
            }
            leaf security-level {
              tailf:cli-drop-node-name;
              type enumeration {
                enum auth;
                enum noauth;
                enum priv;
              }
            }
          }
          leaf security-level {
            tailf:cli-drop-node-name;
            tailf:cli-prefix-key {
              tailf:cli-before-key "2";
            }
            type enumeration {
              enum auth;
              enum noauth;
              enum priv;
            }
          }
        }
      }
    }
    leaf location {
      tailf:cli-multi-value;
      type string;
    }
    container vrf {
      list vrf-list {
        tailf:cli-drop-node-name;
        tailf:cli-suppress-mode;
        key "name";
        leaf name {
          type string;
        }
      }
      list vrf-local-interface-list {
        tailf:cli-drop-node-name;
        tailf:cli-suppress-mode;
        tailf:cli-delete-when-empty;
        key "name";
        leaf name {
          type string;
        }
        container local-interface {
          uses interface-grouping;
        }
      }
      leaf default {
        type boolean;
      }
    }
  }
  container no-spanning-tree {
    choice no-spanning-tree-vlan-choice {
      list vlan {
        tailf:cli-suppress-mode;
        tailf:cli-range-list-syntax;
        key "id";
        leaf id {
          type uint32;
        }
      }
      list vlan-id {
        tailf:cli-suppress-mode;
        tailf:cli-range-list-syntax;
        key "id";
        leaf id {
          type uint32;
        }
      }
    }
  }
  container spanning-tree {
    container edge-port {
      container bpduguard {
        leaf default {
          type empty;
        }
      }
      container bpdufilter {
        leaf default {
          type empty;
        }
      }
    }
    container guard {
      container loop {
        leaf default {
          type empty;
        }
      }
    }
    leaf mode {
      type enumeration {
        enum backup;
        enum mstp;
        enum none;
        enum rapid-pvst;
        enum rstp;
      }
    }
    container mst {
      container pvst {
        leaf border {
          type empty;
        }
      }
      list mst-instances {
        tailf:cli-drop-node-name;
        tailf:cli-suppress-mode;
        tailf:cli-range-list-syntax;
        key "instance";
        leaf instance {
          type uint16;
        }
        leaf priority {
          type uint16;
        }
      }
      container configuration {
        tailf:cli-add-mode;
        leaf name {
          type string;
        }
        leaf revision {
          type uint32;
        }
        list instance {
          tailf:cli-suppress-mode;
          tailf:cli-range-list-syntax;
          tailf:cli-sequence-commands;
          key "vlan";
          leaf instance-id {
            tailf:cli-drop-node-name;
            tailf:cli-prefix-key;
            type uint16;
          }
          leaf vlan {
            tailf:cli-expose-key-name;
            type uint16;
          }
        }
      }
    }
    container portfast {
      leaf bpdufilter {
        type enumeration {
          enum default;
        }
      }
      leaf bpduguard {
        type enumeration {
          enum default;
        }
      }
    }
    container vlan {
      list vlan-list {
        tailf:cli-drop-node-name;
        tailf:cli-suppress-mode;
        tailf:cli-range-list-syntax;
        key "id";
        leaf id {
          type uint32;
        }
        leaf priority {
          type uint32;
        }
      }
    }
    container vlan-id {
      list vlan-list {
        tailf:cli-drop-node-name;
        tailf:cli-suppress-mode;
        tailf:cli-range-list-syntax;
        key "id";
        leaf id {
          type uint32;
        }
        leaf priority {
          type uint32;
        }
      }
    }
  }
  container switch {
    leaf forwarding-mode {
      type enumeration {
        enum cut-through;
        enum store-and-forward;
      }
    }
  }
  container switchport {
    container default {
      leaf mode {
        type enumeration {
          enum access;
          enum routed;
        }
      }
    }
  }
  container service {
    container interface {
      container inactive {
        container port-id {
          container allocation {
            leaf disabled {
              type empty;
            }
          }
        }
      }
    }
    container unsupported-transceiver {
      tailf:cli-compact-syntax;
      tailf:cli-sequence-commands {
        tailf:cli-reset-siblings;
      }
      leaf licensee {
        tailf:cli-drop-node-name;
        type string;
      }
      leaf key {
        tailf:cli-drop-node-name;
        type string;
      }
    }
    container running-config {
      leaf timestamp {
        type empty;
      }
    }
    container routing {
      container protocols {
        leaf model {
          type enumeration {
            enum multi-agent;
            enum ribd;
          }
        }
      }
    }
  }
  container mlag {
    container configuration {
      tailf:cli-add-mode;
      leaf domain-id {
        type string;
      }
      container dual-primary {
        container detection {
          tailf:cli-compact-syntax;
          tailf:cli-sequence-commands;
          leaf delay {
            type uint32;
          }
          container action {
            tailf:cli-flatten-container;
            leaf errdisable {
              type enumeration {
                enum all-interfaces;
              }
            }
          }
        }
      }
      container heartbeat-interval {
        leaf disabled {
          type empty;
        }
        leaf values {
          tailf:cli-drop-node-name;
          type uint16;
        }
      }
      container local-interface {
        leaf Vlan {
          tailf:cli-allow-join-with-value;
          type uint16;
        }
      }
      container peer-address {
        leaf ip {
          tailf:cli-drop-node-name;
          type inet:ipv4-address;
        }
        container heartbeat {
          tailf:cli-compact-syntax;
          tailf:cli-sequence-commands {
            tailf:cli-reset-siblings;
          }
          leaf ip {
            tailf:cli-drop-node-name;
            type inet:ipv4-address;
          }
          leaf vrf {
            type string;
          }
        }
      }
      container peer-link {
        leaf Ethernet {
          tailf:cli-allow-join-with-value;
          type string;
        }
        leaf Port-Channel {
          tailf:cli-allow-join-with-value;
          type string;
        }
      }
      container reload-delay {
        leaf infinity {
          type empty;
        }
        container mlag {
          leaf infinity {
            type empty;
          }
          leaf seconds {
            tailf:cli-drop-node-name;
            type uint32;
          }
        }
        container non-mlag {
          leaf infinity {
            type empty;
          }
          leaf seconds {
            tailf:cli-drop-node-name;
            type uint32;
          }
        }
        leaf seconds {
          tailf:cli-drop-node-name;
          type uint32;
        }
      }
      leaf shutdown {
        type empty;
      }
    }
  }
  leaf prompt {
    type string;
  }
  container qos {
    tailf:cli-compact-syntax;
    container map {
      tailf:cli-compact-syntax;
      list cos {
        tailf:cli-range-list-syntax;
        tailf:cli-suppress-mode;
        tailf:cli-delete-when-empty;
        key "name";
        leaf name {
          type uint8;
        }
        container to {
          leaf traffic-class {
            type uint8;
          }
        }
      }
      list dscp {
        tailf:cli-range-list-syntax;
        tailf:cli-suppress-mode;
        tailf:cli-delete-when-empty;
        key "name";
        leaf name {
          type uint8;
        }
        container to {
          leaf traffic-class {
            type uint8;
          }
        }
      }
    }
    list profile {
      key "name";
      leaf name {
        type string;
      }
      container qos {
        leaf cos {
          type uint8;
        }
      }
      container shape {
        container rate {
          choice qos-profile-choice {
            container rate-percent {
              tailf:cli-drop-node-name;
              tailf:cli-compact-syntax;
              leaf rate {
                tailf:cli-drop-node-name;
                type uint8;
              }
              leaf percent {
                type empty;
              }
            }
            container rate-kbps {
              tailf:cli-drop-node-name;
              tailf:cli-compact-syntax;
              leaf rate {
                tailf:cli-drop-node-name;
                type uint32;
              }
            }
          }
        }
      }
    }
    container rewrite {
      leaf cos {
        type boolean;
      }
      leaf dscp {
        type empty;
      }
    }
  }
  container traffic-policies {
    tailf:cli-add-mode;
    container cpu {
      tailf:cli-add-mode;
      tailf:cli-compact-syntax;
      tailf:cli-sequence-commands;
      presence "true";
      leaf traffic-policy {
        tailf:cli-hide-in-submode;
        type string;
      }
      leaf vrf {
        tailf:cli-hide-in-submode;
        type enumeration {
          enum all;
        }
      }
      container enforcement {
        leaf management {
          type empty;
        }
      }
    }
    container field-set {
      list ipv4 {
        key "prefix";
        leaf prefix {
          tailf:cli-expose-key-name;
          type string;
        }
        leaf-list prefixes {
          tailf:cli-drop-node-name;
          tailf:cli-flat-list-syntax;
          type inet:ipv4-prefix;
        }
      }
      list ipv6 {
        key "prefix";
        leaf prefix {
          tailf:cli-expose-key-name;
          type string;
        }
        leaf-list prefixes {
          tailf:cli-drop-node-name;
          tailf:cli-flat-list-syntax;
          type inet:ipv6-prefix;
        }
      }
    }
    list traffic-policy {
      key "name";
      leaf name {
        type string;
      }
      list match {
        tailf:cli-delete-when-empty;
        tailf:cli-sequence-commands;
        key "name";
        leaf name {
          type string;
        }
        leaf proto {
          tailf:cli-drop-node-name;
          tailf:cli-hide-in-submode;
          type enumeration {
            enum ipv4;
            enum ipv6;
          }
        }
        container destination {
          tailf:cli-break-sequence-commands;
          container prefix {
            leaf-list field-set {
              tailf:cli-flat-list-syntax;
              type string;
            }
          }
        }
        container source {
          container prefix {
            leaf-list field-set {
              tailf:cli-flat-list-syntax;
              type string;
            }
          }
        }
        container protocol {
          container tcp {
            container source {
              list port {
                tailf:cli-suppress-mode;
                tailf:cli-delete-when-empty;
                key "name";
                leaf name {
                  tailf:cli-multi-word-key;
                  type string;
                }
                container destination {
                  leaf-list port {
                    tailf:cli-flat-list-syntax;
                    type string;
                  }
                }
              }
            }
          }
          container udp {
            container source {
              list port {
                tailf:cli-suppress-mode;
                tailf:cli-delete-when-empty;
                key "name";
                leaf name {
                  tailf:cli-multi-word-key;
                  type string;
                }
                container destination {
                  leaf-list port {
                    tailf:cli-flat-list-syntax;
                    type string;
                  }
                }
              }
            }
          }
          container icmp {
            presence "true";
            uses protocol-icmp-grouping;
          }
          container icmpv6 {
            presence "true";
            uses protocol-icmp-grouping;
          }
          container igmp {
            presence "true";
          }
          container neighbors {
            leaf bgp {
              type empty;
            }
          }
        }
        leaf-list ttl {
          tailf:cli-range-list-syntax;
          type uint16;
        }
        container actions {
          tailf:cli-add-mode;
          container count {
            presence "true";
            leaf name {
              tailf:cli-drop-node-name;
              type string;
            }
          }
          leaf drop {
            type empty;
          }
          container police {
            container rate {
              tailf:cli-compact-syntax;
              tailf:cli-sequence-commands {
                tailf:cli-reset-siblings;
              }
              leaf value {
                tailf:cli-drop-node-name;
                type uint64;
              }
              leaf units {
                tailf:cli-drop-node-name;
                type enumeration {
                  enum bps;
                  enum burst-size;
                  enum gbps;
                  enum kbps;
                  enum mbps;
                }
              }
            }
          }
        }
      }
    }
  }
}
