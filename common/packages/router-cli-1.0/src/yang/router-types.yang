submodule router-types {
  yang-version 1.1;
  belongs-to router {
    prefix r;
  }

  description
    "Common types used within router.";

  revision 2021-10-13 {
    description
      "YANG 1.1 compatible.";
  }
  revision 2008-11-04 {
    description
      "draft-ietf-netmod-yang-02 compatible.";
  }
  revision 2007-08-29 {
    description
      "Syntax fixes after pyang validation.";
  }
  revision 2007-06-08 {
    description
      "Initial revision.";
  }

  typedef prefixLengthIPv4 {
    type int32 {
      range "0..32";
    }
  }

  typedef prefixLengthIPv6 {
    type int32 {
      range "0..128";
    }
  }

  typedef interfaceName {
    type string {
      length "1..30";
      pattern "[A-Za-z][^/:.]*";
    }
  }

  typedef interfaceLogicalUnit {
    type int32 {
      range "0..9999";
    }
  }
}
