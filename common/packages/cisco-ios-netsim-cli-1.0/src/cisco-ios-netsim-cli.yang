module cisco-ios-netsim-cli {
  yang-version 1.1;
  namespace "http://tail-f.com/ns/ned-id/cisco-ios-netsim-cli";
  prefix cisco-ios-netsim-cli;

  import tailf-common {
    prefix tailf;
  }

  import tailf-ncs-ned {
    prefix ned;
  }

  identity cisco-ios-netsim-cli {
    tailf:abstract;
    base ned:cli-ned-id;
  }
}
