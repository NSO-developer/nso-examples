module cisco-ios-netsim-cli-1.0 {
  yang-version 1.1;
  namespace "http://tail-f.com/ns/ned-id/cisco-ios-netsim-cli-1.0";
  prefix cisco-ios-netsim-cli-1.0;

  import cisco-ios-netsim-cli {
    prefix family;
  }

  identity cisco-ios-netsim-cli-1.0 {
    base family:cisco-ios-netsim-cli;
  }
}
