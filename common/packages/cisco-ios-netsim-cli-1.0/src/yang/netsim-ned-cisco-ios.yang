module netsim-ned-cisco-ios {
  namespace "urn:ios";
  prefix ios;

  import tailf-common {
    prefix tailf;
  }
  import ietf-inet-types {
    prefix inet;
  }
  import ietf-yang-types {
    prefix yang;
  }

  revision 2026-03-25;

  typedef percentage-type {
    type uint8;
  }

  typedef ppp-auth-method {
    type enumeration {
      enum "chap";
      enum "eap";
      enum "ms-chap";
      enum "ms-chap-v2";
      enum "pap";
    }
  }

  typedef mac-address-type {
    type string;
  }

  typedef ios-ipv6-address-ORG {
    type string;
  }

  typedef ios-ipv6-address {
    type string;
  }

  typedef all-address {
    type union {
      type inet:ipv4-address;
      type inet:ipv6-address;
      type ios-ipv6-address;
    }
  }

  typedef ipv4-prefix {
    type tailf:ipv4-address-and-prefix-length;
  }

  typedef ipv6-prefix {
    type tailf:ipv6-address-and-prefix-length;
  }

  typedef rd-type {
    type string;
  }

  typedef vpn-id-type {
    type string;
  }

  typedef asn-ip-type {
    type string;
  }

  typedef hhmm-type {
    type string;
  }

  typedef weekday-type {
    type enumeration {
      enum "Mon";
      enum "Tue";
      enum "Wed";
      enum "Thu";
      enum "Fri";
      enum "Sat";
      enum "Sun";
    }
  }

  typedef month-type {
    type enumeration {
      enum "Jan";
      enum "Feb";
      enum "Mar";
      enum "Apr";
      enum "May";
      enum "Jun";
      enum "Jul";
      enum "Aug";
      enum "Sep";
      enum "Oct";
      enum "Nov";
      enum "Dec";
    }
  }

  typedef month-full-type {
    type enumeration {
      enum "January";
      enum "February";
      enum "March";
      enum "April";
      enum "May";
      enum "June";
      enum "July";
      enum "August";
      enum "September";
      enum "October";
      enum "November";
      enum "December";
    }
  }

  typedef std-acl-type {
    type union {
      type uint16;
      type uint16;
      type string;
    }
  }

  typedef ext-acl-type {
    type union {
      type uint16;
      type uint16;
      type string;
    }
  }

  typedef std-ip-acl-type {
    type union {
      type uint16;
      type uint16;
      type string;
    }
  }

  typedef base-acl-type {
    type union {
      type uint16;
      type string;
    }
  }

  typedef ip-acl-type {
    type union {
      type uint16;
      type string;
    }
  }

  typedef ext-ip-acl-type {
    type union {
      type uint16;
      type uint16;
      type string;
    }
  }

  typedef exp-ip-acl-type {
    type union {
      type uint16;
      type uint16;
      type string;
    }
  }

  typedef ip-nat-timeout-type {
    type union {
      type uint32;
      type enumeration {
        enum "never";
      }
    }
  }

  typedef ldp-discovery-address-type {
    type union {
      type enumeration {
        enum "interface" {
          tailf:code-name "ldp_interface";
        }
      }
      type inet:ipv4-address;
    }
  }

  typedef dscp-type {
    type union {
      type uint8;
      type enumeration {
        enum "af11" {
          value 10011;
        }
        enum "af12" {
          value 10012;
        }
        enum "af13" {
          value 10013;
        }
        enum "af21" {
          value 10021;
        }
        enum "af22" {
          value 10022;
        }
        enum "af23" {
          value 10023;
        }
        enum "af31" {
          value 10031;
        }
        enum "af32" {
          value 10032;
        }
        enum "af33" {
          value 10033;
        }
        enum "af41" {
          value 10041;
        }
        enum "af42" {
          value 10042;
        }
        enum "af43" {
          value 10043;
        }
        enum "cs1" {
          value 10001;
        }
        enum "cs2" {
          value 10002;
        }
        enum "cs3" {
          value 10003;
        }
        enum "cs4" {
          value 10004;
        }
        enum "cs5" {
          value 10005;
        }
        enum "cs6" {
          value 10006;
        }
        enum "cs7" {
          value 10007;
        }
        enum "default" {
          tailf:code-name "dscp_default";
          value 1000;
        }
        enum "dscp" {
          value 1001;
        }
        enum "ef" {
          value 1002;
        }
        enum "precedence" {
          value 1003;
        }
      }
    }
  }

  typedef precedence-type {
    type union {
      type uint8;
      type enumeration {
        enum "critical";
        enum "flash";
        enum "flash-override";
        enum "immediate";
        enum "internet" {
          tailf:code-name "prec_internet";
        }
        enum "network";
        enum "priority" {
          tailf:code-name "prec_priority";
        }
        enum "routine";
      }
    }
  }

  typedef cos_value-type {
    type union {
      type uint8;
      type enumeration {
        enum "cos" {
          value 1001;
        }
        enum "dscp" {
          value 1002;
        }
        enum "exp" {
          value 1003;
        }
        enum "precedence" {
          value 1004;
        }
      }
    }
  }

  typedef qos_value-type {
    type union {
      type uint8;
      type enumeration {
        enum "cos" {
          value 1001;
        }
        enum "dscp" {
          value 1002;
        }
        enum "exp" {
          value 1003;
        }
        enum "precedence" {
          value 1004;
        }
      }
    }
  }

  typedef exp_value-type {
    type union {
      type uint8;
      type enumeration {
        enum "cos" {
          value 1001;
        }
        enum "dscp" {
          value 1002;
        }
        enum "exp" {
          value 1003;
        }
        enum "precedence" {
          value 1004;
        }
      }
    }
  }

  typedef prec_value-type {
    type union {
      type uint8;
      type enumeration {
        enum "cos" {
          value 1001;
        }
        enum "dscp" {
          value 1002;
        }
        enum "exp" {
          value 1003;
        }
        enum "precedence" {
          value 1004;
        }
      }
    }
  }

  typedef redist-ospf-external-type {
    type enumeration {
      enum "1";
      enum "2";
    }
  }

  typedef ospf-area-type {
    type union {
      type uint32;
      type inet:ipv4-address;
    }
  }

  typedef ospf-metric-type {
    type uint32;
  }

  typedef limit-dc-non-dc-type {
    type union {
      type uint32;
      type enumeration {
        enum "disable";
      }
    }
  }

  typedef isis-level-type {
    type enumeration {
      enum "level-1";
      enum "level-1-2";
      enum "level-2";
    }
  }

  typedef logging-level-type {
    type union {
      type uint16;
      type enumeration {
        enum "alerts" {
          value 1;
        }
        enum "critical" {
          value 2;
        }
        enum "debugging" {
          value 7;
        }
        enum "emergencies" {
          value 0;
        }
        enum "errors" {
          value 3;
        }
        enum "informational" {
          value 6;
        }
        enum "notifications" {
          value 5;
        }
        enum "warnings" {
          value 4;
        }
      }
    }
  }

  typedef operator-type {
    type enumeration {
      enum "eq";
      enum "ge";
      enum "gt";
      enum "le";
      enum "lt";
      enum "ne";
    }
  }

  typedef police-packets-bytes-type {
    type enumeration {
      enum "packets";
      enum "bytes";
      enum "cells";
    }
  }

  typedef police-pps-bps-type {
    type enumeration {
      enum "pps";
      enum "bps";
      enum "cps";
    }
  }

  typedef police-bps-type {
    type uint64;
  }

  typedef police-burst-type {
    type uint64;
  }

  typedef aaa-authorization-name-type {
    type union {
      type enumeration {
        enum "default";
      }
      type string;
    }
  }

  typedef aaa-authentication-name-type {
    type union {
      type enumeration {
        enum "default";
      }
      type string;
    }
  }

  typedef aaa-accounting-name-type {
    type union {
      type enumeration {
        enum "default";
      }
      type string;
    }
  }

  typedef aaa-group-type {
    type union {
      type string;
      type enumeration {
        enum "ldap";
        enum "radius";
        enum "tacacs+";
      }
    }
  }

  typedef ipsec-window-size-type {
    type enumeration {
      enum "1024";
      enum "128";
      enum "256";
      enum "512";
      enum "64";
    }
  }

  typedef bgp-as-no-type {
    type union {
      type uint32;
      type string;
    }
  }

  typedef eigrp-as-no-type {
    type union {
      type uint16;
      type string;
    }
  }

  typedef l2protocol-type {
    type enumeration {
      enum "cdp";
      enum "dtp";
      enum "lacp";
      enum "stp";
      enum "vtp";
      enum "lldp";
      enum "pagp";
      enum "udld";
      enum "dot1x";
      enum "all";
      enum "elmi";
      enum "esmc";
      enum "loam";
      enum "mmrp";
      enum "mvrp";
      enum "ptppd";
      enum "R4";
      enum "R5";
      enum "R6";
      enum "R8";
      enum "R9";
      enum "RA";
      enum "RB";
      enum "RC";
      enum "RD";
      enum "RF";
    }
  }

  typedef cable-downstream-interleaver-depth-option {
    type enumeration {
      enum "I128-J1";
      enum "I128-J2";
      enum "I128-J3";
      enum "I128-J4";
      enum "I128-J5";
      enum "I128-J6";
      enum "I128-J7";
      enum "I128-J8";
      enum "I16-J8";
      enum "I32-J4";
      enum "I64-J2";
      enum "I8-J16";
    }
  }

  typedef object-group-service-icmp-type {
    type union {
      type uint16;
      type enumeration {
        enum "alternate-address";
        enum "conversion-error";
        enum "echo";
        enum "echo-reply";
        enum "information-reply";
        enum "information-request";
        enum "mask-reply";
        enum "mask-request";
        enum "mobile-redirect";
        enum "parameter-problem";
        enum "redirect";
        enum "router-advertisement";
        enum "router-solicitation";
        enum "source-quench";
        enum "time-exceeded";
        enum "timestamp-reply";
        enum "timestamp-request";
        enum "traceroute";
        enum "unreachable";
      }
    }
  }

  typedef object-group-service-tcp-type {
    type union {
      type uint16;
      type enumeration {
        enum "bgp";
        enum "chargen";
        enum "cmd";
        enum "connectedapps-plain";
        enum "connectedapps-tls";
        enum "daytime";
        enum "discard";
        enum "domain";
        enum "echo";
        enum "exec";
        enum "finger";
        enum "ftp";
        enum "ftp-data";
        enum "gopher";
        enum "hostname";
        enum "ident";
        enum "irc";
        enum "klogin";
        enum "kshell";
        enum "login";
        enum "lpd";
        enum "msrpc";
        enum "nntp";
        enum "pim-auto-rp";
        enum "pop2";
        enum "pop3";
        enum "smtp";
        enum "sunrpc";
        enum "syslog";
        enum "tacacs";
        enum "talk";
        enum "telnet";
        enum "time";
        enum "uucp";
        enum "whois";
        enum "www";
      }
    }
  }

  typedef object-group-service-udp-type {
    type union {
      type uint16;
      type enumeration {
        enum "biff";
        enum "bootpc";
        enum "discard";
        enum "dnsix";
        enum "domain";
        enum "echo";
        enum "isakmp";
        enum "mobile-ip";
        enum "nameserver";
        enum "netbios-dgm";
        enum "netbios-ns";
        enum "netbios-ss";
        enum "non500-isakmp";
        enum "ntp";
        enum "pim-auto-rp";
        enum "rip";
        enum "ripv6";
        enum "snmp";
        enum "snmptrap";
        enum "sunrpc";
        enum "syslog";
        enum "tacacs";
        enum "talk";
        enum "tftp";
        enum "time";
        enum "who";
        enum "xdmcp";
      }
    }
  }

  typedef object-group-service-tcp-udp-type {
    type union {
      type uint16;
      type enumeration {
        enum "discard";
        enum "domain";
        enum "echo";
        enum "pim-auto-rp";
        enum "sunrpc";
        enum "syslog";
        enum "tacacs";
        enum "talk";
      }
    }
  }

  typedef isakmp-pfs-type {
    type enumeration {
      enum "group1";
      enum "group14";
      enum "group15";
      enum "group16";
      enum "group19";
      enum "group2";
      enum "group20";
      enum "group21";
      enum "group24";
      enum "group5";
    }
  }

  typedef qam-modulation-type {
    type enumeration {
      enum "16-QAM";
      enum "64-QAM";
      enum "128-QAM";
      enum "256-QAM";
      enum "512-QAM";
      enum "1024-QAM";
      enum "2048-QAM";
      enum "4096-QAM";
    }
  }

  typedef qam-modulation-type9 {
    type enumeration {
      enum "16-QAM";
      enum "64-QAM";
      enum "128-QAM";
      enum "256-QAM";
      enum "512-QAM";
      enum "1024-QAM";
      enum "2048-QAM";
      enum "4096-QAM";
      enum "QPSK";
    }
  }

  typedef utd-category-type {
    type enumeration {
      enum "abortion";
      enum "abused-drugs";
      enum "adult-and-pornography";
      enum "alcohol-and-tobacco";
      enum "auctions";
      enum "bot-nets";
      enum "business-and-economy";
      enum "cdns";
      enum "cheating";
      enum "computer-and-internet-info";
      enum "computer-and-internet-security";
      enum "confirmed-spam-sources";
      enum "cult-and-occult";
      enum "dating";
      enum "dead-sites";
      enum "dynamic-content";
      enum "educational-institutions";
      enum "entertainment-and-arts";
      enum "fashion-and-beauty";
      enum "financial-services";
      enum "gambling";
      enum "games";
      enum "government";
      enum "gross";
      enum "hacking";
      enum "hate-and-racism";
      enum "health-and-medicine";
      enum "home";
      enum "hunting-and-fishing";
      enum "illegal";
      enum "image-and-video-search";
      enum "individual-stock-advice-and-tools";
      enum "internet-communications";
      enum "internet-portals";
      enum "job-search";
      enum "keyloggers-and-monitoring";
      enum "kids";
      enum "legal";
      enum "local-information";
      enum "malware-sites";
      enum "marijuana";
      enum "military";
      enum "motor-vehicles";
      enum "music";
      enum "news-and-media";
      enum "nudity";
      enum "online-greeting-cards";
      enum "online-personal-storage";
      enum "open-http-proxies";
      enum "p2p";
      enum "parked-sites";
      enum "pay-to-surf";
      enum "personal-sites-and-blogs";
      enum "philosophy-and-political-advocacy";
      enum "phishing-and-other-frauds";
      enum "private-ip-addresses";
      enum "proxy-avoid-and-anonymizers";
      enum "questionable";
      enum "real-estate";
      enum "recreation-and-hobbies";
      enum "reference-and-research";
      enum "religion";
      enum "search-engines";
      enum "sex-education";
      enum "shareware-and-freeware";
      enum "shopping";
      enum "social-network";
      enum "society";
      enum "spam-urls";
      enum "sports";
      enum "spyware-and-adware";
      enum "streaming-media";
      enum "swimsuits-and-intimate-apparel";
      enum "training-and-tools";
      enum "translation";
      enum "travel";
      enum "uncategorized";
      enum "unconfirmed-spam-sources";
      enum "violence";
      enum "weapons";
      enum "web-advertisements";
      enum "web-based-email";
      enum "web-hosting";
    }
  }

  typedef subjectname-type {
    type enumeration {
      enum "all";
      enum "commonname";
      enum "country";
      enum "email";
      enum "ipaddress";
      enum "locality";
      enum "organization";
      enum "organizationalunit";
      enum "postalcode";
      enum "serialnumber";
      enum "state";
      enum "streetaddress";
      enum "title";
      enum "unstructuredname";
    }
  }

  typedef snmp-traps-type {
    type enumeration {
      enum "aaa_server";
      enum "alarms";
      enum "atm";
      enum "bfd";
      enum "bgp";
      enum "bstun";
      enum "bulkstat";
      enum "cable";
      enum "call-home";
      enum "casa";
      enum "cef";
      enum "cnpd";
      enum "config";
      enum "config-copy";
      enum "config-ctid";
      enum "cpu";
      enum "dhcp";
      enum "dlsw";
      enum "ds1";
      enum "dsp";
      enum "dspu";
      enum "eigrp";
      enum "entity";
      enum "entity-diag";
      enum "entity-qfp";
      enum "entity-state";
      enum "envmon";
      enum "ethernet-cfm";
      enum "evc";
      enum "event-manager";
      enum "firewall";
      enum "flash";
      enum "flowmon";
      enum "frame-relay";
      enum "fru-ctrl";
      enum "gdoi";
      enum "hsrp";
      enum "iplocalpool";
      enum "ipmulticast";
      enum "ipsec";
      enum "ipsla";
      enum "isakmp";
      enum "isg-mib";
      enum "isis";
      enum "l2tun-pseudowire-status";
      enum "l2tun-session";
      enum "license";
      enum "mac-notification";
      enum "memory";
      enum "mpls-fast-reroute";
      enum "mpls-ldp";
      enum "mpls-traffic-eng";
      enum "mpls-vpn";
      enum "msdp";
      enum "mvpn";
      enum "nhrp";
      enum "ospf";
      enum "ospfv3";
      enum "pfr";
      enum "pim";
      enum "pw-vc";
      enum "resource-policy";
      enum "rf";
      enum "rsrb";
      enum "rsvp";
      enum "sdlc";
      enum "sdllc";
      enum "snmp";
      enum "sonet";
      enum "srp";
      enum "stun";
      enum "syslog";
      enum "trustsec-sxp";
      enum "tty";
      enum "voice";
      enum "vrfmib";
      enum "vrrp";
      enum "x25";
      enum "bridge";
      enum "rtr";
      enum "port-security";
      enum "vlan-membership";
      enum "vtp";
      enum "vlancreate";
      enum "vlandelete";
      enum "MAC-Notification";
      enum "cluster";
    }
  }

  typedef mpls-label-mode-type {
    type enumeration {
      enum "per-ce";
      enum "per-prefix";
      enum "per-vrf";
      enum "vrf-conn-aggr";
    }
  }

  typedef pm-class-type-control-event-type {
    type enumeration {
      enum "access-reject";
      enum "account-logoff";
      enum "account-logon";
      enum "acct-notification";
      enum "credit-exhausted";
      enum "dummy-event";
      enum "flow-timeout";
      enum "quota-depleted";
      enum "radius-timeout";
      enum "service-failed";
      enum "service-start";
      enum "service-stop";
      enum "session-default-service";
      enum "session-restart";
      enum "session-service-found";
      enum "session-start";
      enum "timed-policy-expiry";
    }
  }

  typedef netconf-yang-cia-log-level {
    type enumeration {
      enum "none";
      enum "error";
      enum "warning";
      enum "information";
      enum "debug";
    }
  }

  grouping description-grouping {
    leaf description {
      tailf:cli-multi-value;
      type string;
    }
  }

  grouping description-quote-grouping {
    leaf description {
      type string;
    }
  }

  grouping password-grouping {
    leaf type {
      tailf:cli-drop-node-name;
      tailf:cli-optional-in-sequence;
      type enumeration {
        enum "0";
        enum "5";
        enum "6";
        enum "7";
      }
    }
    leaf secret {
      tailf:cli-drop-node-name;
      type string;
    }
  }

  grouping crypto-key-grouping {
    leaf encryption {
      tailf:cli-drop-node-name;
      tailf:cli-optional-in-sequence;
      type enumeration {
        enum "0";
        enum "6";
        enum "7";
      }
    }
    leaf secret {
      tailf:cli-drop-node-name;
      type string;
    }
  }

  grouping interface-name-grouping {
    choice interface-choice {
      leaf Null {
        tailf:cli-allow-join-with-value;
        type uint8;
      }
      leaf Loopback {
        tailf:cli-allow-join-with-value;
        type string;
      }
      leaf VirtualPortGroup {
        tailf:cli-allow-join-with-value;
        type uint8;
      }
      leaf Embedded-Service-Engine {
        tailf:cli-allow-join-with-value;
        type string;
      }
      leaf Service-Engine {
        tailf:cli-allow-join-with-value;
        type string;
      }
      leaf Tunnel {
        tailf:cli-allow-join-with-value;
        type uint32;
      }
      leaf Port-channel {
        tailf:cli-allow-join-with-value;
        type uint32;
      }
      container Port-channel-subinterface {
        tailf:cli-drop-node-name;
        tailf:cli-flatten-container;
        tailf:cli-compact-syntax;
        leaf Port-channel {
          tailf:cli-allow-join-with-value;
          type string;
        }
      }
      leaf Multilink {
        tailf:cli-allow-join-with-value;
        type uint32;
      }
      leaf nve {
        tailf:cli-allow-join-with-value;
        type uint16;
      }
      leaf vmi {
        tailf:cli-allow-join-with-value;
        type uint32;
      }
      leaf MFR {
        tailf:cli-allow-join-with-value;
        type uint32;
      }
      container MFR-subinterface {
        tailf:cli-drop-node-name;
        tailf:cli-flatten-container;
        tailf:cli-compact-syntax;
        leaf MFR {
          tailf:cli-allow-join-with-value;
          type string;
        }
      }
      leaf BRI {
        tailf:cli-allow-join-with-value;
        type string;
      }
      leaf Ethernet-Internal {
        tailf:cli-allow-join-with-value;
        type string;
      }
      leaf Ethernet {
        tailf:cli-allow-join-with-value;
        type string;
      }
      leaf FastEthernet {
        tailf:cli-allow-join-with-value;
        type string;
      }
      leaf GigabitEthernet {
        tailf:cli-allow-join-with-value;
        type string;
      }
      leaf TwoGigabitEthernet {
        tailf:cli-allow-join-with-value;
        type string;
      }
      leaf FiveGigabitEthernet {
        tailf:cli-allow-join-with-value;
        type string;
      }
      leaf TenGigabitEthernet {
        tailf:cli-allow-join-with-value;
        type string;
      }
      leaf TwentyFiveGigE {
        tailf:cli-allow-join-with-value;
        type string;
      }
      leaf FortyGigabitEthernet {
        tailf:cli-allow-join-with-value;
        type string;
      }
      leaf FiftyGigE {
        tailf:cli-allow-join-with-value;
        type string;
      }
      leaf HundredGigE {
        tailf:cli-allow-join-with-value;
        type string;
      }
      leaf TwoHundredGigE {
        tailf:cli-allow-join-with-value;
        type string;
      }
      leaf FourHundredGigE {
        tailf:cli-allow-join-with-value;
        type string;
      }
      leaf AppGigabitEthernet {
        tailf:cli-allow-join-with-value;
        type string;
      }
      leaf mgmt {
        tailf:cli-allow-join-with-value;
        type uint8;
      }
      leaf Wlan-GigabitEthernet {
        tailf:cli-allow-join-with-value;
        type string;
      }
      leaf wlan-ap {
        tailf:cli-allow-join-with-value;
        type string;
      }
      leaf ISM {
        tailf:cli-allow-join-with-value;
        type string;
      }
      leaf Analysis-Module {
        tailf:cli-allow-join-with-value;
        type string;
      }
      leaf Integrated-Service-Engine {
        tailf:cli-allow-join-with-value;
        type string;
      }
      leaf ATM {
        tailf:cli-allow-join-with-value;
        type string;
      }
      leaf CEM {
        tailf:cli-allow-join-with-value;
        type string;
      }
      leaf CEM-ACR {
        tailf:cli-allow-join-with-value;
        type string;
      }
      leaf Vif {
        tailf:cli-allow-join-with-value;
        type uint32;
      }
      leaf BDI {
        tailf:cli-allow-join-with-value;
        type uint16;
      }
      leaf BVI {
        tailf:cli-allow-join-with-value;
        type string;
      }
      leaf Cable {
        tailf:cli-allow-join-with-value;
        type string;
      }
      leaf CMON-Tunnel {
        tailf:cli-allow-join-with-value;
        type string;
      }
      leaf Video {
        tailf:cli-allow-join-with-value;
        type string;
      }
      leaf Integrated-Cable {
        tailf:cli-allow-join-with-value;
        type string;
      }
      leaf Modular-Cable {
        tailf:cli-allow-join-with-value;
        type string;
      }
      leaf Wideband-Cable {
        tailf:cli-allow-join-with-value;
        type string;
      }
      leaf Dialer {
        tailf:cli-allow-join-with-value;
        type string;
      }
      leaf Bundle {
        tailf:cli-allow-join-with-value;
        type uint8;
      }
      container Bundle-subinterface {
        tailf:cli-drop-node-name;
        tailf:cli-flatten-container;
        tailf:cli-compact-syntax;
        leaf Bundle {
          tailf:cli-allow-join-with-value;
          type string;
        }
      }
      leaf Cellular {
        tailf:cli-allow-join-with-value;
        type string;
      }
      leaf Qam-red {
        tailf:cli-allow-join-with-value;
        type string;
      }
      leaf Asi {
        tailf:cli-allow-join-with-value;
        type string;
      }
      leaf Vlan {
        tailf:cli-allow-join-with-value;
        type uint16;
      }
      leaf Async {
        tailf:cli-allow-join-with-value;
        type string;
      }
      leaf Group-Async {
        tailf:cli-allow-join-with-value;
        type uint16;
      }
      leaf POS {
        tailf:cli-allow-join-with-value;
        type string;
      }
      leaf SM {
        tailf:cli-allow-join-with-value;
        type string;
      }
      leaf Serial {
        tailf:cli-allow-join-with-value;
        type string;
      }
      container Serial-subinterface {
        tailf:cli-drop-node-name;
        tailf:cli-flatten-container;
        tailf:cli-compact-syntax;
        leaf Serial {
          tailf:cli-allow-join-with-value;
          type string;
        }
      }
      leaf Virtual-Template {
        tailf:cli-allow-join-with-value;
        type uint16;
      }
      leaf Virtual-PPP {
        tailf:cli-allow-join-with-value;
        type uint32;
      }
      leaf pseudowire {
        tailf:cli-allow-join-with-value;
        type uint32;
      }
      leaf LISP {
        tailf:cli-allow-join-with-value;
        type uint16;
      }
      container LISP-subinterface {
        tailf:cli-drop-node-name;
        tailf:cli-flatten-container;
        tailf:cli-compact-syntax;
        leaf LISP {
          tailf:cli-allow-join-with-value;
          type string;
        }
      }
      leaf ToP {
        tailf:cli-allow-join-with-value;
        type string;
      }
      leaf Dot11Radio {
        tailf:cli-allow-join-with-value;
        type string;
      }
      leaf vasileft {
        tailf:cli-allow-join-with-value;
        type uint16;
      }
      leaf vasiright {
        tailf:cli-allow-join-with-value;
        type uint16;
      }
      leaf AppNav-Compress {
        tailf:cli-allow-join-with-value;
        type uint16;
      }
      leaf AppNav-UnCompress {
        tailf:cli-allow-join-with-value;
        type uint16;
      }
      leaf ucse {
        tailf:cli-allow-join-with-value;
        type string;
      }
      leaf GMPLS {
        tailf:cli-allow-join-with-value;
        type uint16;
      }
      container GMPLS-subinterface {
        tailf:cli-drop-node-name;
        tailf:cli-flatten-container;
        tailf:cli-compact-syntax;
        leaf GMPLS {
          tailf:cli-allow-join-with-value;
          type string;
        }
      }
    }
  }

  grouping interface-nodiff-name-grouping {
    choice interface-choice {
      leaf Null {
        tailf:cli-allow-join-with-value;
        type uint8;
      }
      leaf Loopback {
        tailf:cli-allow-join-with-value;
        type string;
      }
      leaf VirtualPortGroup {
        tailf:cli-allow-join-with-value;
        type uint8;
      }
      leaf Embedded-Service-Engine {
        tailf:cli-allow-join-with-value;
        type string;
      }
      leaf Service-Engine {
        tailf:cli-allow-join-with-value;
        type string;
      }
      leaf Tunnel {
        tailf:cli-allow-join-with-value;
        type uint32;
      }
      leaf Port-channel {
        tailf:cli-allow-join-with-value;
        type uint32;
      }
      container Port-channel-subinterface {
        tailf:cli-drop-node-name;
        tailf:cli-flatten-container;
        tailf:cli-compact-syntax;
        leaf Port-channel {
          tailf:cli-allow-join-with-value;
          type string;
        }
      }
      leaf Multilink {
        tailf:cli-allow-join-with-value;
        type uint32;
      }
      leaf nve {
        tailf:cli-allow-join-with-value;
        type uint16;
      }
      leaf vmi {
        tailf:cli-allow-join-with-value;
        type uint32;
      }
      leaf MFR {
        tailf:cli-allow-join-with-value;
        type uint32;
      }
      container MFR-subinterface {
        tailf:cli-drop-node-name;
        tailf:cli-flatten-container;
        tailf:cli-compact-syntax;
        leaf MFR {
          tailf:cli-allow-join-with-value;
          type string;
        }
      }
      leaf BRI {
        tailf:cli-allow-join-with-value;
        type string;
      }
      leaf Ethernet-Internal {
        tailf:cli-allow-join-with-value;
        type string;
      }
      leaf Ethernet {
        tailf:cli-allow-join-with-value;
        type string;
      }
      leaf FastEthernet {
        tailf:cli-allow-join-with-value;
        type string;
      }
      leaf GigabitEthernet {
        tailf:cli-allow-join-with-value;
        type string;
      }
      leaf TwoGigabitEthernet {
        tailf:cli-allow-join-with-value;
        type string;
      }
      leaf FiveGigabitEthernet {
        tailf:cli-allow-join-with-value;
        type string;
      }
      leaf TenGigabitEthernet {
        tailf:cli-allow-join-with-value;
        type string;
      }
      leaf TwentyFiveGigE {
        tailf:cli-allow-join-with-value;
        type string;
      }
      leaf FortyGigabitEthernet {
        tailf:cli-allow-join-with-value;
        type string;
      }
      leaf FiftyGigE {
        tailf:cli-allow-join-with-value;
        type string;
      }
      leaf HundredGigE {
        tailf:cli-allow-join-with-value;
        type string;
      }
      leaf TwoHundredGigE {
        tailf:cli-allow-join-with-value;
        type string;
      }
      leaf FourHundredGigE {
        tailf:cli-allow-join-with-value;
        type string;
      }
      leaf AppGigabitEthernet {
        tailf:cli-allow-join-with-value;
        type string;
      }
      leaf mgmt {
        tailf:cli-allow-join-with-value;
        type uint8;
      }
      leaf Wlan-GigabitEthernet {
        tailf:cli-allow-join-with-value;
        type string;
      }
      leaf wlan-ap {
        tailf:cli-allow-join-with-value;
        type string;
      }
      leaf ISM {
        tailf:cli-allow-join-with-value;
        type string;
      }
      leaf Analysis-Module {
        tailf:cli-allow-join-with-value;
        type string;
      }
      leaf Integrated-Service-Engine {
        tailf:cli-allow-join-with-value;
        type string;
      }
      leaf ATM {
        tailf:cli-allow-join-with-value;
        type string;
      }
      leaf CEM {
        tailf:cli-allow-join-with-value;
        type string;
      }
      leaf CEM-ACR {
        tailf:cli-allow-join-with-value;
        type string;
      }
      leaf Vif {
        tailf:cli-allow-join-with-value;
        type uint32;
      }
      leaf BDI {
        tailf:cli-allow-join-with-value;
        type uint16;
      }
      leaf BVI {
        tailf:cli-allow-join-with-value;
        type string;
      }
      leaf Cable {
        tailf:cli-allow-join-with-value;
        type string;
      }
      leaf CMON-Tunnel {
        tailf:cli-allow-join-with-value;
        type string;
      }
      leaf Video {
        tailf:cli-allow-join-with-value;
        type string;
      }
      leaf Integrated-Cable {
        tailf:cli-allow-join-with-value;
        type string;
      }
      leaf Modular-Cable {
        tailf:cli-allow-join-with-value;
        type string;
      }
      leaf Wideband-Cable {
        tailf:cli-allow-join-with-value;
        type string;
      }
      leaf Dialer {
        tailf:cli-allow-join-with-value;
        type string;
      }
      leaf Bundle {
        tailf:cli-allow-join-with-value;
        type uint8;
      }
      container Bundle-subinterface {
        tailf:cli-drop-node-name;
        tailf:cli-flatten-container;
        tailf:cli-compact-syntax;
        leaf Bundle {
          tailf:cli-allow-join-with-value;
          type string;
        }
      }
      leaf Cellular {
        tailf:cli-allow-join-with-value;
        type string;
      }
      leaf Qam-red {
        tailf:cli-allow-join-with-value;
        type string;
      }
      leaf Asi {
        tailf:cli-allow-join-with-value;
        type string;
      }
      leaf Vlan {
        tailf:cli-allow-join-with-value;
        type uint16;
      }
      leaf Async {
        tailf:cli-allow-join-with-value;
        type string;
      }
      leaf Group-Async {
        tailf:cli-allow-join-with-value;
        type uint16;
      }
      leaf POS {
        tailf:cli-allow-join-with-value;
        type string;
      }
      leaf SM {
        tailf:cli-allow-join-with-value;
        type string;
      }
      leaf Serial {
        tailf:cli-allow-join-with-value;
        type string;
      }
      container Serial-subinterface {
        tailf:cli-drop-node-name;
        tailf:cli-flatten-container;
        tailf:cli-compact-syntax;
        leaf Serial {
          tailf:cli-allow-join-with-value;
          type string;
        }
      }
      leaf Virtual-Template {
        tailf:cli-allow-join-with-value;
        type uint16;
      }
      leaf Virtual-PPP {
        tailf:cli-allow-join-with-value;
        type uint32;
      }
      leaf pseudowire {
        tailf:cli-allow-join-with-value;
        type uint32;
      }
      leaf LISP {
        tailf:cli-allow-join-with-value;
        type uint16;
      }
      container LISP-subinterface {
        tailf:cli-drop-node-name;
        tailf:cli-flatten-container;
        tailf:cli-compact-syntax;
        leaf LISP {
          tailf:cli-allow-join-with-value;
          type string;
        }
      }
      leaf ToP {
        tailf:cli-allow-join-with-value;
        type string;
      }
      leaf Dot11Radio {
        tailf:cli-allow-join-with-value;
        type string;
      }
      leaf vasileft {
        tailf:cli-allow-join-with-value;
        type uint16;
      }
      leaf vasiright {
        tailf:cli-allow-join-with-value;
        type uint16;
      }
      leaf AppNav-Compress {
        tailf:cli-allow-join-with-value;
        type uint16;
      }
      leaf AppNav-UnCompress {
        tailf:cli-allow-join-with-value;
        type uint16;
      }
      leaf ucse {
        tailf:cli-allow-join-with-value;
        type string;
      }
      leaf GMPLS {
        tailf:cli-allow-join-with-value;
        type uint16;
      }
      container GMPLS-subinterface {
        tailf:cli-drop-node-name;
        tailf:cli-flatten-container;
        tailf:cli-compact-syntax;
        leaf GMPLS {
          tailf:cli-allow-join-with-value;
          type string;
        }
      }
    }
  }

  grouping service-policy-grouping {
    leaf output {
      type string;
    }
    leaf input {
      type string;
    }
  }

  grouping police-action-transmit-grouping {
    leaf transmit {
      type empty;
    }
  }

  grouping police-action-drop-grouping {
    leaf drop {
      type empty;
    }
  }

  grouping police-conform-action-grouping {
    container conform-action {
      tailf:cli-flatten-container;
      choice conform-action-choice {
        leaf set-clp-transmit {
          type empty;
        }
        leaf set-cos-transmit {
          type cos_value-type;
        }
        leaf set-discard-class-transmit {
          type uint8;
        }
        leaf set-dscp-transmit {
          type dscp-type;
        }
        leaf set-frde-transmit {
          type empty;
        }
        leaf set-mpls-exp-imposition-transmit {
          type exp_value-type;
        }
        leaf set-mpls-exp-topmost-transmit {
          type exp_value-type;
        }
        leaf set-prec-transmit {
          type prec_value-type;
        }
        leaf set-qos-transmit {
          type qos_value-type;
        }
        leaf transmit {
          type empty;
        }
        leaf drop {
          type empty;
        }
      }
    }
    leaf table {
      tailf:cli-optional-in-sequence;
      type string;
    }
  }

  grouping police-exceed-action-grouping {
    container exceed-action {
      tailf:cli-flatten-container;
      choice exceed-action-choice {
        leaf dscp {
          type dscp-type;
        }
        leaf set-clp-transmit {
          type empty;
        }
        leaf set-cos-transmit {
          type cos_value-type;
        }
        leaf set-discard-class-transmit {
          type uint8;
        }
        leaf set-dscp-transmit {
          type dscp-type;
        }
        leaf set-frde-transmit {
          type empty;
        }
        leaf set-mpls-exp-imposition-transmit {
          type exp_value-type;
        }
        leaf set-mpls-exp-topmost-transmit {
          type exp_value-type;
        }
        leaf set-prec-transmit {
          type prec_value-type;
        }
        leaf set-qos-transmit {
          type qos_value-type;
        }
        leaf transmit {
          type empty;
        }
        leaf drop {
          type empty;
        }
        leaf policed-dscp-transmit {
          type empty;
        }
      }
    }
  }

  grouping police-violate-action-grouping {
    container violate-action {
      tailf:cli-flatten-container;
      choice violate-action-choice {
        leaf set-clp-transmit {
          type empty;
        }
        leaf set-cos-transmit {
          type cos_value-type;
        }
        leaf set-discard-class-transmit {
          type uint8;
        }
        leaf set-dscp-transmit {
          type dscp-type;
        }
        leaf set-frde-transmit {
          type empty;
        }
        leaf set-mpls-exp-imposition-transmit {
          type exp_value-type;
        }
        leaf set-mpls-exp-topmost-transmit {
          type exp_value-type;
        }
        leaf set-prec-transmit {
          type prec_value-type;
        }
        leaf set-qos-transmit {
          type qos_value-type;
        }
        leaf transmit {
          type empty;
        }
        leaf drop {
          type empty;
        }
      }
    }
  }

  grouping police-multiple-conform-action-grouping {
    container conform-set-clp-transmit {
      tailf:cli-no-keyword;
      tailf:cli-drop-node-name;
      tailf:cli-flatten-container;
      container conform-action {
        tailf:cli-flatten-container;
        leaf set-clp-transmit {
          type empty;
        }
      }
    }
    choice conform-set-cos-transmit-choice {
      container conform-set-cos-transmit {
        tailf:cli-no-keyword;
        tailf:cli-drop-node-name;
        tailf:cli-flatten-container;
        container conform-action {
          tailf:cli-flatten-container;
          leaf set-cos-transmit {
            type cos_value-type;
          }
        }
      }
      container conform-set-cos-transmit-table {
        tailf:cli-no-keyword;
        tailf:cli-drop-node-name;
        tailf:cli-flatten-container;
        container conform-action {
          tailf:cli-flatten-container;
          tailf:cli-compact-syntax;
          tailf:cli-sequence-commands;
          leaf set-cos-transmit {
            type cos_value-type;
          }
          leaf table {
            type string;
          }
        }
      }
    }
    container conform-set-discard-class-transmit {
      tailf:cli-no-keyword;
      tailf:cli-drop-node-name;
      tailf:cli-flatten-container;
      container conform-action {
        tailf:cli-flatten-container;
        leaf set-discard-class-transmit {
          type uint8;
        }
      }
    }
    choice conform-set-dscp-transmit-choice {
      container conform-set-dscp-transmit {
        tailf:cli-no-keyword;
        tailf:cli-drop-node-name;
        tailf:cli-flatten-container;
        container conform-action {
          tailf:cli-flatten-container;
          leaf set-dscp-transmit {
            type dscp-type;
          }
        }
      }
      container conform-set-dscp-transmit-table {
        tailf:cli-no-keyword;
        tailf:cli-drop-node-name;
        tailf:cli-flatten-container;
        container conform-action {
          tailf:cli-flatten-container;
          tailf:cli-compact-syntax;
          tailf:cli-sequence-commands;
          leaf set-dscp-transmit {
            type dscp-type;
          }
          leaf table {
            type string;
          }
        }
      }
    }
    container conform-set-frde-transmit {
      tailf:cli-no-keyword;
      tailf:cli-drop-node-name;
      tailf:cli-flatten-container;
      container conform-action {
        tailf:cli-flatten-container;
        leaf set-frde-transmit {
          type empty;
        }
      }
    }
    choice conform-set-mpls-exp-imposition-transmit-choice {
      container conform-set-mpls-exp-imposition-transmit {
        tailf:cli-no-keyword;
        tailf:cli-drop-node-name;
        tailf:cli-flatten-container;
        container conform-action {
          tailf:cli-flatten-container;
          leaf set-mpls-exp-imposition-transmit {
            type exp_value-type;
          }
        }
      }
      container conform-set-mpls-exp-imposition-transmit-table {
        tailf:cli-no-keyword;
        tailf:cli-drop-node-name;
        tailf:cli-flatten-container;
        container conform-action {
          tailf:cli-flatten-container;
          tailf:cli-compact-syntax;
          tailf:cli-sequence-commands;
          leaf set-mpls-exp-imposition-transmit {
            type exp_value-type;
          }
          leaf table {
            type string;
          }
        }
      }
    }
    choice conform-set-mpls-exp-topmost-transmit-choice {
      container conform-set-mpls-exp-topmost-transmit {
        tailf:cli-no-keyword;
        tailf:cli-drop-node-name;
        tailf:cli-flatten-container;
        container conform-action {
          tailf:cli-flatten-container;
          leaf set-mpls-exp-topmost-transmit {
            type exp_value-type;
          }
        }
      }
      container conform-set-mpls-exp-topmost-transmit-table {
        tailf:cli-no-keyword;
        tailf:cli-drop-node-name;
        tailf:cli-flatten-container;
        container conform-action {
          tailf:cli-flatten-container;
          tailf:cli-compact-syntax;
          tailf:cli-sequence-commands;
          leaf set-mpls-exp-topmost-transmit {
            type exp_value-type;
          }
          leaf table {
            type string;
          }
        }
      }
    }
    choice conform-set-prec-transmit-choice {
      container conform-set-prec-transmit {
        tailf:cli-no-keyword;
        tailf:cli-drop-node-name;
        tailf:cli-flatten-container;
        container conform-action {
          tailf:cli-flatten-container;
          leaf set-prec-transmit {
            type prec_value-type;
          }
        }
      }
      container conform-set-prec-transmit-table {
        tailf:cli-no-keyword;
        tailf:cli-drop-node-name;
        tailf:cli-flatten-container;
        container conform-action {
          tailf:cli-flatten-container;
          tailf:cli-compact-syntax;
          tailf:cli-sequence-commands;
          leaf set-prec-transmit {
            type prec_value-type;
          }
          leaf table {
            type string;
          }
        }
      }
    }
    choice conform-set-qos-transmit-choice {
      container conform-set-qos-transmit {
        tailf:cli-no-keyword;
        tailf:cli-drop-node-name;
        tailf:cli-flatten-container;
        container conform-action {
          tailf:cli-flatten-container;
          leaf set-qos-transmit {
            type qos_value-type;
          }
        }
      }
      container conform-set-qos-transmit-table {
        tailf:cli-no-keyword;
        tailf:cli-drop-node-name;
        tailf:cli-flatten-container;
        container conform-action {
          tailf:cli-flatten-container;
          tailf:cli-compact-syntax;
          tailf:cli-sequence-commands;
          leaf set-qos-transmit {
            type qos_value-type;
          }
          leaf table {
            type string;
          }
        }
      }
    }
    container conform-transmit {
      tailf:cli-no-keyword;
      tailf:cli-drop-node-name;
      tailf:cli-flatten-container;
      container conform-action {
        tailf:cli-flatten-container;
        uses police-action-transmit-grouping;
      }
    }
    container conform-drop {
      tailf:cli-no-keyword;
      tailf:cli-drop-node-name;
      tailf:cli-flatten-container;
      container conform-action {
        tailf:cli-flatten-container;
        uses police-action-drop-grouping;
      }
    }
  }

  grouping police-multiple-exceed-action-grouping {
    container exceed-dscp {
      tailf:cli-no-keyword;
      tailf:cli-drop-node-name;
      tailf:cli-flatten-container;
      container exceed-action {
        tailf:cli-flatten-container;
        leaf dscp {
          type dscp-type;
        }
      }
    }
    container exceed-set-clp-transmit {
      tailf:cli-no-keyword;
      tailf:cli-drop-node-name;
      tailf:cli-flatten-container;
      container exceed-action {
        tailf:cli-flatten-container;
        leaf set-clp-transmit {
          type empty;
        }
      }
    }
    choice exceed-set-cos-transmit-choice {
      container exceed-set-cos-transmit {
        tailf:cli-no-keyword;
        tailf:cli-drop-node-name;
        tailf:cli-flatten-container;
        container exceed-action {
          tailf:cli-flatten-container;
          leaf set-cos-transmit {
            type cos_value-type;
          }
        }
      }
      container exceed-set-cos-transmit-table {
        tailf:cli-no-keyword;
        tailf:cli-drop-node-name;
        tailf:cli-flatten-container;
        container exceed-action {
          tailf:cli-flatten-container;
          tailf:cli-compact-syntax;
          tailf:cli-sequence-commands;
          leaf set-cos-transmit {
            type cos_value-type;
          }
          leaf table {
            type string;
          }
        }
      }
    }
    container exceed-set-discard-class-transmit {
      tailf:cli-no-keyword;
      tailf:cli-drop-node-name;
      tailf:cli-flatten-container;
      container exceed-action {
        tailf:cli-flatten-container;
        leaf set-discard-class-transmit {
          type uint8;
        }
      }
    }
    choice exceed-set-dscp-transmit-choice {
      container exceed-set-dscp-transmit {
        tailf:cli-no-keyword;
        tailf:cli-drop-node-name;
        tailf:cli-flatten-container;
        container exceed-action {
          tailf:cli-flatten-container;
          leaf set-dscp-transmit {
            type dscp-type;
          }
        }
      }
      container exceed-set-dscp-transmit-table {
        tailf:cli-no-keyword;
        tailf:cli-drop-node-name;
        tailf:cli-flatten-container;
        container exceed-action {
          tailf:cli-flatten-container;
          tailf:cli-compact-syntax;
          tailf:cli-sequence-commands;
          leaf set-dscp-transmit {
            type dscp-type;
          }
          leaf table {
            type string;
          }
        }
      }
    }
    container exceed-set-frde-transmit {
      tailf:cli-no-keyword;
      tailf:cli-drop-node-name;
      tailf:cli-flatten-container;
      container exceed-action {
        tailf:cli-flatten-container;
        leaf set-frde-transmit {
          type empty;
        }
      }
    }
    container exceed-set-mpls-exp-imposition-transmit {
      tailf:cli-no-keyword;
      tailf:cli-drop-node-name;
      tailf:cli-flatten-container;
      container exceed-action {
        tailf:cli-flatten-container;
        leaf set-mpls-exp-imposition-transmit {
          type exp_value-type;
        }
      }
    }
    container exceed-set-mpls-exp-topmost-transmit {
      tailf:cli-no-keyword;
      tailf:cli-drop-node-name;
      tailf:cli-flatten-container;
      container exceed-action {
        tailf:cli-flatten-container;
        leaf set-mpls-exp-topmost-transmit {
          type exp_value-type;
        }
      }
    }
    container exceed-set-prec-transmit {
      tailf:cli-no-keyword;
      tailf:cli-drop-node-name;
      tailf:cli-flatten-container;
      container exceed-action {
        tailf:cli-flatten-container;
        leaf set-prec-transmit {
          type prec_value-type;
        }
      }
    }
    choice exceed-set-qos-transmit-choice {
      container exceed-set-qos-transmit {
        tailf:cli-no-keyword;
        tailf:cli-drop-node-name;
        tailf:cli-flatten-container;
        container exceed-action {
          tailf:cli-flatten-container;
          leaf set-qos-transmit {
            type qos_value-type;
          }
        }
      }
      container exceed-set-qos-transmit-table {
        tailf:cli-no-keyword;
        tailf:cli-drop-node-name;
        tailf:cli-flatten-container;
        container exceed-action {
          tailf:cli-flatten-container;
          tailf:cli-compact-syntax;
          tailf:cli-sequence-commands;
          leaf set-qos-transmit {
            type cos_value-type;
          }
          leaf table {
            type string;
          }
        }
      }
    }
    container exceed-transmit {
      tailf:cli-no-keyword;
      tailf:cli-drop-node-name;
      tailf:cli-flatten-container;
      container exceed-action {
        tailf:cli-flatten-container;
        uses police-action-transmit-grouping;
      }
    }
    container exceed-drop {
      tailf:cli-no-keyword;
      tailf:cli-drop-node-name;
      tailf:cli-flatten-container;
      container exceed-action {
        tailf:cli-flatten-container;
        uses police-action-drop-grouping;
      }
    }
  }

  grouping police-multiple-violate-action-grouping {
    container violate-set-clp-transmit {
      tailf:cli-no-keyword;
      tailf:cli-drop-node-name;
      tailf:cli-flatten-container;
      container violate-action {
        tailf:cli-flatten-container;
        leaf set-clp-transmit {
          type empty;
        }
      }
    }
    container violate-set-cos-transmit {
      tailf:cli-no-keyword;
      tailf:cli-drop-node-name;
      tailf:cli-flatten-container;
      container violate-action {
        tailf:cli-flatten-container;
        leaf set-cos-transmit {
          type cos_value-type;
        }
      }
    }
    container violate-set-discard-class-transmit {
      tailf:cli-no-keyword;
      tailf:cli-drop-node-name;
      tailf:cli-flatten-container;
      container violate-action {
        tailf:cli-flatten-container;
        leaf set-discard-class-transmit {
          type uint8;
        }
      }
    }
    container violate-set-dscp-transmit {
      tailf:cli-no-keyword;
      tailf:cli-drop-node-name;
      tailf:cli-flatten-container;
      container violate-action {
        tailf:cli-flatten-container;
        leaf set-dscp-transmit {
          type dscp-type;
        }
      }
    }
    container violate-set-frde-transmit {
      tailf:cli-no-keyword;
      tailf:cli-drop-node-name;
      tailf:cli-flatten-container;
      container violate-action {
        tailf:cli-flatten-container;
        leaf set-frde-transmit {
          type empty;
        }
      }
    }
    container violate-set-mpls-exp-imposition-transmit {
      tailf:cli-no-keyword;
      tailf:cli-drop-node-name;
      tailf:cli-flatten-container;
      container violate-action {
        tailf:cli-flatten-container;
        leaf set-mpls-exp-imposition-transmit {
          type exp_value-type;
        }
      }
    }
    container violate-set-mpls-exp-topmost-transmit {
      tailf:cli-no-keyword;
      tailf:cli-drop-node-name;
      tailf:cli-flatten-container;
      container violate-action {
        tailf:cli-flatten-container;
        leaf set-mpls-exp-topmost-transmit {
          type exp_value-type;
        }
      }
    }
    container violate-set-prec-transmit {
      tailf:cli-no-keyword;
      tailf:cli-drop-node-name;
      tailf:cli-flatten-container;
      container violate-action {
        tailf:cli-flatten-container;
        leaf set-prec-transmit {
          type prec_value-type;
        }
      }
    }
    container violate-set-qos-transmit {
      tailf:cli-no-keyword;
      tailf:cli-drop-node-name;
      tailf:cli-flatten-container;
      container violate-action {
        tailf:cli-flatten-container;
        leaf set-qos-transmit {
          type qos_value-type;
        }
      }
    }
    container violate-transmit {
      tailf:cli-no-keyword;
      tailf:cli-drop-node-name;
      tailf:cli-flatten-container;
      container violate-action {
        tailf:cli-flatten-container;
        uses police-action-transmit-grouping;
      }
    }
    container violate-drop {
      tailf:cli-no-keyword;
      tailf:cli-drop-node-name;
      tailf:cli-flatten-container;
      container violate-action {
        tailf:cli-flatten-container;
        uses police-action-drop-grouping;
      }
    }
  }

  grouping police-action-grouping {
    container actions {
      tailf:cli-break-sequence-commands;
      tailf:cli-no-keyword;
      tailf:cli-drop-node-name;
      tailf:cli-flatten-container;
      uses police-multiple-conform-action-grouping;
      uses police-multiple-exceed-action-grouping;
      uses police-multiple-violate-action-grouping;
    }
  }

  grouping policy-map-class-grouping {
    leaf fragment {
      tailf:cli-hide-in-submode;
      type string;
    }
    leaf service-fragment {
      tailf:cli-hide-in-submode;
      type string;
    }
    container flow {
      tailf:cli-compact-syntax;
      tailf:cli-sequence-commands {
        tailf:cli-reset-siblings;
      }
      leaf monitor {
        type string;
      }
      leaf sampler {
        type string;
      }
    }
    container monitor {
      container metric {
        container rtp {
          tailf:cli-add-mode;
          list clock-rate {
            tailf:cli-suppress-mode;
            tailf:cli-delete-when-empty;
            key "id";
            leaf id {
              type uint8;
            }
            leaf rate {
              tailf:cli-drop-node-name;
              type uint32;
            }
          }
        }
      }
    }
    list react {
      key "id";
      leaf id {
        type uint16;
      }
      leaf type {
        tailf:cli-drop-node-name;
        tailf:cli-hide-in-submode;
        type enumeration {
          enum "media-stop";
          enum "mrv";
          enum "network-delay";
          enum "one-way-delay";
          enum "rtp-jitter-average";
          enum "rtp-jitter-inter-arrival-mean";
          enum "transport-bytes-lost-rate";
          enum "transport-packets-lost-rate";
        }
      }
      container threshold {
        container value {
          leaf ge {
            type string;
          }
        }
      }
      container action {
        leaf syslog {
          type empty;
        }
        leaf snmp {
          type empty;
        }
      }
    }
    leaf pass-through {
      type empty;
    }
    container policy {
      tailf:cli-drop-node-name;
      tailf:cli-compact-syntax;
      tailf:cli-sequence-commands {
        tailf:cli-reset-siblings;
      }
      leaf action {
        tailf:cli-drop-node-name;
        type enumeration {
          enum "drop";
          enum "inspect";
          enum "pass";
          enum "allow";
          enum "deny";
        }
      }
      leaf log {
        tailf:cli-optional-in-sequence;
        type empty;
      }
      leaf parameter-map {
        tailf:cli-drop-node-name;
        type string;
      }
    }
    container inspect-police {
      tailf:cli-drop-node-name;
      container police {
        tailf:cli-compact-syntax;
        tailf:cli-sequence-commands {
          tailf:cli-reset-siblings;
        }
        leaf rate {
          type uint32;
        }
        leaf burst {
          type uint32;
        }
      }
    }
    container bandwidth {
      leaf bits {
        tailf:cli-drop-node-name;
        type uint32;
      }
      leaf percent {
        type percentage-type;
      }
      container remaining {
        container percent {
          tailf:cli-compact-syntax;
          tailf:cli-sequence-commands;
          leaf percent {
            tailf:cli-drop-node-name;
            type percentage-type;
          }
          uses bandwidth-remaining-account-grouping;
        }
        container ratio {
          tailf:cli-compact-syntax;
          tailf:cli-sequence-commands;
          leaf ratio {
            tailf:cli-drop-node-name;
            type uint32;
          }
          uses bandwidth-remaining-account-grouping;
        }
      }
    }
    container compress {
      container header {
        container ip {
          tailf:cli-delete-when-empty;
          presence "true";
          leaf protocol {
            tailf:cli-drop-node-name;
            type enumeration {
              enum "rtp";
              enum "tcp";
            }
          }
        }
      }
    }
    leaf dbl {
      type empty;
    }
    container estimate {
      container bandwidth {
        tailf:cli-compact-syntax;
        tailf:cli-sequence-commands;
        presence "true";
        container delay-one-in {
          tailf:cli-compact-syntax;
          tailf:cli-sequence-commands;
          leaf doi {
            tailf:cli-drop-node-name;
            type uint32;
          }
          leaf milliseconds {
            type uint32;
          }
        }
        leaf drop-one-in {
          type uint32;
        }
      }
    }
    leaf account {
      type empty;
    }
    container fair-queue {
      tailf:cli-delete-when-empty;
      presence "true";
      leaf dynamic-queues {
        tailf:cli-drop-node-name;
        type uint32;
      }
      leaf queue-limit {
        type uint32;
      }
    }
    leaf netflow-sampler {
      type string;
    }
    container police-aggregate {
      tailf:cli-no-keyword;
      tailf:cli-drop-node-name;
      container police {
        leaf aggregate {
          type string;
        }
      }
    }
    choice police-choice {
      case police-cirmode-case {
        container police-policy-map {
          tailf:cli-no-keyword;
          tailf:cli-drop-node-name;
          container police {
            tailf:cli-add-mode;
            tailf:cli-flatten-container;
            tailf:cli-sequence-commands {
              tailf:cli-reset-siblings;
            }
            leaf cir {
              tailf:cli-hide-in-submode;
              type police-bps-type;
            }
            leaf bc {
              tailf:cli-optional-in-sequence;
              tailf:cli-hide-in-submode;
              type police-burst-type;
            }
            leaf be {
              tailf:cli-optional-in-sequence;
              tailf:cli-hide-in-submode;
              type police-burst-type;
            }
            leaf pir {
              tailf:cli-optional-in-sequence;
              tailf:cli-hide-in-submode;
              type police-bps-type;
            }
            container pir-be {
              tailf:cli-drop-node-name;
              tailf:cli-optional-in-sequence;
              tailf:cli-flatten-container;
              tailf:cli-hide-in-submode;
              leaf be {
                type police-burst-type;
              }
            }
            container account {
              tailf:cli-optional-in-sequence;
              tailf:cli-flatten-container;
              tailf:cli-hide-in-submode;
              leaf user-defined {
                type int8;
              }
            }
            uses police-action-grouping;
            container conform-color {
              tailf:cli-compact-syntax;
              tailf:cli-sequence-commands {
                tailf:cli-reset-siblings;
              }
              leaf class-map-name {
                tailf:cli-drop-node-name;
                type string;
              }
              leaf exceed-color {
                type string;
              }
            }
          }
        }
      }
      case police-cir-percent-case {
        container police-cir-percent {
          tailf:cli-no-keyword;
          tailf:cli-drop-node-name;
          container police {
            container cir {
              container percent {
                tailf:cli-add-mode;
                tailf:cli-flatten-container;
                tailf:cli-sequence-commands {
                  tailf:cli-reset-siblings;
                }
                leaf percentage {
                  tailf:cli-drop-node-name;
                  tailf:cli-hide-in-submode;
                  type percentage-type;
                }
                leaf bc {
                  tailf:cli-optional-in-sequence;
                  tailf:cli-hide-in-submode;
                  type uint16;
                }
                container bc-ms {
                  tailf:cli-drop-node-name;
                  tailf:cli-optional-in-sequence;
                  tailf:cli-hide-in-submode;
                  tailf:cli-flatten-container;
                  tailf:cli-compact-syntax;
                  leaf ms {
                    tailf:cli-no-keyword;
                    type empty;
                  }
                }
                leaf be {
                  tailf:cli-optional-in-sequence;
                  tailf:cli-hide-in-submode;
                  type uint16;
                }
                container be-ms {
                  tailf:cli-drop-node-name;
                  tailf:cli-hide-in-submode;
                  tailf:cli-flatten-container;
                  tailf:cli-compact-syntax;
                  leaf ms {
                    tailf:cli-no-keyword;
                    type empty;
                  }
                }
                container pir {
                  tailf:cli-flatten-container;
                  tailf:cli-compact-syntax;
                  tailf:cli-hide-in-submode;
                  tailf:cli-optional-in-sequence;
                  leaf percent {
                    type percentage-type;
                  }
                }
                container pir-be {
                  tailf:cli-drop-node-name;
                  tailf:cli-optional-in-sequence;
                  tailf:cli-flatten-container;
                  tailf:cli-hide-in-submode;
                  leaf be {
                    type uint16;
                  }
                }
                container pir-be-ms {
                  tailf:cli-drop-node-name;
                  tailf:cli-optional-in-sequence;
                  tailf:cli-hide-in-submode;
                  tailf:cli-flatten-container;
                  leaf ms {
                    tailf:cli-no-keyword;
                    type empty;
                  }
                }
                uses police-action-grouping;
              }
            }
          }
        }
      }
      case police-cirflat-percent-case {
        container police-cirflat-percent {
          tailf:cli-no-keyword;
          tailf:cli-drop-node-name;
          container police {
            container cir {
              container percent {
                tailf:cli-compact-syntax;
                tailf:cli-sequence-commands {
                  tailf:cli-reset-siblings;
                }
                leaf percentage {
                  tailf:cli-drop-node-name;
                  type percentage-type;
                }
                leaf bc {
                  tailf:cli-optional-in-sequence;
                  type uint16;
                }
                container bc-ms {
                  tailf:cli-drop-node-name;
                  tailf:cli-optional-in-sequence;
                  tailf:cli-flatten-container;
                  tailf:cli-compact-syntax;
                  leaf ms {
                    tailf:cli-no-keyword;
                    type empty;
                  }
                }
                leaf be {
                  tailf:cli-optional-in-sequence;
                  type uint16;
                }
                container be-ms {
                  tailf:cli-drop-node-name;
                  tailf:cli-flatten-container;
                  tailf:cli-compact-syntax;
                  leaf ms {
                    tailf:cli-no-keyword;
                    type empty;
                  }
                }
                container pir {
                  tailf:cli-flatten-container;
                  tailf:cli-compact-syntax;
                  tailf:cli-optional-in-sequence;
                  leaf percent {
                    type percentage-type;
                  }
                }
                container pir-be {
                  tailf:cli-drop-node-name;
                  tailf:cli-optional-in-sequence;
                  tailf:cli-flatten-container;
                  leaf be {
                    type uint16;
                  }
                }
                container pir-be-ms {
                  tailf:cli-drop-node-name;
                  tailf:cli-optional-in-sequence;
                  tailf:cli-flatten-container;
                  leaf ms {
                    tailf:cli-no-keyword;
                    type empty;
                  }
                }
                uses police-action-grouping;
              }
            }
          }
        }
      }
      case police-rate-unit-case {
        container police-rate-unit {
          tailf:cli-no-keyword;
          tailf:cli-drop-node-name;
          container police {
            container rate {
              tailf:cli-add-mode;
              tailf:cli-sequence-commands {
                tailf:cli-reset-siblings;
              }
              leaf units {
                tailf:cli-drop-node-name;
                tailf:cli-hide-in-submode;
                type uint64;
              }
              leaf xps {
                tailf:cli-no-keyword;
                tailf:cli-drop-node-name;
                tailf:cli-optional-in-sequence;
                tailf:cli-hide-in-submode;
                type police-pps-bps-type;
              }
              leaf child-conform-aware {
                tailf:cli-optional-in-sequence;
                tailf:cli-hide-in-submode;
                type empty;
              }
              leaf burst {
                tailf:cli-optional-in-sequence;
                tailf:cli-hide-in-submode;
                type uint64;
              }
              leaf burst-type {
                tailf:cli-no-keyword;
                tailf:cli-drop-node-name;
                tailf:cli-optional-in-sequence;
                tailf:cli-hide-in-submode;
                type police-packets-bytes-type;
              }
              leaf peak-rate {
                tailf:cli-optional-in-sequence;
                tailf:cli-hide-in-submode;
                type uint64;
              }
              leaf peak-rate-type {
                tailf:cli-no-keyword;
                tailf:cli-drop-node-name;
                tailf:cli-optional-in-sequence;
                tailf:cli-hide-in-submode;
                type police-pps-bps-type;
              }
              leaf peak-burst {
                tailf:cli-optional-in-sequence;
                tailf:cli-hide-in-submode;
                type uint64;
              }
              leaf peak-burst-type {
                tailf:cli-no-keyword;
                tailf:cli-drop-node-name;
                tailf:cli-optional-in-sequence;
                tailf:cli-hide-in-submode;
                type police-packets-bytes-type;
              }
              uses police-action-grouping;
            }
          }
        }
      }
      case police-rate-percent-case {
        container police-rate-percent {
          tailf:cli-no-keyword;
          tailf:cli-drop-node-name;
          container police {
            container rate {
              container percent {
                tailf:cli-add-mode;
                tailf:cli-sequence-commands {
                  tailf:cli-reset-siblings;
                }
                leaf percentage {
                  tailf:cli-drop-node-name;
                  tailf:cli-hide-in-submode;
                  type percentage-type;
                }
                leaf burst {
                  tailf:cli-optional-in-sequence;
                  tailf:cli-hide-in-submode;
                  type uint16;
                }
                leaf ms {
                  tailf:cli-hide-in-submode;
                  type empty;
                }
                container peak-rate {
                  tailf:cli-hide-in-submode;
                  tailf:cli-optional-in-sequence;
                  tailf:cli-flatten-container;
                  leaf percent {
                    type percentage-type;
                  }
                }
                leaf peak-burst {
                  tailf:cli-hide-in-submode;
                  tailf:cli-optional-in-sequence;
                  type uint16;
                }
                container peak-burst-ms {
                  tailf:cli-drop-node-name;
                  tailf:cli-optional-in-sequence;
                  tailf:cli-hide-in-submode;
                  tailf:cli-flatten-container;
                  leaf ms {
                    tailf:cli-no-keyword;
                    type empty;
                  }
                }
                uses police-action-grouping;
              }
            }
          }
        }
      }
      case police-rate-pdp-case {
        container police-rate-pdp {
          tailf:cli-no-keyword;
          tailf:cli-drop-node-name;
          container police {
            container rate {
              container pdp {
                tailf:cli-add-mode;
                tailf:cli-flatten-container;
                tailf:cli-sequence-commands {
                  tailf:cli-reset-siblings;
                }
                leaf burst {
                  tailf:cli-hide-in-submode;
                  tailf:cli-optional-in-sequence;
                  type police-burst-type;
                }
                leaf peak-rate {
                  tailf:cli-hide-in-submode;
                  tailf:cli-optional-in-sequence;
                  type enumeration {
                    enum "pdp";
                  }
                }
                leaf peak-burst {
                  tailf:cli-hide-in-submode;
                  tailf:cli-optional-in-sequence;
                  type police-burst-type;
                }
                uses police-action-grouping;
              }
            }
          }
        }
      }
      case police-flow-case {
        container police-flow {
          tailf:cli-no-keyword;
          tailf:cli-drop-node-name;
          container police {
            container flow {
              tailf:cli-add-mode;
              tailf:cli-flatten-container;
              tailf:cli-sequence-commands {
                tailf:cli-reset-siblings;
              }
              leaf mask {
                tailf:cli-hide-in-submode;
                tailf:cli-optional-in-sequence;
                type enumeration {
                  enum "dest-only";
                  enum "full-flow";
                  enum "src-only";
                }
              }
              leaf bps {
                tailf:cli-drop-node-name;
                tailf:cli-hide-in-submode;
                type police-bps-type;
              }
              leaf burst-normal {
                tailf:cli-drop-node-name;
                tailf:cli-hide-in-submode;
                tailf:cli-optional-in-sequence;
                type police-burst-type;
              }
              uses police-action-grouping;
            }
          }
        }
      }
      case police-bpsflat-case {
        container police-catalyst {
          tailf:cli-no-keyword;
          tailf:cli-drop-node-name;
          container police {
            tailf:cli-add-mode;
            tailf:cli-flatten-container;
            tailf:cli-sequence-commands {
              tailf:cli-reset-siblings;
            }
            leaf bps-value {
              tailf:cli-no-keyword;
              tailf:cli-drop-node-name;
              tailf:cli-hide-in-submode;
              type string;
            }
            choice bps-type-choice {
              leaf bps {
                tailf:cli-hide-in-submode;
                tailf:cli-optional-in-sequence;
                type empty;
              }
              leaf kbps {
                tailf:cli-hide-in-submode;
                tailf:cli-optional-in-sequence;
                type empty;
              }
              leaf mbps {
                tailf:cli-hide-in-submode;
                tailf:cli-optional-in-sequence;
                type empty;
              }
              leaf gbps {
                tailf:cli-hide-in-submode;
                type empty;
              }
            }
            leaf byte-value {
              tailf:cli-no-keyword;
              tailf:cli-drop-node-name;
              tailf:cli-hide-in-submode;
              type string;
            }
            choice byte-type-choice {
              leaf byte {
                tailf:cli-optional-in-sequence;
                tailf:cli-hide-in-submode;
                type empty;
              }
              leaf kbyte {
                tailf:cli-optional-in-sequence;
                tailf:cli-hide-in-submode;
                type empty;
              }
              leaf mbyte {
                tailf:cli-optional-in-sequence;
                tailf:cli-hide-in-submode;
                type empty;
              }
              leaf gbyte {
                tailf:cli-hide-in-submode;
                type empty;
              }
            }
            container actions {
              tailf:cli-break-sequence-commands;
              tailf:cli-no-keyword;
              tailf:cli-drop-node-name;
              tailf:cli-flatten-container;
              tailf:cli-hide-in-submode;
              uses police-multiple-conform-action-grouping;
              uses police-multiple-exceed-action-grouping;
              uses police-multiple-violate-action-grouping;
            }
          }
        }
      }
      case police-switch-case {
        container police-switch {
          tailf:cli-no-keyword;
          tailf:cli-drop-node-name;
          container police {
            tailf:cli-compact-syntax;
            tailf:cli-sequence-commands {
              tailf:cli-reset-siblings;
            }
            leaf cir {
              tailf:cli-drop-node-name;
              type uint32;
            }
            leaf bc {
              tailf:cli-drop-node-name;
              type uint32;
            }
            leaf exceed-action {
              type enumeration {
                enum "drop";
                enum "policed-dscp-transmit";
              }
            }
          }
        }
      }
      case police-numflat-case {
        container police-numflat {
          tailf:cli-no-keyword;
          tailf:cli-drop-node-name;
          container police {
            tailf:cli-compact-syntax;
            tailf:cli-sequence-commands {
              tailf:cli-reset-siblings;
            }
            leaf cir {
              tailf:cli-drop-node-name;
              type police-bps-type;
            }
            leaf bc {
              tailf:cli-drop-node-name;
              tailf:cli-optional-in-sequence;
              type police-burst-type;
            }
            leaf be {
              tailf:cli-drop-node-name;
              tailf:cli-optional-in-sequence;
              type police-burst-type;
            }
            container actions {
              tailf:cli-break-sequence-commands;
              tailf:cli-no-keyword;
              tailf:cli-drop-node-name;
              tailf:cli-flatten-container;
              uses police-multiple-conform-action-grouping;
              uses police-multiple-exceed-action-grouping;
              uses police-multiple-violate-action-grouping;
            }
          }
        }
      }
      case police-cirflat-case {
        container police-cirflat {
          tailf:cli-no-keyword;
          tailf:cli-drop-node-name;
          container police {
            tailf:cli-compact-syntax;
            tailf:cli-sequence-commands {
              tailf:cli-reset-siblings;
            }
            leaf cir {
              type police-bps-type;
            }
            leaf bc {
              tailf:cli-optional-in-sequence;
              type police-burst-type;
            }
            leaf pir {
              tailf:cli-optional-in-sequence;
              type police-bps-type;
            }
            leaf be {
              tailf:cli-optional-in-sequence;
              type police-burst-type;
            }
            container actions {
              tailf:cli-break-sequence-commands;
              tailf:cli-drop-node-name;
              tailf:cli-flatten-container;
              tailf:cli-compact-syntax;
              uses police-conform-action-grouping;
              uses police-exceed-action-grouping;
              uses police-violate-action-grouping;
            }
          }
        }
      }
    }
    container priority {
      tailf:cli-compact-syntax;
      tailf:cli-sequence-commands;
      tailf:cli-delete-when-empty;
      presence "true";
      leaf level {
        tailf:cli-optional-in-sequence;
        type uint8;
      }
      choice priority-type {
        leaf kilo-bits {
          tailf:cli-drop-node-name;
          type uint32;
        }
        leaf percent {
          type uint16;
        }
      }
      leaf burst {
        tailf:cli-drop-node-name;
        type uint32;
      }
    }
    container shape {
      leaf adaptive {
        type uint32;
      }
      container adaptive-bound {
        tailf:cli-drop-node-name;
        container adaptive {
          tailf:cli-compact-syntax;
          tailf:cli-sequence-commands {
            tailf:cli-reset-siblings;
          }
          container upper-bound {
            tailf:cli-flatten-container;
            tailf:cli-compact-syntax;
            choice upper-choice {
              leaf value {
                tailf:cli-drop-node-name;
                type uint32;
              }
              leaf percent {
                type uint8;
              }
            }
          }
          container lower-bound {
            tailf:cli-flatten-container;
            tailf:cli-compact-syntax;
            choice lower-choice {
              leaf value {
                tailf:cli-drop-node-name;
                type uint32;
              }
              leaf percent {
                type uint8;
              }
            }
          }
        }
      }
      choice shape-average-peak {
        container average {
          tailf:cli-compact-syntax;
          tailf:cli-sequence-commands;
          choice average-choice {
            case a {
              leaf bit-rate {
                tailf:cli-drop-node-name;
                type uint64;
              }
              leaf bits-per-interval-sustained {
                tailf:cli-drop-node-name;
                tailf:cli-optional-in-sequence;
                type uint32;
              }
              leaf bits-per-interval-excess {
                tailf:cli-drop-node-name;
                tailf:cli-optional-in-sequence;
                type uint32;
              }
              leaf account {
                type empty;
              }
              leaf user-defined {
                type int8;
              }
              leaf atm {
                type empty;
              }
            }
            case b {
              leaf percent {
                type percentage-type;
              }
              leaf burst-size-sustained {
                tailf:cli-drop-node-name;
                type uint16;
              }
              leaf ms {
                type empty;
              }
              container bse {
                tailf:cli-drop-node-name;
                tailf:cli-flatten-container;
                tailf:cli-compact-syntax;
                tailf:cli-sequence-commands;
                leaf burst-size-excess {
                  type uint16;
                }
                leaf ms {
                  type empty;
                }
              }
            }
          }
        }
        container peak {
          tailf:cli-compact-syntax;
          tailf:cli-sequence-commands {
            tailf:cli-reset-siblings;
          }
          choice peak-choice {
            case a {
              leaf bit-rate {
                tailf:cli-drop-node-name;
                type uint64;
              }
              leaf burst-size {
                tailf:cli-drop-node-name;
                type uint64;
              }
              leaf excess-burst-size {
                tailf:cli-drop-node-name;
                type uint64;
              }
            }
            leaf percent {
              type uint8;
            }
          }
        }
      }
      leaf fecn-adapt {
        type empty;
      }
      container fr-voice-adapt {
        presence "true";
        leaf deactivation {
          type uint16;
        }
      }
      leaf max-buffers {
        type uint16;
      }
    }
    container queue-buffers {
      leaf ratio {
        type uint16;
      }
    }
    container random-detect {
      container base {
        tailf:cli-drop-node-name;
        tailf:cli-compact-syntax;
        tailf:cli-sequence-commands {
          tailf:cli-reset-siblings;
        }
        leaf type {
          tailf:cli-drop-node-name;
          type enumeration {
            enum "cos-based";
            enum "precedence-based";
            enum "discard-class-based";
            enum "dscp-based";
          }
        }
        leaf aggregate {
          type empty;
        }
        leaf minimum-thresh {
          type uint32;
        }
        leaf maximum-thresh {
          type uint32;
        }
        leaf mark-probability {
          tailf:alt-name "mark-prob";
          type empty;
        }
        leaf denominator {
          tailf:cli-drop-node-name;
          type uint32;
        }
      }
      leaf exponential-weighting-constant {
        type uint16;
      }
      leaf ecn {
        type empty;
      }
      list cos {
        tailf:cli-suppress-mode;
        tailf:cli-delete-when-empty;
        tailf:cli-compact-syntax;
        tailf:cli-sequence-commands;
        key "cos";
        leaf cos {
          type uint8;
        }
        uses random-detect-grouping;
      }
      list precedence {
        tailf:cli-suppress-mode;
        tailf:cli-delete-when-empty;
        tailf:cli-compact-syntax;
        tailf:cli-sequence-commands;
        key "prec";
        leaf prec {
          type union {
            type uint8;
            type enumeration {
              enum "rsvp";
            }
          }
        }
        uses random-detect-grouping;
      }
      container precedence-values {
        tailf:cli-drop-node-name;
        list precedence {
          tailf:cli-suppress-mode;
          tailf:cli-delete-when-empty;
          tailf:cli-compact-syntax;
          tailf:cli-sequence-commands;
          key "values";
          leaf values {
            tailf:cli-expose-key-name;
            type uint8;
          }
          uses random-detect-values-grouping;
        }
      }
      list discard-class {
        tailf:cli-suppress-mode;
        tailf:cli-delete-when-empty;
        tailf:cli-compact-syntax;
        tailf:cli-sequence-commands;
        key "dclass";
        leaf dclass {
          type uint16;
        }
        uses random-detect-grouping;
      }
      list dscp {
        tailf:cli-suppress-mode;
        tailf:cli-delete-when-empty;
        tailf:cli-compact-syntax;
        tailf:cli-sequence-commands;
        key "dscpvalue";
        leaf dscpvalue {
          type dscp-type;
        }
        uses random-detect-grouping;
      }
      container dscp-values {
        tailf:cli-drop-node-name;
        list dscp {
          tailf:cli-suppress-mode;
          tailf:cli-delete-when-empty;
          tailf:cli-compact-syntax;
          tailf:cli-sequence-commands;
          key "values";
          leaf values {
            tailf:cli-expose-key-name;
            type dscp-type;
          }
          uses random-detect-values-grouping;
        }
      }
    }
    container queue-limit {
      tailf:cli-compact-syntax;
      tailf:cli-sequence-commands;
      container percent {
        tailf:cli-optional-in-sequence;
        leaf value {
          tailf:cli-drop-node-name;
          type percentage-type;
        }
      }
      leaf queue-limit-value {
        tailf:cli-drop-node-name;
        tailf:cli-optional-in-sequence;
        type uint32;
      }
      leaf queue-limit-type {
        tailf:cli-drop-node-name;
        tailf:cli-optional-in-sequence;
        type enumeration {
          enum "bytes";
          enum "ms";
          enum "us";
          enum "packets";
        }
      }
      list dscp {
        tailf:cli-suppress-mode;
        tailf:cli-delete-when-empty;
        key "dscp";
        leaf dscp {
          type dscp-type;
        }
        leaf percent {
          type percentage-type;
        }
        container absolute {
          tailf:cli-drop-node-name;
          tailf:cli-compact-syntax;
          tailf:cli-sequence-commands;
          leaf value {
            tailf:cli-drop-node-name;
            type uint32;
          }
          leaf type {
            tailf:cli-drop-node-name;
            type enumeration {
              enum "bytes";
              enum "ms";
              enum "us";
              enum "packets";
            }
          }
        }
      }
    }
    container set {
      leaf atm-clp {
        type empty;
      }
      container cos {
        tailf:cli-compact-syntax;
        tailf:cli-sequence-commands;
        choice cos-type {
          case a {
            leaf val {
              tailf:cli-drop-node-name;
              type uint16;
            }
          }
          case b {
            leaf pack {
              tailf:cli-drop-node-name;
              type enumeration {
                enum "dscp" {
                  tailf:code-name "pack_dscp";
                }
                enum "precedence" {
                  tailf:code-name "pack_precedence";
                }
                enum "cos";
                enum "qos-group";
              }
            }
            leaf table {
              type string;
            }
          }
        }
      }
      container cos-inner {
        leaf val {
          tailf:cli-drop-node-name;
          type uint16;
        }
      }
      leaf discard-class {
        type uint16;
      }
      container dscp {
        leaf tunnel {
          type dscp-type;
        }
        choice dscp-choice {
          leaf value {
            tailf:cli-drop-node-name;
            type dscp-type;
          }
          container dscp {
            leaf table {
              type string;
            }
          }
        }
      }
      leaf fr-de {
        type empty;
      }
      container ip {
        choice ip-choice {
          leaf dscp {
            type dscp-type;
          }
          container precedence {
            presence "Set IP precedence";
            leaf precedence-val {
              tailf:cli-drop-node-name;
              type precedence-type;
            }
          }
        }
      }
      container ipv4 {
        tailf:cli-compact-syntax;
        tailf:cli-sequence-commands {
          tailf:cli-reset-siblings;
        }
        choice ipv4-choice {
          leaf global {
            type empty;
          }
          leaf vrf {
            type string;
          }
        }
        leaf-list next-hop {
          tailf:cli-flat-list-syntax;
          ordered-by user;
          type inet:ipv4-address;
        }
      }
      container mpls {
        container experimental {
          leaf exp-value {
            tailf:cli-drop-node-name;
            type uint8;
          }
          container imposition {
            leaf exp-value {
              tailf:cli-drop-node-name;
              type uint8;
            }
          }
          container topmost {
            choice topmost-choice {
              leaf exp-value {
                tailf:cli-drop-node-name;
                type uint8;
              }
              container qos-group {
                tailf:cli-delete-when-empty;
                presence "true";
                leaf table {
                  type string;
                }
              }
            }
          }
        }
      }
      container qos-group {
        leaf qos-group-value {
          tailf:cli-drop-node-name;
          type uint8;
        }
      }
      container precedence {
        tailf:cli-compact-syntax;
        tailf:cli-sequence-commands;
        choice precedence-choice {
          case precedence-value {
            leaf precedence-value {
              tailf:cli-drop-node-name;
              tailf:cli-no-keyword;
              type precedence-type;
            }
          }
          case precedence-from-field {
            leaf from-field {
              tailf:cli-drop-node-name;
              tailf:cli-no-keyword;
              type enumeration {
                enum "cos";
                enum "qos-group";
              }
            }
            leaf table {
              type string;
            }
          }
        }
      }
    }
    leaf service-policy {
      type string;
    }
    container service-policy-inspect {
      tailf:cli-drop-node-name;
      container service-policy {
        tailf:cli-compact-syntax;
        tailf:cli-sequence-commands;
        leaf dpi {
          tailf:cli-drop-node-name;
          type enumeration {
            enum "avc";
            enum "gtpv0";
            enum "gtpv1";
            enum "http";
            enum "imap";
            enum "pop3";
            enum "smtp";
            enum "sunrpc";
          }
        }
        leaf name {
          tailf:cli-drop-node-name;
          type string;
        }
      }
    }
    leaf trust {
      type enumeration {
        enum "cos";
        enum "dscp";
        enum "ip-precedence";
      }
    }
    container distribute {
      list service-node-group {
        tailf:cli-suppress-mode;
        tailf:cli-delete-when-empty;
        key "name";
        leaf name {
          type string;
        }
      }
    }
    leaf monitor-load {
      type enumeration {
        enum "MS-port-mapper";
        enum "cifs";
        enum "http";
        enum "ica";
        enum "mapi";
        enum "nfs";
        enum "ssl";
        enum "video";
        enum "ice";
      }
    }
    leaf direct-cloud-access {
      type empty;
    }
  }

  grouping policy-map-type-control-class-grouping {
    list action {
      tailf:cli-break-sequence-commands;
      tailf:cli-drop-node-name;
      tailf:cli-suppress-mode;
      tailf:cli-delete-when-empty;
      key "id";
      leaf id {
        type uint8;
      }
      container service {
        tailf:cli-compact-syntax;
        tailf:cli-sequence-commands {
          tailf:cli-reset-siblings;
        }
        leaf action {
          tailf:cli-drop-node-name;
          type enumeration {
            enum "deny";
            enum "disconnect";
            enum "local";
            enum "permit";
          }
        }
        leaf delay {
          type uint32;
        }
      }
      container service-policy {
        container type {
          container service {
            tailf:cli-compact-syntax;
            tailf:cli-sequence-commands {
              tailf:cli-reset-siblings;
            }
            leaf unapply {
              tailf:cli-optional-in-sequence;
              type empty;
            }
            leaf name {
              tailf:cli-optional-in-sequence;
              type string;
            }
            leaf identifier {
              type enumeration {
                enum "authenticated-domain";
                enum "authenticated-username";
                enum "dnis";
                enum "nas-port";
                enum "service-name";
                enum "tunnel-name";
                enum "unauthenticated-domain";
                enum "unauthenticated-username";
              }
            }
          }
        }
      }
      container authorize {
        container aaa {
          tailf:cli-compact-syntax;
          tailf:cli-sequence-commands {
            tailf:cli-reset-siblings;
          }
          leaf list {
            tailf:cli-optional-in-sequence;
            type empty;
          }
          leaf name {
            tailf:cli-drop-node-name;
            tailf:cli-optional-in-sequence;
            type string;
          }
          leaf password {
            tailf:cli-optional-in-sequence;
            type string;
          }
          leaf identifier {
            type enumeration {
              enum "authenticated-domain";
              enum "authenticated-username";
              enum "auto-detect";
              enum "circuit-id";
              enum "ctag-cos";
              enum "ctag-vlan-id";
              enum "dnis";
              enum "generic-service-name";
              enum "hostname";
              enum "mac-address";
              enum "nas-port";
              enum "payload-etype";
              enum "peer-ip-address";
              enum "remote-id";
              enum "source-ip-address";
              enum "stag-cos";
              enum "stag-type";
              enum "stag-vlan-id";
              enum "tunnel-name";
              enum "unauthenticated-domain";
              enum "unauthenticated-username";
              enum "vc-id";
              enum "vendor-class-id";
            }
          }
          leaf plus {
            type enumeration {
              enum "circuit-id";
              enum "ctag-cos";
              enum "ctag-vlan-id";
              enum "hostname";
              enum "nas-port";
              enum "payload-etype";
              enum "peer-ip-address";
              enum "remote-id";
              enum "stag-cos";
              enum "stag-type";
              enum "stag-vlan-id";
              enum "vc-id";
              enum "vendor-class-id";
            }
          }
        }
      }
      container authenticate {
        container aaa {
          leaf list {
            type union {
              type enumeration {
                enum "default";
              }
              type string;
            }
          }
        }
      }
      container set-timer {
        tailf:cli-compact-syntax;
        tailf:cli-sequence-commands {
          tailf:cli-reset-siblings;
        }
        leaf name {
          tailf:cli-drop-node-name;
          type string;
        }
        leaf value {
          tailf:cli-drop-node-name;
          type uint16;
        }
      }
    }
  }

  grouping distribute-list-content-grouping {
    leaf access-list-name {
      tailf:cli-drop-node-name;
      tailf:cli-prefix-key;
      tailf:cli-optional-in-sequence;
      type exp-ip-acl-type;
    }
    leaf prefix-list {
      tailf:cli-prefix-key;
      tailf:cli-optional-in-sequence;
      type string;
    }
    leaf prefix {
      tailf:cli-prefix-key;
      tailf:cli-optional-in-sequence;
      type string;
    }
    leaf gateway {
      tailf:cli-prefix-key;
      tailf:cli-optional-in-sequence;
      type string;
    }
    leaf route-map {
      tailf:cli-prefix-key;
      tailf:cli-optional-in-sequence;
      type string;
    }
  }

  grouping redistribute-ospf-match-grouping {
    leaf match {
      type empty;
    }
    leaf internal {
      type empty;
    }
    container external-1 {
      tailf:cli-drop-node-name;
      tailf:cli-flatten-container;
      leaf external {
        type enumeration {
          enum "1";
        }
      }
    }
    container external-2 {
      tailf:cli-drop-node-name;
      tailf:cli-flatten-container;
      leaf external {
        type enumeration {
          enum "2";
        }
      }
    }
    container nssa-external-1 {
      tailf:cli-drop-node-name;
      tailf:cli-flatten-container;
      leaf nssa-external {
        type enumeration {
          enum "1";
        }
      }
    }
    container nssa-external-2 {
      tailf:cli-drop-node-name;
      tailf:cli-flatten-container;
      leaf nssa-external {
        type enumeration {
          enum "2";
        }
      }
    }
  }

  grouping router-distribute-list-grouping {
    list distribute-list {
      tailf:cli-suppress-mode;
      tailf:cli-delete-when-empty;
      tailf:cli-compact-syntax;
      tailf:cli-sequence-commands;
      key "direction";
      leaf direction {
        type enumeration {
          enum "in";
          enum "out";
        }
      }
      uses distribute-list-content-grouping;
    }
    container distribute-list-interface {
      tailf:cli-drop-node-name;
      list distribute-list {
        tailf:cli-suppress-mode;
        tailf:cli-delete-when-empty;
        tailf:cli-compact-syntax;
        tailf:cli-sequence-commands;
        key "direction interface";
        leaf direction {
          type enumeration {
            enum "in";
            enum "out";
          }
        }
        leaf interface {
          type string;
        }
        uses distribute-list-content-grouping;
      }
    }
  }

  grouping router-offset-list-grouping {
    list offset-list {
      tailf:cli-suppress-mode;
      tailf:cli-delete-when-empty;
      tailf:cli-compact-syntax;
      tailf:cli-sequence-commands;
      key "direction";
      leaf id {
        tailf:cli-drop-node-name;
        tailf:cli-prefix-key;
        type union {
          type uint32;
          type uint32;
          type string;
        }
      }
      leaf direction {
        type enumeration {
          enum "in";
          enum "out";
        }
      }
      leaf offset {
        tailf:cli-drop-node-name;
        type uint32;
      }
    }
    container offset-list-interface {
      tailf:cli-drop-node-name;
      list offset-list {
        tailf:cli-suppress-mode;
        tailf:cli-delete-when-empty;
        tailf:cli-compact-syntax;
        tailf:cli-sequence-commands;
        key "direction interface";
        leaf id {
          tailf:cli-drop-node-name;
          tailf:cli-prefix-key;
          type union {
            type uint32;
            type uint32;
            type string;
          }
        }
        leaf direction {
          type enumeration {
            enum "in";
            enum "out";
          }
        }
        leaf offset {
          tailf:cli-drop-node-name;
          tailf:cli-prefix-key {
            tailf:cli-before-key "2";
          }
          type uint32;
        }
        leaf interface {
          type string;
        }
      }
    }
  }

  grouping passive-interface-grouping {
    container passive-interface {
      leaf default {
        type empty;
      }
      list interface {
        tailf:cli-drop-node-name;
        tailf:cli-suppress-mode;
        tailf:cli-delete-when-empty;
        key "name";
        leaf name {
          type string;
        }
      }
    }
    container disable {
      list passive-interface {
        tailf:cli-suppress-mode;
        tailf:cli-delete-when-empty;
        key "interface";
        leaf interface {
          type string;
        }
      }
    }
  }

  grouping ip-community-list-grouping {
    list entry {
      tailf:cli-drop-node-name;
      tailf:cli-suppress-mode;
      tailf:cli-delete-when-empty;
      tailf:cli-compact-syntax;
      ordered-by user;
      key "expr";
      leaf expr {
        tailf:cli-multi-word-key;
        type string;
      }
    }
  }

  grouping ip-extcommunity-list-grouping {
    list entry {
      tailf:cli-drop-node-name;
      tailf:cli-suppress-mode;
      tailf:cli-delete-when-empty;
      tailf:cli-compact-syntax;
      ordered-by user;
      key "expr";
      leaf expr {
        tailf:cli-multi-word-key;
        type string;
      }
    }
  }

  grouping ip-route-options-grouping {
    leaf dhcp {
      tailf:cli-optional-in-sequence;
      tailf:cli-case-insensitive;
      type empty;
    }
    leaf global {
      tailf:cli-break-sequence-commands;
      type empty;
    }
    leaf metric {
      tailf:cli-drop-node-name;
      type uint8;
    }
    leaf name {
      type string;
    }
    leaf permanent {
      type empty;
    }
    leaf multicast {
      type empty;
    }
    leaf tag {
      type uint32;
    }
    leaf track {
      type uint16;
    }
  }

  grouping ip-route-grouping {
    list ip-route-interface-forwarding-list {
      tailf:cli-drop-node-name;
      tailf:cli-suppress-mode;
      tailf:cli-delete-when-empty;
      tailf:cli-compact-syntax;
      tailf:cli-sequence-commands;
      key "prefix mask interface forwarding-address";
      leaf prefix {
        type inet:ipv4-address;
      }
      leaf mask {
        type inet:ipv4-address;
      }
      leaf interface {
        type string;
      }
      leaf forwarding-address {
        type union {
          type inet:ipv4-address;
          type enumeration {
            enum "multicast";
          }
        }
      }
      uses ip-route-options-grouping;
    }
    list ip-route-forwarding-list {
      tailf:cli-drop-node-name;
      tailf:cli-suppress-mode;
      tailf:cli-delete-when-empty;
      tailf:cli-compact-syntax;
      tailf:cli-sequence-commands;
      key "prefix mask forwarding-address";
      leaf prefix {
        type inet:ipv4-address;
      }
      leaf mask {
        type inet:ipv4-address;
      }
      leaf forwarding-address {
        type inet:ipv4-address;
      }
      uses ip-route-options-grouping;
    }
    list ip-route-interface-list {
      tailf:cli-drop-node-name;
      tailf:cli-suppress-mode;
      tailf:cli-delete-when-empty;
      tailf:cli-compact-syntax;
      tailf:cli-sequence-commands;
      key "prefix mask interface";
      leaf prefix {
        type inet:ipv4-address;
      }
      leaf mask {
        type inet:ipv4-address;
      }
      leaf interface {
        type union {
          type string;
          type enumeration {
            enum "dhcp";
          }
        }
      }
      uses ip-route-options-grouping;
    }
    list ip-route-sr-list {
      tailf:cli-drop-node-name;
      tailf:cli-suppress-mode;
      tailf:cli-delete-when-empty;
      tailf:cli-compact-syntax;
      tailf:cli-sequence-commands;
      key "prefix mask";
      leaf prefix {
        type inet:ipv4-address;
      }
      leaf mask {
        type inet:ipv4-address;
      }
      container segment-routing {
        container mpls {
          container path {
            leaf name {
              type string;
            }
          }
        }
      }
    }
  }

  grouping ipv6-route-options-grouping {
    leaf distance {
      tailf:cli-drop-node-name;
      tailf:cli-break-sequence-commands;
      type uint8;
    }
    choice type-choice {
      leaf multicast {
        type empty;
      }
      leaf unicast {
        type empty;
      }
    }
    leaf tag {
      type uint32;
    }
    leaf track {
      type uint32;
    }
    leaf name {
      type string;
    }
  }

  grouping ipv6-route-grouping {
    list ipv6-route-interface-destination-list {
      tailf:cli-drop-node-name;
      tailf:cli-suppress-mode;
      tailf:cli-delete-when-empty;
      tailf:cli-compact-syntax;
      tailf:cli-sequence-commands;
      key "prefix interface destination";
      leaf prefix {
        type ipv6-prefix;
      }
      leaf interface {
        type string;
      }
      leaf destination {
        type inet:ipv6-address;
      }
      uses ipv6-route-options-grouping;
    }
    list ipv6-route-destination-list {
      tailf:cli-drop-node-name;
      tailf:cli-suppress-mode;
      tailf:cli-delete-when-empty;
      tailf:cli-compact-syntax;
      tailf:cli-sequence-commands;
      key "prefix destination";
      leaf prefix {
        type ipv6-prefix;
      }
      leaf destination {
        type inet:ipv6-address;
      }
      uses ipv6-route-options-grouping;
    }
    list ipv6-route-interface-list {
      tailf:cli-drop-node-name;
      tailf:cli-suppress-mode;
      tailf:cli-delete-when-empty;
      tailf:cli-compact-syntax;
      tailf:cli-sequence-commands;
      key "prefix interface";
      leaf prefix {
        type ipv6-prefix;
      }
      leaf interface {
        type string;
      }
      uses ipv6-route-options-grouping;
    }
  }

  grouping ip-mroute-grouping {
    list address-list {
      tailf:cli-drop-node-name;
      tailf:cli-suppress-mode;
      tailf:cli-delete-when-empty;
      tailf:cli-compact-syntax;
      tailf:cli-sequence-commands;
      key "source-address mask";
      leaf source-address {
        type inet:ipv4-address;
      }
      leaf mask {
        type inet:ipv4-address;
      }
      choice mroute-choice {
        container fallback-lookup {
          tailf:cli-flatten-container;
          tailf:cli-compact-syntax;
          tailf:cli-optional-in-sequence;
          choice fallback-choice {
            leaf global {
              type empty;
            }
            leaf vrf {
              type string;
            }
          }
        }
        leaf rpf-address {
          tailf:cli-drop-node-name;
          type inet:ipv4-address;
        }
        container interface {
          tailf:cli-drop-node-name;
          tailf:cli-flatten-container;
          tailf:cli-compact-syntax;
          uses interface-name-grouping;
        }
      }
      leaf distance {
        tailf:cli-drop-node-name;
        type uint8;
      }
    }
  }

  grouping random-detect-grouping {
    choice threshold-choice {
      container percent {
        tailf:cli-compact-syntax;
        tailf:cli-sequence-commands {
          tailf:cli-reset-siblings;
        }
        leaf min {
          tailf:cli-drop-node-name;
          type uint8;
        }
        leaf max {
          tailf:cli-drop-node-name;
          type uint8;
        }
      }
      case numeric {
        leaf min-threshold {
          tailf:cli-drop-node-name;
          type uint32;
        }
        leaf min-threshold-unit {
          tailf:cli-drop-node-name;
          tailf:cli-optional-in-sequence;
          type enumeration {
            enum "bytes";
            enum "ms";
            enum "us";
            enum "packets";
          }
        }
        leaf max-threshold {
          tailf:cli-drop-node-name;
          type uint32;
        }
        leaf max-threshold-unit {
          tailf:cli-drop-node-name;
          tailf:cli-optional-in-sequence;
          type enumeration {
            enum "bytes";
            enum "ms";
            enum "us";
            enum "packets";
          }
        }
        leaf denominator {
          tailf:cli-drop-node-name;
          type uint32;
        }
      }
    }
  }

  grouping random-detect-values-grouping {
    leaf minimum-thresh {
      type uint32;
    }
    leaf maximum-thresh {
      type uint32;
    }
    leaf mark-prob {
      type uint32;
    }
  }

  grouping class-map-match-grouping {
    list application {
      tailf:cli-suppress-mode;
      tailf:cli-delete-when-empty;
      key "name";
      leaf name {
        tailf:cli-multi-word-key;
        type string;
      }
    }
    container access-group {
      leaf-list index {
        tailf:cli-drop-node-name;
        type uint32;
      }
      leaf-list name {
        type string;
      }
    }
    leaf any {
      type empty;
    }
    leaf-list class-map {
      type string;
    }
    leaf-list cos {
      tailf:cli-flat-list-syntax;
      type uint16;
    }
    container cos-inner {
      tailf:cli-drop-node-name;
      container cos {
        leaf-list inner {
          tailf:cli-flat-list-syntax;
          type uint16;
        }
      }
    }
    container destination-address {
      leaf-list mac {
        type string;
      }
    }
    leaf-list discard-class {
      type uint8;
    }
    leaf-list dscp {
      tailf:cli-flat-list-syntax;
      type dscp-type;
    }
    container match-multi-line {
      tailf:cli-drop-node-name;
      list dscp {
        tailf:cli-suppress-mode;
        tailf:cli-delete-when-empty;
        ordered-by user;
        key "name";
        leaf name {
          tailf:cli-multi-word-key;
          type string;
        }
      }
      list precedence {
        tailf:cli-suppress-mode;
        tailf:cli-delete-when-empty;
        ordered-by user;
        key "name";
        leaf name {
          tailf:cli-multi-word-key;
          type string;
        }
      }
    }
    leaf fr-de {
      type empty;
    }
    leaf-list fr-dlci {
      type uint16;
    }
    leaf non-client-nrt {
      type empty;
    }
    container input {
      leaf-list vlan {
        type union {
          type uint16;
          type string;
        }
      }
    }
    list input-interface {
      tailf:cli-suppress-mode;
      tailf:cli-delete-when-empty;
      key "name";
      leaf name {
        tailf:cli-multi-word-key;
        type string;
      }
    }
    container ip {
      leaf-list dscp {
        tailf:cli-flat-list-syntax;
        type dscp-type;
      }
      leaf-list precedence {
        tailf:cli-flat-list-syntax;
        type precedence-type;
      }
      list rtp {
        tailf:cli-suppress-mode;
        tailf:cli-delete-when-empty;
        key "port1 port2";
        leaf port1 {
          type uint16;
        }
        leaf port2 {
          type uint16;
        }
      }
    }
    container mpls {
      container experimental {
        leaf-list topmost {
          tailf:cli-flat-list-syntax;
          type uint16;
        }
      }
    }
    leaf-list precedence {
      tailf:cli-flat-list-syntax;
      type precedence-type;
    }
    container protocol {
      container attribute {
        list category {
          tailf:cli-suppress-mode;
          tailf:cli-delete-when-empty;
          key "category-type";
          leaf category-type {
            type enumeration {
              enum "voice-and-video";
              enum "database";
              enum "email";
              enum "browsing";
              enum "trojan";
              enum "gaming";
              enum "anonymizers";
              enum "backup-and-storage";
              enum "business-and-productivity-tools";
              enum "epayement";
              enum "file-sharing";
              enum "industrial-protocols";
              enum "instant-messaging";
              enum "inter-process-rpc";
              enum "internet-security";
              enum "layer3-over-ip";
              enum "location-based-services";
              enum "net-admin";
              enum "newsgroup";
              enum "other";
              enum "social-networking";
              enum "software-updates";
              enum "consumer-file-sharing";
              enum "consumer-internet";
              enum "consumer-messaging";
              enum "consumer-streaming";
            }
          }
        }
        list sub-category {
          tailf:cli-suppress-mode;
          tailf:cli-delete-when-empty;
          key "name";
          leaf name {
            type string;
          }
        }
        list application-group {
          tailf:cli-suppress-mode;
          tailf:cli-delete-when-empty;
          key "name";
          leaf name {
            type string;
          }
        }
        list traffic-class {
          tailf:cli-suppress-mode;
          tailf:cli-delete-when-empty;
          key "traffic-class-type";
          leaf traffic-class-type {
            type enumeration {
              enum "broadcast-video";
              enum "bulk-data";
              enum "multimedia-conferencing";
              enum "multimedia-streaming";
              enum "network-control";
              enum "ops-admin-mgmt";
              enum "real-time-interactive";
              enum "signaling";
              enum "transactional-data";
              enum "voip-telephony";
            }
          }
        }
        list business-relevance {
          tailf:cli-suppress-mode;
          tailf:cli-delete-when-empty;
          key "business-relevance-type";
          leaf business-relevance-type {
            type enumeration {
              enum "business-irrelevant";
              enum "business-relevant";
              enum "default";
            }
          }
        }
      }
      list protocol-list {
        tailf:cli-drop-node-name;
        tailf:cli-suppress-mode;
        tailf:cli-delete-when-empty;
        key "name";
        leaf name {
          type string;
        }
        list values {
          tailf:cli-drop-node-name;
          tailf:cli-suppress-mode;
          tailf:cli-delete-when-empty;
          ordered-by user;
          key "value";
          leaf value {
            tailf:cli-multi-word-key;
            type string;
          }
        }
      }
    }
    container packet {
      list length {
        tailf:cli-suppress-mode;
        tailf:cli-delete-when-empty;
        ordered-by user;
        key "line";
        leaf line {
          tailf:cli-multi-word-key;
          type string;
        }
      }
    }
    leaf-list qos-group {
      type uint16;
    }
    container source-address {
      leaf-list mac {
        type string;
      }
    }
    container vlan-inner {
      tailf:cli-drop-node-name;
      container vlan {
        leaf-list inner {
          type union {
            type uint16;
            type string;
          }
        }
      }
    }
    leaf-list vlan {
      type union {
        type uint16;
        type string;
      }
    }
    container service {
      container instance {
        leaf-list ethernet {
          type string;
        }
      }
    }
    container security-group {
      list source {
        tailf:cli-suppress-mode;
        tailf:cli-delete-when-empty;
        key "tag";
        leaf tag {
          tailf:cli-expose-key-name;
          type uint16;
        }
      }
      list destination {
        tailf:cli-suppress-mode;
        tailf:cli-delete-when-empty;
        key "tag";
        leaf tag {
          tailf:cli-expose-key-name;
          type uint16;
        }
      }
    }
    container flow {
      list record {
        tailf:cli-suppress-mode;
        tailf:cli-delete-when-empty;
        key "name";
        leaf name {
          type string;
        }
      }
    }
  }

  grouping ip-name-server-grouping {
    list name-server-list {
      tailf:cli-drop-node-name;
      tailf:cli-suppress-mode;
      tailf:cli-delete-when-empty;
      ordered-by user;
      key "address";
      leaf address {
        type union {
          type inet:ipv4-address;
          type inet:ipv6-address;
        }
      }
    }
  }

  grouping ip-host-grouping {
    list host-list {
      tailf:cli-drop-node-name;
      tailf:cli-suppress-mode;
      tailf:cli-delete-when-empty;
      tailf:cli-compact-syntax;
      tailf:cli-sequence-commands;
      key "hostname";
      leaf hostname {
        type string;
      }
      leaf tcp-port-number {
        tailf:cli-drop-node-name;
        tailf:cli-optional-in-sequence;
        type uint16;
      }
      leaf-list ip-address1 {
        tailf:cli-drop-node-name;
        tailf:cli-flat-list-syntax;
        type inet:ipv4-address;
      }
    }
  }

  grouping ip-dhcp-excluded-address-grouping {
    list low-list {
      tailf:cli-drop-node-name;
      tailf:cli-suppress-mode;
      tailf:cli-delete-when-empty;
      key "low";
      leaf low {
        type inet:ipv4-address;
      }
    }
    list low-high-list {
      tailf:cli-drop-node-name;
      tailf:cli-suppress-mode;
      tailf:cli-delete-when-empty;
      key "low high";
      leaf low {
        type inet:ipv4-address;
      }
      leaf high {
        type inet:ipv4-address;
      }
    }
  }

  grouping ntp-peer-grouping {
    list peer-list {
      tailf:cli-drop-node-name;
      tailf:cli-suppress-mode;
      tailf:cli-delete-when-empty;
      tailf:cli-compact-syntax;
      key "name";
      leaf name {
        type inet:host;
      }
      leaf burst {
        type empty;
      }
      leaf iburst {
        type empty;
      }
      leaf key {
        type uint32;
      }
      leaf maxpoll {
        type uint8;
      }
      leaf minpoll {
        type uint8;
      }
      leaf normal-sync {
        type empty;
      }
      leaf prefer {
        type empty;
      }
      container source {
        tailf:cli-flatten-container;
        tailf:cli-compact-syntax;
        uses interface-name-grouping;
      }
      leaf version {
        type uint8;
      }
    }
  }

  grouping sntp-server-grouping {
    list server-list {
      tailf:cli-drop-node-name;
      tailf:cli-suppress-mode;
      tailf:cli-delete-when-empty;
      tailf:cli-compact-syntax;
      key "name";
      leaf name {
        type inet:host;
      }
      leaf key {
        type uint32;
      }
      leaf version {
        type uint8;
      }
    }
  }

  grouping line-grouping {
    leaf location {
      tailf:cli-multi-value;
      type string;
    }
    leaf absolute-timeout {
      type uint32;
    }
    container access-class {
      list access-list {
        tailf:cli-drop-node-name;
        tailf:cli-suppress-mode;
        tailf:cli-delete-when-empty;
        tailf:cli-compact-syntax;
        tailf:cli-sequence-commands {
          tailf:cli-reset-siblings;
        }
        key "direction";
        leaf direction {
          type enumeration {
            enum "in";
            enum "out";
          }
        }
        leaf access-list {
          tailf:cli-drop-node-name;
          tailf:cli-prefix-key;
          type exp-ip-acl-type;
        }
        leaf vrf-also {
          type empty;
        }
      }
    }
    container access-class-vrf {
      tailf:cli-drop-node-name;
      list access-class {
        tailf:cli-suppress-mode;
        tailf:cli-delete-when-empty;
        tailf:cli-compact-syntax;
        tailf:cli-sequence-commands {
          tailf:cli-reset-siblings;
        }
        key "direction vrfname";
        leaf access-list {
          tailf:cli-drop-node-name;
          tailf:cli-prefix-key;
          type exp-ip-acl-type;
        }
        leaf direction {
          type enumeration {
            enum "in";
            enum "out";
          }
        }
        leaf vrfname {
          tailf:cli-expose-key-name;
          type string;
        }
      }
    }
    leaf flush-at-activation {
      type boolean;
    }
    leaf special-character-bits {
      type uint8;
    }
    container activation-character-choice {
      tailf:cli-drop-node-name;
      choice activation-character-choice {
        leaf activation-character {
          type boolean;
        }
        container activation-character-conf {
          tailf:cli-drop-node-name;
          leaf activation-character {
            type union {
              type string;
              type uint8;
            }
          }
        }
      }
    }
    leaf escape-character {
      type union {
        type uint8;
        type enumeration {
          enum "BREAK";
          enum "DEFAULT";
          enum "NONE";
        }
      }
    }
    leaf disconnect-character {
      type uint8;
    }
    container script {
      leaf dialer {
        type string;
      }
    }
    container modem {
      leaf enable {
        type boolean;
      }
      leaf Dialin {
        type empty;
      }
      container InOut {
        presence "true";
        leaf hangup {
          type empty;
        }
      }
      leaf DTR-active {
        type empty;
      }
      leaf Host {
        type empty;
      }
      container autoconfigure {
        leaf discovery {
          type empty;
        }
        leaf type {
          type string;
        }
      }
    }
    leaf terminal-type {
      type string;
    }
    container exec-choice {
      tailf:cli-drop-node-name;
      choice exec-choice {
        leaf exec {
          type boolean;
        }
        container exec-conf {
          tailf:cli-drop-node-name;
          container exec {
            container prompt {
              leaf timestamp {
                type empty;
              }
            }
          }
        }
      }
    }
    container exec-timeout {
      tailf:cli-compact-syntax;
      tailf:cli-sequence-commands;
      leaf minutes {
        tailf:cli-drop-node-name;
        type uint32;
      }
      leaf seconds {
        tailf:cli-drop-node-name;
        type uint32;
      }
    }
    leaf exec-banner {
      type boolean;
    }
    leaf motd-banner {
      type boolean;
    }
    leaf refuse-message {
      type string;
    }
    leaf vacant-message {
      type string;
    }
    leaf international {
      type empty;
    }
    container timeout {
      container login {
        leaf response {
          type uint16;
        }
      }
    }
    leaf session-limit {
      type uint32;
    }
    container session-disconnect-warning {
      tailf:cli-compact-syntax;
      tailf:cli-sequence-commands {
        tailf:cli-reset-siblings;
      }
      leaf seconds {
        tailf:cli-drop-node-name;
        type uint32;
      }
      leaf message {
        tailf:cli-multi-value;
        type string;
      }
    }
    container logging {
      container synchronous {
        tailf:cli-delete-when-empty;
        presence "true";
        leaf level {
          type union {
            type uint8;
            type enumeration {
              enum "all";
            }
          }
        }
      }
    }
    leaf rotary {
      type uint8;
    }
    container login {
      tailf:cli-delete-when-empty;
      presence "true";
      leaf local {
        type empty;
      }
    }
    container local-authentication {
      tailf:cli-drop-node-name;
      container login {
        leaf tacacs {
          type empty;
        }
        leaf authentication {
          type union {
            type string;
            type enumeration {
              enum "default";
            }
          }
        }
      }
    }
    leaf autohangup {
      type empty;
    }
    container autoselect {
      leaf during-login {
        type empty;
      }
      leaf ppp {
        type empty;
      }
    }
    container autocommand {
      leaf command {
        tailf:cli-drop-node-name;
        tailf:cli-multi-value;
        type string;
      }
    }
    container accounting {
      leaf exec {
        type union {
          type string;
          type enumeration {
            enum "default";
          }
        }
      }
      list commands {
        tailf:cli-suppress-mode;
        tailf:cli-delete-when-empty;
        tailf:cli-compact-syntax;
        key "level";
        leaf level {
          type uint8;
        }
        leaf name {
          tailf:cli-drop-node-name;
          type union {
            type string;
            type enumeration {
              enum "default";
            }
          }
        }
      }
    }
    leaf logout-warning {
      type uint32;
    }
    container ip {
      leaf netmask-format {
        type enumeration {
          enum "bit-count";
          enum "decimal";
          enum "hexadecimal";
        }
      }
    }
    container ipv6 {
      list access-class {
        tailf:cli-suppress-mode;
        tailf:cli-delete-when-empty;
        tailf:cli-compact-syntax;
        tailf:cli-sequence-commands;
        key "direction";
        leaf direction {
          type enumeration {
            enum "in";
            enum "out";
          }
        }
        leaf access-list {
          tailf:cli-drop-node-name;
          tailf:cli-prefix-key;
          type exp-ip-acl-type;
        }
      }
      container access-class-vrf {
        tailf:cli-drop-node-name;
        list access-class {
          tailf:cli-suppress-mode;
          tailf:cli-delete-when-empty;
          key "direction vrfname";
          leaf access-list {
            tailf:cli-drop-node-name;
            tailf:cli-prefix-key;
            type exp-ip-acl-type;
          }
          leaf direction {
            type enumeration {
              enum "in";
              enum "out";
            }
          }
          leaf vrfname {
            tailf:cli-expose-key-name;
            type string;
          }
        }
      }
    }
    container authorization {
      leaf exec {
        type union {
          type enumeration {
            enum "default";
          }
          type string;
        }
      }
      list commands {
        tailf:cli-suppress-mode;
        tailf:cli-delete-when-empty;
        tailf:cli-compact-syntax;
        key "level";
        leaf level {
          type uint8;
        }
        leaf name {
          tailf:cli-drop-node-name;
          type union {
            type string;
            type enumeration {
              enum "default";
            }
          }
        }
      }
    }
    container history {
      leaf size {
        type uint16;
      }
    }
    leaf full-help {
      type empty;
    }
    container password {
      tailf:cli-compact-syntax;
      tailf:cli-sequence-commands;
      uses password-grouping {
        refine "secret";
      }
    }
    container privilege {
      leaf level {
        type uint8;
      }
    }
    container session-timeout {
      tailf:cli-compact-syntax;
      tailf:cli-sequence-commands;
      leaf session-timeout-value {
        tailf:cli-drop-node-name;
        type uint16;
      }
      leaf output {
        type empty;
      }
    }
    leaf stopbits {
      type enumeration {
        enum "1";
        enum "1.5";
        enum "2";
      }
    }
    container telnet {
      leaf break-on-ip {
        type empty;
      }
      leaf transparent {
        type empty;
      }
    }
    leaf domain-lookup {
      type boolean;
    }
    container transport {
      leaf-list input {
        tailf:cli-flat-list-syntax;
        type enumeration {
          enum "all";
          enum "none";
          enum "ssh";
          enum "telnet";
          enum "lat";
          enum "pad";
          enum "udptn";
          enum "rlogin";
          enum "lapb-ta";
          enum "mop";
          enum "v120";
          enum "acercon";
          enum "nasi";
        }
      }
      leaf-list output {
        tailf:cli-flat-list-syntax;
        type enumeration {
          enum "all";
          enum "none";
          enum "ssh";
          enum "telnet";
          enum "lat";
          enum "pad";
          enum "udptn";
          enum "rlogin";
          enum "lapb-ta";
          enum "mop";
          enum "v120";
          enum "acercon";
          enum "nasi";
        }
      }
      leaf preferred {
        type enumeration {
          enum "none";
          enum "ssh";
          enum "telnet";
        }
      }
    }
    leaf speed {
      type uint32;
    }
    leaf rxspeed {
      type uint32;
    }
    leaf txspeed {
      type uint32;
    }
    container flowcontrol {
      choice flowcontrol-choice {
        container hardware {
          presence "true";
          leaf out {
            type empty;
          }
        }
        container software {
          presence "true";
        }
        container none {
          tailf:cli-drop-node-name;
          tailf:cli-compact-syntax;
          tailf:cli-sequence-commands {
            tailf:cli-reset-siblings;
          }
          leaf mode {
            tailf:cli-drop-node-name;
            type enumeration {
              enum "NONE";
            }
          }
          leaf lock {
            type empty;
          }
        }
      }
    }
    leaf length {
      type uint16;
    }
    leaf width {
      type uint16;
    }
    container media-type {
      leaf rj45 {
        type empty;
      }
    }
  }

  grouping queue-size-grouping {
    leaf queue-size-1 {
      tailf:cli-drop-node-name;
      type uint8;
    }
    leaf queue-size-2 {
      tailf:cli-drop-node-name;
      type uint8;
    }
    leaf queue-size-3 {
      tailf:cli-drop-node-name;
      type uint8;
    }
    leaf queue-size-4 {
      tailf:cli-drop-node-name;
      type uint8;
    }
    leaf queue-size-5 {
      tailf:cli-drop-node-name;
      type uint8;
    }
    leaf queue-size-6 {
      tailf:cli-drop-node-name;
      type uint8;
    }
    leaf queue-size-7 {
      tailf:cli-drop-node-name;
      type uint8;
    }
    leaf queue-size-8 {
      tailf:cli-drop-node-name;
      type uint8;
    }
  }

  grouping interface-common-pre-grouping {
    leaf mac-address {
      type string;
    }
    leaf description {
      tailf:cli-multi-value;
      type string;
    }
    container backup {
      container delay {
        tailf:cli-compact-syntax;
        tailf:cli-sequence-commands;
        leaf enable-delay-period {
          tailf:cli-drop-node-name;
          type union {
            type uint32;
            type enumeration {
              enum "never";
            }
          }
        }
        leaf disable-delay-period {
          tailf:cli-drop-node-name;
          type union {
            type uint32;
            type enumeration {
              enum "never";
            }
          }
        }
      }
      container interface {
        uses interface-name-grouping;
      }
    }
    list glbp {
      tailf:cli-suppress-mode;
      tailf:cli-delete-when-empty;
      key "group-number";
      leaf group-number {
        type uint16;
      }
      leaf ip {
        type inet:ipv4-address;
      }
      container ip-secondary-list {
        tailf:cli-drop-node-name;
        list ip {
          tailf:cli-suppress-mode;
          tailf:cli-delete-when-empty;
          key "address";
          leaf address {
            type inet:ipv4-address;
          }
          leaf secondary {
            type empty;
          }
        }
      }
      container timers {
        tailf:cli-compact-syntax;
        tailf:cli-sequence-commands {
          tailf:cli-reset-siblings;
        }
        container hellotime {
          tailf:cli-drop-node-name;
          tailf:cli-flatten-container;
          tailf:cli-compact-syntax;
          choice hellotime-choice {
            leaf seconds {
              tailf:cli-drop-node-name;
              type uint8;
            }
            leaf msec {
              type uint32;
            }
          }
        }
        container holdtime {
          tailf:cli-drop-node-name;
          tailf:cli-flatten-container;
          tailf:cli-compact-syntax;
          choice holdtime-choice {
            leaf seconds {
              tailf:cli-drop-node-name;
              type uint8;
            }
            leaf msec {
              type uint32;
            }
          }
        }
      }
      leaf priority {
        type uint8;
      }
      container preempt {
        tailf:cli-delete-when-empty;
        presence "true";
        container delay {
          leaf minimum {
            type uint32;
          }
        }
      }
      leaf load-balancing {
        type enumeration {
          enum "host-dependent";
          enum "round-robin";
          enum "weighted";
        }
      }
      container authentication {
        leaf text {
          type string;
        }
      }
      container weighting {
        list track {
          tailf:cli-suppress-mode;
          tailf:cli-delete-when-empty;
          key "id";
          leaf id {
            type uint16;
          }
          leaf decrement {
            type uint8;
          }
        }
      }
    }
  }

  grouping interface-ospfv3-grouping {
    container area {
      tailf:cli-compact-syntax;
      tailf:cli-sequence-commands;
      leaf id {
        tailf:cli-drop-node-name;
        type union {
          type uint32;
          type inet:ipv4-address;
        }
      }
      leaf instance {
        type uint8;
      }
    }
    leaf priority {
      type uint8;
    }
    leaf cost {
      type uint16;
    }
    container cost-dynamic {
      tailf:cli-drop-node-name;
      container cost {
        leaf dynamic {
          type empty;
        }
        container dynamic-conf {
          tailf:cli-drop-node-name;
          container dynamic {
            container hysteresis {
              tailf:cli-compact-syntax;
              tailf:cli-sequence-commands;
              tailf:cli-delete-when-empty;
              presence "true";
              choice hysteresis-choice {
                leaf percent {
                  type uint8;
                }
                leaf threshold {
                  type uint16;
                }
              }
            }
            container weight {
              leaf throughput {
                type uint8;
              }
              leaf resources {
                type uint8;
              }
              leaf latency {
                type uint8;
              }
              leaf L2-factor {
                type uint8;
              }
            }
          }
        }
      }
    }
    container authentication {
      choice authentication-choice {
        leaf key-chain {
          type string;
        }
        leaf null {
          type empty;
        }
        container ipsec {
          tailf:cli-compact-syntax;
          tailf:cli-sequence-commands;
          leaf spi {
            type uint32;
          }
          leaf auth {
            tailf:cli-drop-node-name;
            type enumeration {
              enum "md5";
              enum "sha1";
            }
          }
          leaf type {
            tailf:cli-drop-node-name;
            tailf:cli-optional-in-sequence;
            type enumeration {
              enum "0";
              enum "7";
            }
          }
          leaf secret {
            tailf:cli-drop-node-name;
            type string;
          }
        }
      }
    }
    container flood-reduction {
      tailf:cli-delete-when-empty;
      presence "true";
      leaf disable {
        type empty;
      }
    }
    container bfd {
      tailf:cli-delete-when-empty;
      presence "true";
      choice bfd-choice {
        leaf disable {
          type empty;
        }
        leaf strict-mode {
          type empty;
        }
      }
    }
    container network {
      choice network-choice {
        container point-to-multipoint {
          tailf:cli-delete-when-empty;
          presence "true";
          leaf non-broadcast {
            type empty;
          }
        }
        leaf point-to-point {
          type empty;
        }
        leaf broadcast {
          type empty;
        }
        leaf non-broadcast {
          type empty;
        }
        leaf manet {
          type empty;
        }
      }
    }
    leaf hello-interval {
      type uint16;
    }
    leaf dead-interval {
      type uint16;
    }
  }

  grouping interface-storm-control-grouping {
    container level-bps-pps {
      tailf:cli-drop-node-name;
      container level {
        tailf:cli-compact-syntax;
        tailf:cli-sequence-commands {
          tailf:cli-reset-siblings;
        }
        choice level-choice {
          case bps {
            leaf bps {
              type string;
            }
            leaf bps-falling {
              tailf:cli-drop-node-name;
              type string;
            }
          }
          case pps {
            leaf pps {
              type string;
            }
            leaf pps-falling {
              tailf:cli-drop-node-name;
              type string;
            }
          }
        }
      }
    }
    container level-threshold {
      tailf:cli-drop-node-name;
      container level {
        tailf:cli-compact-syntax;
        leaf rising {
          tailf:cli-drop-node-name;
          type decimal64 {
            fraction-digits 2;
          }
        }
        leaf falling {
          tailf:cli-drop-node-name;
          type decimal64 {
            fraction-digits 2;
          }
        }
      }
    }
  }

  grouping interface-queue-grouping {
    container bandwidth {
      tailf:cli-compact-syntax;
      tailf:cli-sequence-commands {
        tailf:cli-reset-siblings;
      }
      choice bandwidth-choice {
        case a {
          leaf weight-1 {
            tailf:cli-drop-node-name;
            type uint8;
          }
          leaf weight-2 {
            tailf:cli-drop-node-name;
            type uint8;
          }
          leaf weight-3 {
            tailf:cli-drop-node-name;
            type uint8;
          }
          leaf weight-4 {
            tailf:cli-drop-node-name;
            type uint8;
          }
          leaf weight-5 {
            tailf:cli-drop-node-name;
            type uint8;
          }
          leaf weight-6 {
            tailf:cli-drop-node-name;
            type uint8;
          }
          leaf weight-7 {
            tailf:cli-drop-node-name;
            type uint8;
          }
        }
        case b {
          container percent {
            tailf:cli-compact-syntax;
            tailf:cli-sequence-commands {
              tailf:cli-reset-siblings;
            }
            leaf percent-1 {
              tailf:cli-drop-node-name;
              type uint8;
            }
            leaf percent-2 {
              tailf:cli-drop-node-name;
              type uint8;
            }
            leaf percent-3 {
              tailf:cli-drop-node-name;
              type uint8;
            }
            leaf percent-4 {
              tailf:cli-drop-node-name;
              type uint8;
            }
            leaf percent-5 {
              tailf:cli-drop-node-name;
              type uint8;
            }
            leaf percent-6 {
              tailf:cli-drop-node-name;
              type uint8;
            }
            leaf percent-7 {
              tailf:cli-drop-node-name;
              type uint8;
            }
          }
        }
      }
    }
    list dscp-map {
      tailf:cli-suppress-mode;
      tailf:cli-delete-when-empty;
      tailf:cli-compact-syntax;
      key "queue threshold";
      leaf queue {
        type uint8;
      }
      leaf threshold {
        type uint8;
      }
      list values {
        tailf:cli-drop-node-name;
        tailf:cli-suppress-mode;
        tailf:cli-delete-when-empty;
        ordered-by user;
        key "value";
        leaf value {
          tailf:cli-multi-word-key;
          type string;
        }
      }
    }
    list cos-map {
      tailf:cli-suppress-mode;
      tailf:cli-delete-when-empty;
      tailf:cli-compact-syntax;
      tailf:cli-sequence-commands {
        tailf:cli-reset-siblings;
      }
      key "queue-id threshold-id";
      leaf queue-id {
        type uint8;
      }
      leaf threshold-id {
        type uint8;
      }
      leaf-list cos-values {
        tailf:cli-drop-node-name;
        tailf:cli-flat-list-syntax;
        type uint8;
      }
    }
    container queue-limit {
      tailf:cli-compact-syntax;
      tailf:cli-sequence-commands {
        tailf:cli-reset-siblings;
      }
      leaf weight-a {
        tailf:cli-drop-node-name;
        type uint8;
      }
      leaf weight-b {
        tailf:cli-drop-node-name;
        type uint8;
      }
      leaf weight-c {
        tailf:cli-drop-node-name;
        type uint8;
      }
      leaf weight-d {
        tailf:cli-drop-node-name;
        type uint8;
      }
      leaf weight-e {
        tailf:cli-drop-node-name;
        type uint8;
      }
      leaf weight-f {
        tailf:cli-drop-node-name;
        type uint8;
      }
      leaf weight-g {
        tailf:cli-drop-node-name;
        type uint8;
      }
    }
    container random-detect {
      list max-threshold {
        tailf:cli-suppress-mode;
        tailf:cli-delete-when-empty;
        tailf:cli-compact-syntax;
        tailf:cli-sequence-commands {
          tailf:cli-reset-siblings;
        }
        key "id";
        leaf id {
          type uint8;
        }
        uses queue-size-grouping;
      }
      list min-threshold {
        tailf:cli-suppress-mode;
        tailf:cli-delete-when-empty;
        tailf:cli-compact-syntax;
        tailf:cli-sequence-commands {
          tailf:cli-reset-siblings;
        }
        key "id";
        leaf id {
          type uint8;
        }
        uses queue-size-grouping;
      }
    }
    list threshold {
      tailf:cli-suppress-mode;
      tailf:cli-delete-when-empty;
      tailf:cli-compact-syntax;
      tailf:cli-sequence-commands {
        tailf:cli-reset-siblings;
      }
      key "id";
      leaf id {
        type uint8;
      }
      uses queue-size-grouping;
    }
    list min-reserve {
      tailf:cli-suppress-mode;
      tailf:cli-delete-when-empty;
      key "id";
      leaf id {
        type uint8;
      }
      leaf level {
        tailf:cli-drop-node-name;
        type uint8;
      }
    }
  }

  grouping interface-common-grouping {
    container arp {
      leaf timeout {
        type uint32;
      }
      leaf frame-relay {
        type boolean;
      }
      leaf authorized {
        type empty;
      }
    }
    container access-session {
      leaf host-mode {
        type enumeration {
          enum "multi-auth";
          enum "multi-domain";
          enum "multi-host";
          enum "single-host";
        }
      }
      leaf control-direction {
        type enumeration {
          enum "both";
          enum "in";
        }
      }
      leaf closed {
        type empty;
      }
      leaf port-control {
        type enumeration {
          enum "auto";
          enum "force-authorized";
          enum "force-unauthorized";
        }
      }
    }
    container mab {
      presence "true";
      leaf eap {
        type empty;
      }
    }
    leaf medium {
      type enumeration {
        enum "p2p";
      }
    }
    container fair-queue {
      tailf:cli-compact-syntax;
      tailf:cli-sequence-commands;
      tailf:cli-delete-when-empty;
      presence "true";
      leaf congestive-discard-threshold {
        tailf:cli-drop-node-name;
        type uint16;
      }
      leaf dynamic-queues {
        tailf:cli-drop-node-name;
        type uint16;
      }
      leaf reservable-queues {
        tailf:cli-drop-node-name;
        type uint16;
      }
    }
    container flowcontrol {
      leaf bidirectional {
        type boolean;
      }
      leaf receive {
        type enumeration {
          enum "desired";
          enum "off";
          enum "on";
        }
      }
      leaf send {
        type enumeration {
          enum "desired";
          enum "off";
          enum "on";
        }
      }
    }
    container traffic-shape {
      container rate {
        tailf:cli-compact-syntax;
        tailf:cli-sequence-commands;
        leaf bit-rate {
          tailf:cli-drop-node-name;
          type uint32;
        }
        leaf burst-size {
          tailf:cli-drop-node-name;
          type uint32;
        }
        leaf excess-burst-size {
          tailf:cli-drop-node-name;
          type uint32;
        }
        leaf max-buffers {
          tailf:cli-drop-node-name;
          type uint16;
        }
      }
      list group {
        tailf:cli-suppress-mode;
        tailf:cli-delete-when-empty;
        tailf:cli-compact-syntax;
        tailf:cli-sequence-commands;
        key "access-list";
        leaf access-list {
          type uint16;
        }
        leaf bit-rate {
          tailf:cli-drop-node-name;
          type uint32;
        }
        leaf burst-size {
          tailf:cli-drop-node-name;
          type uint32;
        }
        leaf excess-burst-size {
          tailf:cli-drop-node-name;
          type uint32;
        }
        leaf max-buffers {
          tailf:cli-drop-node-name;
          type uint16;
        }
      }
    }
    choice keepalive-choice {
      leaf keepalive {
        type boolean;
      }
      container keepalive-period {
        tailf:cli-drop-node-name;
        leaf keepalive {
          type uint16;
        }
      }
      container keepalive-period-retries {
        tailf:cli-drop-node-name;
        container keepalive {
          tailf:cli-compact-syntax;
          tailf:cli-sequence-commands {
            tailf:cli-reset-siblings;
          }
          leaf period {
            tailf:cli-drop-node-name;
            type uint16;
          }
          leaf retries {
            tailf:cli-drop-node-name;
            type uint8;
          }
        }
      }
    }
    container snmp {
      container ifindex {
        leaf persist {
          type empty;
        }
      }
      container trap {
        leaf link-status {
          type boolean;
        }
        container link-status-capas {
          tailf:cli-drop-node-name;
          container link-status {
            container permit {
              leaf duplicates {
                type empty;
              }
            }
          }
        }
        container mac-notification {
          container change {
            leaf added {
              type empty;
            }
            leaf removed {
              type empty;
            }
          }
        }
      }
    }
    container flow-sampler {
      leaf name {
        tailf:cli-drop-node-name;
        type string;
      }
      container egress {
        tailf:cli-drop-node-name;
        tailf:cli-compact-syntax;
        tailf:cli-sequence-commands;
        leaf name {
          tailf:cli-drop-node-name;
          type string;
        }
        leaf egress {
          type empty;
        }
      }
    }
    container lldp {
      leaf transmit {
        type boolean;
      }
      leaf receive {
        type boolean;
      }
    }
    container bfd {
      container interval {
        tailf:cli-compact-syntax;
        tailf:cli-sequence-commands {
          tailf:cli-reset-siblings;
        }
        leaf msecs {
          tailf:cli-drop-node-name;
          type uint16;
        }
        leaf min_rx {
          type uint16;
        }
        leaf multiplier {
          type uint8;
        }
      }
      leaf echo {
        type boolean;
      }
      leaf template {
        type string;
      }
    }
    leaf dapr {
      type enumeration {
        enum "egress";
        enum "ingress";
      }
    }
    container bandwidth {
      tailf:cli-compact-syntax;
      tailf:cli-sequence-commands {
        tailf:cli-reset-siblings;
      }
      leaf inherit {
        tailf:cli-optional-in-sequence;
        type empty;
      }
      leaf kilobits {
        tailf:cli-drop-node-name;
        type uint32;
      }
    }
    container bandwidth-no-compact {
      tailf:cli-drop-node-name;
      container bandwidth {
        leaf qos-reference {
          type uint32;
        }
      }
    }
    container cdp {
      leaf enable {
        type boolean;
      }
      container tlv {
        container app {
          tailf:cli-compact-syntax;
          tailf:cli-sequence-commands;
          presence "true";
          leaf tlvtype {
            type uint16;
          }
          leaf value {
            type string;
          }
        }
        leaf server-location {
          type empty;
        }
        leaf location {
          type empty;
        }
      }
      leaf filter-tlv-list {
        type string;
      }
    }
    leaf vtp {
      type boolean;
    }
    container mop {
      leaf xenabled {
        tailf:alt-name "enabled";
        type boolean;
      }
      leaf sysid {
        type boolean;
      }
    }
    container dampening {
      tailf:cli-compact-syntax;
      tailf:cli-sequence-commands {
        tailf:cli-reset-siblings;
      }
      tailf:cli-delete-when-empty;
      presence "true";
      leaf dampening-time {
        tailf:cli-drop-node-name;
        type uint16;
      }
      leaf reuse-threshold {
        tailf:cli-drop-node-name;
        type uint16;
      }
      leaf suppress-threshold {
        tailf:cli-drop-node-name;
        type uint16;
      }
      leaf max-suppress {
        tailf:cli-drop-node-name;
        type uint8;
      }
      leaf restart {
        type uint16;
      }
    }
    list vlan-range {
      key "id";
      leaf id {
        tailf:cli-suppress-range;
        type uint16;
      }
      container service-policy {
        uses service-policy-grouping {
          refine "output";
          refine "input";
        }
      }
    }
    container mace {
      leaf enable {
        type empty;
      }
    }
    container private-vlan {
      container mapping {
        leaf vlans {
          tailf:cli-drop-node-name;
          type string;
        }
      }
    }
    list hold-queue {
      tailf:cli-suppress-mode;
      tailf:cli-delete-when-empty;
      tailf:cli-compact-syntax;
      tailf:cli-sequence-commands {
        tailf:cli-reset-siblings;
      }
      key "direction";
      leaf direction {
        type enumeration {
          enum "in";
          enum "out";
        }
      }
      leaf queue-length {
        tailf:cli-drop-node-name;
        tailf:cli-prefix-key;
        type uint32;
      }
    }
    container mpls {
      container accounting {
        container experimental {
          leaf input {
            type empty;
          }
          leaf output {
            type empty;
          }
        }
      }
      container bgp {
        leaf forwarding {
          type empty;
        }
      }
      container label {
        leaf protocol {
          type enumeration {
            enum "both";
            enum "ldp";
            enum "tdp";
          }
        }
      }
      container ldp {
        container igp {
          leaf autoconfig {
            type boolean;
          }
          choice sync-choice {
            leaf sync {
              type boolean;
            }
            container sync-delay {
              tailf:cli-drop-node-name;
              container sync {
                leaf delay {
                  type uint8;
                }
              }
            }
          }
        }
        container discovery {
          leaf transport-address {
            type ldp-discovery-address-type;
          }
        }
      }
      leaf mtu {
        type union {
          type uint16;
          type uint16;
          type uint16;
          type enumeration {
            enum "max";
          }
        }
      }
      container traffic-eng {
        leaf administrative-weight {
          type uint32;
        }
        leaf tunnels {
          type empty;
        }
        leaf backup-path {
          type string;
        }
        leaf attribute-flags {
          type string;
        }
        container flooding {
          container thresholds {
            leaf-list down {
              tailf:cli-flat-list-syntax;
              type uint8;
            }
            leaf-list up {
              tailf:cli-flat-list-syntax;
              type uint8;
            }
          }
        }
      }
      container flow {
        list monitor {
          tailf:cli-suppress-mode;
          tailf:cli-delete-when-empty;
          tailf:cli-compact-syntax;
          tailf:cli-sequence-commands {
            tailf:cli-reset-siblings;
          }
          key "name direction";
          leaf name {
            type string;
          }
          leaf sampler {
            tailf:cli-prefix-key {
              tailf:cli-before-key "2";
            }
            tailf:cli-optional-in-sequence;
            type string;
          }
          leaf direction {
            type enumeration {
              enum "input";
              enum "output";
            }
          }
        }
      }
      leaf ip {
        type empty;
      }
      leaf nhrp {
        type empty;
      }
      leaf propagate-cos {
        type empty;
      }
    }
    container isis {
      container bfd {
        tailf:cli-delete-when-empty;
        presence "true";
        leaf disable {
          type empty;
        }
      }
      leaf tag {
        type uint32;
      }
      leaf circuit-type {
        type enumeration {
          enum "level-1";
          enum "level-1-2";
          enum "level-2-only";
        }
      }
      leaf network {
        type enumeration {
          enum "point-to-point";
        }
      }
      container metric-level {
        tailf:cli-drop-node-name;
        list metric {
          tailf:cli-suppress-mode;
          tailf:cli-delete-when-empty;
          tailf:cli-compact-syntax;
          tailf:cli-sequence-commands;
          key "level";
          leaf level {
            type enumeration {
              enum "level-1";
              enum "level-2";
            }
          }
          leaf default {
            tailf:cli-drop-node-name;
            tailf:cli-prefix-key;
            type union {
              type uint32;
              type enumeration {
                enum "maximum";
              }
            }
          }
        }
      }
      leaf lsp-interval {
        type uint32;
      }
      uses router-isis-interface-grouping;
      container ipv6 {
        choice metric-choice {
          leaf metric {
            type union {
              type uint32;
              type enumeration {
                enum "maximum";
              }
            }
          }
          container metric-level {
            tailf:cli-drop-node-name;
            list metric {
              tailf:cli-suppress-mode;
              tailf:cli-delete-when-empty;
              tailf:cli-compact-syntax;
              tailf:cli-sequence-commands;
              key "level";
              leaf level {
                type enumeration {
                  enum "level-1";
                  enum "level-2";
                }
              }
              leaf value {
                tailf:cli-drop-node-name;
                tailf:cli-prefix-key;
                type union {
                  type uint32;
                  type enumeration {
                    enum "maximum";
                  }
                }
              }
            }
          }
        }
        leaf tag {
          type uint32;
        }
      }
      leaf three-way-handshake {
        type enumeration {
          enum "cisco";
          enum "ietf";
        }
      }
      choice priority-choice {
        leaf priority {
          type uint8;
        }
        container priority-level-1-2 {
          tailf:cli-drop-node-name;
          list priority {
            tailf:cli-suppress-mode;
            tailf:cli-delete-when-empty;
            tailf:cli-compact-syntax;
            tailf:cli-sequence-commands;
            key "level";
            leaf level {
              type enumeration {
                enum "level-1";
                enum "level-2";
              }
            }
            leaf priority {
              tailf:cli-drop-node-name;
              tailf:cli-prefix-key;
              type uint8;
            }
          }
        }
      }
      container hello {
        choice padding-choice {
          container padding-always {
            tailf:cli-drop-node-name;
            container padding {
              leaf always {
                type boolean;
              }
            }
          }
          leaf padding {
            type boolean;
          }
        }
      }
      container hello-multiplier {
        leaf seconds {
          tailf:cli-drop-node-name;
          type uint16;
        }
      }
      container hello-interval {
        choice hello-interval-choice {
          leaf seconds {
            tailf:cli-drop-node-name;
            type uint16;
          }
          leaf minimal {
            type empty;
          }
        }
      }
      choice csnp-interval-choice {
        leaf csnp-interval {
          type uint16;
        }
        container csnp-interval-level {
          tailf:cli-drop-node-name;
          list csnp-interval {
            tailf:cli-suppress-mode;
            tailf:cli-delete-when-empty;
            tailf:cli-compact-syntax;
            tailf:cli-sequence-commands;
            key "level";
            leaf level {
              type enumeration {
                enum "level-1";
                enum "level-2";
              }
            }
            leaf seconds {
              tailf:cli-drop-node-name;
              tailf:cli-prefix-key;
              type uint16;
            }
          }
        }
      }
      choice password-choice {
        leaf password {
          type string;
        }
        container password-level-1-2 {
          tailf:cli-drop-node-name;
          list password {
            tailf:cli-compact-syntax;
            tailf:cli-sequence-commands;
            key "level";
            leaf password {
              tailf:cli-prefix-key;
              tailf:cli-drop-node-name;
              type string;
            }
            leaf level {
              type enumeration {
                enum "level-1";
                enum "level-2";
              }
            }
          }
        }
      }
      container affinity {
        container flex-algo {
          tailf:cli-add-mode;
          list name {
            tailf:cli-suppress-mode;
            tailf:cli-delete-when-empty;
            key "name";
            leaf name {
              type string;
            }
          }
        }
      }
      container delay {
        container normalize {
          tailf:cli-compact-syntax;
          tailf:cli-sequence-commands {
            tailf:cli-reset-siblings;
          }
          leaf interval {
            type uint32;
          }
          leaf offset {
            type uint32;
          }
        }
      }
      container fast-reroute {
        container protection {
          leaf level-1 {
            type empty;
          }
          leaf level-2 {
            type empty;
          }
        }
        container candidate {
          leaf level-1 {
            type empty;
          }
          leaf level-2 {
            type empty;
          }
        }
        container ti-lfa {
          container protection {
            leaf level-1 {
              type empty;
            }
            leaf level-2 {
              type empty;
            }
          }
        }
      }
      container advertise {
        leaf prefix {
          type boolean;
        }
      }
    }
    choice vrf-choice {
      container ip-vrf {
        tailf:cli-drop-node-name;
        container ip {
          container vrf {
            leaf forwarding {
              type string;
            }
          }
        }
      }
      container vrf-downstream {
        tailf:cli-drop-node-name;
        container vrf {
          tailf:cli-compact-syntax;
          tailf:cli-sequence-commands {
            tailf:cli-reset-siblings;
          }
          leaf forwarding {
            type string;
          }
          leaf downstream {
            type string;
          }
        }
      }
      container vrf {
        leaf forwarding {
          type string;
        }
      }
    }
    leaf mtu {
      type uint16;
    }
    container pm-path {
      tailf:cli-compact-syntax;
      tailf:cli-sequence-commands {
        tailf:cli-reset-siblings;
      }
      leaf name {
        tailf:cli-drop-node-name;
        type string;
      }
      leaf interface-id {
        type uint32;
      }
    }
    container ip {
      list access-group {
        tailf:cli-suppress-mode;
        tailf:cli-delete-when-empty;
        tailf:cli-compact-syntax;
        tailf:cli-sequence-commands {
          tailf:cli-reset-siblings;
        }
        key "direction";
        leaf direction {
          type enumeration {
            enum "in" {
              tailf:code-name "access_group_direction_in";
            }
            enum "out" {
              tailf:code-name "access_group_direction_out";
            }
          }
        }
        leaf common {
          tailf:cli-prefix-key;
          tailf:cli-optional-in-sequence;
          type empty;
        }
        leaf access-list {
          tailf:cli-drop-node-name;
          tailf:cli-prefix-key;
          type exp-ip-acl-type;
        }
        leaf regular-access-list {
          tailf:cli-drop-node-name;
          tailf:cli-prefix-key;
          tailf:cli-optional-in-sequence;
          type exp-ip-acl-type;
        }
      }
      container authentication {
        container mode {
          list eigrp {
            tailf:cli-suppress-mode;
            tailf:cli-delete-when-empty;
            key "as-no";
            leaf as-no {
              type uint16;
            }
            leaf md5 {
              type empty;
            }
          }
        }
        container key-chain {
          list eigrp {
            tailf:cli-suppress-mode;
            tailf:cli-delete-when-empty;
            key "as-no";
            leaf as-no {
              type uint16;
            }
            leaf key-chain {
              tailf:cli-drop-node-name;
              type string;
            }
          }
        }
      }
      container accounting {
        tailf:cli-delete-when-empty;
        presence "true";
        leaf output-packets {
          type empty;
        }
        container precedence {
          leaf input {
            type empty;
          }
          leaf output {
            type empty;
          }
        }
        leaf access-violations {
          type empty;
        }
      }
      container vrf {
        leaf receive {
          type string;
        }
        leaf sitemap {
          type string;
        }
      }
      container arp {
        container inspection {
          leaf trust {
            type empty;
          }
          container limit {
            tailf:cli-compact-syntax;
            tailf:cli-sequence-commands {
              tailf:cli-reset-siblings;
            }
            choice limit-choice {
              leaf none {
                type empty;
              }
              leaf rate {
                type uint16;
              }
            }
            container burst {
              tailf:cli-flatten-container;
              leaf interval {
                type uint8;
              }
            }
          }
        }
      }
      choice address-choice {
        case no-address {
          container no-address {
            tailf:cli-drop-node-name;
            leaf address {
              type boolean;
            }
          }
          container unnumbered {
            tailf:cli-compact-syntax;
            tailf:cli-sequence-commands {
              tailf:cli-reset-siblings;
            }
            uses interface-name-grouping;
            leaf poll {
              type empty;
            }
            leaf point-to-point {
              type empty;
            }
          }
        }
        container address {
          choice address-choice {
            case fixed-case {
              container primary {
                tailf:cli-drop-node-name;
                tailf:cli-compact-syntax;
                tailf:cli-sequence-commands;
                leaf address {
                  tailf:cli-drop-node-name;
                  type inet:ipv4-address;
                }
                leaf mask {
                  tailf:cli-drop-node-name;
                  type inet:ipv4-address;
                }
              }
              list secondary {
                tailf:cli-drop-node-name;
                tailf:cli-suppress-mode;
                tailf:cli-delete-when-empty;
                tailf:cli-compact-syntax;
                key "address mask";
                leaf address {
                  type inet:ipv4-address;
                }
                leaf mask {
                  type inet:ipv4-address;
                }
                leaf secondary {
                  type empty;
                }
              }
            }
            case dhcp-case {
              container dhcp {
                tailf:cli-compact-syntax;
                tailf:cli-sequence-commands;
                presence "true";
                container client-id {
                  tailf:cli-optional-in-sequence;
                  tailf:cli-flatten-container;
                  tailf:cli-compact-syntax;
                  uses interface-name-grouping;
                }
                leaf hostname {
                  type string;
                }
              }
            }
            case negotiated-case {
              container negotiated {
                tailf:cli-delete-when-empty;
                presence "true";
                leaf previous {
                  type empty;
                }
              }
            }
          }
        }
      }
      container directed-broadcast {
        tailf:cli-delete-when-empty;
        presence "true";
        leaf access-list {
          tailf:cli-drop-node-name;
          type union {
            type uint16;
            type uint16;
          }
        }
      }
      leaf broadcast-address {
        type inet:ipv4-address;
      }
      container sticky-arp {
        tailf:cli-delete-when-empty;
        presence "true";
        leaf ignore {
          type empty;
        }
      }
      container split-horizon-eigrp {
        tailf:cli-drop-node-name;
        container split-horizon {
          container eigrp {
            list no-list {
              tailf:cli-suppress-mode;
              tailf:cli-delete-when-empty;
              key "as-no";
              leaf as-no {
                type uint16;
              }
            }
          }
        }
      }
      leaf split-horizon {
        type boolean;
      }
      container router {
        container isis {
          tailf:cli-delete-when-empty;
          presence "true";
          leaf tag {
            tailf:cli-drop-node-name;
            type string;
          }
        }
      }
      container flow {
        leaf ingress {
          type empty;
        }
        leaf egress {
          type empty;
        }
        uses ip-flow-monitor-grouping;
      }
      container helper-address {
        list helper-address-list {
          tailf:cli-drop-node-name;
          tailf:cli-suppress-mode;
          tailf:cli-delete-when-empty;
          ordered-by user;
          key "address";
          leaf address {
            type inet:ipv4-address;
          }
        }
        list global {
          tailf:cli-suppress-mode;
          tailf:cli-delete-when-empty;
          ordered-by user;
          key "address";
          leaf address {
            type inet:ipv4-address;
          }
        }
        list vrf {
          tailf:cli-suppress-mode;
          tailf:cli-delete-when-empty;
          ordered-by user;
          key "vrf address";
          leaf vrf {
            type string;
          }
          leaf address {
            type inet:ipv4-address;
          }
        }
      }
      container summary-address {
        list eigrp {
          tailf:cli-suppress-mode;
          tailf:cli-delete-when-empty;
          tailf:cli-compact-syntax;
          tailf:cli-sequence-commands {
            tailf:cli-reset-siblings;
          }
          key "as-no ip-address wildcard-mask";
          leaf as-no {
            type uint16;
          }
          leaf ip-address {
            type inet:ipv4-address;
          }
          leaf wildcard-mask {
            type inet:ipv4-address;
          }
          leaf distance {
            tailf:cli-drop-node-name;
            tailf:cli-optional-in-sequence;
            type uint8;
          }
          leaf leak-map {
            type string;
          }
        }
      }
      container ospf {
        list process-id {
          tailf:cli-drop-node-name;
          tailf:cli-suppress-mode;
          tailf:cli-delete-when-empty;
          tailf:cli-compact-syntax;
          tailf:cli-sequence-commands {
            tailf:cli-reset-siblings;
          }
          key "id";
          leaf id {
            tailf:cli-suppress-range;
            type uint16;
          }
          leaf area {
            type union {
              type uint32;
              type inet:ipv4-address;
            }
          }
          leaf secondaries {
            type empty;
          }
          leaf none {
            type empty;
          }
        }
        container authentication {
          tailf:cli-delete-when-empty;
          presence "true";
          choice authentication-choice {
            leaf message-digest {
              type empty;
            }
            leaf null {
              type empty;
            }
            leaf key-chain {
              type string;
            }
          }
        }
        container authentication-key {
          tailf:cli-compact-syntax;
          tailf:cli-sequence-commands;
          uses password-grouping {
            refine "secret";
          }
        }
        list message-digest-key {
          tailf:cli-suppress-mode;
          tailf:cli-delete-when-empty;
          tailf:cli-compact-syntax;
          tailf:cli-sequence-commands;
          key "id";
          leaf id {
            type uint8;
          }
          container md5 {
            tailf:cli-flatten-container;
            tailf:cli-compact-syntax;
            tailf:cli-sequence-commands;
            uses password-grouping {
              refine "secret";
            }
          }
        }
        leaf-list network {
          tailf:cli-flat-list-syntax;
          type enumeration {
            enum "point-to-multipoint";
            enum "point-to-point";
            enum "broadcast";
            enum "non-broadcast";
          }
        }
        leaf prefix-suppression {
          type empty;
        }
        container dead-interval {
          tailf:cli-compact-syntax;
          tailf:cli-sequence-commands {
            tailf:cli-reset-siblings;
          }
          choice dead-interva-choice {
            leaf seconds {
              tailf:cli-drop-node-name;
              type uint16;
            }
            case minimal {
              leaf minimal {
                type empty;
              }
              leaf hello-multiplier {
                type uint8;
              }
            }
          }
        }
        leaf hello-interval {
          type uint16;
        }
        leaf retransmit-interval {
          type uint16;
        }
        leaf transmit-delay {
          type uint16;
        }
        leaf flood-reduction {
          type empty;
        }
        container demand-circuit {
          tailf:cli-delete-when-empty;
          presence "true";
          leaf ignore {
            type empty;
          }
        }
        leaf resync-timeout {
          type uint16;
        }
        container bfd {
          tailf:cli-delete-when-empty;
          presence "true";
          leaf enable {
            tailf:cli-drop-node-name;
            type enumeration {
              enum "disable";
              enum "strict-mode";
            }
          }
        }
        leaf mtu-ignore {
          type empty;
        }
        leaf cost {
          type uint16;
        }
        container ttl-security {
          tailf:cli-delete-when-empty;
          presence "true";
          leaf hops {
            type uint8;
          }
        }
        leaf priority {
          type uint8;
        }
        container lls {
          tailf:cli-delete-when-empty;
          presence "true";
          leaf disable {
            type empty;
          }
        }
        container database-filter {
          container all {
            leaf out {
              type empty;
            }
          }
        }
        leaf shutdown {
          type empty;
        }
      }
      container irdp-enable {
        tailf:cli-drop-node-name;
        leaf irdp {
          type empty;
        }
      }
      container irdp {
        leaf multicast {
          type empty;
        }
        leaf maxadvertinterval {
          type uint16;
        }
        leaf minadvertinterval {
          type uint16;
        }
        leaf holdtime {
          type uint16;
        }
        leaf preference {
          type int32;
        }
      }
      container pim {
        leaf bfd {
          type empty;
        }
        list redundancy {
          tailf:cli-suppress-mode;
          tailf:cli-delete-when-empty;
          tailf:cli-compact-syntax;
          tailf:cli-sequence-commands {
            tailf:cli-reset-siblings;
          }
          key "name";
          leaf name {
            type string;
          }
          leaf protocol {
            tailf:cli-drop-node-name;
            tailf:cli-optional-in-sequence;
            type enumeration {
              enum "hsrp";
              enum "vrrp";
            }
          }
          leaf dr-priority {
            type uint32;
          }
        }
        leaf query-interval {
          type uint16;
        }
        leaf bsr-border {
          type empty;
        }
        leaf nbma-mode {
          type empty;
        }
        choice ip-pim-dense-mode-choice {
          leaf mode {
            tailf:cli-drop-node-name;
            type enumeration {
              enum "sparse-mode";
              enum "sparse-dense-mode";
              enum "dense-mode";
            }
          }
          container sparse-mode {
            container encap-helper {
              leaf Tunnel {
                tailf:cli-allow-join-with-value;
                type uint32;
              }
            }
          }
          container dense-mode {
            container proxy-register {
              leaf list {
                type ext-acl-type;
              }
            }
          }
        }
        leaf dr-priority {
          type uint32;
        }
        leaf snooping {
          type empty;
        }
        leaf passive {
          type empty;
        }
        leaf neighbor-filter {
          type base-acl-type;
        }
      }
      container multicast {
        container boundary {
          tailf:cli-compact-syntax;
          tailf:cli-sequence-commands {
            tailf:cli-reset-siblings;
          }
          leaf access-list {
            tailf:cli-drop-node-name;
            type string;
          }
          leaf filter-autorp {
            type empty;
          }
        }
        container boundary-conf {
          tailf:cli-drop-node-name;
          container boundary {
            tailf:cli-compact-syntax;
            tailf:cli-sequence-commands {
              tailf:cli-reset-siblings;
            }
            list access-list {
              tailf:cli-drop-node-name;
              tailf:cli-suppress-mode;
              tailf:cli-delete-when-empty;
              tailf:cli-compact-syntax;
              tailf:cli-sequence-commands;
              key "direction";
              leaf direction {
                type enumeration {
                  enum "in";
                  enum "out";
                }
              }
              leaf name {
                tailf:cli-drop-node-name;
                tailf:cli-prefix-key;
                type string;
              }
            }
          }
        }
        container limit {
          list access-lists {
            tailf:cli-drop-node-name;
            tailf:cli-suppress-mode;
            tailf:cli-delete-when-empty;
            key "access-list";
            leaf access-list {
              tailf:cli-suppress-range;
              type ip-acl-type;
            }
            leaf allowed-state {
              tailf:cli-drop-node-name;
              type uint32;
            }
          }
          list connected {
            tailf:cli-suppress-mode;
            tailf:cli-delete-when-empty;
            key "access-list";
            leaf access-list {
              tailf:cli-suppress-range;
              type ip-acl-type;
            }
            leaf allowed-state {
              tailf:cli-drop-node-name;
              type uint32;
            }
          }
          list out {
            tailf:cli-suppress-mode;
            tailf:cli-delete-when-empty;
            key "access-list";
            leaf access-list {
              tailf:cli-suppress-range;
              type ip-acl-type;
            }
            leaf allowed-state {
              tailf:cli-drop-node-name;
              type uint32;
            }
          }
          list rpf {
            tailf:cli-suppress-mode;
            tailf:cli-delete-when-empty;
            key "access-list";
            leaf access-list {
              tailf:cli-suppress-range;
              type ip-acl-type;
            }
            leaf allowed-state {
              tailf:cli-drop-node-name;
              type uint32;
            }
          }
        }
        container rate-limit {
          container in {
            leaf value {
              tailf:cli-drop-node-name;
              type uint32;
            }
          }
        }
      }
      container cgmp {
        presence "true";
      }
      container policy {
        leaf route-map {
          type string;
        }
      }
      leaf unreachables {
        type boolean;
      }
      leaf local-proxy-arp {
        type empty;
      }
      leaf proxy-arp {
        type boolean;
      }
      container route-cache-conf {
        tailf:cli-drop-node-name;
        leaf route-cache {
          type boolean;
        }
      }
      container route-cache {
        leaf cef {
          type boolean;
        }
        leaf flow {
          type boolean;
        }
        leaf policy {
          type boolean;
        }
        leaf same-interface {
          type boolean;
        }
      }
      leaf mroute-cache {
        type boolean;
      }
      container service {
        list reflect {
          tailf:cli-suppress-mode;
          tailf:cli-delete-when-empty;
          tailf:cli-compact-syntax;
          tailf:cli-sequence-commands {
            tailf:cli-reset-siblings;
          }
          key "interface destination to";
          leaf interface {
            type string;
          }
          leaf destination {
            tailf:cli-expose-key-name;
            type inet:ipv4-address;
          }
          leaf to {
            tailf:cli-expose-key-name;
            type inet:ipv4-address;
          }
          leaf mask-len {
            type uint8;
          }
          leaf source {
            type inet:ipv4-address;
          }
          container source-to {
            tailf:cli-drop-node-name;
            tailf:cli-flatten-container;
            leaf to {
              type inet:ipv4-address;
            }
          }
          leaf src-mask-len {
            type uint8;
          }
        }
      }
      container igmp {
        container max-groups {
          leaf number {
            tailf:cli-drop-node-name;
            type uint32;
          }
          leaf action {
            type enumeration {
              enum "deny";
              enum "replace";
            }
          }
        }
        leaf filter {
          type uint32;
        }
        list join-group {
          tailf:cli-suppress-mode;
          tailf:cli-delete-when-empty;
          tailf:cli-compact-syntax;
          key "address";
          leaf address {
            type inet:ipv4-address;
          }
          leaf source {
            type inet:ipv4-address;
          }
        }
        container static-group {
          list groups {
            tailf:cli-drop-node-name;
            tailf:cli-suppress-mode;
            tailf:cli-delete-when-empty;
            key "name";
            leaf name {
              tailf:cli-suppress-range;
              type union {
                type inet:ipv4-address;
                type enumeration {
                  enum "*";
                }
              }
            }
          }
          list groups-source {
            tailf:cli-drop-node-name;
            tailf:cli-suppress-mode;
            tailf:cli-delete-when-empty;
            key "name source";
            leaf name {
              tailf:cli-suppress-range;
              type inet:ipv4-address;
            }
            leaf source {
              tailf:cli-expose-key-name;
              type union {
                type inet:ipv4-address;
                type enumeration {
                  enum "ssm-map";
                }
              }
            }
          }
          list class-map {
            tailf:cli-suppress-mode;
            tailf:cli-delete-when-empty;
            key "id";
            leaf id {
              type string;
            }
          }
        }
        leaf last-member-query-interval {
          type uint16;
        }
        leaf last-member-query-count {
          type uint8;
        }
        leaf version {
          type uint8;
        }
        leaf v3lite {
          type empty;
        }
        container helper-address {
          leaf address {
            tailf:cli-drop-node-name;
            type inet:ipv4-address;
          }
        }
        leaf explicit-tracking {
          type empty;
        }
        leaf query-interval {
          type uint16;
        }
        leaf proxy-service {
          type empty;
        }
        leaf access-group {
          type exp-ip-acl-type;
        }
        container snooping {
          leaf report-suppression {
            type boolean;
          }
          container tcn {
            leaf flood {
              type boolean;
            }
          }
          leaf fast-leave {
            type empty;
          }
          leaf querier {
            type empty;
          }
          container mrouter {
            container interface {
              uses interface-name-grouping;
            }
          }
        }
        container snooping-enable {
          tailf:cli-drop-node-name;
          leaf snooping {
            type boolean;
          }
        }
        container limit {
          tailf:cli-compact-syntax;
          tailf:cli-sequence-commands {
            tailf:cli-reset-siblings;
          }
          leaf value {
            tailf:cli-drop-node-name;
            type uint16;
          }
          leaf except {
            type ip-acl-type;
          }
        }
        container mroute-proxy {
          tailf:cli-flatten-container;
          tailf:cli-compact-syntax;
          uses interface-name-grouping;
        }
      }
      leaf redirects {
        type boolean;
      }
      container hello-interval {
        list eigrp {
          tailf:cli-suppress-mode;
          tailf:cli-delete-when-empty;
          key "as-number";
          leaf as-number {
            type uint16;
          }
          leaf seconds {
            tailf:cli-drop-node-name;
            type uint16;
          }
        }
      }
      container hold-time {
        list eigrp {
          tailf:cli-suppress-mode;
          tailf:cli-delete-when-empty;
          key "as-number";
          leaf as-number {
            type uint16;
          }
          leaf seconds {
            tailf:cli-drop-node-name;
            type uint16;
          }
        }
      }
      container nbar {
        leaf protocol-discovery {
          type empty;
        }
        container protocol-discovery-af {
          tailf:cli-drop-node-name;
          container protocol-discovery {
            leaf ipv4 {
              type empty;
            }
            leaf ipv6 {
              type empty;
            }
          }
        }
      }
      container nhrp {
        leaf authentication {
          type string;
        }
        leaf group {
          type string;
        }
        container map {
          list map-list {
            tailf:cli-drop-node-name;
            tailf:cli-suppress-mode;
            tailf:cli-delete-when-empty;
            key "ip-address";
            leaf ip-address {
              type inet:ipv4-address;
            }
            leaf nbma-address {
              tailf:cli-drop-node-name;
              type union {
                type inet:ipv4-address;
                type inet:ipv6-address;
              }
            }
          }
          container multicast {
            leaf dynamic {
              type boolean;
            }
            list multicast-list {
              tailf:cli-drop-node-name;
              tailf:cli-suppress-mode;
              tailf:cli-delete-when-empty;
              key "nbma-address";
              leaf nbma-address {
                type union {
                  type inet:ipv4-address;
                  type inet:ipv6-address;
                }
              }
            }
          }
          list group {
            tailf:cli-suppress-mode;
            tailf:cli-delete-when-empty;
            key "name";
            leaf name {
              type string;
            }
            container service-policy {
              leaf output {
                type string;
              }
            }
          }
        }
        leaf network-id {
          type union {
            type uint32;
            type inet:ipv4-address;
          }
        }
        leaf holdtime {
          type uint16;
        }
        container nhs {
          list nhs-list {
            tailf:cli-drop-node-name;
            tailf:cli-suppress-mode;
            tailf:cli-delete-when-empty;
            tailf:cli-compact-syntax;
            key "nhs-address";
            leaf nhs-address {
              type inet:ipv4-address;
            }
            leaf nbma {
              type union {
                type inet:ipv4-address;
                type inet:ipv6-address;
                type string;
              }
            }
            leaf multicast {
              type empty;
            }
            leaf priority {
              type uint8;
            }
          }
          list cluster {
            tailf:cli-suppress-mode;
            tailf:cli-delete-when-empty;
            key "id";
            leaf id {
              type uint8;
            }
            leaf max-connections {
              type uint8;
            }
          }
          leaf fallback {
            type uint8;
          }
        }
        container max-send {
          tailf:cli-compact-syntax;
          tailf:cli-sequence-commands {
            tailf:cli-reset-siblings;
          }
          leaf count {
            tailf:cli-drop-node-name;
            type uint16;
          }
          leaf every {
            type uint16;
          }
        }
        container server-only {
          tailf:cli-delete-when-empty;
          presence "true";
          leaf non-caching {
            type empty;
          }
        }
        container registration {
          leaf no-unique {
            type boolean;
          }
          leaf timeout {
            type uint16;
          }
        }
        container shortcut {
          tailf:cli-delete-when-empty;
          presence "true";
          leaf virtual-template {
            type uint16;
          }
        }
        container redirect {
          tailf:cli-delete-when-empty;
          presence "true";
          leaf timeout {
            type uint8;
          }
        }
      }
      container tcp {
        leaf adjust-mss {
          type uint16;
        }
        container header-compression {
          tailf:cli-delete-when-empty;
          presence "true";
          leaf type {
            tailf:cli-drop-node-name;
            type enumeration {
              enum "ietf-format";
              enum "iphc-format";
              enum "passive";
            }
          }
        }
        leaf compression-connections {
          type uint16;
        }
      }
      container rtp {
        container header-compression {
          tailf:cli-compact-syntax;
          tailf:cli-sequence-commands {
            tailf:cli-reset-siblings;
          }
          leaf type {
            tailf:cli-drop-node-name;
            tailf:cli-optional-in-sequence;
            type enumeration {
              enum "ietf-format";
              enum "iphc-format";
              enum "passive";
            }
          }
          leaf periodic-refresh {
            type empty;
          }
        }
        leaf compression-connections {
          type uint16;
        }
      }
      container header-compression {
        leaf max-header {
          type uint8;
        }
      }
      container mobile {
        container router-service {
          container roam {
            presence "true";
            leaf priority {
              type uint8;
            }
          }
          leaf description {
            tailf:cli-multi-value;
            type string;
          }
          leaf link-type {
            type string;
          }
          container tunnel {
            leaf mode {
              type enumeration {
                enum "gre";
                enum "ipip";
              }
            }
          }
          container collocated {
            tailf:cli-compact-syntax;
            tailf:cli-sequence-commands;
            leaf gateway {
              tailf:cli-optional-in-sequence;
              type inet:ipv4-address;
            }
            leaf ccoa-only {
              tailf:cli-optional-in-sequence;
              type empty;
            }
            container registration {
              tailf:cli-break-sequence-commands;
              leaf retry {
                type uint16;
              }
              container nat {
                container traversal {
                  tailf:cli-compact-syntax;
                  presence "true";
                  leaf keepalive {
                    type uint16;
                  }
                  leaf force {
                    type empty;
                  }
                }
              }
            }
            leaf encapsulation {
              type enumeration {
                enum "slip";
                enum "ppp";
              }
            }
          }
        }
      }
      list inspect {
        tailf:cli-suppress-mode;
        tailf:cli-delete-when-empty;
        tailf:cli-compact-syntax;
        tailf:cli-sequence-commands {
          tailf:cli-reset-siblings;
        }
        key "direction";
        leaf direction {
          type enumeration {
            enum "in";
            enum "out";
          }
        }
        leaf name {
          tailf:cli-prefix-key;
          tailf:cli-drop-node-name;
          type string;
        }
      }
      container virtual-reassembly {
        tailf:cli-delete-when-empty;
        presence "true";
        leaf in {
          type empty;
        }
        leaf out {
          type empty;
        }
        container conf {
          tailf:cli-drop-node-name;
          tailf:cli-compact-syntax;
          leaf drop-fragments {
            type empty;
          }
          leaf max-fragments {
            type uint8;
          }
          leaf max-reassemblies {
            type uint16;
          }
          leaf timeout {
            type uint8;
          }
          leaf percentage {
            type uint8;
          }
          leaf-list dscp {
            tailf:cli-flat-list-syntax;
            type dscp-type;
          }
          leaf-list precedence {
            tailf:cli-flat-list-syntax;
            type precedence-type;
          }
        }
      }
      container virtual-reassembly-out {
        tailf:cli-delete-when-empty;
        presence "true";
      }
      container dns {
        leaf view-group {
          type string;
        }
      }
      container ddns {
        container update {
          leaf hostname {
            type string;
          }
          list list {
            tailf:cli-drop-node-name;
            tailf:cli-suppress-mode;
            tailf:cli-delete-when-empty;
            key "name";
            leaf name {
              type string;
            }
            leaf host-group {
              type string;
            }
          }
        }
      }
      container dhcp {
        container client {
          container update {
            container dns {
              presence "true";
              tailf:cli-delete-when-empty;
              leaf server {
                type enumeration {
                  enum "both";
                  enum "none";
                }
              }
            }
          }
          container request {
            leaf domain-name {
              type boolean;
            }
          }
          container client-id {
            choice client-id-choice {
              leaf ascii {
                type string;
              }
              case interface {
                uses interface-name-grouping;
              }
            }
          }
          leaf hostname {
            type string;
          }
          container lease {
            tailf:cli-compact-syntax;
            tailf:cli-sequence-commands {
              tailf:cli-reset-siblings;
            }
            leaf days {
              tailf:cli-drop-node-name;
              type uint16;
            }
            leaf hours {
              tailf:cli-drop-node-name;
              type uint8;
            }
            leaf minutes {
              tailf:cli-drop-node-name;
              type uint8;
            }
          }
        }
        container relay {
          container information {
            leaf trusted {
              type empty;
            }
            container option {
              leaf subscriber-id {
                type string;
              }
            }
            container option-insert {
              tailf:cli-delete-when-empty;
              presence "true";
              leaf none {
                type empty;
              }
            }
            container check-reply {
              tailf:cli-delete-when-empty;
              presence "true";
              leaf none {
                type empty;
              }
            }
            leaf policy-action {
              type enumeration {
                enum "drop";
                enum "encapsulate";
                enum "keep";
                enum "replace";
              }
            }
          }
          container source-interface {
            uses interface-name-grouping;
          }
        }
        container snooping {
          container limit {
            leaf rate {
              type uint16;
            }
          }
          leaf trust {
            type empty;
          }
          list vlan {
            tailf:cli-suppress-mode;
            tailf:cli-delete-when-empty;
            tailf:cli-compact-syntax;
            key "id";
            leaf id {
              type uint16;
            }
            container information {
              container option {
                container format-type {
                  container circuit-id {
                    tailf:cli-compact-syntax;
                    leaf override {
                      type empty;
                    }
                    leaf string {
                      type string;
                    }
                  }
                }
              }
            }
          }
          list bridge-domain {
            tailf:cli-suppress-mode;
            tailf:cli-delete-when-empty;
            tailf:cli-compact-syntax;
            key "id";
            leaf id {
              type uint16;
            }
            container information {
              tailf:cli-flatten-container;
              container option {
                container format-type {
                  container circuit-id {
                    leaf string {
                      type string;
                    }
                  }
                }
              }
            }
          }
        }
      }
      leaf mtu {
        type uint16;
      }
      container nat {
        leaf allow-static-host {
          type empty;
        }
        leaf enable {
          type empty;
        }
        choice nat-choice {
          leaf inside {
            type empty;
          }
          leaf outside {
            type empty;
          }
        }
      }
      container rsvp {
        container policy {
          uses ip-rsvp-policy-local-grouping;
        }
        container bandwidth {
          tailf:cli-compact-syntax;
          tailf:cli-sequence-commands {
            tailf:cli-reset-siblings;
          }
          tailf:cli-delete-when-empty;
          presence "true";
          leaf interface-bandwidth {
            tailf:cli-drop-node-name;
            type uint32;
          }
          leaf single-flow-bandwidth {
            tailf:cli-drop-node-name;
            type uint32;
          }
        }
        container bandwidth-percent {
          tailf:cli-drop-node-name;
          container bandwidth {
            container percent {
              tailf:cli-compact-syntax;
              tailf:cli-sequence-commands {
                tailf:cli-reset-siblings;
              }
              leaf rsvp-bandwidth {
                tailf:cli-drop-node-name;
                type uint16;
              }
              choice bandwidth-choice {
                leaf max-flow-bw {
                  tailf:cli-drop-node-name;
                  type uint32;
                }
                leaf percent {
                  type uint16;
                }
              }
            }
          }
        }
        container signalling {
          container hello-rr {
            tailf:cli-drop-node-name;
            leaf hello {
              type empty;
            }
          }
          container hello-bfd {
            tailf:cli-drop-node-name;
            container hello {
              leaf bfd {
                type empty;
              }
            }
          }
          container hello {
            container graceful-restart {
              presence "true";
            }
          }
          container hello-gr-nbr {
            tailf:cli-drop-node-name;
            container hello {
              container graceful-restart {
                list neighbor {
                  tailf:cli-suppress-mode;
                  tailf:cli-delete-when-empty;
                  key "address";
                  leaf address {
                    type union {
                      type inet:ipv4-address;
                      type inet:ipv6-address;
                    }
                  }
                }
              }
            }
          }
          leaf dscp {
            type uint8;
          }
        }
        container data-packet {
          container classification {
            leaf none {
              type empty;
            }
          }
        }
        container resource-provider {
          choice resource-provider-choice {
            leaf none {
              type empty;
            }
            leaf wfq {
              type enumeration {
                enum "interface";
                enum "pvc";
              }
            }
          }
        }
        container source {
          container interface {
            uses interface-name-grouping;
          }
        }
        container tunnel {
          leaf overhead-percent {
            type uint8;
          }
        }
      }
      container verify {
        container unicast {
          container reverse-path {
            tailf:cli-compact-syntax;
            tailf:cli-delete-when-empty;
            presence "true";
            leaf allow-self-ping {
              type empty;
            }
            leaf access-list {
              tailf:cli-drop-node-name;
              type exp-ip-acl-type;
            }
          }
          container source {
            tailf:cli-compact-syntax;
            tailf:cli-sequence-commands {
              tailf:cli-reset-all-siblings;
            }
            leaf reachable-via {
              type enumeration {
                enum "any";
                enum "rx";
              }
            }
            leaf allow-self-ping {
              tailf:cli-break-sequence-commands;
              type empty;
            }
            leaf allow-default {
              type empty;
            }
            leaf access-list {
              tailf:cli-drop-node-name;
              type exp-ip-acl-type;
            }
          }
        }
        container source {
          tailf:cli-delete-when-empty;
          presence "true";
          container vlan {
            container dhcp-snooping {
              tailf:cli-delete-when-empty;
              presence "true";
              leaf port-security {
                type empty;
              }
            }
          }
        }
      }
      container rip {
        container send {
          leaf version {
            type enumeration {
              enum "1";
              enum "2";
            }
          }
        }
        container receive {
          leaf version {
            type enumeration {
              enum "1";
              enum "2";
            }
          }
        }
        container authentication {
          leaf mode {
            type enumeration {
              enum "md5";
              enum "text";
            }
          }
          leaf key-chain {
            type string;
          }
        }
      }
      leaf mask-reply {
        type empty;
      }
      container bandwidth-percent {
        list eigrp {
          tailf:cli-suppress-mode;
          tailf:cli-delete-when-empty;
          key "as-number";
          leaf as-number {
            type uint16;
          }
          leaf percent {
            tailf:cli-drop-node-name;
            type uint32;
          }
        }
      }
      container next-hop-self {
        container eigrp {
          list no-list {
            tailf:cli-suppress-mode;
            tailf:cli-delete-when-empty;
            key "as-number";
            leaf as-number {
              type uint16;
            }
          }
        }
      }
      container lisp {
        container source-locator {
          uses interface-name-grouping;
        }
      }
      container wccp {
        uses interface-ip-wccp-grouping;
        list vrf {
          tailf:cli-suppress-mode;
          tailf:cli-delete-when-empty;
          tailf:cli-compact-syntax;
          key "name";
          leaf name {
            type string;
          }
          uses interface-ip-wccp-grouping;
        }
      }
      container device {
        container tracking {
          container probe {
            leaf count {
              type uint16;
            }
            leaf interval {
              type uint32;
            }
          }
          leaf maximum {
            type uint16;
          }
        }
      }
      container mfib {
        container forwarding {
          leaf input {
            type boolean;
          }
          leaf output {
            type boolean;
          }
        }
        container cef {
          leaf input {
            type boolean;
          }
          leaf output {
            type boolean;
          }
        }
      }
      container subscriber {
        tailf:cli-add-mode;
        presence "true";
        leaf type {
          tailf:cli-drop-node-name;
          tailf:cli-hide-in-submode;
          type enumeration {
            enum "interface";
            enum "l2-connected";
            enum "routed";
          }
        }
        container initiator {
          leaf dhcp {
            type empty;
          }
        }
      }
      leaf load-sharing {
        type enumeration {
          enum "per-destination";
          enum "per-packet";
          enum "per-longest-match-prefix";
        }
      }
    }
    container ipv6 {
      container address {
        choice address-choice {
          case dhcp-case {
            container dhcp {
              tailf:cli-delete-when-empty;
              presence "true";
              leaf rapid-commit {
                type empty;
              }
            }
          }
          case manual-case {
            list prefix-list {
              tailf:cli-drop-node-name;
              tailf:cli-suppress-mode;
              tailf:cli-delete-when-empty;
              key "prefix";
              leaf prefix {
                type union {
                  type inet:ipv6-address;
                  type ios:ipv6-prefix;
                }
              }
              leaf link-local {
                type empty;
              }
              leaf anycast {
                type empty;
              }
              leaf eui-64 {
                type empty;
              }
            }
          }
          case general-prefix-case {
            list general-prefix-list {
              tailf:cli-drop-node-name;
              tailf:cli-suppress-mode;
              tailf:cli-delete-when-empty;
              key "name prefix";
              leaf name {
                type string;
              }
              leaf prefix {
                type ios:ipv6-prefix;
              }
              leaf anycast {
                type empty;
              }
              leaf eui-64 {
                type empty;
              }
            }
          }
        }
        container autoconfig {
          tailf:cli-delete-when-empty;
          presence "true";
          leaf default {
            type empty;
          }
        }
      }
      leaf enable {
        type empty;
      }
      container mode {
        container host {
          leaf unicast {
            type empty;
          }
        }
      }
      container unnumbered {
        uses interface-name-grouping;
      }
      list traffic-filter {
        tailf:cli-suppress-mode;
        tailf:cli-delete-when-empty;
        tailf:cli-compact-syntax;
        tailf:cli-sequence-commands;
        key "direction";
        leaf direction {
          type enumeration {
            enum "in";
            enum "out";
          }
        }
        leaf common {
          tailf:cli-prefix-key;
          tailf:cli-optional-in-sequence;
          type empty;
        }
        leaf access-list {
          tailf:cli-drop-node-name;
          tailf:cli-prefix-key;
          type string;
        }
        leaf regular-access-list {
          tailf:cli-drop-node-name;
          tailf:cli-prefix-key;
          tailf:cli-optional-in-sequence;
          type string;
        }
      }
      container nd {
        container dad {
          leaf attempts {
            type uint16;
          }
          leaf time {
            type uint16;
          }
        }
        leaf reachable-time {
          type uint32;
        }
        container cache {
          container interface-limit {
            tailf:cli-compact-syntax;
            tailf:cli-sequence-commands {
              tailf:cli-reset-siblings;
            }
            leaf size {
              tailf:cli-drop-node-name;
              type uint32;
            }
            leaf log {
              type uint16;
            }
          }
          container expire {
            tailf:cli-compact-syntax;
            tailf:cli-sequence-commands {
              tailf:cli-reset-siblings;
            }
            leaf seconds {
              tailf:cli-drop-node-name;
              type uint32;
            }
            leaf refresh {
              type empty;
            }
          }
        }
        container prefix {
          list prefix-list {
            tailf:cli-drop-node-name;
            tailf:cli-suppress-mode;
            tailf:cli-delete-when-empty;
            tailf:cli-compact-syntax;
            tailf:cli-sequence-commands {
              tailf:cli-reset-all-siblings;
            }
            key "ipv6-prefix";
            leaf ipv6-prefix {
              type union {
                type ipv6-prefix;
                type enumeration {
                  enum "default";
                }
              }
            }
            choice advertise-choice {
              case no-advertise {
                leaf no-advertise {
                  type empty;
                }
              }
              case advertise {
                leaf valid-lifetime {
                  tailf:cli-drop-node-name;
                  type union {
                    type enumeration {
                      enum "infinite";
                    }
                    type uint32;
                  }
                }
                leaf preferred-lifetime {
                  tailf:cli-drop-node-name;
                  type union {
                    type enumeration {
                      enum "infinite";
                    }
                    type uint32;
                  }
                }
                leaf off-link {
                  tailf:cli-break-sequence-commands;
                  type empty;
                }
                leaf no-autoconfig {
                  type empty;
                }
                leaf no-rtr-address {
                  type empty;
                }
                leaf no-onlink {
                  type empty;
                }
              }
            }
          }
        }
        leaf managed-config-flag {
          type empty;
        }
        leaf other-config-flag {
          type empty;
        }
        container ra {
          choice suppress-choice {
            container suppress-enable {
              tailf:cli-drop-node-name;
              leaf suppress {
                type boolean;
              }
            }
            container suppress {
              leaf all {
                type empty;
              }
            }
          }
          container interval {
            tailf:cli-compact-syntax;
            tailf:cli-sequence-commands {
              tailf:cli-reset-siblings;
            }
            choice interval-choice {
              case seconds {
                leaf seconds {
                  tailf:cli-drop-node-name;
                  type uint16;
                }
                leaf seconds-interval {
                  tailf:cli-drop-node-name;
                  type uint16;
                }
              }
              case msec {
                leaf msec {
                  type uint32;
                }
                leaf msec-interval {
                  tailf:cli-drop-node-name;
                  type uint32;
                }
              }
            }
          }
          leaf lifetime {
            type uint16;
          }
          container dns {
            list server {
              tailf:cli-suppress-mode;
              tailf:cli-delete-when-empty;
              key "address";
              leaf address {
                type inet:ipv6-address;
              }
            }
          }
        }
        container raguard {
          tailf:cli-delete-when-empty;
          presence "true";
          leaf attach-policy {
            type string;
          }
        }
        container autoconfig {
          leaf prefix {
            type empty;
          }
          leaf default-route {
            type empty;
          }
        }
        leaf router-preference {
          type enumeration {
            enum "Low";
            enum "Medium";
            enum "High";
          }
        }
        container inspection {
          presence "true";
          container vlan {
            choice vlan-choice {
              leaf which {
                tailf:cli-drop-node-name;
                type enumeration {
                  enum "all";
                  enum "none";
                }
              }
              leaf-list vlans {
                tailf:cli-drop-node-name;
                tailf:cli-range-list-syntax;
                type uint16;
              }
            }
          }
        }
      }
      container mld {
        leaf query-timeout {
          type uint16;
        }
        leaf query-interval {
          type uint16;
        }
        leaf access-group {
          type string;
        }
        leaf router {
          type boolean;
        }
        container snooping-enable {
          tailf:cli-drop-node-name;
          leaf snooping {
            type boolean;
          }
        }
      }
      container pim {
        leaf passive {
          type empty;
        }
        leaf hello-interval {
          type uint16;
        }
      }
      leaf redirects {
        type boolean;
      }
      leaf unreachables {
        type boolean;
      }
      container tcp {
        leaf adjust-mss {
          type uint16;
        }
      }
      container router {
        container isis {
          tailf:cli-delete-when-empty;
          presence "true";
          leaf tag {
            tailf:cli-drop-node-name;
            type string;
          }
        }
      }
      container ospf {
        leaf network {
          type enumeration {
            enum "broadcast";
            enum "non-broadcast";
            enum "point-to-multipoint";
            enum "point-to-point";
          }
        }
        list process {
          tailf:cli-drop-node-name;
          tailf:cli-suppress-mode;
          tailf:cli-delete-when-empty;
          tailf:cli-compact-syntax;
          tailf:cli-sequence-commands {
            tailf:cli-reset-siblings;
          }
          key "id";
          leaf id {
            type uint16;
          }
          leaf area {
            type union {
              type uint32;
              type inet:ipv4-address;
            }
          }
          leaf instance {
            type union {
              type uint8;
              type uint8;
            }
          }
        }
        container bfd {
          presence "true";
          leaf disable {
            type empty;
          }
        }
        leaf cost {
          type uint16;
        }
        container database-filter {
          choice database {
            leaf all {
              type enumeration {
                enum "out";
              }
            }
            leaf disable {
              type empty;
            }
          }
        }
        leaf dead-interval {
          type uint16;
        }
        container demand-circuit {
          presence "true";
          leaf disable {
            type empty;
          }
        }
        container flood-reduction {
          presence "true";
          leaf disable {
            type empty;
          }
        }
        leaf hello-interval {
          type uint16;
        }
        container mtu-ignore {
          presence "true";
          leaf disable {
            type empty;
          }
        }
        leaf priority {
          type uint16;
        }
        leaf retransmit-interval {
          type uint16;
        }
        leaf transmit-delay {
          type uint16;
        }
      }
      leaf-list eigrp {
        type uint16;
      }
      leaf mtu {
        type uint16;
      }
      container crypto {
        container map {
          tailf:cli-compact-syntax;
          tailf:cli-sequence-commands {
            tailf:cli-reset-siblings;
          }
          leaf map-name {
            tailf:cli-drop-node-name;
            type string;
          }
          leaf redundancy {
            type string;
          }
          leaf stateful {
            type empty;
          }
        }
      }
      container hold-time {
        list eigrp {
          tailf:cli-suppress-mode;
          tailf:cli-delete-when-empty;
          key "as-no";
          leaf as-no {
            type uint16;
          }
          leaf seconds {
            tailf:cli-drop-node-name;
            type uint16;
          }
        }
      }
      container hello-interval {
        list eigrp {
          tailf:cli-suppress-mode;
          tailf:cli-delete-when-empty;
          key "as-no";
          leaf as-no {
            type uint16;
          }
          leaf seconds {
            tailf:cli-drop-node-name;
            type uint16;
          }
        }
      }
      container verify {
        container unicast {
          container source {
            leaf reachable-via {
              type enumeration {
                enum "any";
                enum "rx";
              }
            }
          }
          container reverse-path {
            tailf:cli-delete-when-empty;
            presence "true";
            leaf access-list {
              tailf:cli-drop-node-name;
              type string;
            }
          }
        }
      }
      container dhcp {
        container relay {
          list destination {
            tailf:cli-suppress-mode;
            tailf:cli-delete-when-empty;
            tailf:cli-compact-syntax;
            tailf:cli-sequence-commands {
              tailf:cli-reset-siblings;
            }
            key "ipv6-address";
            leaf ipv6-address {
              type inet:ipv6-address;
            }
            leaf source-address {
              tailf:cli-optional-in-sequence;
              type inet:ipv6-address;
            }
            leaf link-address {
              type inet:ipv6-address;
            }
          }
          container source-interface {
            uses interface-name-grouping;
          }
        }
        container client {
          container information {
            container refresh {
              leaf minimum {
                type uint16;
              }
            }
          }
          container request {
            leaf vendor {
              type empty;
            }
          }
        }
        choice server-choice {
          leaf server {
            type empty;
          }
          container server-name {
            tailf:cli-drop-node-name;
            container server {
              tailf:cli-compact-syntax;
              tailf:cli-sequence-commands {
                tailf:cli-reset-all-siblings;
              }
              leaf poolname {
                tailf:cli-drop-node-name;
                type string;
              }
              leaf rapid-commit {
                tailf:cli-break-sequence-commands;
                type empty;
              }
              leaf preference {
                type uint8;
              }
              leaf allow-hint {
                type empty;
              }
            }
          }
        }
        container guard {
          tailf:cli-delete-when-empty;
          presence "true";
          leaf attach-policy {
            type string;
          }
        }
      }
      container nhrp {
        container map {
          list map-list {
            tailf:cli-drop-node-name;
            tailf:cli-suppress-mode;
            tailf:cli-delete-when-empty;
            key "ipv6-address";
            leaf ipv6-address {
              tailf:cli-drop-node-name;
              type ipv6-prefix;
            }
            leaf nbma-address {
              tailf:cli-drop-node-name;
              type union {
                type inet:ipv4-address;
                type inet:ipv6-address;
              }
            }
          }
          container multicast {
            leaf dynamic {
              type empty;
            }
            list multicast-list {
              tailf:cli-drop-node-name;
              tailf:cli-suppress-mode;
              tailf:cli-delete-when-empty;
              key "nbma-address";
              leaf nbma-address {
                type union {
                  type inet:ipv4-address;
                  type inet:ipv6-address;
                }
              }
            }
          }
        }
        leaf network-id {
          type uint32;
        }
        leaf holdtime {
          type uint16;
        }
        container nhs {
          list nhs-list {
            tailf:cli-drop-node-name;
            tailf:cli-suppress-mode;
            tailf:cli-delete-when-empty;
            tailf:cli-compact-syntax;
            key "nhs-address";
            leaf nhs-address {
              type inet:ipv6-address;
            }
            leaf nbma {
              type union {
                type inet:ipv4-address;
                type inet:ipv6-address;
                type string;
              }
            }
            leaf multicast {
              type empty;
            }
          }
        }
        container server-only {
          tailf:cli-delete-when-empty;
          presence "true";
          leaf non-caching {
            type empty;
          }
        }
        container registration {
          leaf no-unique {
            type empty;
          }
          leaf timeout {
            type uint16;
          }
        }
        container shortcut {
          presence "true";
        }
        container redirect {
          tailf:cli-delete-when-empty;
          presence "true";
          leaf timeout {
            type uint8;
          }
        }
      }
      container summary-address {
        list eigrp {
          tailf:cli-delete-when-empty;
          tailf:cli-suppress-mode;
          key "as-no ipv6-address";
          leaf as-no {
            type uint16;
          }
          leaf ipv6-address {
            type ios:ipv6-prefix;
          }
          leaf distance {
            tailf:cli-drop-node-name;
            type uint8;
          }
        }
      }
      list rip {
        tailf:cli-suppress-mode;
        tailf:cli-delete-when-empty;
        key "id";
        leaf id {
          type string;
        }
        leaf enable {
          type empty;
        }
        container default-information {
          tailf:cli-compact-syntax;
          tailf:cli-sequence-commands;
          leaf default-route {
            tailf:cli-drop-node-name;
            type enumeration {
              enum "only";
              enum "originate";
            }
          }
          leaf metric {
            type uint8;
          }
        }
      }
      container wccp {
        uses interface-ip-wccp-grouping;
        list vrf {
          tailf:cli-suppress-mode;
          tailf:cli-delete-when-empty;
          tailf:cli-compact-syntax;
          key "name";
          leaf name {
            type string;
          }
          uses interface-ip-wccp-grouping;
        }
      }
      container policy {
        leaf route-map {
          type string;
        }
      }
      container flow {
        list monitor {
          tailf:cli-suppress-mode;
          tailf:cli-delete-when-empty;
          tailf:cli-compact-syntax;
          tailf:cli-sequence-commands {
            tailf:cli-reset-siblings;
          }
          key "name direction";
          leaf name {
            type string;
          }
          leaf sampler {
            tailf:cli-prefix-key {
              tailf:cli-before-key "2";
            }
            tailf:cli-optional-in-sequence;
            type string;
          }
          leaf direction {
            type enumeration {
              enum "input";
              enum "output";
            }
          }
        }
      }
    }
    container ospfv3 {
      uses interface-ospfv3-grouping;
      list ospfv3-list {
        tailf:cli-drop-node-name;
        tailf:cli-suppress-mode;
        tailf:cli-delete-when-empty;
        key "id";
        leaf id {
          tailf:cli-suppress-range;
          type uint16;
        }
        uses interface-ospfv3-grouping;
        container ipv4 {
          uses interface-ospfv3-grouping;
        }
        container ipv6 {
          uses interface-ospfv3-grouping;
        }
      }
    }
    container nat64 {
      leaf enable {
        type empty;
      }
    }
    container punt-control {
      tailf:cli-compact-syntax;
      tailf:cli-sequence-commands {
        tailf:cli-reset-siblings;
      }
      leaf enable {
        type empty;
      }
      leaf pps {
        tailf:cli-drop-node-name;
        type uint32;
      }
    }
    container lisp {
      container mobility {
        container liveness {
          leaf test {
            type boolean;
          }
        }
        list name-list {
          tailf:cli-drop-node-name;
          tailf:cli-suppress-mode;
          tailf:cli-delete-when-empty;
          key "name";
          leaf name {
            type string;
          }
        }
      }
    }
    container nhrp {
      leaf group {
        type string;
      }
      container map {
        list group {
          tailf:cli-suppress-mode;
          tailf:cli-delete-when-empty;
          tailf:cli-compact-syntax;
          tailf:cli-sequence-commands {
            tailf:cli-reset-siblings;
          }
          key "name";
          leaf name {
            type string;
          }
          container service-policy {
            leaf output {
              type string;
            }
          }
        }
      }
      leaf route-watch {
        type boolean;
      }
    }
    container if-state {
      leaf nhrp {
        type empty;
      }
    }
    container umbrella {
      leaf out {
        type empty;
      }
      container in {
        tailf:cli-flatten-container;
        tailf:cli-compact-syntax;
        tailf:cli-sequence-commands {
          tailf:cli-reset-siblings;
        }
        leaf direct-cloud-access {
          tailf:cli-optional-in-sequence;
          type string;
        }
        leaf tag {
          tailf:cli-drop-node-name;
          type string;
        }
      }
    }
    container utd {
      leaf enable {
        type empty;
      }
    }
    container redundancy {
      leaf rii {
        type uint16;
      }
      container group {
        tailf:cli-compact-syntax;
        tailf:cli-sequence-commands {
          tailf:cli-reset-siblings;
        }
        leaf id {
          tailf:cli-drop-node-name;
          type uint8;
        }
        leaf ip {
          type inet:ipv4-address;
        }
        leaf exclusive {
          type empty;
        }
      }
    }
    leaf delay {
      type uint32;
    }
    leaf load-interval {
      type uint16;
    }
    container loopback {
      choice loopback-choice {
        leaf mac {
          type empty;
        }
        leaf external {
          type empty;
        }
        leaf internal {
          type empty;
        }
      }
    }
    leaf loopdetect {
      type empty;
    }
    container logging {
      container event {
        leaf link-status {
          type boolean;
        }
        leaf trunk-status {
          type empty;
        }
        leaf bundle-status {
          type empty;
        }
        leaf subif-link-status {
          type empty;
        }
        container spanning-tree {
          tailf:cli-delete-when-empty;
          presence "true";
          leaf status {
            type empty;
          }
        }
        leaf nfas-status {
          type empty;
        }
        leaf power-inline-status {
          type boolean;
        }
      }
      container ip {
        container access-list {
          container cache {
            leaf in {
              type empty;
            }
            leaf out {
              type empty;
            }
          }
        }
      }
    }
    leaf max-reserved-bandwidth {
      type uint8;
    }
    container history {
      tailf:cli-compact-syntax;
      tailf:cli-sequence-commands {
        tailf:cli-reset-siblings;
      }
      leaf xps {
        tailf:cli-drop-node-name;
        type enumeration {
          enum "BPS";
          enum "PPS";
        }
      }
      leaf-list filter {
        tailf:cli-drop-node-name;
        tailf:cli-flat-list-syntax;
        type string;
      }
    }
    leaf unidirectional {
      type enumeration {
        enum "receive-only";
        enum "send-only";
      }
    }
    container mls {
      container ip {
        leaf directed-broadcast {
          type enumeration {
            enum "drop";
            enum "exclude-router";
            enum "include-router";
          }
        }
      }
      container netflow {
        leaf sampling {
          type empty;
        }
      }
      container qos {
        container cos {
          leaf cos-value {
            tailf:cli-drop-node-name;
            type uint8;
          }
          leaf override {
            type empty;
          }
        }
        leaf channel-consistency {
          type boolean;
        }
        container trust {
          container device {
            leaf cisco-phone {
              type empty;
            }
          }
          choice trust-choice {
            container cos {
              tailf:cli-delete-when-empty;
              presence "true";
              container pass-through {
                leaf dscp {
                  type empty;
                }
              }
            }
            container dscp {
              presence "true";
              container pass-through {
                leaf cos {
                  type empty;
                }
              }
            }
            container ip-precedence {
              presence "true";
            }
          }
        }
        container monitor {
          leaf-list dscp {
            tailf:cli-flat-list-syntax;
            type uint8;
          }
        }
        leaf vlan-based {
          type empty;
        }
        leaf bridged {
          type empty;
        }
        leaf dscp-mutation {
          type string;
        }
      }
      container l2tpv3 {
        container reserve {
          leaf slot {
            type uint8;
          }
          leaf-list interface {
            tailf:cli-flat-list-syntax;
            ordered-by user;
            type string;
          }
        }
      }
      container rp {
        leaf vtp-domain {
          type string;
        }
        leaf ip {
          type empty;
        }
      }
    }
    container trust {
      leaf device {
        type enumeration {
          enum "cisco-phone";
          enum "cts";
          enum "ip-camera";
          enum "media-player";
        }
      }
    }
    container auto {
      container qos {
        container voip {
          leaf cisco-phone {
            type empty;
          }
          leaf trust {
            type empty;
          }
        }
        container trust {
          presence "true";
          leaf cos {
            type empty;
          }
          leaf dscp {
            type empty;
          }
        }
      }
    }
    container ntp {
      container broadcast {
        presence "true";
        container client {
          presence "true";
        }
        list destination {
          tailf:cli-suppress-mode;
          tailf:cli-delete-when-empty;
          tailf:cli-compact-syntax;
          key "address";
          leaf version {
            type uint8;
          }
          leaf key {
            type uint32;
          }
          leaf address {
            type inet:ipv4-address;
          }
        }
        container version-key {
          tailf:cli-drop-node-name;
          tailf:cli-compact-syntax;
          leaf version {
            type uint8;
          }
          leaf key {
            type uint32;
          }
        }
      }
      leaf disable {
        type empty;
      }
      container multicast {
        tailf:cli-compact-syntax;
        presence "true";
        list address-list {
          tailf:cli-drop-node-name;
          tailf:cli-suppress-mode;
          tailf:cli-delete-when-empty;
          tailf:cli-compact-syntax;
          key "group-address";
          leaf group-address {
            type union {
              type inet:ipv4-address;
              type inet:ipv6-address;
            }
          }
          leaf version {
            type uint8;
          }
          leaf key {
            type uint32;
          }
          leaf ttl {
            type uint8;
          }
        }
        leaf version {
          type uint8;
        }
        leaf key {
          type uint32;
        }
        leaf ttl {
          type uint8;
        }
        container client-list {
          tailf:cli-drop-node-name;
          leaf-list client {
            tailf:cli-suppress-list-no;
            type union {
              type inet:ipv4-address;
              type inet:ipv6-address;
            }
          }
        }
        leaf client {
          type empty;
        }
      }
    }
    container power {
      container inline {
        tailf:cli-compact-syntax;
        tailf:cli-sequence-commands {
          tailf:cli-reset-siblings;
        }
        container port {
          tailf:cli-optional-in-sequence;
          leaf two-event {
            tailf:alt-name "2-event";
            type empty;
          }
        }
        leaf consumption {
          tailf:cli-optional-in-sequence;
          type uint16;
        }
        leaf mode {
          tailf:cli-drop-node-name;
          type enumeration {
            enum "auto";
            enum "never";
            enum "static";
          }
        }
        leaf max {
          type uint16;
        }
      }
      container client {
        leaf local {
          type empty;
        }
      }
    }
    list rate-limit {
      tailf:cli-suppress-mode;
      tailf:cli-delete-when-empty;
      key "line";
      leaf line {
        tailf:cli-multi-word-key;
        type string;
      }
    }
    container service-policy {
      leaf history {
        type empty;
      }
      uses service-policy-grouping {
        refine "output";
        refine "input";
      }
      container type {
        container control {
          choice control-choice {
            leaf subscriber {
              type string;
            }
            leaf name {
              tailf:cli-drop-node-name;
              type string;
            }
          }
        }
        container performance-monitor {
          uses service-policy-grouping {
            refine "output";
            refine "input";
          }
        }
        container epbr {
          uses service-policy-grouping;
        }
      }
    }
    container service-insertion {
      leaf waas {
        type empty;
      }
      leaf appqoe {
        type empty;
      }
    }
    container service-module {
      container fail-open {
        presence "true";
      }
      container ip {
        container address {
          container primary {
            tailf:cli-drop-node-name;
            tailf:cli-compact-syntax;
            tailf:cli-sequence-commands;
            leaf address {
              tailf:cli-drop-node-name;
              type inet:ipv4-address;
            }
            leaf mask {
              tailf:cli-drop-node-name;
              type inet:ipv4-address;
            }
          }
        }
        leaf default-gateway {
          type inet:ipv4-address;
        }
      }
      container t1 {
        container clock {
          leaf source {
            type enumeration {
              enum "line";
              enum "internal";
            }
          }
        }
        leaf framing {
          type enumeration {
            enum "esf";
            enum "sf";
          }
        }
        container timeslots {
          tailf:cli-compact-syntax;
          tailf:cli-sequence-commands {
            tailf:cli-reset-siblings;
          }
          leaf-list list {
            tailf:cli-drop-node-name;
            tailf:cli-range-list-syntax;
            type uint8;
          }
          leaf speed {
            type enumeration {
              enum "56";
              enum "64";
            }
          }
        }
      }
    }
    leaf group {
      type uint16;
    }
    leaf shutdown {
      type empty;
    }
    container tcam {
      leaf priority {
        type enumeration {
          enum "low";
          enum "high";
        }
      }
    }
    container standby {
      container redirect-enable {
        tailf:cli-drop-node-name;
        leaf redirect {
          type boolean;
        }
      }
      container redirect {
        leaf unknown {
          type boolean;
        }
        container timers {
          tailf:cli-compact-syntax;
          tailf:cli-sequence-commands {
            tailf:cli-reset-siblings;
          }
          leaf advertisement {
            tailf:cli-drop-node-name;
            type uint16;
          }
          leaf holddown {
            tailf:cli-drop-node-name;
            type uint16;
          }
        }
        container advertisement {
          container authentication {
            container md5 {
              leaf key-chain {
                type string;
              }
              container key-string {
                tailf:cli-flatten-container;
                tailf:cli-compact-syntax;
                tailf:cli-sequence-commands;
                uses password-grouping {
                  refine "secret";
                }
                leaf timeout {
                  type uint16;
                }
              }
            }
          }
        }
      }
      leaf version {
        type enumeration {
          enum "1";
          enum "2";
        }
      }
      leaf bfd {
        type boolean;
      }
      container delay {
        tailf:cli-compact-syntax;
        leaf minimum {
          type uint16;
        }
        leaf reload {
          type uint16;
        }
      }
      leaf mac-refresh {
        type uint8;
      }
      container use-bia {
        presence "true";
        container scope {
          leaf interface {
            type empty;
          }
        }
      }
      list standby-list {
        tailf:cli-drop-node-name;
        tailf:cli-suppress-mode;
        tailf:cli-delete-when-empty;
        key "group-number";
        leaf group-number {
          tailf:cli-suppress-range;
          type uint16;
        }
        container authentication {
          choice auth-choice {
            leaf word {
              tailf:cli-drop-node-name;
              type string;
            }
            container md5 {
              leaf key-chain {
                type string;
              }
              container key-string {
                tailf:cli-flatten-container;
                tailf:cli-compact-syntax;
                tailf:cli-sequence-commands;
                uses password-grouping {
                  refine "secret";
                }
                leaf timeout {
                  type uint16;
                }
              }
            }
            leaf text {
              type string;
            }
          }
        }
        leaf follow {
          type string;
        }
        container ip {
          tailf:cli-delete-when-empty;
          presence "true";
          leaf address {
            tailf:cli-drop-node-name;
            type inet:ipv4-address;
          }
          list secondary {
            tailf:cli-drop-node-name;
            tailf:cli-suppress-mode;
            tailf:cli-delete-when-empty;
            tailf:cli-compact-syntax;
            key "address";
            leaf address {
              type inet:ipv4-address;
            }
            leaf secondary {
              type empty;
            }
          }
        }
        leaf-list ipv6 {
          type union {
            type inet:ipv6-address;
            type ios:ipv6-prefix;
            type enumeration {
              enum "autoconfig";
            }
          }
        }
        leaf mac-address {
          type string;
        }
        leaf name {
          type string;
        }
        container timers {
          tailf:cli-compact-syntax;
          tailf:cli-sequence-commands {
            tailf:cli-reset-siblings;
          }
          container hello-interval {
            tailf:cli-drop-node-name;
            tailf:cli-flatten-container;
            tailf:cli-compact-syntax;
            choice hello-interval-choice {
              leaf seconds {
                tailf:cli-drop-node-name;
                type uint8;
              }
              leaf msec {
                type uint16;
              }
            }
          }
          container hold-time {
            tailf:cli-drop-node-name;
            tailf:cli-flatten-container;
            tailf:cli-compact-syntax;
            choice hold-time-choice {
              leaf seconds {
                tailf:cli-drop-node-name;
                type uint8;
              }
              leaf msec {
                type uint16;
              }
            }
          }
        }
        leaf priority {
          type uint8;
        }
        container preempt {
          tailf:cli-compact-syntax;
          presence "true";
          container delay {
            tailf:cli-compact-syntax;
            leaf minimum {
              type uint16;
            }
            leaf reload {
              type uint16;
            }
            leaf sync {
              type uint16;
            }
          }
        }
        list track {
          tailf:cli-suppress-mode;
          tailf:cli-delete-when-empty;
          tailf:cli-compact-syntax;
          key "name";
          leaf name {
            tailf:cli-suppress-range;
            type union {
              type uint16;
              type string;
            }
          }
          choice options {
            case interface {
              leaf priority-decrement {
                tailf:cli-drop-node-name;
                type uint16;
              }
            }
            case group-number {
              leaf decrement {
                type uint16;
              }
              leaf shutdown {
                type empty;
              }
            }
          }
        }
      }
    }
    container storm-control {
      container action {
        leaf shutdown {
          type empty;
        }
        leaf trap {
          type empty;
        }
        leaf level {
          type decimal64 {
            fraction-digits 2;
          }
        }
      }
      container broadcast {
        leaf level {
          type decimal64 {
            fraction-digits 2;
          }
        }
        uses interface-storm-control-grouping;
        container include {
          leaf multicast {
            type empty;
          }
        }
      }
      container multicast {
        leaf level {
          type decimal64 {
            fraction-digits 2;
          }
        }
        uses interface-storm-control-grouping;
      }
      container unicast {
        leaf level {
          type decimal64 {
            fraction-digits 2;
          }
        }
        uses interface-storm-control-grouping;
      }
      container unknown-unicast {
        leaf level {
          type decimal64 {
            fraction-digits 2;
          }
        }
        uses interface-storm-control-grouping;
      }
    }
    container pagp {
      leaf rate {
        type enumeration {
          enum "normal";
          enum "fast";
        }
      }
    }
    container wrr-queue {
      uses interface-queue-grouping;
    }
    container no-list {
      container wrr-queue {
        list random-detect {
          tailf:cli-suppress-mode;
          tailf:cli-delete-when-empty;
          key "id";
          leaf id {
            type uint32;
          }
        }
      }
      container rcv-queue {
        list random-detect {
          tailf:cli-suppress-mode;
          tailf:cli-delete-when-empty;
          key "id";
          leaf id {
            type uint32;
          }
        }
      }
    }
    container priority-queue {
      leaf queue-limit {
        type uint8;
      }
      list dscp-map {
        tailf:cli-suppress-mode;
        tailf:cli-delete-when-empty;
        tailf:cli-compact-syntax;
        key "id";
        leaf id {
          type uint8;
        }
        list values {
          tailf:cli-drop-node-name;
          tailf:cli-suppress-mode;
          tailf:cli-delete-when-empty;
          ordered-by user;
          key "value";
          leaf value {
            tailf:cli-multi-word-key;
            type string;
          }
        }
      }
      container cos-map {
        tailf:cli-compact-syntax;
        tailf:cli-sequence-commands;
        leaf id {
          tailf:cli-drop-node-name;
          type uint8;
        }
        leaf-list cos-values {
          tailf:cli-drop-node-name;
          tailf:cli-flat-list-syntax;
          type uint8;
        }
      }
      leaf out {
        type empty;
      }
    }
    container rep {
      container block {
        container port {
          tailf:cli-sequence-commands {
            tailf:cli-reset-siblings;
          }
          tailf:cli-compact-syntax;
          choice port-choice {
            leaf neighbor-offset {
              tailf:cli-drop-node-name;
              type int16;
            }
            leaf id {
              type string;
            }
            leaf preferred {
              type empty;
            }
          }
          leaf vlan {
            type union {
              type string;
              type enumeration {
                enum "all";
              }
            }
          }
        }
      }
      container preempt {
        leaf delay {
          type uint16;
        }
      }
      container segment {
        tailf:cli-compact-syntax;
        tailf:cli-sequence-commands {
          tailf:cli-reset-siblings;
        }
        leaf id {
          tailf:cli-drop-node-name;
          type uint16;
        }
        leaf edge {
          tailf:cli-optional-in-sequence;
          type empty;
        }
        leaf no-neighbor {
          tailf:cli-optional-in-sequence;
          type empty;
        }
        leaf primary {
          tailf:cli-optional-in-sequence;
          type empty;
        }
        leaf preferred {
          type empty;
        }
      }
      leaf lsl-retries {
        type uint8;
      }
      leaf lsl-age-timer {
        type uint16;
      }
      container stcn {
        leaf segment {
          type string;
        }
        leaf stp {
          type empty;
        }
      }
    }
    container rcv-queue {
      uses interface-queue-grouping;
    }
    container udld {
      container port {
        tailf:cli-delete-when-empty;
        presence "true";
        choice port-choice {
          leaf aggressive {
            type empty;
          }
          leaf disable {
            type empty;
          }
        }
      }
    }
    container peer {
      leaf neighbor-route {
        type boolean;
      }
      container ip {
        container address {
          leaf forced {
            type empty;
          }
        }
      }
      container default {
        container ip {
          choice address-choice {
            case no-address {
              container no-address {
                tailf:cli-drop-node-name;
                leaf address {
                  type boolean;
                }
              }
            }
            container address {
              choice address-choice {
                leaf dhcp {
                  type empty;
                }
                container dhcp-pool {
                  presence "true";
                  leaf pools {
                    tailf:cli-drop-node-name;
                    tailf:cli-multi-value;
                    type string;
                  }
                }
                container pool {
                  presence "true";
                  leaf pools {
                    tailf:cli-drop-node-name;
                    tailf:cli-multi-value;
                    type string;
                  }
                }
              }
            }
          }
        }
      }
    }
    leaf random-detect {
      type empty;
    }
    container clns {
      leaf enable {
        type empty;
      }
      leaf mtu {
        type uint32;
      }
      container router {
        container isis {
          tailf:cli-delete-when-empty;
          presence "true";
          leaf tag {
            tailf:cli-drop-node-name;
            type string;
          }
        }
      }
      leaf route-cache {
        type boolean;
      }
    }
    container dsu {
      leaf bandwidth {
        type uint32;
      }
      leaf mode {
        type enumeration {
          enum "1";
          enum "2";
        }
      }
    }
    leaf framing {
      type enumeration {
        enum "bypass";
        enum "g751";
        enum "c-bit";
        enum "m13";
      }
    }
    leaf cablelength {
      type union {
        type uint32;
        type enumeration {
          enum "short";
          enum "long";
        }
      }
    }
    container isdn {
      leaf switch-type {
        type string;
      }
      leaf protocol-emulate {
        type enumeration {
          enum "network";
          enum "user";
        }
      }
      container incoming-voice {
        choice incoming-voice-choice {
          leaf voice {
            type empty;
          }
          container data {
            tailf:cli-delete-when-empty;
            presence "true";
            leaf kbps {
              tailf:cli-drop-node-name;
              type enumeration {
                enum "56";
                enum "64";
              }
            }
          }
          container modem {
            tailf:cli-delete-when-empty;
            presence "true";
            leaf kbps {
              tailf:cli-drop-node-name;
              type enumeration {
                enum "56";
                enum "64";
              }
            }
          }
        }
      }
      container supp-service {
        container name {
          container calling {
            tailf:cli-delete-when-empty;
            presence "true";
          }
        }
      }
      container termination {
        leaf multidrop {
          type empty;
        }
      }
      leaf point-to-point-setup {
        type empty;
      }
      container map {
        container address {
          list address-list {
            tailf:cli-drop-node-name;
            tailf:cli-suppress-mode;
            tailf:cli-delete-when-empty;
            tailf:cli-compact-syntax;
            tailf:cli-sequence-commands {
              tailf:cli-reset-siblings;
            }
            key "address";
            leaf address {
              type string;
            }
            leaf plan {
              type string;
            }
            leaf type {
              type string;
            }
          }
          leaf transparent {
            type empty;
          }
        }
      }
      container bind-l3 {
        leaf ccm-manager {
          type empty;
        }
      }
      container outgoing {
        leaf display-ie {
          type empty;
        }
        container ie {
          container facility {
            tailf:cli-delete-when-empty;
            tailf:cli-compact-syntax;
            tailf:cli-sequence-commands {
              tailf:cli-reset-siblings;
            }
            presence "true";
            uses interface-isdn-outgoing-ie-grouping;
          }
          container extended-facility {
            tailf:cli-delete-when-empty;
            tailf:cli-compact-syntax;
            tailf:cli-sequence-commands {
              tailf:cli-reset-siblings;
            }
            presence "true";
            uses interface-isdn-outgoing-ie-grouping;
          }
          container progress-indicator {
            tailf:cli-delete-when-empty;
            tailf:cli-compact-syntax;
            tailf:cli-sequence-commands {
              tailf:cli-reset-siblings;
            }
            presence "true";
            uses interface-isdn-outgoing-ie-grouping;
          }
          container network-facility {
            tailf:cli-delete-when-empty;
            tailf:cli-compact-syntax;
            tailf:cli-sequence-commands {
              tailf:cli-reset-siblings;
            }
            presence "true";
            uses interface-isdn-outgoing-ie-grouping;
          }
          container notify-indicator {
            tailf:cli-delete-when-empty;
            tailf:cli-compact-syntax;
            tailf:cli-sequence-commands {
              tailf:cli-reset-siblings;
            }
            presence "true";
            uses interface-isdn-outgoing-ie-grouping;
          }
          container connected-number {
            tailf:cli-delete-when-empty;
            tailf:cli-compact-syntax;
            tailf:cli-sequence-commands {
              tailf:cli-reset-siblings;
            }
            presence "true";
            uses interface-isdn-outgoing-ie-grouping;
          }
          container connected-subaddr {
            tailf:cli-delete-when-empty;
            tailf:cli-compact-syntax;
            tailf:cli-sequence-commands {
              tailf:cli-reset-siblings;
            }
            presence "true";
            uses interface-isdn-outgoing-ie-grouping;
          }
          container caller-number {
            tailf:cli-delete-when-empty;
            tailf:cli-compact-syntax;
            tailf:cli-sequence-commands {
              tailf:cli-reset-siblings;
            }
            presence "true";
            uses interface-isdn-outgoing-ie-grouping;
          }
          container caller-subaddr {
            tailf:cli-delete-when-empty;
            tailf:cli-compact-syntax;
            tailf:cli-sequence-commands {
              tailf:cli-reset-siblings;
            }
            presence "true";
            uses interface-isdn-outgoing-ie-grouping;
          }
          container called-number {
            tailf:cli-delete-when-empty;
            tailf:cli-compact-syntax;
            tailf:cli-sequence-commands {
              tailf:cli-reset-siblings;
            }
            presence "true";
            uses interface-isdn-outgoing-ie-grouping;
          }
          container called-subaddr {
            tailf:cli-delete-when-empty;
            tailf:cli-compact-syntax;
            tailf:cli-sequence-commands {
              tailf:cli-reset-siblings;
            }
            presence "true";
            uses interface-isdn-outgoing-ie-grouping;
          }
          container redirecting-number {
            tailf:cli-delete-when-empty;
            tailf:cli-compact-syntax;
            tailf:cli-sequence-commands {
              tailf:cli-reset-siblings;
            }
            presence "true";
            uses interface-isdn-outgoing-ie-grouping;
          }
          container user-user {
            tailf:cli-delete-when-empty;
            tailf:cli-compact-syntax;
            tailf:cli-sequence-commands {
              tailf:cli-reset-siblings;
            }
            presence "true";
            uses interface-isdn-outgoing-ie-grouping;
          }
          container high-layer-compat {
            tailf:cli-delete-when-empty;
            tailf:cli-compact-syntax;
            tailf:cli-sequence-commands {
              tailf:cli-reset-siblings;
            }
            presence "true";
            uses interface-isdn-outgoing-ie-grouping;
          }
          container low-layer-compat {
            tailf:cli-delete-when-empty;
            tailf:cli-compact-syntax;
            tailf:cli-sequence-commands {
              tailf:cli-reset-siblings;
            }
            presence "true";
            uses interface-isdn-outgoing-ie-grouping;
          }
        }
      }
      leaf bchan-number-order {
        type enumeration {
          enum "ascending";
          enum "descending";
        }
      }
    }
    leaf scramble {
      type empty;
    }
    container clock {
      leaf source {
        type enumeration {
          enum "internal";
          enum "external";
          enum "line";
        }
      }
      leaf rate {
        type uint32;
      }
    }
    leaf down-when-looped {
      type empty;
    }
    leaf crc {
      type enumeration {
        enum "16";
        enum "32";
      }
    }
    container carrier-delay {
      uses carrier-delay-grouping {
        refine "delay-choice/seconds/seconds";
      }
      container up {
        uses carrier-delay-grouping;
      }
      container down {
        uses carrier-delay-grouping;
      }
    }
    leaf trunk-group {
      type string;
    }
    container eapol {
      leaf eth-type {
        type enumeration {
          enum "876F";
        }
      }
      leaf destination-address {
        type union {
          type string;
          type enumeration {
            enum "bridge-group-address";
            enum "broadcast-address";
            enum "lldp-multicast-address";
          }
        }
      }
    }
    container mka {
      leaf policy {
        type string;
      }
      container pre-shared-key {
        tailf:cli-compact-syntax;
        tailf:cli-sequence-commands {
          tailf:cli-reset-siblings;
        }
        leaf key-chain {
          type string;
        }
        leaf fallback-key-chain {
          type string;
        }
      }
    }
    container macsec-enable {
      tailf:cli-drop-node-name;
      leaf macsec {
        type empty;
      }
    }
    container macsec {
      container replay-protection {
        leaf window-size {
          type uint32;
        }
      }
      leaf network-link {
        type empty;
      }
      leaf dot1q-in-clear {
        type enumeration {
          enum "1";
        }
      }
      leaf access-control {
        type enumeration {
          enum "must-secure";
          enum "should-secure";
        }
      }
    }
    container crypto {
      container engine {
        tailf:cli-compact-syntax;
        tailf:cli-sequence-commands {
          tailf:cli-reset-siblings;
        }
        leaf slot {
          type string;
        }
        leaf location {
          tailf:cli-drop-node-name;
          type enumeration {
            enum "inside";
            enum "outside";
          }
        }
      }
      container map {
        container ipv4 {
          tailf:cli-drop-node-name;
          tailf:cli-compact-syntax;
          tailf:cli-sequence-commands {
            tailf:cli-reset-siblings;
          }
          leaf map-name {
            tailf:cli-drop-node-name;
            type string;
          }
          leaf redundancy {
            type string;
          }
          leaf stateful {
            type empty;
          }
        }
        container ipv6 {
          tailf:cli-compact-syntax;
          tailf:cli-sequence-commands {
            tailf:cli-reset-siblings;
          }
          leaf map-name {
            tailf:cli-drop-node-name;
            type string;
          }
          leaf redundancy {
            type string;
          }
          leaf stateful {
            type empty;
          }
        }
      }
      container ipsec {
        leaf df-bit {
          type enumeration {
            enum "clear";
            enum "copy";
            enum "set";
          }
        }
      }
    }
    container routing {
      leaf dynamic {
        type boolean;
      }
    }
    container autonomic {
      leaf connect {
        type empty;
      }
    }
    container performance {
      container monitor {
        list context {
          tailf:cli-suppress-mode;
          tailf:cli-delete-when-empty;
          key "name";
          leaf name {
            type string;
          }
        }
      }
    }
    choice qos-choice {
      container qos-enable {
        tailf:cli-drop-node-name;
        leaf qos {
          type boolean;
        }
      }
      container qos {
        container trust {
          tailf:cli-compact-syntax;
          choice trust-choice {
            leaf dscp {
              type empty;
            }
            leaf cos {
              type empty;
            }
            leaf device {
              type enumeration {
                enum "cisco-phone";
                enum "cts";
                enum "ip-camera";
                enum "media-player";
              }
            }
            container extend {
              tailf:cli-delete-when-empty;
              presence "true";
              leaf cos {
                type uint8;
              }
            }
          }
        }
        leaf pre-classify {
          type empty;
        }
        container vlan-based {
          presence "true";
        }
        leaf dscp {
          type uint8;
        }
      }
    }
    container qos-config {
      container scheduling-mode {
        leaf min-bw-guarantee {
          type boolean;
        }
      }
    }
    list tx-queue {
      key "id";
      leaf id {
        type uint8;
      }
      container bandwidth {
        tailf:cli-compact-syntax;
        tailf:cli-sequence-commands {
          tailf:cli-reset-siblings;
        }
        choice bandwidth-choice {
          case numeric {
            leaf value {
              tailf:cli-drop-node-name;
              type string;
            }
            leaf unit {
              tailf:cli-drop-node-name;
              type string;
            }
          }
          leaf percent {
            type uint8;
          }
        }
      }
      container shape {
        tailf:cli-compact-syntax;
        tailf:cli-sequence-commands {
          tailf:cli-reset-siblings;
        }
        choice shape-choice {
          case numeric {
            leaf value {
              tailf:cli-drop-node-name;
              type string;
            }
            leaf unit {
              tailf:cli-drop-node-name;
              type string;
            }
          }
          leaf percent {
            type uint8;
          }
        }
      }
      leaf priority {
        type enumeration {
          enum "high";
        }
      }
    }
    container link {
      container state {
        container group {
          tailf:cli-compact-syntax;
          tailf:cli-sequence-commands {
            tailf:cli-reset-siblings;
          }
          leaf number {
            tailf:cli-drop-node-name;
            type uint8;
          }
          leaf direction {
            tailf:cli-drop-node-name;
            type enumeration {
              enum "downstream";
              enum "upstream";
            }
          }
        }
      }
    }
    container source {
      leaf template {
        type string;
      }
    }
    container l2protocol {
      choice l2protocol-choice {
        leaf drop {
          type empty;
        }
        leaf peer {
          type empty;
        }
        list protocols {
          tailf:cli-drop-node-name;
          tailf:cli-suppress-mode;
          tailf:cli-delete-when-empty;
          tailf:cli-compact-syntax;
          tailf:cli-sequence-commands;
          key "protocol";
          leaf protocol {
            type enumeration {
              enum "cdp";
              enum "dtp";
              enum "lacp";
              enum "stp";
              enum "vtp";
            }
          }
          leaf option {
            tailf:cli-drop-node-name;
            tailf:cli-prefix-key;
            type enumeration {
              enum "drop";
              enum "peer";
            }
          }
        }
      }
    }
    container zone-member {
      leaf security {
        type string;
      }
    }
    container et-analytics {
      leaf enable {
        type empty;
      }
    }
    container srlg {
      list gid {
        tailf:cli-suppress-mode;
        tailf:cli-delete-when-empty;
        key "id";
        leaf id {
          type uint16;
        }
      }
    }
    container stackwise-virtual {
      leaf link {
        type uint8;
      }
      leaf dual-active-detection {
        type empty;
      }
    }
    container location {
      leaf civic-location-id {
        type union {
          type string;
          type enumeration {
            enum "host";
            enum "none";
          }
        }
      }
    }
    leaf bridge-group {
      type uint8;
    }
    container bridge-group-conf {
      tailf:cli-drop-node-name;
      list bridge-group {
        tailf:cli-suppress-mode;
        tailf:cli-delete-when-empty;
        key "id";
        leaf id {
          type uint8;
        }
        leaf subscriber-loop-control {
          type empty;
        }
        leaf block-unknown-source {
          type empty;
        }
        leaf source-learning {
          type boolean;
        }
        leaf unicast-flooding {
          type boolean;
        }
        leaf spanning-disabled {
          type empty;
        }
      }
    }
    leaf tx-ring-limit {
      type uint16;
    }
    leaf tx-queue-limit {
      type uint16;
    }
    container l2proto-forward {
      container tagged {
        presence "true";
      }
    }
    container tag-switching {
      container mtu {
        choice mtu-choice {
          leaf override {
            type uint16;
          }
          leaf value {
            tailf:cli-drop-node-name;
            type uint16;
          }
        }
      }
      leaf ip {
        type empty;
      }
    }
    container cws-tunnel {
      leaf in {
        type empty;
      }
      container out {
        leaf tunnel-number {
          type uint16;
        }
      }
    }
    container site-manager {
      container inside {
        presence "true";
      }
      container link-group {
        tailf:cli-compact-syntax;
        tailf:cli-sequence-commands {
          tailf:cli-reset-siblings;
        }
        leaf group {
          tailf:cli-drop-node-name;
          type string;
        }
        leaf direct-internet-access {
          type empty;
        }
      }
      container path {
        tailf:cli-compact-syntax;
        tailf:cli-sequence-commands {
          tailf:cli-reset-siblings;
        }
        leaf color {
          tailf:cli-drop-node-name;
          type string;
        }
        leaf direct-internet-access {
          type empty;
        }
      }
    }
    container cemoudp {
      container reserve {
        leaf bay {
          type uint8;
        }
      }
    }
    container topology {
      container ipv4 {
        container multicast {
          container base {
            tailf:cli-add-mode;
            container ip {
              container ospf {
                leaf cost {
                  type uint16;
                }
              }
            }
          }
        }
      }
    }
  }

  grouping interface-common-ptp-grouping {
    uses interface-common-grouping {
      refine "service-policy/input";
      refine "service-policy/output";
      refine "peer/neighbor-route";
    }
  }

  grouping interface-tunnel-grouping {
    container tunnel {
      leaf source {
        type string;
      }
      leaf destination {
        type inet:host;
      }
      container mode {
        choice mode-choice {
          container ethernet {
            container gre {
              choice af-choice {
                container ipv4 {
                  tailf:cli-delete-when-empty;
                  presence "true";
                }
                container ipv6 {
                  tailf:cli-delete-when-empty;
                  presence "true";
                }
              }
            }
          }
          container ipsec {
            choice af-choice {
              container ipv4 {
                tailf:cli-delete-when-empty;
                presence "true";
              }
              container ipv6 {
                tailf:cli-delete-when-empty;
                presence "true";
              }
            }
          }
          container mpls {
            container traffic-eng {
              tailf:cli-delete-when-empty;
              presence "true";
              leaf gre-ip {
                type empty;
              }
              leaf point-to-multipoint {
                type empty;
              }
            }
          }
          container gre {
            choice gre-choice {
              container multipoint {
                presence "true";
                leaf ipv6 {
                  type empty;
                }
              }
              leaf ip {
                type empty;
              }
              leaf ipv6 {
                type empty;
              }
            }
          }
          leaf eon {
            type empty;
          }
          leaf ipv6 {
            type empty;
          }
          container ipip {
            presence "true";
          }
          container vxlan {
            container ipv4 {
              leaf default-mac {
                type empty;
              }
            }
          }
        }
      }
      container vxlan {
        leaf vni {
          type uint32;
        }
      }
      leaf key {
        type uint32;
      }
      leaf vrf {
        type string;
      }
      container path-mtu-discovery {
        presence "true";
      }
      container bandwidth {
        leaf receive {
          type uint32;
        }
        leaf transmit {
          type uint32;
        }
      }
      container protection {
        container ipsec-conf {
          tailf:cli-drop-node-name;
          container ipsec {
            container policy {
              leaf ipv4 {
                type ext-acl-type;
              }
            }
          }
        }
        container ipsec {
          tailf:cli-compact-syntax;
          tailf:cli-sequence-commands {
            tailf:cli-reset-siblings;
          }
          leaf profile {
            type string;
          }
          choice profile-choice {
            leaf isakmp-profile {
              type string;
            }
            leaf ikev2-profile {
              type string;
            }
            leaf shared {
              type empty;
            }
          }
        }
      }
      container mpls {
        container traffic-eng {
          container forwarding-adjacency {
            tailf:cli-delete-when-empty;
            presence "true";
            leaf holdtime {
              type uint32;
            }
          }
          leaf load-share {
            type uint32;
          }
          leaf name {
            type string;
          }
          container affinity {
            tailf:cli-compact-syntax;
            tailf:cli-sequence-commands {
              tailf:cli-reset-siblings;
            }
            leaf attributes {
              tailf:cli-drop-node-name;
              type string;
            }
            leaf mask {
              type string;
            }
          }
          container autoroute {
            leaf announce {
              type empty;
            }
            leaf destination {
              type empty;
            }
            container metric {
              choice metric-choice {
                leaf value {
                  tailf:cli-drop-node-name;
                  type uint32;
                }
                leaf absolute {
                  type uint32;
                }
                leaf relative {
                  type int8;
                }
              }
            }
          }
          container backup-bw {
            leaf bandwidth {
              tailf:cli-drop-node-name;
              type uint32;
            }
          }
          container priority {
            tailf:cli-compact-syntax;
            tailf:cli-sequence-commands {
              tailf:cli-reset-siblings;
            }
            leaf setup-priority {
              tailf:cli-drop-node-name;
              type uint8;
            }
            leaf hold-priority {
              tailf:cli-drop-node-name;
              type uint8;
            }
          }
          container bandwidth {
            leaf requirement {
              tailf:cli-drop-node-name;
              type uint32;
            }
          }
          list path-option {
            tailf:cli-suppress-mode;
            tailf:cli-delete-when-empty;
            tailf:cli-compact-syntax;
            tailf:cli-sequence-commands {
              tailf:cli-reset-all-siblings;
            }
            key "id";
            leaf id {
              tailf:cli-suppress-range;
              type uint16;
            }
            choice path-option-choice {
              leaf dynamic {
                tailf:cli-optional-in-sequence;
                type empty;
              }
              container explicit {
                tailf:cli-flatten-container;
                tailf:cli-compact-syntax;
                tailf:cli-optional-in-sequence;
                choice explicit-choice {
                  leaf name {
                    type string;
                  }
                  leaf identifier {
                    type uint16;
                  }
                }
              }
            }
            uses if-tunnel-mpls-traffic-eng-path-option-grouping;
          }
          container path-option-protect {
            tailf:cli-drop-node-name;
            container path-option {
              list protect {
                tailf:cli-suppress-mode;
                tailf:cli-delete-when-empty;
                tailf:cli-compact-syntax;
                tailf:cli-sequence-commands {
                  tailf:cli-reset-siblings;
                }
                key "id";
                leaf id {
                  tailf:cli-suppress-range;
                  type uint16;
                }
                choice path-option-choice {
                  leaf diverse {
                    tailf:cli-optional-in-sequence;
                    type empty;
                  }
                  container explicit {
                    tailf:cli-optional-in-sequence;
                    tailf:cli-flatten-container;
                    tailf:cli-compact-syntax;
                    choice explicit-choice {
                      leaf name {
                        type string;
                      }
                      leaf identifier {
                        type uint16;
                      }
                    }
                  }
                }
                uses if-tunnel-mpls-traffic-eng-path-option-grouping;
              }
            }
          }
          container bidirectional {
            container association {
              container id {
                tailf:cli-compact-syntax;
                tailf:cli-sequence-commands {
                  tailf:cli-reset-siblings;
                }
                leaf value {
                  tailf:cli-drop-node-name;
                  type uint16;
                }
                leaf source-address {
                  type inet:ipv4-address;
                }
                leaf global-id {
                  type uint32;
                }
              }
              container type {
                container co-routed {
                  tailf:cli-compact-syntax;
                  tailf:cli-sequence-commands {
                    tailf:cli-reset-siblings;
                  }
                  tailf:cli-delete-when-empty;
                  presence "true";
                  leaf fault-oam {
                    type empty;
                  }
                  leaf wrap-protection {
                    type empty;
                  }
                }
              }
            }
          }
          container path-selection {
            leaf metric {
              type enumeration {
                enum "igp";
                enum "te";
              }
            }
            container segment-routing {
              leaf adjacency {
                type enumeration {
                  enum "protected";
                  enum "unprotected";
                }
              }
            }
          }
          container auto-bw {
            tailf:cli-compact-syntax;
            tailf:cli-delete-when-empty;
            presence "true";
            leaf frequency {
              type uint32;
            }
            leaf adjustment-threshold {
              type uint8;
            }
            leaf max-bw {
              type uint32;
            }
            leaf min-bw {
              type uint32;
            }
            leaf collect-bw {
              type empty;
            }
          }
          leaf record-route {
            type empty;
          }
          container fast-reroute {
            presence "true";
          }
          container bfd {
            container encap-mode {
              leaf gal {
                type string;
              }
            }
          }
        }
      }
      leaf-list vlan {
        tailf:cli-range-list-syntax;
        type uint16;
      }
      leaf checksum {
        type empty;
      }
      container route-via {
        tailf:cli-compact-syntax;
        tailf:cli-sequence-commands {
          tailf:cli-reset-all-siblings;
        }
        uses interface-name-grouping;
        leaf mandatory-preferred {
          tailf:cli-drop-node-name;
          type enumeration {
            enum "mandatory";
            enum "preferred";
          }
        }
      }
    }
    container domain {
      tailf:cli-compact-syntax;
      tailf:cli-sequence-commands {
        tailf:cli-reset-all-siblings;
      }
      leaf domain-name {
        tailf:cli-drop-node-name;
        tailf:cli-optional-in-sequence;
        type string;
      }
      choice path-choice {
        leaf dynamic-path {
          type empty;
        }
        leaf dci-path {
          type string;
        }
        leaf path {
          type string;
        }
        container saf {
          tailf:cli-flatten-container;
          leaf neighboring {
            type empty;
          }
        }
      }
      leaf path-id {
        tailf:cli-break-sequence-commands;
        type uint8;
      }
      leaf internet-bound {
        type empty;
      }
      leaf zero-sla {
        type empty;
      }
      leaf path-last-resort {
        type empty;
      }
    }
    container domain-smart-probe {
      tailf:cli-drop-node-name;
      container domain {
        tailf:cli-compact-syntax;
        tailf:cli-sequence-commands {
          tailf:cli-reset-siblings;
        }
        leaf domain-name {
          tailf:cli-drop-node-name;
          tailf:cli-optional-in-sequence;
          type string;
        }
        container smart-probe {
          tailf:cli-flatten-container;
          leaf profile {
            type uint8;
          }
        }
      }
    }
  }

  grouping interface-ethernet-pre-grouping {
    leaf port-type {
      type enumeration {
        enum "eni";
        enum "nni";
        enum "uni";
      }
    }
    container platform {
      container qos {
        leaf vlan-based {
          type empty;
        }
        container queue-mode {
          leaf mode-dscp {
            type empty;
          }
        }
      }
      container ring {
        leaf rx {
          type uint16;
        }
        leaf tx {
          type uint16;
        }
      }
    }
    container encapsulation {
      container dot1Q {
        tailf:cli-compact-syntax;
        tailf:cli-sequence-commands;
        leaf vlan-id {
          tailf:cli-drop-node-name;
          type uint16;
        }
        leaf second-dot1q {
          tailf:cli-optional-in-sequence;
          type union {
            type enumeration {
              enum "any";
            }
            type string;
          }
        }
        leaf native {
          type empty;
        }
      }
    }
  }

  grouping interface-ethernet-grouping {
    container authentication {
      leaf control-direction {
        type enumeration {
          enum "both";
          enum "in";
        }
      }
      container event {
        container fail {
          tailf:cli-compact-syntax;
          leaf retry {
            type uint8;
          }
          container action {
            tailf:cli-flatten-container;
            choice authentication-event-fail-action-choice {
              container authorize {
                tailf:cli-flatten-container;
                tailf:cli-compact-syntax;
                leaf vlan {
                  type uint16;
                }
              }
              leaf next-method {
                type empty;
              }
            }
          }
        }
        container server {
          container dead {
            container action {
              container reinitialize {
                leaf vlan {
                  type uint16;
                }
              }
              container authorize-enable {
                tailf:cli-drop-node-name;
                leaf authorize {
                  type empty;
                }
              }
              container authorize {
                leaf-list vlan {
                  type uint16;
                }
                leaf voice {
                  type empty;
                }
              }
            }
          }
          container alive {
            container action {
              leaf reinitialize {
                type empty;
              }
            }
          }
        }
        container no-response {
          container action {
            container authorize {
              leaf vlan {
                type uint16;
              }
            }
          }
        }
      }
      leaf host-mode {
        type enumeration {
          enum "multi-auth";
          enum "multi-domain";
          enum "multi-host";
          enum "single-host";
        }
      }
      leaf open {
        type empty;
      }
      leaf-list order {
        tailf:cli-flat-list-syntax;
        ordered-by user;
        type enumeration {
          enum "dot1x";
          enum "mab";
          enum "webauth";
        }
      }
      leaf-list priority {
        tailf:cli-flat-list-syntax;
        ordered-by user;
        type enumeration {
          enum "dot1x";
          enum "mab";
          enum "webauth";
        }
      }
      leaf port-control {
        type enumeration {
          enum "auto";
          enum "force-authorized";
          enum "force-unauthorized";
        }
      }
      leaf periodic {
        type empty;
      }
      container timer {
        leaf reauthenticate {
          type union {
            type uint16;
            type enumeration {
              enum "server";
            }
          }
        }
        container inactivity {
          tailf:cli-compact-syntax;
          tailf:cli-sequence-commands {
            tailf:cli-reset-siblings;
          }
          leaf value {
            tailf:cli-drop-node-name;
            type union {
              type uint16;
              type enumeration {
                enum "server";
              }
            }
          }
          leaf dynamic {
            type empty;
          }
        }
      }
      leaf violation {
        type enumeration {
          enum "protect";
          enum "replace";
          enum "restrict";
          enum "shutdown";
        }
      }
    }
    container mac {
      list access-group {
        tailf:cli-suppress-mode;
        tailf:cli-delete-when-empty;
        tailf:cli-compact-syntax;
        tailf:cli-sequence-commands;
        key "direction";
        leaf direction {
          type enumeration {
            enum "in";
            enum "out";
          }
        }
        leaf access-list {
          tailf:cli-drop-node-name;
          tailf:cli-prefix-key;
          type string;
        }
      }
    }
    container rmon {
      leaf promiscuous {
        type empty;
      }
      container collection {
        list stats {
          tailf:cli-suppress-mode;
          tailf:cli-delete-when-empty;
          key "id";
          leaf id {
            type uint16;
          }
          leaf owner {
            type string;
          }
        }
      }
    }
    container spanning-tree-enable {
      tailf:cli-drop-node-name;
      leaf spanning-tree {
        type empty;
      }
    }
    container spanning-tree {
      leaf bpdufilter {
        type enumeration {
          enum "disable";
          enum "enable";
        }
      }
      container bpduguard {
        choice bpduguard-choice {
          leaf disable {
            type empty;
          }
          leaf enable {
            type empty;
          }
        }
      }
      leaf cost {
        type uint32;
      }
      leaf guard {
        type enumeration {
          enum "loop";
          enum "none";
          enum "root";
        }
      }
      leaf link-type {
        type enumeration {
          enum "auto" {
            tailf:code-name "link_type_auto";
          }
          enum "none";
          enum "point-to-point";
          enum "root";
          enum "shared";
        }
      }
      container mst {
        choice mst-choice {
          list instance-range {
            tailf:cli-drop-node-name;
            tailf:cli-suppress-mode;
            tailf:cli-delete-when-empty;
            tailf:cli-compact-syntax;
            tailf:cli-range-list-syntax;
            key "id";
            leaf id {
              type uint16;
            }
            leaf cost {
              type uint32;
            }
            leaf port-priority {
              type uint16;
            }
          }
          leaf pre-standard {
            type empty;
          }
        }
      }
      container portfast {
        tailf:cli-compact-syntax;
        tailf:cli-delete-when-empty;
        presence "true";
        choice portfast-choice {
          leaf disable {
            type empty;
          }
          leaf network {
            type empty;
          }
          case trunk-mode {
            leaf edge {
              type empty;
            }
            leaf trunk {
              type empty;
            }
          }
        }
      }
      container loopguard {
        leaf default {
          type empty;
        }
      }
      leaf port-priority {
        type uint8;
      }
      list vlan {
        tailf:cli-suppress-mode;
        tailf:cli-delete-when-empty;
        tailf:cli-range-list-syntax;
        key "id";
        leaf id {
          type uint16;
        }
        leaf port-priority {
          type uint8;
        }
        leaf cost {
          type uint32;
        }
      }
    }
    container srr-queue {
      container bandwidth {
        leaf limit {
          type uint8;
        }
        container shape {
          tailf:cli-compact-syntax;
          tailf:cli-sequence-commands;
          leaf weight1 {
            tailf:cli-drop-node-name;
            type uint16;
          }
          leaf weight2 {
            tailf:cli-drop-node-name;
            type uint16;
          }
          leaf weight3 {
            tailf:cli-drop-node-name;
            type uint16;
          }
          leaf weight4 {
            tailf:cli-drop-node-name;
            type uint16;
          }
        }
        container share {
          tailf:cli-compact-syntax;
          tailf:cli-sequence-commands;
          leaf weight1 {
            tailf:cli-drop-node-name;
            type uint8;
          }
          leaf weight2 {
            tailf:cli-drop-node-name;
            type uint8;
          }
          leaf weight3 {
            tailf:cli-drop-node-name;
            type uint8;
          }
          leaf weight4 {
            tailf:cli-drop-node-name;
            type uint8;
          }
        }
      }
    }
    leaf queue-set {
      type uint8;
    }
    container dot1q {
      container tunneling {
        leaf ethertype {
          type enumeration {
            enum "0x88A8";
            enum "0x9100";
          }
        }
      }
    }
    container dot1x {
      container pae {
        choice pae-choice {
          leaf authenticator {
            type empty;
          }
          leaf supplicant {
            type empty;
          }
          leaf both {
            type empty;
          }
        }
      }
      leaf credentials {
        type string;
      }
      container authenticator {
        container eap {
          leaf profile {
            type string;
          }
        }
      }
      container supplicant {
        container eap {
          leaf profile {
            type string;
          }
        }
      }
      container timeout {
        leaf quiet-period {
          type uint16;
        }
        leaf tx-period {
          type uint16;
        }
        leaf supp-timeout {
          type uint16;
        }
        leaf supp-period {
          type uint16;
        }
        leaf ratelimit-period {
          type uint16;
        }
        leaf held-period {
          type uint16;
        }
      }
      leaf max-reauth-req {
        type uint8;
      }
    }
    container macro {
      uses description-grouping;
      container auto {
        leaf processing {
          type boolean;
        }
      }
    }
    container itu {
      leaf channel {
        type uint8;
      }
    }
    choice media-type-choice {
      leaf media-type {
        type enumeration {
          enum "rj45";
          enum "sfp";
          enum "auto-select";
          enum "gbic";
        }
      }
      container media-type-ext {
        tailf:cli-drop-node-name;
        container media-type {
          tailf:cli-compact-syntax;
          tailf:cli-sequence-commands {
            tailf:cli-reset-siblings;
          }
          container sfp {
            leaf auto-failover {
              type empty;
            }
          }
        }
      }
    }
    container mdix {
      leaf auto {
        type boolean;
      }
    }
    leaf channel-protocol {
      type enumeration {
        enum "lacp";
        enum "pagp";
      }
    }
    container lacp {
      leaf rate {
        type enumeration {
          enum "fast";
          enum "normal";
        }
      }
      leaf failover {
        type enumeration {
          enum "brute-force";
          enum "non-revertive";
        }
      }
      leaf fast-switchover {
        type empty;
      }
      leaf min-bundle {
        type uint8;
      }
      leaf max-bundle {
        type uint8;
      }
      leaf port-priority {
        type uint16;
      }
    }
    container plim {
      container ethernet {
        container vlan {
          container filter {
            leaf disable {
              type empty;
            }
          }
        }
      }
    }
    container ethernet {
      container oam-conf {
        tailf:cli-drop-node-name;
        container oam {
          leaf max-rate {
            type uint8;
          }
          leaf min-rate {
            type uint8;
          }
          leaf mode {
            type enumeration {
              enum "active";
              enum "passive";
            }
          }
          container remote-loopback {
            leaf supported {
              type empty;
            }
          }
          leaf timeout {
            type uint8;
          }
          container link-monitor {
            leaf supported {
              type boolean;
            }
            leaf on {
              type boolean;
            }
            container receive-crc {
              leaf window {
                type uint16;
              }
            }
          }
        }
      }
      leaf oam {
        type empty;
      }
      container dot1ad {
        choice dot1ad-choice {
          leaf nni {
            type empty;
          }
          container uni {
            choice uni-choice {
              container c-port {
                tailf:cli-delete-when-empty;
                presence "true";
                leaf isolate {
                  type empty;
                }
              }
              container s-port {
                tailf:cli-delete-when-empty;
                presence "true";
                leaf isolate {
                  type empty;
                }
              }
            }
          }
        }
      }
      container cfm {
        container mip {
          list level {
            tailf:cli-suppress-mode;
            tailf:cli-delete-when-empty;
            key "level";
            leaf level {
              type uint8;
            }
            leaf-list vlan {
              tailf:cli-range-list-syntax;
              type uint16;
            }
          }
        }
        container mep {
          list mep-list {
            tailf:cli-drop-node-name;
            tailf:cli-compact-syntax;
            tailf:cli-sequence-commands {
              tailf:cli-reset-siblings;
            }
            key "domain";
            leaf domain {
              tailf:cli-expose-key-name;
              type string;
            }
            leaf mpid {
              tailf:cli-hide-in-submode;
              type uint16;
            }
            leaf port {
              tailf:cli-hide-in-submode;
              type empty;
            }
          }
          list mep-list-vlan {
            tailf:cli-drop-node-name;
            tailf:cli-compact-syntax;
            tailf:cli-sequence-commands {
              tailf:cli-reset-siblings;
            }
            key "domain vlan";
            leaf domain {
              tailf:cli-expose-key-name;
              type string;
            }
            leaf mpid {
              tailf:cli-prefix-key {
                tailf:cli-before-key "2";
              }
              type uint16;
            }
            leaf vlan {
              tailf:cli-expose-key-name;
              type uint16;
            }
          }
          list mep-list-service {
            tailf:cli-drop-node-name;
            tailf:cli-compact-syntax;
            tailf:cli-sequence-commands {
              tailf:cli-reset-siblings;
            }
            key "domain service";
            leaf domain {
              tailf:cli-expose-key-name;
              type string;
            }
            leaf mpid {
              tailf:cli-prefix-key {
                tailf:cli-before-key "2";
              }
              type uint16;
            }
            leaf service {
              tailf:cli-expose-key-name;
              type string;
            }
          }
        }
        leaf enable {
          type boolean;
        }
        leaf interface {
          type boolean;
        }
      }
      container uni {
        leaf id {
          type string;
        }
        container bundle {
          tailf:cli-delete-when-empty;
          presence "true";
          leaf all-to-one {
            type empty;
          }
        }
      }
      container lmi {
        leaf interface {
          type boolean;
        }
      }
      container backup {
        leaf interface {
          type string;
        }
      }
      container loopback {
        tailf:cli-compact-syntax;
        tailf:cli-sequence-commands {
          tailf:cli-reset-all-siblings;
        }
        tailf:cli-delete-when-empty;
        presence "true";
        leaf type {
          tailf:cli-drop-node-name;
          type enumeration {
            enum "facility";
            enum "terminal";
          }
        }
        leaf vlan {
          tailf:cli-break-sequence-commands;
          type string;
        }
        leaf mac-address {
          tailf:cli-break-sequence-commands;
          type enumeration {
            enum "copy";
            enum "swap";
          }
        }
        leaf timeout {
          type union {
            type enumeration {
              enum "none";
            }
            type uint16;
          }
        }
        leaf supported {
          type empty;
        }
      }
    }
    container negotiation {
      leaf auto {
        type boolean;
      }
    }
    container synchronous {
      leaf mode {
        type empty;
      }
    }
    container network-clock {
      leaf wait-to-restore {
        type uint32;
      }
    }
    container esmc {
      container mode {
        leaf direction {
          tailf:cli-drop-node-name;
          type enumeration {
            enum "rx";
            enum "tx";
          }
        }
        leaf ql-disabled {
          type empty;
        }
      }
    }
    leaf enable {
      type boolean;
    }
    leaf speed {
      type enumeration {
        enum "10";
        enum "100";
        enum "1000";
        enum "10000";
        enum "25000";
        enum "auto";
        enum "nonegotiate";
        enum "2000";
        enum "5000";
        enum "40000";
        enum "50000";
        enum "100000";
        enum "200000";
        enum "400000";
      }
    }
    container speed-auto {
      tailf:cli-drop-node-name;
      container speed {
        leaf-list auto {
          tailf:cli-flat-list-syntax;
          type enumeration {
            enum "10";
            enum "100";
            enum "1000";
          }
        }
      }
    }
    leaf duplex {
      type enumeration {
        enum "auto" {
          tailf:code-name "duplex_auto";
        }
        enum "full" {
          tailf:code-name "duplex_full";
        }
        enum "half" {
          tailf:code-name "duplex_half";
        }
      }
    }
    leaf half-duplex {
      type empty;
    }
    leaf full-duplex {
      type empty;
    }
    leaf fec {
      type enumeration {
        enum "auto";
        enum "cl108";
        enum "cl74";
        enum "off";
      }
    }
    uses xconnect-if-grouping;
    container member {
      leaf vfi {
        type string;
      }
    }
    container pppoe {
      container enable {
        presence "true";
        leaf group {
          type union {
            type string;
            type enumeration {
              enum "global";
            }
          }
        }
      }
      leaf max-sessions {
        type uint16;
      }
      container intermediate-agent {
        leaf trust {
          type empty;
        }
      }
      container intermediate-agent-enable {
        tailf:cli-drop-node-name;
        leaf intermediate-agent {
          type empty;
        }
      }
    }
    uses pppoe-client-grouping;
    container vlan-id {
      list dot1q {
        key "id";
        leaf id {
          type uint16;
        }
      }
    }
    leaf secondary-admin-state {
      type enumeration {
        enum "auto-in-service";
        enum "maintenance";
        enum "normal";
        enum "in-service";
      }
    }
    container attach {
      leaf profile {
        type string;
      }
    }
    container service {
      list instance {
        tailf:cli-compact-syntax;
        tailf:cli-sequence-commands;
        key "id";
        leaf id {
          type uint32;
        }
        leaf trunk {
          tailf:cli-optional-in-sequence;
          tailf:cli-prefix-key;
          type empty;
        }
        leaf ethernet {
          tailf:cli-hide-in-submode;
          type empty;
        }
        leaf ethernet-evc-name {
          tailf:cli-drop-node-name;
          tailf:cli-hide-in-submode;
          type string;
        }
        leaf description {
          tailf:cli-break-sequence-commands;
          tailf:cli-multi-value;
          type string;
        }
        container encapsulation {
          choice encapsulation-choice {
            container dot1q {
              tailf:cli-compact-syntax;
              tailf:cli-sequence-commands {
                tailf:cli-reset-siblings;
              }
              uses if-srv-encapsulation-dot1q-grouping;
            }
            container dot1ad {
              tailf:cli-compact-syntax;
              tailf:cli-sequence-commands {
                tailf:cli-reset-siblings;
              }
              leaf-list id {
                tailf:cli-drop-node-name;
                tailf:cli-range-list-syntax;
                type uint16;
              }
              leaf-list dot1q {
                tailf:cli-range-list-syntax;
                type uint16;
              }
            }
            container untagged {
              tailf:cli-compact-syntax;
              tailf:cli-sequence-commands {
                tailf:cli-reset-siblings;
              }
              tailf:cli-delete-when-empty;
              presence "true";
              leaf comma {
                tailf:alt-name ",";
                type empty;
              }
              container dot1q {
                tailf:cli-flatten-container;
                tailf:cli-compact-syntax;
                tailf:cli-sequence-commands {
                  tailf:cli-reset-siblings;
                }
                uses if-srv-encapsulation-dot1q-grouping;
              }
            }
            container default {
              presence "true";
            }
          }
        }
        container rewrite {
          container ingress {
            container tag {
              tailf:cli-compact-syntax;
              tailf:cli-sequence-commands {
                tailf:cli-reset-siblings;
              }
              choice tag-choice {
                leaf pop {
                  type enumeration {
                    enum "1";
                    enum "2";
                  }
                }
                case push {
                  leaf push {
                    type enumeration {
                      enum "dot1ad";
                      enum "dot1q";
                    }
                  }
                  leaf vlan-id {
                    tailf:cli-drop-node-name;
                    type uint16;
                  }
                }
                case translate {
                  leaf translate {
                    type enumeration {
                      enum "1-to-1";
                      enum "1-to-2";
                      enum "2-to-1";
                      enum "2-to-2";
                    }
                  }
                  leaf dot1ad {
                    tailf:cli-optional-in-sequence;
                    type uint16;
                  }
                  leaf dot1q {
                    type uint16;
                  }
                  leaf second-dot1q {
                    tailf:cli-optional-in-sequence;
                    type uint16;
                  }
                  leaf vlan-type {
                    tailf:cli-optional-in-sequence;
                    type enumeration {
                      enum "0x88A8";
                      enum "0x9100";
                      enum "0x9200";
                    }
                  }
                }
              }
              leaf mode {
                tailf:cli-drop-node-name;
                type enumeration {
                  enum "symmetric";
                }
              }
            }
          }
        }
        container storm-control {
          container unicast {
            leaf cir {
              type string;
            }
          }
          container broadcast {
            leaf cir {
              type string;
            }
          }
          container multicast {
            leaf cir {
              type string;
            }
          }
        }
        container ip {
          list access-group {
            tailf:cli-suppress-mode;
            tailf:cli-delete-when-empty;
            tailf:cli-compact-syntax;
            tailf:cli-sequence-commands;
            key "direction";
            leaf direction {
              type enumeration {
                enum "in" {
                  tailf:code-name "access_group_direction_in";
                }
                enum "out" {
                  tailf:code-name "access_group_direction_out";
                }
              }
            }
            leaf access-list {
              tailf:cli-drop-node-name;
              tailf:cli-prefix-key;
              type exp-ip-acl-type;
            }
          }
        }
        leaf group {
          type uint16;
        }
        container errdisable {
          container recovery {
            container cause {
              leaf mac-security {
                type uint32;
              }
            }
          }
        }
        container snmp {
          container trap {
            leaf link-status {
              type empty;
            }
          }
          container ifindex {
            leaf persist {
              type empty;
            }
          }
        }
        leaf shutdown {
          type empty;
        }
        container mac {
          container security {
            tailf:cli-delete-when-empty;
            presence "true";
            list address {
              tailf:cli-suppress-mode;
              tailf:cli-delete-when-empty;
              key "operation mac-address";
              leaf operation {
                type enumeration {
                  enum "deny";
                  enum "permit";
                }
              }
              leaf mac-address {
                type string;
              }
            }
            container maximum {
              leaf addresses {
                type uint16;
              }
            }
            container aging {
              container time {
                tailf:cli-compact-syntax;
                tailf:cli-sequence-commands {
                  tailf:cli-reset-siblings;
                }
                leaf value {
                  tailf:cli-drop-node-name;
                  type uint16;
                }
                leaf inactivity {
                  type empty;
                }
              }
              leaf static {
                type empty;
              }
              leaf sticky {
                type empty;
              }
            }
            leaf violation {
              type enumeration {
                enum "protect";
                enum "restrict";
              }
            }
            container sticky {
              presence "true";
              list address {
                tailf:cli-suppress-mode;
                tailf:cli-delete-when-empty;
                key "mac-addr";
                leaf mac-addr {
                  type string;
                }
              }
            }
          }
          container static {
            list address {
              tailf:cli-suppress-mode;
              tailf:cli-delete-when-empty;
              key "mac-addr";
              leaf mac-addr {
                type string;
              }
            }
          }
          list access-group {
            tailf:cli-suppress-mode;
            tailf:cli-delete-when-empty;
            tailf:cli-compact-syntax;
            tailf:cli-sequence-commands;
            key "direction";
            leaf direction {
              type enumeration {
                enum "in";
                enum "out";
              }
            }
            leaf access-list {
              tailf:cli-drop-node-name;
              tailf:cli-prefix-key;
              type string;
            }
          }
        }
        container l2protocol {
          choice l2protocol-choice {
            leaf discard {
              type empty;
            }
            leaf peer {
              type empty;
            }
            leaf forward {
              type empty;
            }
            leaf tunnel {
              type empty;
            }
            list protocols {
              tailf:cli-drop-node-name;
              tailf:cli-suppress-mode;
              tailf:cli-delete-when-empty;
              tailf:cli-compact-syntax;
              tailf:cli-sequence-commands;
              key "protocol";
              leaf protocol {
                type l2protocol-type;
              }
              leaf option {
                tailf:cli-drop-node-name;
                tailf:cli-prefix-key;
                type enumeration {
                  enum "discard";
                  enum "peer";
                  enum "forward";
                  enum "tunnel";
                }
              }
            }
          }
        }
        container bridge-domain {
          tailf:cli-compact-syntax;
          tailf:cli-sequence-commands {
            tailf:cli-reset-siblings;
          }
          leaf from-encapsulation {
            tailf:cli-optional-in-sequence;
            type empty;
          }
          leaf bridge-id {
            tailf:cli-drop-node-name;
            type uint16;
          }
          leaf split-horizon {
            type empty;
          }
          leaf group {
            type uint8;
          }
        }
        container service-policy {
          list input {
            tailf:cli-suppress-mode;
            tailf:cli-delete-when-empty;
            key "name";
            leaf name {
              type string;
            }
          }
          list output {
            tailf:cli-suppress-mode;
            tailf:cli-delete-when-empty;
            key "name";
            leaf name {
              type string;
            }
          }
        }
        container xconnect {
          tailf:cli-add-mode;
          tailf:cli-compact-syntax;
          tailf:cli-sequence-commands;
          tailf:cli-delete-when-empty;
          presence "true";
          leaf address {
            tailf:cli-drop-node-name;
            tailf:cli-hide-in-submode;
            type inet:ipv4-address;
          }
          leaf vcid {
            tailf:cli-drop-node-name;
            tailf:cli-hide-in-submode;
            type uint32;
          }
          leaf encapsulation {
            tailf:cli-hide-in-submode;
            tailf:cli-optional-in-sequence;
            type enumeration {
              enum "mpls";
              enum "l2tpv3";
            }
          }
          leaf manual {
            tailf:cli-optional-in-sequence;
            tailf:cli-hide-in-submode;
            type empty;
          }
          leaf pw-class {
            tailf:cli-optional-in-sequence;
            tailf:cli-hide-in-submode;
            type string;
          }
          leaf sequencing {
            tailf:cli-hide-in-submode;
            type enumeration {
              enum "both";
              enum "receive";
              enum "transmit";
            }
          }
          leaf circuit-type {
            tailf:cli-optional-in-sequence;
            tailf:cli-hide-in-submode;
            type enumeration {
              enum "ethernet";
            }
          }
          container backup {
            tailf:cli-break-sequence-commands;
            container peer {
              tailf:cli-compact-syntax;
              tailf:cli-sequence-commands {
                tailf:cli-reset-siblings;
              }
              leaf peer-router-ip-addr {
                tailf:cli-drop-node-name;
                type inet:ipv4-address;
              }
              leaf vcid {
                tailf:cli-drop-node-name;
                type uint32;
              }
              leaf pw-class {
                tailf:cli-optional-in-sequence;
                type string;
              }
              leaf priority {
                type uint8;
              }
            }
            container delay {
              tailf:cli-compact-syntax;
              tailf:cli-sequence-commands;
              leaf enable-delay {
                tailf:cli-drop-node-name;
                type uint8;
              }
              leaf disable-delay {
                tailf:cli-drop-node-name;
                type union {
                  type uint8;
                  type enumeration {
                    enum "never";
                  }
                }
              }
            }
          }
          container mpls {
            container label {
              tailf:cli-compact-syntax;
              tailf:cli-sequence-commands;
              leaf local {
                tailf:cli-drop-node-name;
                type uint32;
              }
              leaf remote {
                tailf:cli-drop-node-name;
                type uint32;
              }
            }
            leaf control-word {
              type empty;
            }
          }
          leaf mtu {
            type uint16;
          }
          container remote {
            container link {
              container failure {
                leaf notification {
                  type boolean;
                }
              }
            }
          }
        }
        container cfm {
          container mip {
            leaf level {
              type uint8;
            }
          }
          container mep {
            tailf:cli-add-mode;
            tailf:cli-compact-syntax;
            tailf:cli-sequence-commands;
            tailf:cli-delete-when-empty;
            presence "true";
            leaf domain {
              tailf:cli-hide-in-submode;
              type string;
            }
            leaf mpid {
              tailf:cli-hide-in-submode;
              type uint16;
            }
            container continuity-check {
              tailf:cli-break-sequence-commands;
              container static {
                leaf rmep {
                  type empty;
                }
              }
            }
            container rmep {
              leaf mpid {
                type uint16;
              }
            }
            leaf cos {
              type uint8;
            }
            container alarm {
              leaf notification {
                type enumeration {
                  enum "none";
                  enum "xcon";
                  enum "error-xcon";
                  enum "remote-error-xcon";
                  enum "mac-remote-error-xcon";
                  enum "all";
                }
              }
            }
          }
        }
        container ethernet-if-srv {
          tailf:cli-drop-node-name;
          container ethernet {
            container lmi {
              container ce-vlan {
                leaf-list map {
                  tailf:cli-range-list-syntax;
                  type union {
                    type uint16;
                    type enumeration {
                      enum "default";
                      enum "untagged";
                    }
                  }
                }
              }
            }
            container loopback {
              container permit {
                leaf external {
                  type empty;
                }
                leaf internal {
                  type empty;
                }
              }
            }
          }
        }
      }
    }
    container cts {
      container manual {
        tailf:cli-add-mode;
        presence "true";
        container policy {
          container static {
            tailf:cli-compact-syntax;
            tailf:cli-sequence-commands {
              tailf:cli-reset-siblings;
            }
            leaf sgt {
              type uint16;
            }
            leaf trusted {
              type empty;
            }
          }
        }
        container propagate {
          leaf sgt {
            type boolean;
          }
        }
      }
      container role-based {
        leaf enforcement {
          type boolean;
        }
      }
    }
    container channel-group {
      tailf:cli-compact-syntax;
      tailf:cli-sequence-commands {
        tailf:cli-reset-siblings;
      }
      leaf number {
        tailf:cli-drop-node-name;
        type uint16;
      }
      leaf mode {
        type enumeration {
          enum "active";
          enum "auto";
          enum "desirable";
          enum "on";
          enum "passive";
        }
      }
      leaf non-silent {
        type empty;
      }
    }
    container soak {
      container link {
        leaf notification {
          type uint16;
        }
      }
    }
    container mvr {
      leaf type {
        type enumeration {
          enum "receiver";
          enum "source";
        }
      }
      list vlan {
        tailf:cli-suppress-mode;
        tailf:cli-delete-when-empty;
        key "id";
        leaf id {
          tailf:cli-suppress-range;
          type uint16;
        }
        container receiver {
          list vlan {
            tailf:cli-suppress-mode;
            tailf:cli-delete-when-empty;
            key "id";
            leaf id {
              tailf:cli-suppress-range;
              type uint16;
            }
          }
        }
        list group {
          tailf:cli-suppress-mode;
          tailf:cli-delete-when-empty;
          key "address";
          leaf address {
            tailf:cli-suppress-range;
            type inet:ipv4-address;
          }
          container receiver {
            list vlan {
              tailf:cli-suppress-mode;
              tailf:cli-delete-when-empty;
              key "id";
              leaf id {
                tailf:cli-suppress-range;
                type uint16;
              }
            }
          }
        }
      }
    }
    container mac-addr-filter {
      presence "true";
    }
  }

  grouping interface-ethernet-switch-grouping {
    uses interface-ethernet-grouping {
      refine "service/instance";
    }
  }

  grouping interface-common-macsec-grouping {
    uses interface-common-grouping {
      refine "mka";
      refine "macsec";
    }
  }

  grouping interface-ethernet-post-grouping {
    container fhrp {
      container delay {
        leaf minimum {
          type uint16;
        }
        leaf reload {
          type uint16;
        }
      }
    }
    container vrrp-conf {
      tailf:cli-drop-node-name;
      container vrrp {
        container delay {
          tailf:cli-compact-syntax;
          leaf minimum {
            type uint16;
          }
          leaf reload {
            type uint16;
          }
        }
      }
    }
    list vrrp {
      tailf:cli-suppress-mode;
      tailf:cli-delete-when-empty;
      key "id";
      leaf id {
        type uint8;
      }
      container authentication {
        choice auth {
          leaf word {
            tailf:cli-drop-node-name;
            type string;
          }
          container md5 {
            leaf key-chain {
              type string;
            }
            container key-string {
              tailf:cli-flatten-container;
              tailf:cli-compact-syntax;
              tailf:cli-sequence-commands;
              uses password-grouping {
                refine "secret";
              }
              leaf timeout {
                type uint16;
              }
            }
          }
          leaf text {
            type string;
          }
        }
      }
      uses interface-vrrp-grouping;
      container ip {
        leaf address {
          tailf:cli-drop-node-name;
          type inet:ipv4-address;
        }
        list secondary-address {
          tailf:cli-drop-node-name;
          tailf:cli-suppress-mode;
          tailf:cli-delete-when-empty;
          key "address";
          leaf address {
            type inet:ipv4-address;
          }
          leaf secondary {
            type empty;
          }
        }
      }
    }
    container vrrv3p-v3 {
      tailf:cli-drop-node-name;
      list vrrp {
        key "id address-family";
        leaf id {
          type uint8;
        }
        leaf address-family {
          tailf:cli-expose-key-name;
          type enumeration {
            enum "ipv4";
            enum "ipv6";
          }
        }
        uses interface-vrrp-grouping;
        container address {
          list primary-list {
            tailf:cli-drop-node-name;
            tailf:cli-suppress-mode;
            tailf:cli-delete-when-empty;
            key "address";
            leaf address {
              type union {
                type inet:ipv4-address;
                type inet:ipv6-address;
              }
            }
            leaf primary {
              type empty;
            }
          }
          list secondary-list {
            tailf:cli-drop-node-name;
            tailf:cli-suppress-mode;
            tailf:cli-delete-when-empty;
            key "address";
            leaf address {
              type union {
                type inet:ipv4-address;
                type ios:ipv6-prefix;
              }
            }
            leaf secondary {
              type empty;
            }
          }
        }
      }
    }
    container vrrs {
      list pathway {
        key "name";
        leaf name {
          type string;
        }
        uses description-grouping;
        list address {
          tailf:cli-suppress-mode;
          tailf:cli-delete-when-empty;
          key "address";
          leaf address {
            type union {
              type inet:ipv4-address;
              type inet:ipv6-address;
              type ios:ipv6-prefix;
            }
          }
        }
      }
    }
  }

  grouping interface-pointtopoint-grouping {
    container encapsulation-pointtopoint {
      tailf:cli-drop-node-name;
      container encapsulation {
        choice encapsulation-choice {
          container isl {
            tailf:cli-compact-syntax;
            tailf:cli-sequence-commands;
            leaf vlan-id {
              tailf:cli-drop-node-name;
              type uint16;
            }
          }
          container ppp {
            presence "true";
          }
          container slip {
            presence "true";
          }
          container frame-relay {
            tailf:cli-delete-when-empty;
            presence "true";
            leaf IETF {
              type empty;
            }
            leaf MFR {
              tailf:cli-allow-join-with-value;
              type uint32;
            }
          }
          container hdlc {
            tailf:cli-delete-when-empty;
            presence "true";
          }
        }
      }
    }
    container frame-relay {
      container multilink {
        leaf output-threshold {
          type uint32;
        }
        container bid {
          leaf bid {
            tailf:cli-drop-node-name;
            type string;
          }
        }
      }
      leaf class {
        type string;
      }
      container interface-dlci {
        tailf:cli-add-mode;
        tailf:cli-compact-syntax;
        tailf:cli-sequence-commands {
          tailf:cli-reset-siblings;
        }
        tailf:cli-delete-when-empty;
        presence "true";
        leaf dlci {
          tailf:cli-drop-node-name;
          tailf:cli-hide-in-submode;
          type uint16;
        }
        leaf encapsulation {
          tailf:cli-drop-node-name;
          tailf:cli-hide-in-submode;
          type enumeration {
            enum "cisco";
            enum "IETF";
            enum "ppp";
            enum "switched";
          }
        }
        leaf class {
          type string;
        }
      }
      leaf lmi-type {
        type enumeration {
          enum "ansi";
          enum "cisco";
          enum "q933a";
        }
      }
      leaf intf-type {
        type enumeration {
          enum "dce";
          enum "dte";
          enum "nni";
        }
      }
      list route {
        tailf:cli-suppress-mode;
        tailf:cli-delete-when-empty;
        tailf:cli-compact-syntax;
        tailf:cli-sequence-commands {
          tailf:cli-reset-siblings;
        }
        key "in-dlci";
        leaf in-dlci {
          type uint16;
        }
        leaf interface {
          type string;
        }
        leaf out-dlci {
          tailf:cli-drop-node-name;
          type uint16;
        }
      }
    }
    container dialer {
      container in-band {
        tailf:cli-delete-when-empty;
        presence "true";
        leaf parity {
          tailf:cli-drop-node-name;
          type enumeration {
            enum "no-parity";
            enum "odd-parity";
          }
        }
      }
      leaf remote-name {
        type string;
      }
      container idle-timeout {
        tailf:cli-compact-syntax;
        tailf:cli-sequence-commands {
          tailf:cli-reset-siblings;
        }
        leaf seconds {
          tailf:cli-drop-node-name;
          type uint32;
        }
        leaf direction {
          tailf:cli-drop-node-name;
          type enumeration {
            enum "either";
            enum "inbound";
          }
        }
      }
      leaf enable-timeout {
        type uint32;
      }
      leaf string {
        type string;
      }
      leaf hold-queue {
        type uint8;
      }
      container persistent {
        presence "true";
      }
      leaf pool {
        type uint8;
      }
      list pool-member {
        tailf:cli-suppress-mode;
        tailf:cli-delete-when-empty;
        tailf:cli-compact-syntax;
        tailf:cli-sequence-commands {
          tailf:cli-reset-siblings;
        }
        key "id";
        leaf id {
          type uint8;
        }
        leaf priority {
          tailf:cli-optional-in-sequence;
          type uint8;
        }
        leaf min-link {
          tailf:cli-optional-in-sequence;
          type uint8;
        }
        leaf max-link {
          type uint8;
        }
      }
      container map {
        list ip {
          tailf:cli-suppress-mode;
          tailf:cli-delete-when-empty;
          tailf:cli-compact-syntax;
          key "address";
          leaf address {
            type inet:ipv4-address;
          }
          leaf name {
            type string;
          }
          leaf class {
            type string;
          }
        }
      }
      leaf watch-group {
        type uint16;
      }
      container load-threshold {
        tailf:cli-compact-syntax;
        tailf:cli-sequence-commands {
          tailf:cli-reset-siblings;
        }
        leaf load {
          tailf:cli-drop-node-name;
          type uint8;
        }
        leaf direction {
          tailf:cli-drop-node-name;
          type enumeration {
            enum "inbound";
            enum "outbound";
            enum "either";
          }
        }
      }
    }
    leaf dialer-group {
      type uint8;
    }
    container ppp {
      container mtu {
        leaf adaptive {
          type empty;
        }
        container pppoe {
          leaf unlimited {
            type empty;
          }
        }
      }
      container pfc {
        leaf local {
          type enumeration {
            enum "forbid";
            enum "request";
          }
        }
      }
      container acfc {
        leaf local {
          type enumeration {
            enum "forbid";
            enum "request";
          }
        }
        leaf remote {
          type enumeration {
            enum "apply";
            enum "ignore";
            enum "reject";
          }
        }
      }
      leaf accounting {
        type union {
          type string;
          type enumeration {
            enum "default";
          }
        }
      }
      container encrypt {
        container mppe {
          tailf:cli-compact-syntax;
          tailf:cli-sequence-commands {
            tailf:cli-reset-siblings;
          }
          leaf bits {
            tailf:cli-drop-node-name;
            type enumeration {
              enum "auto";
              enum "40";
              enum "128";
            }
          }
          leaf mode {
            tailf:cli-drop-node-name;
            type enumeration {
              enum "passive";
              enum "required";
              enum "stateful";
            }
          }
        }
      }
      container authentication {
        tailf:cli-compact-syntax;
        tailf:cli-sequence-commands {
          tailf:cli-reset-all-siblings;
        }
        leaf method {
          tailf:cli-drop-node-name;
          type ppp-auth-method;
        }
        leaf method2 {
          tailf:cli-drop-node-name;
          tailf:cli-optional-in-sequence;
          type ppp-auth-method;
        }
        leaf method3 {
          tailf:cli-drop-node-name;
          tailf:cli-optional-in-sequence;
          type ppp-auth-method;
        }
        leaf callin {
          tailf:cli-break-sequence-commands;
          type empty;
        }
        leaf callout {
          type empty;
        }
        leaf callback {
          type empty;
        }
        leaf optional {
          type empty;
        }
        leaf list-name {
          tailf:cli-drop-node-name;
          type union {
            type string;
            type enumeration {
              enum "default";
            }
          }
        }
        leaf one-time {
          type empty;
        }
      }
      leaf authorization {
        type union {
          type string;
          type enumeration {
            enum "default";
          }
        }
      }
      container pap {
        container sent-username {
          tailf:cli-compact-syntax;
          tailf:cli-sequence-commands {
            tailf:cli-reset-siblings;
          }
          leaf username {
            tailf:cli-drop-node-name;
            type string;
          }
          container password {
            tailf:cli-flatten-container;
            tailf:cli-compact-syntax;
            tailf:cli-sequence-commands;
            uses password-grouping {
              refine "secret";
            }
          }
        }
        container refuse {
          presence "true";
        }
      }
      container chap {
        leaf hostname {
          type string;
        }
        container password {
          tailf:cli-compact-syntax;
          tailf:cli-sequence-commands;
          uses password-grouping {
            refine "secret";
          }
        }
        container refuse {
          presence "true";
        }
      }
      container ipcp {
        container address {
          tailf:cli-compact-syntax;
          leaf accept {
            type empty;
          }
          leaf proxy {
            type inet:ipv4-address;
          }
          leaf request {
            type enumeration {
              enum "ignore";
            }
          }
          leaf required {
            type empty;
          }
          leaf unique {
            type empty;
          }
        }
        container dns {
          tailf:cli-compact-syntax;
          tailf:cli-sequence-commands;
          choice dns-choice {
            case dns-address {
              leaf primary {
                tailf:cli-drop-node-name;
                type inet:ipv4-address;
              }
              leaf secondary {
                tailf:cli-drop-node-name;
                type inet:ipv4-address;
              }
            }
            container request {
              tailf:cli-delete-when-empty;
              presence "true";
              leaf accept {
                type empty;
              }
            }
          }
        }
      }
      container multilink {
        presence "true";
        leaf interleave {
          type empty;
        }
        container links {
          container maximum {
            leaf maximum-value {
              tailf:cli-drop-node-name;
              type uint8;
            }
          }
          container minimum {
            tailf:cli-compact-syntax;
            tailf:cli-sequence-commands {
              tailf:cli-reset-siblings;
            }
            leaf minimum-value {
              tailf:cli-drop-node-name;
              type uint8;
            }
            leaf mandatory {
              type empty;
            }
          }
        }
        leaf group {
          type uint32;
        }
        leaf fragment-delay {
          type uint16;
        }
        container fragment {
          leaf disable {
            type empty;
          }
          leaf size {
            type uint16;
          }
          container delay {
            tailf:cli-compact-syntax;
            tailf:cli-sequence-commands {
              tailf:cli-reset-siblings;
            }
            leaf delay-value {
              tailf:cli-drop-node-name;
              type uint16;
            }
            leaf additional-delay-value {
              tailf:cli-drop-node-name;
              type uint16;
            }
          }
        }
        leaf fragmentation {
          type boolean;
        }
        container queue {
          container depth {
            leaf fifo {
              type uint8;
            }
            leaf qos {
              type uint8;
            }
          }
        }
        container min-links {
          tailf:cli-compact-syntax;
          tailf:cli-sequence-commands {
            tailf:cli-reset-siblings;
          }
          leaf links {
            tailf:cli-drop-node-name;
            type uint8;
          }
          leaf mandatory {
            type empty;
          }
        }
      }
      container timeout {
        leaf retry {
          type uint8;
        }
        leaf ncp {
          type uint16;
        }
      }
    }
    container pseudowire {
      tailf:cli-add-mode;
      tailf:cli-compact-syntax;
      tailf:cli-sequence-commands;
      tailf:cli-delete-when-empty;
      presence "true";
      leaf address {
        tailf:cli-drop-node-name;
        tailf:cli-hide-in-submode;
        type inet:ipv4-address;
      }
      leaf vcid {
        tailf:cli-drop-node-name;
        tailf:cli-hide-in-submode;
        type uint32;
      }
      leaf encapsulation {
        tailf:cli-hide-in-submode;
        tailf:cli-optional-in-sequence;
        type enumeration {
          enum "mpls";
          enum "l2tpv2";
          enum "l2tpv3";
        }
      }
      leaf pw-class {
        tailf:cli-hide-in-submode;
        type string;
      }
    }
    container multilink {
      leaf max-links {
        type uint8;
      }
      container min-links {
        tailf:cli-compact-syntax;
        tailf:cli-sequence-commands {
          tailf:cli-reset-siblings;
        }
        leaf links {
          tailf:cli-drop-node-name;
          type uint8;
        }
        leaf mandatory {
          type empty;
        }
      }
      leaf max-fragments {
        type uint8;
      }
    }
    leaf multilink-group {
      type uint32;
    }
    leaf physical-layer {
      type enumeration {
        enum "async";
        enum "sync";
      }
    }
    container async {
      container mode {
        leaf dedicated {
          type empty;
        }
        leaf interactive {
          type empty;
        }
      }
    }
    container pulse-time {
      choice pulse-time-choice {
        leaf seconds {
          tailf:cli-drop-node-name;
          type uint8;
        }
        leaf msec {
          type uint16;
        }
      }
    }
    container serial {
      container restart-delay {
        tailf:cli-compact-syntax;
        tailf:cli-sequence-commands {
          tailf:cli-reset-siblings;
        }
        leaf seconds {
          tailf:cli-drop-node-name;
          type uint16;
        }
        leaf milliseconds {
          tailf:cli-drop-node-name;
          type uint16;
        }
      }
    }
    leaf dce-terminal-timing-enable {
      type boolean;
    }
  }

  grouping interface-switch-grouping {
    container switchport {
      presence "true";
      container mode {
        choice mode-choice {
          container access {
            presence "true";
          }
          container dot1q-tunnel {
            presence "true";
          }
          leaf dynamic {
            type enumeration {
              enum "auto";
              enum "desirable";
            }
          }
          container trunk {
            presence "true";
          }
          container private-vlan {
            choice private-vlan-choice {
              leaf host {
                type empty;
              }
              leaf promiscuous {
                type empty;
              }
              container trunk {
                tailf:cli-delete-when-empty;
                presence "true";
                leaf mode {
                  tailf:cli-drop-node-name;
                  type enumeration {
                    enum "promiscuous";
                    enum "secondary";
                  }
                }
              }
            }
          }
        }
      }
      container trunk {
        leaf encapsulation {
          type enumeration {
            enum "dot1q";
            enum "isl";
            enum "negotiate";
          }
        }
        container native {
          leaf vlan {
            type union {
              type enumeration {
                enum "tag";
              }
              type uint16;
            }
          }
        }
        container allowed {
          container vlan {
            choice vlan-choice {
              container vlans-string {
                tailf:cli-drop-node-name;
                leaf vlans {
                  tailf:cli-drop-node-name;
                  type string;
                }
              }
              leaf-list vlans {
                tailf:cli-drop-node-name;
                tailf:cli-range-list-syntax;
                type uint16;
              }
              leaf none {
                type empty;
              }
            }
          }
        }
        container pruning {
          container vlan {
            choice vlan-choice {
              leaf-list vlans {
                tailf:cli-drop-node-name;
                tailf:cli-range-list-syntax;
                type uint16;
              }
              leaf none {
                type empty;
              }
            }
          }
        }
      }
      container autostate {
        leaf exclude {
          type empty;
        }
      }
      container capture-enable {
        tailf:cli-drop-node-name;
        leaf capture {
          type empty;
        }
      }
      container capture {
        container allowed {
          container vlan {
            leaf-list vlans {
              tailf:cli-range-list-syntax;
              tailf:cli-drop-node-name;
              type uint16;
            }
          }
        }
      }
      container private-vlan {
        container trunk {
          container native {
            leaf vlan {
              type uint16;
            }
            container vlan-tag {
              tailf:cli-drop-node-name;
              container vlan {
                leaf tag {
                  type boolean;
                }
              }
            }
          }
          container allowed {
            container vlan {
              choice vlan-choice {
                leaf-list vlans {
                  tailf:cli-range-list-syntax;
                  tailf:cli-drop-node-name;
                  type uint16;
                }
                leaf none {
                  type empty;
                }
              }
            }
          }
        }
        container association {
          list trunk {
            tailf:cli-suppress-mode;
            tailf:cli-delete-when-empty;
            key "primary-vlan-id";
            leaf primary-vlan-id {
              type uint16;
            }
            leaf secondary-vlan-id {
              tailf:cli-drop-node-name;
              type uint16;
            }
          }
        }
        container host-association {
          tailf:cli-compact-syntax;
          tailf:cli-sequence-commands {
            tailf:cli-reset-siblings;
          }
          leaf primary-vlan-id {
            tailf:cli-drop-node-name;
            type uint16;
          }
          leaf secondary-vlan-id {
            tailf:cli-drop-node-name;
            type uint16;
          }
        }
        container mapping-trunk {
          tailf:cli-drop-node-name;
          container mapping {
            list trunk {
              tailf:cli-suppress-mode;
              tailf:cli-delete-when-empty;
              key "primary-vlan-id";
              leaf primary-vlan-id {
                type uint16;
              }
              leaf secondary-vlan-id {
                tailf:cli-drop-node-name;
                type string;
              }
            }
          }
        }
        container mapping {
          tailf:cli-compact-syntax;
          tailf:cli-sequence-commands {
            tailf:cli-reset-siblings;
          }
          leaf primary-vlan-id {
            tailf:cli-drop-node-name;
            type uint16;
          }
          leaf secondary-vlan-id {
            tailf:cli-drop-node-name;
            type string;
          }
        }
      }
      container vlan {
        container mapping-enable {
          tailf:cli-drop-node-name;
          container mapping {
            leaf enable {
              type empty;
            }
          }
        }
        list mapping {
          tailf:cli-suppress-mode;
          tailf:cli-delete-when-empty;
          tailf:cli-compact-syntax;
          tailf:cli-sequence-commands {
            tailf:cli-reset-siblings;
          }
          key "id";
          leaf id {
            type union {
              type uint16;
              type enumeration {
                enum "default";
              }
            }
          }
          choice translated-choice {
            leaf dot1q-tunnel {
              type uint16;
            }
            leaf drop {
              type empty;
            }
            leaf translated-id {
              tailf:cli-drop-node-name;
              type uint16;
            }
          }
        }
        container mapping-conf {
          tailf:cli-drop-node-name;
          container mapping {
            list dot1q-tunnel {
              tailf:cli-suppress-mode;
              tailf:cli-delete-when-empty;
              key "outer inner";
              leaf outer {
                type uint16;
              }
              leaf inner {
                type union {
                  type uint16;
                  type enumeration {
                    enum "drop";
                  }
                }
              }
              leaf translated {
                tailf:cli-drop-node-name;
                type uint16;
              }
            }
          }
        }
      }
      container access {
        leaf vlan {
          type union {
            type uint16;
            type enumeration {
              enum "dynamic";
            }
          }
        }
      }
      container backup {
        list interface {
          tailf:cli-suppress-mode;
          key "name";
          leaf name {
            type string;
          }
          container preemption {
            leaf mode {
              type enumeration {
                enum "bandwidth";
                enum "forced";
                enum "off";
              }
            }
            leaf delay {
              type uint16;
            }
          }
        }
      }
      leaf nonegotiate {
        type empty;
      }
      container block {
        leaf multicast {
          type empty;
        }
        leaf unicast {
          type empty;
        }
      }
      container port-security-enable {
        tailf:cli-drop-node-name;
        leaf port-security {
          type empty;
        }
      }
      container port-security {
        container aging {
          leaf time {
            type uint16;
          }
          leaf type {
            type enumeration {
              enum "absolute";
              enum "inactivity";
            }
          }
        }
        container mac-address-sticky {
          tailf:cli-drop-node-name;
          container mac-address {
            leaf sticky {
              type empty;
            }
          }
        }
        list mac-address {
          tailf:cli-suppress-mode;
          tailf:cli-delete-when-empty;
          tailf:cli-compact-syntax;
          tailf:cli-sequence-commands {
            tailf:cli-reset-siblings;
          }
          key "hw-address";
          leaf sticky {
            tailf:cli-optional-in-sequence;
            tailf:cli-prefix-key;
            type empty;
          }
          leaf hw-address {
            type mac-address-type;
          }
          leaf vlan {
            type union {
              type uint16;
              type enumeration {
                enum "access";
              }
            }
          }
        }
        leaf maximum {
          type uint16;
        }
        container maximum-vlan {
          tailf:cli-drop-node-name;
          tailf:cli-compact-syntax;
          tailf:cli-sequence-commands {
            tailf:cli-reset-siblings;
          }
          leaf maximum {
            type uint16;
          }
          leaf vlan {
            type empty;
          }
        }
        container maximum-vlan-list {
          tailf:cli-drop-node-name;
          list maximum {
            tailf:cli-suppress-mode;
            tailf:cli-delete-when-empty;
            tailf:cli-compact-syntax;
            tailf:cli-sequence-commands {
              tailf:cli-reset-siblings;
            }
            key "max-addresses vlan";
            leaf max-addresses {
              type uint16;
            }
            leaf vlan {
              tailf:cli-expose-key-name;
              type string;
            }
          }
        }
        leaf violation {
          type enumeration {
            enum "protect";
            enum "restrict";
            enum "shutdown";
          }
        }
      }
      container priority {
        container extend {
          choice trust-choice {
            leaf trust {
              type empty;
            }
            leaf cos {
              type uint8;
            }
          }
        }
      }
      leaf protected {
        type empty;
      }
      container voice {
        leaf vlan {
          type union {
            type enumeration {
              enum "dot1p";
              enum "none";
              enum "untagged";
            }
            type uint16;
          }
        }
        container detect {
          container cisco-phone {
            presence "true";
            leaf full-duplex {
              type empty;
            }
          }
        }
      }
      leaf host {
        type empty;
      }
    }
    container switch {
      container virtual {
        leaf link {
          type uint8;
        }
      }
    }
    container l2protocol-tunnel {
      tailf:cli-delete-when-empty;
      presence "true";
      leaf cdp {
        type empty;
      }
      container drop-threshold {
        leaf packet-rate {
          tailf:cli-drop-node-name;
          type uint16;
        }
        leaf cdp {
          type uint16;
        }
        leaf stp {
          type uint16;
        }
        leaf vtp {
          type uint16;
        }
      }
      container shutdown-threshold {
        leaf packet-rate {
          tailf:cli-drop-node-name;
          type uint16;
        }
        leaf cdp {
          type uint16;
        }
        leaf lldp {
          type uint16;
        }
        leaf stp {
          type uint16;
        }
        leaf vtp {
          type uint16;
        }
        container point-to-point {
          leaf pagp {
            type uint16;
          }
          leaf lacp {
            type uint16;
          }
          leaf udld {
            type uint16;
          }
        }
      }
      leaf stp {
        type empty;
      }
      leaf vtp {
        type empty;
      }
      leaf lldp {
        type empty;
      }
      container point-to-point {
        leaf lacp {
          type empty;
        }
        leaf pagp {
          type empty;
        }
        leaf udld {
          type empty;
        }
      }
    }
    choice interface-device-tracking-choice {
      container device-tracking {
        leaf attach-policy {
          type string;
        }
      }
      container device-tracking-enable {
        tailf:cli-drop-node-name;
        leaf device-tracking {
          type empty;
        }
      }
    }
  }

  grouping crypto-pki-token-grouping {
    container removal {
      leaf timeout {
        type uint16;
      }
    }
    leaf max-retries {
      type uint8;
    }
  }

  grouping router-bgp-max-path-grouping {
    container paths {
      tailf:cli-drop-node-name;
      tailf:cli-compact-syntax;
      tailf:cli-sequence-commands {
        tailf:cli-reset-siblings;
      }
      leaf number-of-paths {
        tailf:cli-drop-node-name;
        type uint16;
      }
      leaf import {
        type uint16;
      }
    }
  }

  grouping router-bgp-redistribute-isis-grouping {
    choice osi-ip-choice {
      leaf ip {
        type empty;
      }
      leaf clns {
        type empty;
      }
    }
    leaf level {
      tailf:cli-drop-node-name;
      type enumeration {
        enum "level-1";
        enum "level-2";
        enum "level-1-2";
      }
    }
  }

  grouping router-bgp-redistribute-grouping {
    leaf metric {
      type uint32;
    }
    leaf subnets {
      type empty;
    }
    leaf route-map {
      type string;
    }
    leaf include-connected {
      type empty;
    }
  }

  grouping router-bgp-redistribute-ospf-grouping {
    leaf metric {
      type uint32;
    }
    leaf subnets {
      type empty;
    }
    leaf route-map {
      type string;
    }
    leaf include-connected {
      type empty;
    }
    leaf match {
      type empty;
    }
    leaf internal {
      type empty;
    }
    container external-1 {
      tailf:cli-drop-node-name;
      tailf:cli-flatten-container;
      tailf:cli-compact-syntax;
      leaf external {
        type enumeration {
          enum "1";
        }
      }
    }
    container external-2 {
      tailf:cli-drop-node-name;
      tailf:cli-flatten-container;
      tailf:cli-compact-syntax;
      leaf external {
        type enumeration {
          enum "2";
        }
      }
    }
    container nssa-external-1 {
      tailf:cli-drop-node-name;
      tailf:cli-flatten-container;
      tailf:cli-compact-syntax;
      leaf nssa-external {
        type enumeration {
          enum "1";
        }
      }
    }
    container nssa-external-2 {
      tailf:cli-drop-node-name;
      tailf:cli-flatten-container;
      tailf:cli-compact-syntax;
      leaf nssa-external {
        type enumeration {
          enum "2";
        }
      }
    }
  }

  grouping router-bgp-redistribute-ospfv3-grouping {
    leaf metric {
      type uint32;
    }
    leaf route-map {
      type string;
    }
    leaf match {
      type empty;
    }
    leaf internal {
      type empty;
    }
    container external-1 {
      tailf:cli-drop-node-name;
      tailf:cli-flatten-container;
      tailf:cli-compact-syntax;
      leaf external {
        type enumeration {
          enum "1";
        }
      }
    }
    container external-2 {
      tailf:cli-drop-node-name;
      tailf:cli-flatten-container;
      tailf:cli-compact-syntax;
      leaf external {
        type enumeration {
          enum "2";
        }
      }
    }
    container nssa-external-1 {
      tailf:cli-drop-node-name;
      tailf:cli-flatten-container;
      tailf:cli-compact-syntax;
      leaf nssa-external {
        type enumeration {
          enum "1";
        }
      }
    }
    container nssa-external-2 {
      tailf:cli-drop-node-name;
      tailf:cli-flatten-container;
      tailf:cli-compact-syntax;
      leaf nssa-external {
        type enumeration {
          enum "2";
        }
      }
    }
  }

  grouping route-map-metric-grouping {
    leaf route-map {
      type string;
    }
    leaf metric {
      type uint32;
    }
  }

  grouping router-bgp-neighbor-distribute-list-grouping {
    list distribute-list {
      tailf:cli-suppress-mode;
      tailf:cli-delete-when-empty;
      tailf:cli-compact-syntax;
      tailf:cli-sequence-commands;
      key "direction";
      leaf direction {
        type enumeration {
          enum "in";
          enum "out";
        }
      }
      uses distribute-list-content-grouping;
    }
    container distribute-list-interface {
      tailf:cli-drop-node-name;
      list distribute-list {
        tailf:cli-suppress-mode;
        tailf:cli-delete-when-empty;
        tailf:cli-compact-syntax;
        tailf:cli-sequence-commands;
        key "direction interface";
        leaf direction {
          type enumeration {
            enum "in";
            enum "out";
          }
        }
        leaf interface {
          type string;
        }
        uses distribute-list-content-grouping;
      }
    }
  }

  grouping router-bgp-peer-policy-grouping {
    container additional-paths {
      tailf:cli-compact-syntax;
      tailf:cli-sequence-commands {
        tailf:cli-reset-siblings;
      }
      leaf send {
        tailf:cli-optional-in-sequence;
        type empty;
      }
      leaf receive {
        type empty;
      }
    }
    container advertise {
      container additional-paths {
        tailf:cli-compact-syntax;
        leaf all {
          type empty;
        }
        leaf group-best {
          type empty;
        }
        leaf best {
          type uint8;
        }
      }
    }
    leaf advertisement-interval {
      type uint16;
    }
    container next-hop-self {
      tailf:cli-delete-when-empty;
      presence "true";
      leaf all {
        type empty;
      }
    }
    container aigp {
      tailf:cli-delete-when-empty;
      presence "true";
    }
    container send-community {
      tailf:cli-delete-when-empty;
      presence "true";
      leaf send-community-where {
        tailf:cli-drop-node-name;
        type enumeration {
          enum "both";
          enum "extended";
          enum "standard" {
            tailf:code-name "send_standard";
          }
        }
      }
    }
    container send-label {
      tailf:cli-delete-when-empty;
      presence "true";
      leaf explicit-null {
        type empty;
      }
    }
    container maximum-prefix {
      tailf:cli-compact-syntax;
      tailf:cli-sequence-commands {
        tailf:cli-reset-all-siblings;
      }
      leaf max-prefix-no {
        tailf:cli-drop-node-name;
        type uint32;
      }
      leaf threshold {
        tailf:cli-drop-node-name;
        tailf:cli-break-sequence-commands;
        type uint8;
      }
      leaf restart {
        type uint16;
      }
      leaf warning-only {
        type empty;
      }
    }
    container allowas-in {
      tailf:cli-delete-when-empty;
      presence "true";
      leaf as-no {
        tailf:cli-drop-node-name;
        type uint8;
      }
    }
    container as-override {
      tailf:cli-delete-when-empty;
      presence "true";
      leaf disable {
        type empty;
      }
    }
    container default-originate {
      tailf:cli-delete-when-empty;
      presence "true";
      leaf route-map {
        type string;
      }
    }
    list prefix-list {
      tailf:cli-suppress-mode;
      tailf:cli-delete-when-empty;
      tailf:cli-compact-syntax;
      tailf:cli-sequence-commands;
      key "direction";
      leaf direction {
        type enumeration {
          enum "in";
          enum "out";
        }
      }
      leaf prefix-list-name {
        tailf:cli-drop-node-name;
        tailf:cli-prefix-key;
        type string;
      }
    }
    leaf route-reflector-client {
      type empty;
    }
    container slow-peer {
      container split-update-group {
        leaf static {
          type empty;
        }
        leaf dynamic {
          type empty;
        }
      }
    }
    leaf soft-reconfiguration {
      type enumeration {
        enum "inbound";
      }
    }
    container remove-private-as {
      tailf:cli-compact-syntax;
      tailf:cli-sequence-commands {
        tailf:cli-reset-siblings;
      }
      presence "true";
      leaf all {
        type empty;
      }
      leaf replace-as {
        type empty;
      }
    }
    list route-map {
      tailf:cli-suppress-mode;
      tailf:cli-delete-when-empty;
      key "direction";
      leaf direction {
        type enumeration {
          enum "in";
          enum "out";
        }
      }
      leaf route-map-name {
        tailf:cli-drop-node-name;
        tailf:cli-prefix-key;
        type string;
      }
    }
    list advertise-map {
      tailf:cli-suppress-mode;
      tailf:cli-delete-when-empty;
      key "name";
      leaf name {
        type string;
      }
      list exist-map {
        tailf:cli-suppress-mode;
        tailf:cli-delete-when-empty;
        key "name";
        leaf name {
          type string;
        }
      }
    }
    leaf internal-vpn-client {
      type empty;
    }
  }

  grouping router-bgp-peer-session-grouping {
    container local-as {
      tailf:cli-compact-syntax;
      tailf:cli-sequence-commands {
        tailf:cli-reset-siblings;
      }
      tailf:cli-delete-when-empty;
      presence "true";
      leaf as-no {
        tailf:cli-drop-node-name;
        type bgp-as-no-type;
      }
      leaf no-prepend {
        type empty;
      }
      leaf replace-as {
        type empty;
      }
      leaf dual-as {
        type empty;
      }
    }
    container password {
      tailf:cli-compact-syntax;
      tailf:cli-sequence-commands {
        tailf:cli-reset-siblings;
      }
      leaf enctype {
        tailf:cli-drop-node-name;
        tailf:cli-optional-in-sequence;
        type uint8;
      }
      leaf text {
        tailf:cli-drop-node-name;
        tailf:cli-multi-value;
        type string;
      }
    }
    leaf allow-policy {
      type empty;
    }
    container ttl-security {
      leaf hops {
        type uint8;
      }
    }
    container timers {
      tailf:cli-compact-syntax;
      tailf:cli-sequence-commands {
        tailf:cli-reset-siblings;
      }
      leaf keepalive-interval {
        tailf:cli-drop-node-name;
        type uint16;
      }
      leaf holdtime {
        tailf:cli-drop-node-name;
        type uint16;
      }
      leaf minimum-neighbor-hold {
        tailf:cli-drop-node-name;
        type uint16;
      }
    }
    container fall-over {
      tailf:cli-delete-when-empty;
      presence "true";
      leaf route-map {
        type string;
      }
    }
    container fall-over-bfd {
      tailf:cli-drop-node-name;
      container fall-over {
        tailf:cli-compact-syntax;
        tailf:cli-sequence-commands {
          tailf:cli-reset-siblings;
        }
        leaf bfd {
          type empty;
        }
        choice hop-choice {
          leaf multi-hop {
            tailf:cli-optional-in-sequence;
            type empty;
          }
          leaf single-hop {
            tailf:cli-optional-in-sequence;
            type empty;
          }
        }
        leaf check-control-plane-failure {
          tailf:cli-optional-in-sequence;
          type empty;
        }
        leaf strict-mode {
          type empty;
        }
      }
    }
    container ebgp-multihop {
      tailf:cli-delete-when-empty;
      presence "true";
      leaf max-hop {
        tailf:cli-drop-node-name;
        type uint8;
      }
    }
    container ao {
      tailf:cli-compact-syntax;
      tailf:cli-sequence-commands {
        tailf:cli-reset-siblings;
      }
      leaf keychain-name {
        tailf:cli-drop-node-name;
        type string;
      }
      leaf include-tcp-options {
        tailf:cli-optional-in-sequence;
        type empty;
      }
      leaf accept-ao-mismatch-connections {
        type empty;
      }
    }
    container bmp-activate {
      leaf all {
        type empty;
      }
      leaf server {
        type uint8;
      }
    }
    leaf cluster-id {
      type union {
        type uint32;
        type inet:ipv4-address;
      }
    }
    container update-source {
      uses interface-nodiff-name-grouping;
    }
    container path-attribute {
      list discard {
        tailf:cli-suppress-mode;
        tailf:cli-delete-when-empty;
        key "id";
        leaf id {
          type uint8;
        }
        leaf in {
          type empty;
        }
      }
    }
    leaf version {
      type uint8;
    }
    container transport {
      leaf connection-mode {
        type enumeration {
          enum "active";
          enum "passive";
        }
      }
      container path-mtu-discovery {
        tailf:cli-delete-when-empty;
        presence "true";
        leaf disable {
          type empty;
        }
      }
    }
    leaf disable-connected-check {
      type empty;
    }
  }

  grouping router-bgp-neighbor-grouping {
    leaf activate {
      type empty;
    }
    container inherit {
      leaf peer-session {
        type string;
      }
      leaf peer-policy {
        type string;
      }
    }
    uses router-bgp-peer-session-grouping;
    uses router-bgp-peer-policy-grouping;
    leaf soo {
      type string;
    }
    container capability {
      container orf {
        leaf-list prefix-list {
          tailf:cli-flat-list-syntax;
          type enumeration {
            enum "both";
            enum "receive";
            enum "send";
          }
        }
      }
    }
    leaf description {
      tailf:cli-multi-value;
      type string;
    }
    uses router-bgp-neighbor-distribute-list-grouping;
    leaf dmzlink-bw {
      type empty;
    }
    leaf encap {
      type enumeration {
        enum "mpls";
        enum "vxlan";
      }
    }
    list filter-list {
      tailf:cli-suppress-mode;
      tailf:cli-delete-when-empty;
      tailf:cli-compact-syntax;
      tailf:cli-sequence-commands;
      key "direction";
      leaf direction {
        type enumeration {
          enum "in";
          enum "out";
        }
      }
      leaf as-path-list {
        tailf:cli-drop-node-name;
        tailf:cli-prefix-key;
        type string;
      }
    }
    container next-hop-self-arg {
      tailf:cli-drop-node-name;
      leaf next-hop-self {
        type string;
      }
    }
    leaf next-hop-unchanged {
      type empty;
    }
    container shutdown {
      tailf:cli-compact-syntax;
      tailf:cli-sequence-commands;
      tailf:cli-delete-when-empty;
      presence "true";
      leaf graceful {
        type uint16;
      }
      leaf local-preference {
        type uint32;
      }
    }
    container translate-update {
      container multicast {
        tailf:cli-delete-when-empty;
        presence "true";
        leaf unicast {
          type empty;
        }
      }
    }
    leaf unsuppress-map {
      type string;
    }
    leaf weight {
      type uint16;
    }
    container ha-mode {
      container graceful-restart {
        presence "true";
        leaf disable {
          type empty;
        }
      }
      container sso {
        presence "true";
        leaf disable {
          type empty;
        }
      }
    }
    container suppress-signaling-protocol {
      leaf ldp {
        type empty;
      }
    }
    leaf prefix-length-size {
      type uint8;
    }
    container log-neighbor-changes {
      tailf:cli-delete-when-empty;
      presence "true";
      leaf disable {
        type empty;
      }
    }
  }

  grouping router-bgp-aggregate-address-content-grouping {
    leaf as-set {
      type empty;
    }
    leaf summary-only {
      type empty;
    }
    leaf attribute-map {
      type string;
    }
    leaf advertise-map {
      type string;
    }
    leaf suppress-map {
      type string;
    }
    leaf as-override {
      type empty;
    }
    leaf route-map {
      type string;
    }
  }

  grouping router-bgp-af-grouping {
    container segment-routing-srv6 {
      tailf:cli-drop-node-name;
      container segment-routing {
        container srv6 {
          tailf:cli-add-mode;
          presence "true";
          leaf locator {
            type string;
          }
          container alloc-mode {
            leaf per-vrf {
              type empty;
            }
          }
        }
      }
    }
    leaf synchronization {
      type empty;
    }
    choice table-map-choice {
      leaf table-map {
        type string;
      }
      container table-map-filter {
        tailf:cli-drop-node-name;
        tailf:cli-compact-syntax;
        tailf:cli-sequence-commands;
        leaf table-map {
          type string;
        }
        leaf filter {
          type empty;
        }
      }
    }
    container bgp-af {
      tailf:cli-drop-node-name;
      container bgp {
        leaf redistribute-internal {
          type empty;
        }
        container dampening {
          presence "true";
          choice dampening-choice {
            leaf route-map {
              type string;
            }
            container dampen {
              tailf:cli-drop-node-name;
              tailf:cli-compact-syntax;
              tailf:cli-sequence-commands;
              leaf half-life-time {
                tailf:cli-drop-node-name;
                type uint8;
              }
              leaf reuse-time {
                tailf:cli-drop-node-name;
                type uint16;
              }
              leaf suppress-time {
                tailf:cli-drop-node-name;
                type uint16;
              }
              leaf max-suppress-time {
                tailf:cli-drop-node-name;
                type uint8;
              }
            }
          }
        }
        container additional-paths {
          container select {
            tailf:cli-compact-syntax;
            leaf all {
              type empty;
            }
            leaf group-best {
              type empty;
            }
            leaf best {
              type uint8;
            }
            container backup {
              tailf:cli-delete-when-empty;
              presence "true";
              leaf best-external {
                type empty;
              }
            }
          }
          choice send-receive-choice {
            leaf receive {
              type empty;
            }
            container send {
              tailf:cli-delete-when-empty;
              presence "true";
              leaf receive {
                type empty;
              }
            }
          }
          leaf install {
            type empty;
          }
        }
        container bestpath {
          container igp-metric {
            leaf ignore {
              type empty;
            }
          }
        }
        leaf suppress-inactive {
          type empty;
        }
        leaf dmzlink-bw {
          type empty;
        }
        container slow-peer {
          container detection {
            presence "true";
          }
        }
        leaf soft-reconfig-backup {
          type empty;
        }
        container nexthop {
          leaf route-map {
            type string;
          }
          container trigger {
            leaf delay {
              type uint8;
            }
            leaf enable {
              type boolean;
            }
          }
        }
        leaf scan-time {
          type uint8;
        }
        list inject-map {
          tailf:cli-suppress-mode;
          tailf:cli-delete-when-empty;
          tailf:cli-compact-syntax;
          tailf:cli-sequence-commands;
          key "name";
          leaf name {
            type string;
          }
          leaf exist-map {
            type string;
          }
          leaf copy-attributes {
            type empty;
          }
        }
        container recursion {
          leaf host {
            type empty;
          }
        }
        leaf mpls-local-label {
          type empty;
        }
      }
    }
    list network {
      tailf:cli-suppress-mode;
      tailf:cli-delete-when-empty;
      tailf:cli-compact-syntax;
      key "number mask";
      leaf number {
        type union {
          type inet:ipv4-address;
          type ios:ipv6-prefix;
        }
      }
      leaf mask {
        tailf:cli-expose-key-name;
        type inet:ipv4-address;
      }
      choice option-choice {
        leaf backdoor {
          type empty;
        }
        leaf route-map {
          type string;
        }
      }
    }
    container network-address {
      tailf:cli-drop-node-name;
      list network {
        tailf:cli-suppress-mode;
        tailf:cli-delete-when-empty;
        tailf:cli-compact-syntax;
        key "number";
        leaf number {
          type union {
            type inet:ipv4-address;
            type ios:ipv6-prefix;
          }
        }
        choice option-choice {
          leaf backdoor {
            type empty;
          }
          leaf route-map {
            type string;
          }
        }
      }
    }
    list aggregate-address {
      tailf:cli-suppress-mode;
      tailf:cli-delete-when-empty;
      tailf:cli-compact-syntax;
      key "address mask";
      leaf address {
        type inet:ipv4-address;
      }
      leaf mask {
        type inet:ipv4-address;
      }
      uses router-bgp-aggregate-address-content-grouping;
    }
    container aggregate-addres-ipv6 {
      tailf:cli-drop-node-name;
      list aggregate-address {
        tailf:cli-suppress-mode;
        tailf:cli-delete-when-empty;
        tailf:cli-compact-syntax;
        key "address";
        leaf address {
          type ipv6-prefix;
        }
        uses router-bgp-aggregate-address-content-grouping;
      }
    }
    container redistribute {
      container bgp {
        tailf:cli-compact-syntax;
        tailf:cli-sequence-commands;
        tailf:cli-delete-when-empty;
        leaf as-no {
          tailf:cli-drop-node-name;
          type bgp-as-no-type;
        }
        uses router-bgp-redistribute-grouping {
          refine "metric" {
            tailf:cli-break-sequence-commands;
          }
        }
      }
      container connected {
        tailf:cli-compact-syntax;
        tailf:cli-delete-when-empty;
        presence "true";
        uses router-bgp-redistribute-grouping;
      }
      container static {
        tailf:cli-compact-syntax;
        tailf:cli-delete-when-empty;
        presence "true";
        uses router-bgp-redistribute-grouping;
      }
      container dvmrp {
        tailf:cli-compact-syntax;
        tailf:cli-sequence-commands;
        tailf:cli-delete-when-empty;
        presence "true";
        uses route-map-metric-grouping;
      }
      list eigrp {
        tailf:cli-suppress-mode;
        tailf:cli-delete-when-empty;
        tailf:cli-compact-syntax;
        key "as-no";
        leaf as-no {
          type eigrp-as-no-type;
        }
        uses router-bgp-redistribute-grouping;
      }
      container isis {
        tailf:cli-compact-syntax;
        tailf:cli-delete-when-empty;
        presence "true";
        uses router-bgp-redistribute-isis-grouping;
        uses router-bgp-redistribute-grouping;
        list isis-list {
          tailf:cli-drop-node-name;
          tailf:cli-suppress-mode;
          tailf:cli-delete-when-empty;
          tailf:cli-compact-syntax;
          key "name";
          leaf name {
            type string;
          }
          uses router-bgp-redistribute-isis-grouping;
          uses router-bgp-redistribute-grouping;
        }
      }
      container iso-igrp {
        tailf:cli-compact-syntax;
        tailf:cli-delete-when-empty;
        uses route-map-metric-grouping;
        list iso-igrp-area {
          tailf:cli-drop-node-name;
          tailf:cli-suppress-mode;
          tailf:cli-delete-when-empty;
          tailf:cli-compact-syntax;
          key "name";
          leaf name {
            type string;
          }
          uses route-map-metric-grouping;
        }
      }
      container mobile {
        tailf:cli-compact-syntax;
        tailf:cli-delete-when-empty;
        presence "true";
        uses router-bgp-redistribute-grouping;
      }
      container odr {
        tailf:cli-compact-syntax;
        tailf:cli-delete-when-empty;
        presence "true";
        uses router-bgp-redistribute-grouping;
      }
      list ospf {
        tailf:cli-suppress-mode;
        tailf:cli-flatten-container;
        tailf:cli-compact-syntax;
        tailf:cli-delete-when-empty;
        key "id";
        leaf id {
          type uint16;
        }
        leaf vrf {
          type string;
        }
        uses router-bgp-redistribute-ospf-grouping;
      }
      list ospfv3 {
        tailf:cli-suppress-mode;
        tailf:cli-flatten-container;
        tailf:cli-compact-syntax;
        tailf:cli-delete-when-empty;
        key "id";
        leaf id {
          type uint16;
        }
        uses router-bgp-redistribute-ospfv3-grouping;
      }
      container rip {
        tailf:cli-compact-syntax;
        tailf:cli-delete-when-empty;
        presence "true";
        uses router-bgp-redistribute-grouping;
        list rip-list {
          tailf:cli-drop-node-name;
          tailf:cli-suppress-mode;
          tailf:cli-delete-when-empty;
          key "id";
          leaf id {
            tailf:cli-suppress-range;
            type string;
          }
          uses router-bgp-redistribute-grouping;
        }
      }
      container lisp {
        tailf:cli-compact-syntax;
        tailf:cli-delete-when-empty;
        presence "true";
        uses router-bgp-redistribute-grouping;
      }
    }
    container snmp {
      list context {
        tailf:cli-suppress-mode;
        tailf:cli-delete-when-empty;
        key "name";
        leaf name {
          type string;
        }
      }
    }
    container neighbor-tag {
      tailf:cli-drop-node-name;
      list neighbor {
        tailf:cli-suppress-mode;
        tailf:cli-delete-when-empty;
        key "id";
        leaf id {
          type string;
        }
        leaf peer-group {
          type empty;
        }
        leaf remote-as {
          type string;
        }
        uses router-bgp-neighbor-grouping;
      }
    }
    list neighbor {
      tailf:cli-suppress-mode;
      tailf:cli-delete-when-empty;
      key "id";
      leaf id {
        type union {
          type inet:ipv4-address;
          type inet:ipv6-address;
          type ios-ipv6-address;
        }
      }
      leaf remote-as {
        type string;
      }
      leaf peer-group {
        type string;
      }
      uses router-bgp-neighbor-grouping;
    }
    container maximum-paths {
      uses router-bgp-max-path-grouping;
      container eibgp {
        uses router-bgp-max-path-grouping;
      }
      container ibgp {
        choice ibgp-choice {
          case a {
            container unequal-cost {
              uses router-bgp-max-path-grouping;
            }
          }
          case b {
            uses router-bgp-max-path-grouping;
          }
        }
      }
      leaf import {
        type uint16;
      }
    }
    container maximum-secondary-paths {
      leaf paths {
        tailf:cli-drop-node-name;
        type uint8;
      }
      leaf eibgp {
        type uint8;
      }
      leaf ibgp {
        type uint8;
      }
    }
    container import {
      container l2vpn {
        container evpn {
          tailf:cli-compact-syntax;
          tailf:cli-sequence-commands {
            tailf:cli-reset-siblings;
          }
          tailf:cli-delete-when-empty;
          presence "true";
          leaf re-originate {
            type empty;
          }
          leaf stitching-rt {
            type empty;
          }
        }
      }
      container vpnv4 {
        container unicast {
          tailf:cli-delete-when-empty;
          presence "true";
          leaf re-originate {
            type empty;
          }
        }
      }
      container path {
        container selection {
          choice selection-choice {
            leaf all {
              type empty;
            }
            container bestpath {
              tailf:cli-delete-when-empty;
              presence "true";
              leaf strict {
                type empty;
              }
            }
            container multipaths {
              tailf:cli-delete-when-empty;
              presence "true";
              leaf strict {
                type empty;
              }
            }
          }
        }
        leaf limit {
          type uint8;
        }
      }
    }
    container default-information {
      leaf originate {
        type empty;
      }
    }
    leaf default-metric {
      type uint32;
    }
    uses router-distribute-list-grouping;
    container distance {
      container bgp {
        tailf:cli-compact-syntax;
        tailf:cli-sequence-commands;
        leaf extern-as {
          tailf:cli-drop-node-name;
          type uint16;
        }
        leaf internal-as {
          tailf:cli-drop-node-name;
          type uint16;
        }
        leaf local {
          tailf:cli-drop-node-name;
          type uint16;
        }
      }
      list adm-distance {
        tailf:cli-drop-node-name;
        tailf:cli-suppress-mode;
        tailf:cli-delete-when-empty;
        key "srcip wildbits";
        leaf distance {
          tailf:cli-drop-node-name;
          tailf:cli-prefix-key;
          type uint16;
        }
        leaf srcip {
          type inet:ipv4-address;
        }
        leaf wildbits {
          type inet:ipv4-address;
        }
        leaf access-list {
          tailf:cli-drop-node-name;
          type std-ip-acl-type;
        }
      }
    }
    leaf auto-summary {
      type boolean;
    }
  }

  grouping router-bgp-af2-grouping {
    container segment-routing {
      leaf mpls {
        type empty;
      }
    }
  }

  grouping router-bgp-bgp-grouping {
    container bgp {
      choice router-id-choice {
        leaf router-id {
          type inet:ipv4-address;
        }
        container router-id-interface {
          tailf:cli-drop-node-name;
          container router-id {
            container interface {
              uses interface-name-grouping;
            }
          }
        }
        container router-id-vrf {
          tailf:cli-drop-node-name;
          container router-id {
            container vrf {
              leaf auto-assign {
                type empty;
              }
            }
          }
        }
        container router-id-conf {
          tailf:cli-drop-node-name;
          container router-id {
            leaf auto-assign {
              type empty;
            }
          }
        }
      }
      leaf advertise-best-external {
        type empty;
      }
      container asnotation {
        leaf dot {
          type empty;
        }
      }
      container consistency-checker {
        tailf:cli-compact-syntax;
        tailf:cli-sequence-commands {
          tailf:cli-reset-siblings;
        }
        leaf type {
          tailf:cli-drop-node-name;
          type enumeration {
            enum "auto-repair";
            enum "error-message";
          }
        }
        leaf interval {
          type uint16;
        }
      }
      leaf fast-external-fallover {
        type boolean;
      }
      leaf always-compare-med {
        type empty;
      }
      leaf cluster-id {
        type union {
          type uint32;
          type inet:ipv4-address;
        }
      }
      container transport {
        leaf path-mtu-discovery {
          type boolean;
        }
      }
      leaf enforce-first-as {
        type boolean;
      }
      container client-to-client {
        leaf reflection {
          type boolean;
        }
      }
      leaf log-neighbor-changes {
        type boolean;
      }
      container ha-mode {
        container sso {
          tailf:cli-delete-when-empty;
          presence "true";
          leaf prefer {
            type empty;
          }
        }
      }
      container confederation {
        leaf identifier {
          type bgp-as-no-type;
        }
        container peers {
          leaf-list as-no {
            tailf:cli-drop-node-name;
            tailf:cli-flat-list-syntax;
            type bgp-as-no-type;
          }
        }
      }
      leaf deterministic-med {
        type empty;
      }
      container listen {
        list range {
          tailf:cli-suppress-mode;
          tailf:cli-delete-when-empty;
          key "network-length peer-group";
          leaf network-length {
            type ios:ipv4-prefix;
          }
          leaf peer-group {
            tailf:cli-expose-key-name;
            type string;
          }
        }
        leaf limit {
          type uint32;
        }
      }
      leaf update-delay {
        type uint16;
      }
      container nopeerup-delay {
        leaf nsf-switchover {
          type uint16;
        }
      }
      container graceful-restart-conf {
        tailf:cli-drop-node-name;
        container graceful-restart {
          leaf restart-time {
            type uint16;
          }
          leaf stalepath-time {
            type uint16;
          }
        }
      }
      leaf graceful-restart {
        type empty;
      }
      container regexp {
        leaf deterministic {
          type boolean;
        }
      }
      container bestpath {
        leaf compare-routerid {
          type empty;
        }
        container cost-community {
          leaf ignore {
            type empty;
          }
        }
        container med {
          tailf:cli-compact-syntax;
          leaf confed {
            type empty;
          }
          leaf missing-as-worst {
            type empty;
          }
        }
        container as-path {
          leaf multipath-relax {
            type empty;
          }
        }
      }
      leaf maxas-limit {
        type uint16;
      }
      container default {
        leaf ipv4-unicast {
          type boolean;
        }
        leaf ipv4-activate {
          type boolean;
        }
        leaf ipv6-nexthop {
          type boolean;
        }
        leaf local-preference {
          type uint32;
        }
        container route-target {
          leaf filter {
            type boolean;
          }
        }
      }
      leaf mpls-local-label {
        type empty;
      }
      container rpki {
        container server {
          list tcp {
            tailf:cli-suppress-mode;
            tailf:cli-delete-when-empty;
            key "address port";
            leaf address {
              type union {
                type inet:ipv4-address;
                type inet:ipv6-address;
              }
            }
            leaf port {
              tailf:cli-expose-key-name;
              type uint16;
            }
            leaf refresh {
              type uint16;
            }
          }
        }
      }
    }
    container timers {
      container bgp {
        tailf:cli-compact-syntax;
        tailf:cli-sequence-commands {
          tailf:cli-reset-siblings;
        }
        leaf keepalive {
          tailf:cli-drop-node-name;
          type uint16;
        }
        leaf holdtime {
          tailf:cli-drop-node-name;
          type uint16;
        }
        leaf min-holdtime {
          tailf:cli-drop-node-name;
          type uint16;
        }
      }
    }
  }

  grouping router-ospf-af-grouping;

  grouping router-ospfv3-af-grouping {
    container capability {
      leaf vrf-lite {
        type empty;
      }
    }
    container discard-route {
      leaf external {
        type boolean;
      }
      leaf internal {
        type boolean;
      }
    }
  }

  grouping router-ospf-common-af-grouping {
    container default-information {
      container originate {
        tailf:cli-compact-syntax;
        presence "true";
        leaf always {
          type empty;
        }
        leaf metric {
          type uint32;
        }
        leaf metric-type {
          type ospf-metric-type;
        }
        leaf route-map {
          type string;
        }
      }
    }
    leaf default-metric {
      type uint32;
    }
    container distance {
      leaf weight {
        tailf:cli-drop-node-name;
        type uint8;
      }
      list distance-list {
        tailf:cli-drop-node-name;
        tailf:cli-suppress-mode;
        tailf:cli-delete-when-empty;
        tailf:cli-compact-syntax;
        tailf:cli-sequence-commands {
          tailf:cli-reset-siblings;
        }
        key "ip-address wildcard-mask";
        leaf ip-address {
          type inet:ipv4-address;
        }
        leaf wildcard-mask {
          type inet:ipv4-address;
        }
        leaf weight {
          tailf:cli-drop-node-name;
          tailf:cli-prefix-key;
          type uint8;
        }
        leaf access-list {
          tailf:cli-drop-node-name;
          type std-ip-acl-type;
        }
      }
      container ospf {
        tailf:cli-compact-syntax;
        leaf intra-area {
          type uint32;
        }
        leaf inter-area {
          type uint32;
        }
        leaf external {
          type uint32;
        }
      }
    }
    leaf maximum-paths {
      type uint32;
    }
    leaf nsr {
      type empty;
    }
    container redistribute {
      container connected {
        tailf:cli-compact-syntax;
        presence "true";
        uses router-ospf-redistribute-grouping;
        uses router-ospf-route-map-grouping;
      }
      container static {
        tailf:cli-compact-syntax;
        presence "true";
        uses router-ospf-redistribute-grouping;
        uses router-ospf-route-map-grouping;
      }
      container odr {
        tailf:cli-compact-syntax;
        presence "true";
        uses router-ospf-redistribute-grouping;
        uses router-ospf-route-map-grouping;
      }
      container bgp {
        tailf:cli-compact-syntax;
        tailf:cli-sequence-commands;
        leaf as-no {
          tailf:cli-drop-node-name;
          type bgp-as-no-type;
        }
        uses router-ospf-redistribute-grouping {
          refine "metric" {
            tailf:cli-break-sequence-commands;
          }
        }
        uses router-ospf-route-map-grouping;
      }
      list ospf {
        tailf:cli-suppress-mode;
        tailf:cli-compact-syntax;
        key "id";
        leaf id {
          tailf:cli-suppress-range;
          type uint16;
        }
        uses router-ospf-redistribute-grouping;
        uses redistribute-ospf-match-grouping;
        uses router-ospf-route-map-grouping;
      }
      list ospfv3 {
        tailf:cli-suppress-mode;
        tailf:cli-compact-syntax;
        key "id";
        leaf id {
          tailf:cli-suppress-range;
          type uint16;
        }
        uses router-ospf-redistribute-grouping;
        uses redistribute-ospf-match-grouping;
        uses router-ospf-route-map-grouping;
      }
      container isis {
        tailf:cli-compact-syntax;
        tailf:cli-delete-when-empty;
        presence "true";
        uses router-isis-level-grouping;
        uses router-ospf-redistribute-grouping;
        uses router-ospf-route-map-grouping;
      }
      container isis-area {
        tailf:cli-drop-node-name;
        list isis {
          tailf:cli-suppress-mode;
          tailf:cli-compact-syntax;
          key "name";
          leaf name {
            type string;
          }
          uses router-isis-level-grouping;
          uses router-ospf-redistribute-grouping;
          uses router-ospf-route-map-grouping;
        }
      }
      list eigrp {
        tailf:cli-suppress-mode;
        tailf:cli-delete-when-empty;
        tailf:cli-compact-syntax;
        key "as-no";
        leaf as-no {
          type eigrp-as-no-type;
        }
        uses router-ospf-redistribute-grouping;
        uses router-ospf-route-map-grouping;
      }
      container iso-igrp {
        tailf:cli-compact-syntax;
        tailf:cli-sequence-commands;
        presence "true";
        leaf area-tag {
          tailf:cli-drop-node-name;
          tailf:cli-optional-in-sequence;
          type string;
        }
        uses router-ospf-route-map-grouping;
        uses router-ospf-redistribute-grouping;
      }
      container maximum-prefix {
        tailf:cli-compact-syntax;
        tailf:cli-sequence-commands;
        leaf number {
          tailf:cli-drop-node-name;
          type uint32;
        }
        container threshold-warning-only-container {
          tailf:cli-drop-node-name;
          tailf:cli-flatten-container;
          tailf:cli-compact-syntax;
          leaf threshold {
            tailf:cli-drop-node-name;
            type uint32;
          }
          leaf warning-only {
            type empty;
          }
        }
      }
      container mobile {
        tailf:cli-compact-syntax;
        presence "true";
        uses router-ospf-redistribute-grouping;
        uses router-ospf-route-map-grouping;
      }
      container rip {
        tailf:cli-compact-syntax;
        presence "true";
        uses router-ospf-redistribute-grouping;
        uses router-ospf-route-map-grouping;
        list redistribute-list-rip {
          tailf:cli-drop-node-name;
          tailf:cli-suppress-mode;
          tailf:cli-delete-when-empty;
          tailf:cli-compact-syntax;
          key "name";
          leaf name {
            type string;
          }
          uses router-ospf-redistribute-grouping;
          uses router-ospf-route-map-grouping;
        }
      }
      container lisp {
        container subnets {
          tailf:cli-compact-syntax;
          tailf:cli-delete-when-empty;
          presence "true";
        }
      }
    }
  }

  grouping router-ospfvx-common-grouping {
    list area {
      tailf:cli-suppress-mode;
      tailf:cli-delete-when-empty;
      key "id";
      leaf id {
        tailf:cli-suppress-range;
        type ospf-area-type;
      }
      container authentication {
        tailf:cli-delete-when-empty;
        presence "true";
        leaf message-digest {
          type empty;
        }
        choice authentication-choice {
          leaf null {
            type empty;
          }
          leaf key-chain {
            type string;
          }
          container ipsec {
            tailf:cli-compact-syntax;
            tailf:cli-sequence-commands;
            leaf spi {
              type uint32;
            }
            leaf auth {
              tailf:cli-drop-node-name;
              type enumeration {
                enum "md5";
                enum "sha1";
              }
            }
            leaf type {
              tailf:cli-drop-node-name;
              tailf:cli-optional-in-sequence;
              type enumeration {
                enum "0";
                enum "7";
              }
            }
            leaf secret {
              tailf:cli-drop-node-name;
              type string;
            }
          }
        }
      }
      container nssa {
        tailf:cli-compact-syntax;
        presence "true";
        leaf no-redistribution {
          type empty;
        }
        leaf default-information-originate {
          type empty;
        }
        leaf metric {
          type uint32;
        }
        leaf metric-type {
          type ospf-metric-type;
        }
        leaf nssa-only {
          type empty;
        }
        leaf no-ext-capability {
          type empty;
        }
        leaf no-summary {
          type empty;
        }
        container translate {
          container type7 {
            tailf:cli-compact-syntax;
            leaf always {
              type empty;
            }
            leaf suppress-fa {
              type empty;
            }
          }
        }
      }
      leaf default-cost {
        type uint32;
      }
      list filter-list {
        tailf:cli-suppress-mode;
        tailf:cli-delete-when-empty;
        tailf:cli-compact-syntax;
        tailf:cli-sequence-commands;
        key "direction";
        leaf direction {
          type enumeration {
            enum "in";
            enum "out";
          }
        }
        leaf prefix {
          tailf:cli-prefix-key;
          type string;
        }
      }
      list range {
        tailf:cli-suppress-mode;
        tailf:cli-compact-syntax;
        key "ip mask";
        leaf ip {
          type inet:ipv4-address;
        }
        leaf mask {
          type inet:ipv4-address;
        }
        leaf advertise {
          tailf:cli-drop-node-name;
          type enumeration {
            enum "advertise";
            enum "not-advertise";
          }
        }
        leaf cost {
          type uint32;
        }
      }
      container range-ipv6 {
        tailf:cli-drop-node-name;
        list range {
          tailf:cli-compact-syntax;
          tailf:cli-suppress-mode;
          tailf:cli-delete-when-empty;
          key "prefix";
          leaf prefix {
            type ipv6-prefix;
          }
          leaf advertise {
            tailf:cli-drop-node-name;
            type enumeration {
              enum "advertise";
              enum "not-advertise";
            }
          }
          leaf cost {
            type uint32;
          }
        }
      }
      list sham-link {
        tailf:cli-suppress-mode;
        tailf:cli-compact-syntax;
        key "source dest";
        leaf source {
          type inet:ipv4-address;
        }
        leaf dest {
          type inet:ipv4-address;
        }
        leaf cost {
          type uint16;
        }
        container ttl-security {
          tailf:cli-flatten-container;
          tailf:cli-compact-syntax;
          leaf hops {
            type uint8;
          }
        }
      }
      container stub {
        tailf:cli-compact-syntax;
        presence "true";
        leaf no-summary {
          type empty;
        }
        leaf no-ext-capability {
          type empty;
        }
      }
      list virtual-link {
        tailf:cli-suppress-mode;
        tailf:cli-compact-syntax;
        key "id";
        leaf id {
          type inet:ipv4-address;
        }
        leaf retransmit-interval {
          type uint16;
        }
        leaf transmit-delay {
          type uint16;
        }
        leaf hello-interval {
          type int32;
        }
        leaf dead-interval {
          type uint16;
        }
        leaf authentication {
          type empty;
        }
        container authentication-key {
          tailf:cli-flatten-container;
          tailf:cli-compact-syntax;
          tailf:cli-sequence-commands {
            tailf:cli-reset-siblings;
          }
          uses password-grouping {
            refine "secret";
          }
        }
        list message-digest-key {
          tailf:cli-suppress-mode;
          tailf:cli-delete-when-empty;
          tailf:cli-compact-syntax;
          key "id";
          leaf id {
            tailf:cli-suppress-range;
            type uint8;
          }
          container md5 {
            tailf:cli-compact-syntax;
            tailf:cli-sequence-commands {
              tailf:cli-reset-siblings;
            }
            leaf auth-type {
              tailf:cli-drop-node-name;
              tailf:cli-optional-in-sequence;
              type uint8;
            }
            leaf auth-key {
              tailf:cli-drop-node-name;
              type string;
            }
          }
        }
      }
    }
    container snmp {
      leaf context {
        type string;
      }
    }
    container auto-cost {
      leaf reference-bandwidth {
        type uint32;
      }
    }
    container bfd {
      tailf:cli-compact-syntax;
      tailf:cli-sequence-commands {
        tailf:cli-reset-siblings;
      }
      leaf all-interfaces {
        type empty;
      }
      leaf strict-mode {
        type empty;
      }
    }
    container interface-id {
      leaf snmp-if-index {
        type empty;
      }
    }
    container log-adjacency-changes {
      presence "true";
      leaf detail {
        type empty;
      }
    }
    container max-lsa {
      tailf:cli-compact-syntax;
      tailf:cli-sequence-commands {
        tailf:cli-reset-all-siblings;
      }
      leaf maximum-number {
        tailf:cli-drop-node-name;
        type uint32;
      }
      leaf threshold-percentage {
        tailf:cli-break-sequence-commands;
        tailf:cli-drop-node-name;
        type uint8;
      }
      leaf warning-only {
        type empty;
      }
      leaf ignore-time {
        type uint32;
      }
      leaf reset-time {
        type uint32;
      }
      leaf ignore-count {
        type uint32;
      }
    }
    container graceful-restart-enable {
      tailf:cli-drop-node-name;
      leaf graceful-restart {
        type empty;
      }
    }
    container graceful-restart {
      container helper {
        choice helper-choice {
          leaf disable {
            type empty;
          }
          leaf strict-lsa-checking {
            type empty;
          }
        }
      }
    }
    uses passive-interface-grouping;
    container queue-depth {
      leaf hello {
        type union {
          type uint32;
          type enumeration {
            enum "unlimited";
          }
        }
      }
      leaf update {
        type union {
          type uint32;
          type enumeration {
            enum "unlimited";
          }
        }
      }
    }
    container timers {
      container lsa {
        leaf arrival {
          type uint32;
        }
      }
      container pacing {
        leaf flood {
          type uint32;
        }
        leaf lsa-group {
          type uint32;
        }
        leaf retransmission {
          type uint32;
        }
      }
      container spf {
        tailf:cli-compact-syntax;
        tailf:cli-sequence-commands;
        leaf spf-start {
          tailf:cli-drop-node-name;
          type uint32;
        }
        leaf spf-hold {
          tailf:cli-drop-node-name;
          type uint32;
        }
      }
      container throttle {
        container lsa {
          tailf:cli-compact-syntax;
          tailf:cli-sequence-commands;
          leaf all {
            tailf:cli-optional-in-sequence;
            type empty;
          }
          leaf start-interval {
            tailf:cli-drop-node-name;
            type uint32;
          }
          leaf hold-interval {
            tailf:cli-drop-node-name;
            type uint32;
          }
          leaf max-interval {
            tailf:cli-drop-node-name;
            type uint32;
          }
        }
        container spf {
          tailf:cli-compact-syntax;
          tailf:cli-sequence-commands;
          leaf spf-start {
            tailf:cli-drop-node-name;
            type uint32;
          }
          leaf spf-hold {
            tailf:cli-drop-node-name;
            type uint32;
          }
          leaf spf-max-wait {
            tailf:cli-drop-node-name;
            type uint32;
          }
        }
      }
    }
    leaf priority {
      type uint8;
    }
    leaf router-id {
      type inet:ipv4-address;
    }
  }

  grouping router-ospf-common-grouping {
    uses router-ospfvx-common-grouping {
      refine "log-adjacency-changes";
    }
  }

  grouping router-ospfv3-common-grouping {
    uses router-ospfvx-common-grouping;
  }

  grouping router-ospf-grouping {
    container capability {
      leaf vrf-lite {
        type empty;
      }
      leaf opaque {
        type boolean;
      }
      leaf lls {
        type boolean;
      }
      leaf transit {
        type boolean;
      }
    }
    container compatible {
      leaf rfc1583 {
        type boolean;
      }
    }
    uses router-distribute-list-grouping;
    container domain-id {
      choice domain-id-choice {
        case a {
          leaf ip-format {
            tailf:cli-drop-node-name;
            type inet:ipv4-address;
          }
          container ip-format-secondary {
            tailf:cli-drop-node-name;
            tailf:cli-compact-syntax;
            tailf:cli-sequence-commands;
            leaf ip {
              tailf:cli-drop-node-name;
              type inet:ipv4-address;
            }
            leaf secondary {
              type empty;
            }
          }
        }
        leaf Null {
          type empty;
        }
        container type {
          tailf:cli-sequence-commands;
          tailf:cli-compact-syntax;
          leaf type-leaf {
            tailf:cli-drop-node-name;
            type enumeration {
              enum "0005";
              enum "0105";
              enum "0205";
              enum "8005";
            }
          }
          leaf value {
            type string;
          }
        }
      }
    }
    leaf domain-tag {
      type uint32;
    }
    container ignore {
      container lsa {
        leaf mospf {
          type empty;
        }
      }
    }
    leaf ispf {
      type empty;
    }
    container limit {
      container retransmissions {
        tailf:cli-compact-syntax;
        leaf dc {
          type limit-dc-non-dc-type;
        }
        leaf non-dc {
          type limit-dc-non-dc-type;
        }
      }
    }
    container local-rib-criteria {
      tailf:cli-compact-syntax;
      leaf forwarding-address {
        type empty;
      }
      leaf inter-area-summary {
        type empty;
      }
      leaf nssa-translation {
        type empty;
      }
    }
    container max-metric {
      container router-lsa {
        tailf:cli-compact-syntax;
        presence "true";
        leaf include-stub {
          type empty;
        }
        leaf stub-prefix-lsa {
          type empty;
        }
        leaf summary-lsa {
          type empty;
        }
        leaf summary-lsa-max-metric-value {
          tailf:cli-drop-node-name;
          type uint32;
        }
        leaf inter-area-lsas {
          type empty;
        }
        leaf external-lsa {
          type empty;
        }
        leaf external-lsa-max-metric-value {
          tailf:cli-drop-node-name;
          type uint32;
        }
        container on-startup {
          tailf:cli-flatten-container;
          tailf:cli-compact-syntax;
          choice time-wait-for-bgp-choice {
            leaf seconds {
              tailf:cli-drop-node-name;
              type uint32;
            }
            leaf wait-for-bgp {
              type empty;
            }
          }
        }
      }
    }
    container event-log {
      leaf size {
        type uint16;
      }
    }
    container mpls {
      container ldp {
        container autoconfig {
          presence "Configure LDP automatic configuration";
          leaf area {
            type ospf-area-type;
          }
        }
        container sync {
          presence "Configure LDP-IGP Synchronization";
        }
      }
      container traffic-eng {
        container router-id {
          uses interface-name-grouping;
        }
        leaf-list area {
          type ospf-area-type;
        }
        leaf multicast-intact {
          type empty;
        }
        container interface {
          tailf:cli-compact-syntax;
          tailf:cli-sequence-commands {
            tailf:cli-reset-siblings;
          }
          container name {
            tailf:cli-drop-node-name;
            tailf:cli-flatten-container;
            tailf:cli-compact-syntax;
            uses interface-name-grouping;
          }
          leaf area {
            type uint32;
          }
        }
        list mesh-group {
          tailf:cli-suppress-mode;
          tailf:cli-delete-when-empty;
          tailf:cli-compact-syntax;
          tailf:cli-sequence-commands {
            tailf:cli-reset-siblings;
          }
          key "id area";
          leaf id {
            type uint32;
          }
          leaf area {
            tailf:cli-expose-key-name;
            type ospf-area-type;
          }
          leaf interface {
            tailf:cli-drop-node-name;
            tailf:cli-prefix-key {
              tailf:cli-before-key "2";
            }
            type string;
          }
        }
      }
    }
    list neighbor {
      tailf:cli-suppress-mode;
      tailf:cli-delete-when-empty;
      key "ip";
      leaf ip {
        type inet:ipv4-address;
      }
      container cost-database-filter-container {
        tailf:cli-drop-node-name;
        tailf:cli-compact-syntax;
        leaf cost {
          type uint32;
        }
        container database-filter {
          tailf:cli-flatten-container;
          tailf:cli-compact-syntax;
          container all {
            tailf:cli-flatten-container;
            tailf:cli-compact-syntax;
            leaf out {
              type empty;
            }
          }
        }
      }
      container poll-interval-priority-container {
        tailf:cli-drop-node-name;
        tailf:cli-compact-syntax;
        leaf poll-interval {
          type uint32;
        }
        leaf priority {
          type uint32;
        }
      }
    }
    list network {
      tailf:cli-suppress-mode;
      tailf:cli-delete-when-empty;
      key "ip mask";
      leaf ip {
        type inet:ipv4-address;
      }
      leaf mask {
        type inet:ipv4-address;
      }
      leaf area {
        type ospf-area-type;
      }
    }
    container nsf {
      tailf:cli-delete-when-empty;
      presence "true";
      container cisco {
        presence "true";
        leaf enforce {
          type enumeration {
            enum "global";
          }
        }
      }
    }
    container nsf-ietf {
      tailf:cli-drop-node-name;
      container nsf {
        container ietf {
          presence "true";
          leaf restart-interval {
            type uint16;
          }
        }
      }
    }
    container nsf-helper {
      tailf:cli-drop-node-name;
      container nsf {
        container cisco {
          container helper {
            leaf disable {
              type empty;
            }
          }
        }
        container ietf {
          container helper {
            leaf disable {
              type empty;
            }
            leaf strict-lsa-checking {
              type empty;
            }
          }
        }
      }
    }
    container prefix-priority {
      container high {
        leaf route-map {
          type string;
        }
      }
    }
    leaf prefix-suppression {
      type empty;
    }
    container process-min-time {
      leaf percent {
        type uint32;
      }
    }
    container traffic-share {
      container min {
        leaf across-interfaces {
          type empty;
        }
      }
    }
    leaf shutdown {
      type empty;
    }
    list summary-address {
      tailf:cli-suppress-mode;
      key "ip wildcard";
      leaf ip {
        type inet:ipv4-address;
      }
      leaf wildcard {
        type inet:ipv4-address;
      }
      choice tag-no-advertise-choice {
        leaf tag {
          type uint32;
        }
        leaf not-advertise {
          type empty;
        }
      }
    }
    container discard-route {
      leaf external {
        type union {
          type uint32;
          type enumeration {
            enum "disabled";
          }
        }
      }
      leaf internal {
        type union {
          type uint32;
          type enumeration {
            enum "disabled";
          }
        }
      }
    }
    container segment-routing {
      list area {
        tailf:cli-suppress-mode;
        tailf:cli-delete-when-empty;
        key "id";
        leaf id {
          type union {
            type uint32;
            type inet:ipv4-address;
          }
        }
        leaf status {
          tailf:cli-drop-node-name;
          type enumeration {
            enum "disable";
            enum "mpls";
          }
        }
      }
      leaf mpls {
        type empty;
      }
      container prefix-sid-map {
        leaf advertise-local {
          type empty;
        }
      }
    }
    container fast-reroute {
      leaf keep-all-paths {
        type empty;
      }
      container per-prefix {
        container enable {
          list area {
            tailf:cli-suppress-mode;
            tailf:cli-delete-when-empty;
            tailf:cli-compact-syntax;
            tailf:cli-sequence-commands {
              tailf:cli-reset-siblings;
            }
            key "area";
            leaf area {
              type ospf-area-type;
            }
            leaf prefix-priority {
              type enumeration {
                enum "high";
                enum "low";
              }
            }
          }
          leaf prefix-priority {
            type enumeration {
              enum "high";
              enum "low";
            }
          }
        }
        container remote-lfa {
          leaf area {
            type ospf-area-type;
          }
          leaf maximum-cost {
            type uint32;
          }
          leaf tunnel {
            type enumeration {
              enum "mpls-ldp";
            }
          }
        }
        leaf ti-lfa {
          type empty;
        }
        container ti-lfa-area {
          tailf:cli-drop-node-name;
          container ti-lfa {
            list area {
              tailf:cli-suppress-mode;
              tailf:cli-delete-when-empty;
              key "id";
              leaf id {
                type union {
                  type uint32;
                  type inet:ipv4-address;
                }
              }
              leaf disable {
                type empty;
              }
            }
          }
        }
      }
    }
    container microloop {
      container avoidance {
        tailf:cli-delete-when-empty;
        presence "true";
        choice avoidance-choice {
          leaf protected {
            type empty;
          }
          leaf disable {
            type empty;
          }
          leaf segment-routing {
            type empty;
          }
        }
      }
    }
    container address-family {
      container ipv4 {
        container multicast {
          tailf:cli-add-mode;
          container topology {
            container base {
              tailf:cli-add-mode;
              presence "true";
            }
          }
        }
      }
    }
  }

  grouping router-ospfv3-grouping {
    container authentication {
      leaf mode {
        type enumeration {
          enum "deployment";
          enum "normal";
          enum "strict";
        }
      }
    }
    list summary-prefix {
      tailf:cli-suppress-mode;
      tailf:cli-delete-when-empty;
      tailf:cli-compact-syntax;
      key "prefix";
      leaf prefix {
        type union {
          type ios:ipv4-prefix;
          type ios:ipv6-prefix;
        }
      }
    }
    container manet {
      container peering {
        container selective {
          tailf:cli-compact-syntax;
          tailf:cli-delete-when-empty;
          presence "true";
          choice selective-choice {
            case enable {
              leaf redundancy {
                type uint8;
              }
              leaf per-interface {
                type empty;
              }
            }
            leaf disable {
              type empty;
            }
          }
        }
      }
    }
  }

  grouping ospf-redistribute-match-grouping {
    leaf metric {
      type uint32;
    }
    leaf subnets {
      type empty;
    }
    leaf route-map {
      type string;
    }
    leaf tag {
      type uint32;
    }
  }

  grouping router-isis-level-grouping {
    leaf level {
      tailf:cli-drop-node-name;
      type enumeration {
        enum "level-1";
        enum "level-1-2";
        enum "level-2";
      }
    }
  }

  grouping router-ospf-route-map-grouping {
    leaf route-map {
      type string;
    }
  }

  grouping router-ospf-redistribute-grouping {
    leaf vrf {
      tailf:cli-optional-in-sequence;
      type string;
    }
    leaf metric {
      type uint32;
    }
    leaf metric-type {
      type enumeration {
        enum "1";
        enum "2";
      }
    }
    leaf subnets {
      type empty;
    }
    leaf nssa-only {
      type empty;
    }
    leaf tag {
      type uint32;
    }
  }

  grouping router-rip-af-grouping {
    leaf auto-summary {
      type boolean;
    }
    leaf maximum-paths {
      type uint8;
    }
    list neighbor {
      tailf:cli-suppress-mode;
      tailf:cli-delete-when-empty;
      key "ip";
      leaf ip {
        type inet:ipv4-address;
      }
      leaf bfd {
        type empty;
      }
    }
    list network {
      tailf:cli-suppress-mode;
      tailf:cli-delete-when-empty;
      key "ip";
      leaf ip {
        type inet:ipv4-address;
      }
    }
    leaf validate-update-source {
      type boolean;
    }
    container default-information {
      container originate {
        presence "true";
        leaf route-map {
          type string;
        }
      }
    }
    leaf default-metric {
      type uint32;
    }
    container distance {
      tailf:cli-compact-syntax;
      leaf distance-leaf {
        tailf:cli-drop-node-name;
        type uint8;
      }
      list distance-list {
        tailf:cli-drop-node-name;
        tailf:cli-suppress-mode;
        tailf:cli-delete-when-empty;
        tailf:cli-compact-syntax;
        tailf:cli-sequence-commands {
          tailf:cli-reset-siblings;
        }
        key "ip mask";
        leaf number {
          tailf:cli-prefix-key;
          tailf:cli-drop-node-name;
          type uint8;
        }
        leaf ip {
          type inet:ipv4-address;
        }
        leaf mask {
          type inet:ipv4-address;
        }
        leaf access-list {
          tailf:cli-drop-node-name;
          type std-ip-acl-type;
        }
      }
    }
    uses router-distribute-list-grouping;
    uses router-offset-list-grouping;
    container redistribute {
      container connected {
        tailf:cli-compact-syntax;
        presence "true";
        uses router-rip-redistribute-grouping;
      }
      container bgp {
        tailf:cli-compact-syntax;
        leaf as-no {
          tailf:cli-drop-node-name;
          type bgp-as-no-type;
        }
        uses router-rip-redistribute-grouping;
      }
      list eigrp {
        tailf:cli-suppress-mode;
        tailf:cli-delete-when-empty;
        tailf:cli-compact-syntax;
        key "as-no";
        leaf as-no {
          type eigrp-as-no-type;
        }
        uses router-rip-redistribute-grouping;
      }
      container isis {
        tailf:cli-compact-syntax;
        presence "true";
        list isis-list {
          tailf:cli-drop-node-name;
          tailf:cli-suppress-mode;
          tailf:cli-delete-when-empty;
          tailf:cli-compact-syntax;
          key "name";
          leaf name {
            type string;
          }
          leaf level {
            tailf:cli-drop-node-name;
            type isis-level-type;
          }
          uses router-rip-redistribute-grouping;
        }
        leaf level {
          tailf:cli-drop-node-name;
          type isis-level-type;
        }
        uses router-rip-redistribute-grouping;
      }
      container iso-igrp {
        presence "true";
        list iso-igrp-list {
          tailf:cli-suppress-mode;
          tailf:cli-delete-when-empty;
          tailf:cli-drop-node-name;
          key "name";
          leaf name {
            type string;
          }
          uses router-rip-redistribute-grouping;
        }
        uses router-rip-redistribute-grouping;
      }
      container mobile {
        tailf:cli-compact-syntax;
        presence "Mobile routes";
        uses router-rip-redistribute-grouping;
      }
      container odr {
        tailf:cli-compact-syntax;
        presence "On Demand stub Routes";
        uses router-rip-redistribute-grouping;
      }
      list ospf {
        tailf:cli-suppress-mode;
        tailf:cli-delete-when-empty;
        tailf:cli-compact-syntax;
        key "id";
        leaf id {
          tailf:cli-suppress-range;
          type uint16;
        }
        uses router-rip-redistribute-grouping;
        uses redistribute-ospf-match-grouping;
      }
      container static {
        tailf:cli-compact-syntax;
        tailf:cli-delete-when-empty;
        presence "Static routes";
        uses router-rip-redistribute-grouping;
      }
      container rip {
        tailf:cli-compact-syntax;
        presence "true";
        uses router-rip-redistribute-grouping;
      }
      container lisp {
        tailf:cli-compact-syntax;
        presence "true";
        uses router-rip-redistribute-grouping;
      }
    }
    container timers {
      container basic {
        tailf:cli-compact-syntax;
        tailf:cli-sequence-commands;
        leaf updates {
          tailf:cli-drop-node-name;
          type uint32;
        }
        leaf invalid {
          tailf:cli-drop-node-name;
          type uint32;
        }
        leaf holddown {
          tailf:cli-drop-node-name;
          type uint32;
        }
        leaf flush {
          tailf:cli-drop-node-name;
          type uint32;
        }
        leaf sleep {
          tailf:cli-drop-node-name;
          type uint32;
        }
      }
    }
    leaf version {
      type uint8;
    }
    container traffic-share {
      container min {
        leaf across-interfaces {
          type empty;
        }
      }
    }
  }

  grouping router-rip-grouping {
    uses router-rip-af-grouping;
    uses passive-interface-grouping;
    leaf output-delay {
      type uint8;
    }
    leaf input-queue {
      type uint16;
    }
    leaf flash-update-threshold {
      type uint8;
    }
  }

  grouping router-rip-redistribute-grouping {
    leaf metric {
      type union {
        type uint8;
        type enumeration {
          enum "transparent";
        }
      }
    }
    leaf route-map {
      type string;
    }
  }

  grouping router-eigrp-redistribute-grouping {
    container metric {
      tailf:cli-break-sequence-commands;
      tailf:cli-flatten-container;
      tailf:cli-compact-syntax;
      tailf:cli-sequence-commands {
        tailf:cli-reset-siblings;
      }
      leaf bandwidth-metric {
        tailf:cli-drop-node-name;
        type uint32;
      }
      leaf delay-metric {
        tailf:cli-drop-node-name;
        type uint32;
      }
      leaf reliability-metric {
        tailf:cli-drop-node-name;
        type uint8;
      }
      leaf effective-bandwidth-metric {
        tailf:cli-drop-node-name;
        type uint8;
      }
      leaf mtu-bytes {
        tailf:cli-drop-node-name;
        type uint16;
      }
    }
    leaf route-map {
      type string;
    }
  }

  grouping router-eigrp-grouping {
    container bfd {
      leaf all-interfaces {
        type empty;
      }
      list interface {
        tailf:cli-suppress-mode;
        tailf:cli-delete-when-empty;
        key "name";
        leaf name {
          type string;
        }
      }
    }
    container metric {
      leaf maximum-hops {
        type uint8;
      }
      container weights {
        tailf:cli-compact-syntax;
        tailf:cli-sequence-commands {
          tailf:cli-reset-siblings;
        }
        leaf tos {
          tailf:cli-drop-node-name;
          type uint8;
        }
        leaf k1 {
          tailf:cli-drop-node-name;
          type uint8;
        }
        leaf k2 {
          tailf:cli-drop-node-name;
          type uint8;
        }
        leaf k3 {
          tailf:cli-drop-node-name;
          type uint8;
        }
        leaf k4 {
          tailf:cli-drop-node-name;
          type uint8;
        }
        leaf k5 {
          tailf:cli-drop-node-name;
          type uint8;
        }
      }
    }
    container network-ip {
      tailf:cli-drop-node-name;
      list network {
        tailf:cli-suppress-mode;
        tailf:cli-delete-when-empty;
        key "ip";
        leaf ip {
          type inet:ipv4-address;
        }
      }
    }
    list network {
      tailf:cli-suppress-mode;
      tailf:cli-delete-when-empty;
      key "ip mask";
      leaf ip {
        type inet:ipv4-address;
      }
      leaf mask {
        type inet:ipv4-address;
      }
    }
    container neighbor {
      list neighbor-list {
        tailf:cli-drop-node-name;
        tailf:cli-suppress-mode;
        tailf:cli-delete-when-empty;
        key "address interface";
        leaf address {
          type inet:ipv4-address;
        }
        leaf interface {
          type string;
        }
      }
    }
    container eigrp {
      leaf router-id {
        type inet:ipv4-address;
      }
      container stub {
        tailf:cli-compact-syntax;
        leaf connected {
          type empty;
        }
        leaf static {
          type empty;
        }
        leaf summary {
          type empty;
        }
        leaf redistributed {
          type empty;
        }
      }
      leaf stub-site {
        type string;
      }
      leaf log-neighbor-changes {
        type boolean;
      }
    }
  }

  grouping router-eigrp-base-grouping {
    uses router-distribute-list-grouping;
    leaf maximum-secondary-paths {
      type uint8;
    }
    leaf variance {
      type uint8;
    }
    container timers {
      container nsf {
        leaf converge {
          type uint8;
        }
      }
    }
    leaf maximum-paths {
      type uint8;
    }
    container default-metric {
      tailf:cli-compact-syntax;
      tailf:cli-sequence-commands;
      leaf bandwidth {
        tailf:cli-drop-node-name;
        type uint32;
      }
      leaf delay {
        tailf:cli-drop-node-name;
        type uint32;
      }
      leaf reliability {
        tailf:cli-drop-node-name;
        type uint8;
      }
      leaf loading {
        tailf:cli-drop-node-name;
        type uint8;
      }
      leaf mtu {
        tailf:cli-drop-node-name;
        type uint16;
      }
    }
    list summary-metric {
      tailf:cli-suppress-mode;
      tailf:cli-delete-when-empty;
      tailf:cli-compact-syntax;
      tailf:cli-sequence-commands {
        tailf:cli-reset-siblings;
      }
      key "prefix";
      leaf prefix {
        type ios:ipv4-prefix;
      }
      leaf bandwidth {
        tailf:cli-optional-in-sequence;
        tailf:cli-drop-node-name;
        type uint32;
      }
      leaf delay {
        tailf:cli-drop-node-name;
        type uint32;
      }
      leaf reliability {
        tailf:cli-drop-node-name;
        type uint8;
      }
      leaf load {
        tailf:cli-drop-node-name;
        type uint8;
      }
      leaf mtu {
        tailf:cli-drop-node-name;
        type uint16;
      }
      leaf distance {
        type uint8;
      }
    }
    uses router-offset-list-grouping;
    container redistribute {
      container connected {
        tailf:cli-compact-syntax;
        tailf:cli-delete-when-empty;
        presence "true";
        uses router-eigrp-redistribute-grouping;
      }
      container bgp {
        tailf:cli-compact-syntax;
        tailf:cli-sequence-commands {
          tailf:cli-reset-all-siblings;
        }
        leaf as-no {
          tailf:cli-drop-node-name;
          type bgp-as-no-type;
        }
        uses router-eigrp-redistribute-grouping;
      }
      list eigrp {
        tailf:cli-suppress-mode;
        tailf:cli-delete-when-empty;
        tailf:cli-compact-syntax;
        key "as-no";
        leaf as-no {
          type eigrp-as-no-type;
        }
        uses router-eigrp-redistribute-grouping;
      }
      container isis {
        tailf:cli-compact-syntax;
        tailf:cli-delete-when-empty;
        presence "true";
        list isis-list {
          tailf:cli-drop-node-name;
          tailf:cli-suppress-mode;
          tailf:cli-delete-when-empty;
          tailf:cli-compact-syntax;
          key "name";
          leaf name {
            type string;
          }
          leaf level {
            tailf:cli-drop-node-name;
            type isis-level-type;
          }
          uses router-eigrp-redistribute-grouping;
        }
        leaf level {
          tailf:cli-drop-node-name;
          type isis-level-type;
        }
        uses router-eigrp-redistribute-grouping;
      }
      container iso-igrp {
        tailf:cli-delete-when-empty;
        presence "true";
        list iso-igrp-list {
          tailf:cli-suppress-mode;
          tailf:cli-delete-when-empty;
          tailf:cli-drop-node-name;
          key "name";
          leaf name {
            type string;
          }
          uses router-eigrp-redistribute-grouping;
        }
        uses router-eigrp-redistribute-grouping;
      }
      container mobile {
        tailf:cli-compact-syntax;
        tailf:cli-delete-when-empty;
        presence "true";
        uses router-eigrp-redistribute-grouping;
      }
      container odr {
        tailf:cli-compact-syntax;
        tailf:cli-delete-when-empty;
        presence "true";
        uses router-eigrp-redistribute-grouping;
      }
      list ospf {
        tailf:cli-suppress-mode;
        tailf:cli-delete-when-empty;
        tailf:cli-compact-syntax;
        key "id";
        leaf id {
          tailf:cli-suppress-range;
          type uint16;
        }
        leaf vrf {
          type string;
        }
        uses redistribute-ospf-match-grouping;
        uses router-eigrp-redistribute-grouping;
      }
      container static {
        tailf:cli-compact-syntax;
        tailf:cli-delete-when-empty;
        presence "true";
        uses router-eigrp-redistribute-grouping;
      }
      container rip {
        tailf:cli-compact-syntax;
        tailf:cli-delete-when-empty;
        presence "true";
        uses router-eigrp-redistribute-grouping;
      }
    }
    container distance {
      container eigrp {
        tailf:cli-compact-syntax;
        tailf:cli-sequence-commands;
        leaf internal-distance {
          tailf:cli-drop-node-name;
          type uint8;
        }
        leaf external-distance {
          tailf:cli-drop-node-name;
          type uint8;
        }
      }
      list distance-list {
        tailf:cli-drop-node-name;
        tailf:cli-suppress-mode;
        tailf:cli-delete-when-empty;
        tailf:cli-compact-syntax;
        tailf:cli-sequence-commands {
          tailf:cli-reset-siblings;
        }
        key "ip-address wildcard-mask";
        leaf ip-address {
          type inet:ipv4-address;
        }
        leaf wildcard-mask {
          type inet:ipv4-address;
        }
        leaf weight {
          tailf:cli-drop-node-name;
          tailf:cli-prefix-key;
          type uint8;
        }
        leaf access-list {
          tailf:cli-drop-node-name;
          type std-ip-acl-type;
        }
      }
    }
    leaf auto-summary {
      type empty;
    }
    uses passive-interface-grouping;
    leaf nsf {
      type empty;
    }
  }

  grouping router-eigrp-af-virtual-instance-grouping {
    list af-interface {
      tailf:cli-break-sequence-commands;
      ordered-by user;
      key "name";
      leaf name {
        type string;
      }
      list summary-address {
        tailf:cli-suppress-mode;
        tailf:cli-delete-when-empty;
        tailf:cli-compact-syntax;
        key "ip mask";
        leaf ip {
          type inet:ipv4-address;
        }
        leaf mask {
          type inet:ipv4-address;
        }
        leaf leak-map {
          type string;
        }
      }
      container summary-address-ipv6 {
        tailf:cli-drop-node-name;
        list summary-address {
          tailf:cli-suppress-mode;
          tailf:cli-delete-when-empty;
          tailf:cli-compact-syntax;
          key "ipv6";
          leaf ipv6 {
            type ipv6-prefix;
          }
          leaf leak-map {
            type string;
          }
        }
      }
      container authentication {
        container mode {
          leaf md5 {
            type empty;
          }
        }
        leaf key-chain {
          type string;
        }
      }
      leaf hello-interval {
        type uint16;
      }
      leaf hold-time {
        type uint16;
      }
      leaf next-hop-self {
        type boolean;
      }
      leaf shutdown {
        type boolean;
      }
      leaf passive-interface {
        type empty;
      }
      leaf split-horizon {
        type boolean;
      }
      container stub-site {
        leaf wan-interface {
          type empty;
        }
      }
    }
    container topology {
      container base {
        tailf:cli-add-mode;
        presence "true";
        uses router-eigrp-base-grouping;
      }
    }
    uses router-eigrp-grouping;
    container maximum-prefix {
      tailf:cli-compact-syntax;
      tailf:cli-sequence-commands {
        tailf:cli-reset-all-siblings;
      }
      leaf max-prefix-no {
        tailf:cli-drop-node-name;
        type uint32;
      }
      leaf threshold {
        tailf:cli-drop-node-name;
        tailf:cli-break-sequence-commands;
        type uint8;
      }
      leaf restart {
        type uint16;
      }
      leaf warning-only {
        type empty;
      }
    }
  }

  grouping router-eigrp-srv-af-sf-if-grouping {
    leaf shutdown {
      type boolean;
    }
    leaf hello-interval {
      type uint16;
    }
    leaf hold-time {
      type uint16;
    }
  }

  grouping spf-intervals-grouping {
    leaf interval {
      tailf:cli-drop-node-name;
      type uint8;
    }
    leaf initial-wait {
      tailf:cli-drop-node-name;
      type uint32;
    }
    leaf minimum-wait {
      tailf:cli-drop-node-name;
      type uint32;
    }
  }

  grouping router-isis-authenticate-snp-grouping {
    leaf authenticate {
      type empty;
    }
    leaf snp {
      type enumeration {
        enum "send-only";
        enum "validate";
      }
    }
  }

  grouping lsp-gen-interval-grouping {
    leaf interval {
      tailf:cli-drop-node-name;
      type uint32;
    }
    leaf initial-wait {
      tailf:cli-drop-node-name;
      type uint32;
    }
    leaf wait {
      tailf:cli-drop-node-name;
      type uint32;
    }
  }

  grouping set-overload-bit-suppress-grouping {
    leaf external {
      tailf:cli-break-sequence-commands;
      type empty;
    }
    leaf interlevel {
      type empty;
    }
  }

  grouping redist-level-grouping {
    leaf level {
      tailf:cli-drop-node-name;
      tailf:cli-break-sequence-commands;
      type isis-level-type;
    }
  }

  grouping router-isis-redistribute-grouping {
    leaf metric {
      type uint32;
    }
    leaf route-map {
      type string;
    }
    leaf metric-type {
      type enumeration {
        enum "external";
        enum "internal";
      }
    }
    uses router-isis-level-grouping;
  }

  grouping router-isis-af-redistribute-grouping {
    leaf metric {
      type uint32;
    }
    leaf metric-type {
      type enumeration {
        enum "external";
        enum "internal";
      }
    }
    uses router-isis-level-grouping;
    leaf route-map {
      type string;
    }
    leaf include-connected {
      type empty;
    }
  }

  grouping isis-redist-ospf-match-grouping {
    uses redist-level-grouping;
    leaf metric {
      type uint32;
    }
    leaf route-map {
      type string;
    }
  }

  grouping router-isis-interface-grouping {
    container authentication {
      list mode {
        tailf:cli-suppress-mode;
        tailf:cli-delete-when-empty;
        tailf:cli-compact-syntax;
        tailf:cli-sequence-commands;
        key "level";
        leaf name {
          tailf:cli-drop-node-name;
          tailf:cli-prefix-key;
          type enumeration {
            enum "md5";
            enum "text";
          }
        }
        leaf level {
          type enumeration {
            enum "level-1";
            enum "level-2";
          }
        }
      }
      list key-chain {
        tailf:cli-suppress-mode;
        tailf:cli-delete-when-empty;
        tailf:cli-compact-syntax;
        tailf:cli-sequence-commands;
        key "level";
        leaf name {
          tailf:cli-drop-node-name;
          tailf:cli-prefix-key;
          type string;
        }
        leaf level {
          type enumeration {
            enum "level-1";
            enum "level-2";
          }
        }
      }
      list send-only {
        tailf:cli-suppress-mode;
        tailf:cli-delete-when-empty;
        key "level";
        leaf level {
          type enumeration {
            enum "level-1";
            enum "level-2";
          }
        }
      }
    }
  }

  grouping router-isis-af-early-grouping {
    container metric-style {
      choice metric-style-choice {
        container narrow {
          tailf:cli-compact-syntax;
          tailf:cli-delete-when-empty;
          presence "true";
          uses router-isis-metric-type-grouping;
        }
        container transition {
          tailf:cli-compact-syntax;
          tailf:cli-delete-when-empty;
          presence "true";
          leaf level {
            tailf:cli-drop-node-name;
            type isis-level-type;
          }
        }
        container wide {
          tailf:cli-compact-syntax;
          tailf:cli-delete-when-empty;
          presence "true";
          uses router-isis-metric-type-grouping;
        }
      }
    }
  }

  grouping router-isis-metric-type-grouping {
    leaf transition {
      type empty;
    }
    leaf level {
      tailf:cli-drop-node-name;
      type isis-level-type;
    }
  }

  grouping router-isis-af-late-grouping {
    leaf adjacency-check {
      type boolean;
    }
    container set-overload-bit {
      tailf:cli-delete-when-empty;
      presence "true";
      choice set-overload-bit-choice {
        container on-startup {
          choice on-startup-choice {
            container time {
              tailf:cli-drop-node-name;
              tailf:cli-compact-syntax;
              tailf:cli-sequence-commands;
              leaf time {
                tailf:cli-drop-node-name;
                type uint32;
              }
              leaf suppress {
                type empty;
              }
              uses set-overload-bit-suppress-grouping;
            }
            container wait-for-bgp {
              presence "true";
              container suppress {
                tailf:cli-compact-syntax;
                tailf:cli-sequence-commands;
                uses set-overload-bit-suppress-grouping;
              }
            }
          }
        }
        container suppress {
          tailf:cli-compact-syntax;
          tailf:cli-sequence-commands;
          uses set-overload-bit-suppress-grouping;
        }
      }
    }
    container spf-interval {
      tailf:cli-compact-syntax;
      choice spf-interval-choice {
        list level-1-2 {
          tailf:cli-drop-node-name;
          tailf:cli-suppress-mode;
          tailf:cli-delete-when-empty;
          tailf:cli-compact-syntax;
          tailf:cli-sequence-commands;
          key "level";
          leaf level {
            type enumeration {
              enum "level-1";
              enum "level-2";
            }
          }
          uses spf-intervals-grouping;
        }
        container intervals {
          tailf:cli-drop-node-name;
          tailf:cli-compact-syntax;
          tailf:cli-sequence-commands;
          uses spf-intervals-grouping;
        }
      }
    }
    container prc-interval {
      tailf:cli-compact-syntax;
      tailf:cli-sequence-commands;
      leaf interval {
        tailf:cli-drop-node-name;
        type uint32;
      }
      leaf initial-wait {
        tailf:cli-drop-node-name;
        type uint32;
      }
      leaf minimum-wait {
        tailf:cli-drop-node-name;
        type uint32;
      }
    }
    choice metric-choice {
      case default-case {
        container metric {
          leaf default {
            tailf:cli-drop-node-name;
            type uint32;
          }
        }
      }
      case level-case {
        container metric-level {
          tailf:cli-drop-node-name;
          list metric {
            tailf:cli-suppress-mode;
            tailf:cli-delete-when-empty;
            tailf:cli-compact-syntax;
            tailf:cli-sequence-commands;
            key "level";
            leaf level {
              type enumeration {
                enum "level-1";
                enum "level-2";
              }
            }
            leaf default {
              tailf:cli-drop-node-name;
              tailf:cli-prefix-key;
              type uint32;
            }
          }
        }
      }
    }
    leaf maximum-paths {
      type uint32;
    }
    container default-information {
      container originate {
        tailf:cli-delete-when-empty;
        presence "true";
        leaf route-map {
          type string;
        }
      }
    }
  }

  grouping router-isis-grouping {
    leaf vrf {
      type string;
    }
    container protocol {
      leaf shutdown {
        type empty;
      }
    }
    leaf max-area-addresses {
      type uint32;
    }
    list net {
      tailf:cli-suppress-mode;
      tailf:cli-delete-when-empty;
      key "tag";
      leaf tag {
        type string;
      }
    }
    leaf is-type {
      type enumeration {
        enum "level-1";
        enum "level-1-2";
        enum "level-2-only";
      }
    }
    container advertise {
      leaf passive-only {
        type empty;
      }
      container link {
        leaf attributes {
          type empty;
        }
      }
    }
    uses router-isis-interface-grouping;
    container area-password {
      tailf:cli-compact-syntax;
      tailf:cli-sequence-commands;
      leaf name {
        tailf:cli-drop-node-name;
        type string;
      }
      uses router-isis-authenticate-snp-grouping;
    }
    container ispf {
      tailf:cli-compact-syntax;
      tailf:cli-sequence-commands;
      leaf level {
        tailf:cli-drop-node-name;
        type enumeration {
          enum "level-1";
          enum "level-1-2";
          enum "level-2";
        }
      }
      leaf number {
        tailf:cli-drop-node-name;
        type uint32;
      }
    }
    container purge-transmit {
      container strict {
        leaf level-1 {
          type empty;
        }
        leaf level-2 {
          type empty;
        }
      }
    }
    uses router-isis-af-early-grouping;
    leaf ignore-attached-bit {
      type empty;
    }
    container fast-flood {
      tailf:cli-delete-when-empty;
      presence "true";
      leaf number {
        tailf:cli-drop-node-name;
        type uint8;
      }
    }
    container ip {
      container route {
        container priority {
          container high {
            leaf tag {
              type uint32;
            }
          }
        }
      }
    }
    container set-attached-bit {
      leaf route-map {
        type string;
      }
    }
    leaf max-lsp-lifetime {
      type uint32;
    }
    leaf lsp-refresh-interval {
      type uint32;
    }
    container lsp-gen-interval {
      choice lsp-gen-interval-choice {
        container intervals {
          tailf:cli-drop-node-name;
          tailf:cli-compact-syntax;
          tailf:cli-sequence-commands;
          uses lsp-gen-interval-grouping;
        }
        container intervals-levels {
          tailf:cli-drop-node-name;
          container intervals-level-1 {
            tailf:cli-drop-node-name;
            tailf:cli-compact-syntax;
            tailf:cli-sequence-commands;
            leaf level-1 {
              type empty;
            }
            uses lsp-gen-interval-grouping;
          }
          container intervals-level-2 {
            tailf:cli-drop-node-name;
            tailf:cli-compact-syntax;
            tailf:cli-sequence-commands;
            leaf level-2 {
              type empty;
            }
            uses lsp-gen-interval-grouping;
          }
        }
      }
    }
    container use {
      leaf external-metrics {
        type empty;
      }
    }
    leaf ignore-lsp-errors {
      type boolean;
    }
    container hostname {
      leaf dynamic {
        type boolean;
      }
    }
    container log-adjacency-changes {
      tailf:cli-delete-when-empty;
      presence "true";
      leaf all {
        type empty;
      }
    }
    container partition {
      leaf avoidance {
        type empty;
      }
    }
    leaf lsp-mtu {
      type uint32;
    }
    container lsp-full {
      container suppress {
        choice lsp-full-choince {
          container external-interlevel-container {
            tailf:cli-drop-node-name;
            tailf:cli-compact-syntax;
            leaf external {
              type empty;
            }
            leaf interlevel {
              type empty;
            }
          }
          leaf none {
            type empty;
          }
        }
      }
    }
    leaf update-queue-depth {
      type uint32;
    }
    container nsf {
      leaf cisco {
        type empty;
      }
      leaf ietf {
        type empty;
      }
      leaf interval {
        type uint16;
      }
      container interface {
        leaf wait {
          type uint8;
        }
      }
    }
    container bfd {
      leaf all-interfaces {
        type empty;
      }
      leaf check-ctrl-plane-failure {
        type empty;
      }
    }
    container distance {
      container distance-ip {
        tailf:cli-drop-node-name;
        tailf:cli-compact-syntax;
        tailf:cli-sequence-commands;
        leaf distance {
          tailf:cli-drop-node-name;
          type uint8;
        }
        leaf ip {
          type empty;
        }
      }
      list distance-network-list {
        tailf:cli-drop-node-name;
        tailf:cli-suppress-mode;
        tailf:cli-delete-when-empty;
        tailf:cli-compact-syntax;
        tailf:cli-sequence-commands {
          tailf:cli-reset-siblings;
        }
        key "ip-address wildcard-mask";
        leaf ip-address {
          type inet:ipv4-address;
        }
        leaf wildcard-mask {
          type inet:ipv4-address;
        }
        leaf distance {
          tailf:cli-drop-node-name;
          tailf:cli-prefix-key;
          type uint8;
        }
        leaf access-list {
          tailf:cli-drop-node-name;
          type std-ip-acl-type;
        }
      }
      container distance-clns {
        tailf:cli-drop-node-name;
        tailf:cli-compact-syntax;
        tailf:cli-sequence-commands;
        leaf distance {
          tailf:cli-drop-node-name;
          type uint8;
        }
        leaf clns {
          type empty;
        }
      }
    }
    container domain-password {
      tailf:cli-compact-syntax;
      tailf:cli-sequence-commands;
      leaf name {
        tailf:cli-drop-node-name;
        type string;
      }
      uses router-isis-authenticate-snp-grouping;
    }
    container hello {
      choice padding-choice {
        container padding-multi-point {
          tailf:cli-drop-node-name;
          container padding {
            leaf multi-point {
              type boolean;
            }
          }
        }
        container padding-point-to-point {
          tailf:cli-drop-node-name;
          container padding {
            leaf point-to-point {
              type boolean;
            }
          }
        }
        leaf padding {
          type boolean;
        }
      }
    }
    container traffic-share {
      container min {
        leaf across-interfaces {
          type empty;
        }
      }
    }
    container microloop {
      container avoidance {
        tailf:cli-delete-when-empty;
        presence "true";
        choice avoidance-choice {
          leaf protected {
            type empty;
          }
          leaf disable {
            type empty;
          }
          leaf segment-routing {
            type empty;
          }
        }
      }
      container avoidance-conf {
        tailf:cli-drop-node-name;
        container avoidance {
          leaf segment-routing {
            type empty;
          }
          leaf rib-update-delay {
            type uint32;
          }
        }
      }
    }
    list affinity-map {
      tailf:cli-suppress-mode;
      tailf:cli-delete-when-empty;
      unique "bit-position";
      key "name";
      leaf name {
        type string;
      }
      leaf bit-position {
        type uint8;
      }
    }
    list flex-algo {
      key "id";
      leaf id {
        type uint8;
      }
      leaf advertise-definition {
        type empty;
      }
      leaf priority {
        type uint8;
      }
      container metric-type {
        leaf delay {
          type empty;
        }
      }
      container affinity {
        tailf:cli-add-mode;
        list attribute-list {
          tailf:cli-drop-node-name;
          key "id";
          leaf id {
            type enumeration {
              enum "exclude-any";
              enum "include-all";
              enum "include-any";
            }
          }
          list name {
            tailf:cli-suppress-mode;
            tailf:cli-delete-when-empty;
            key "name";
            leaf name {
              type string;
            }
          }
        }
      }
    }
    leaf display-route-detail {
      type empty;
    }
    container distribute {
      container link-state {
        tailf:cli-compact-syntax;
        tailf:cli-delete-when-empty;
        presence "true";
        leaf instance-id {
          type uint32;
        }
        leaf level {
          tailf:cli-drop-node-name;
          type enumeration {
            enum "level-1";
            enum "level-2";
          }
        }
        leaf throttle {
          type uint8;
        }
      }
    }
    container ucmp {
      container local {
        tailf:cli-delete-when-empty;
        presence "true";
        leaf prefix-list {
          type string;
        }
      }
    }
    container segment-routing {
      leaf mpls {
        type empty;
      }
      container prefix-sid-map {
        leaf advertise-local {
          type empty;
        }
      }
    }
    container fast-reroute {
      container per-prefix {
        container level-1 {
          choice level-choice {
            leaf route-map {
              type string;
            }
            leaf all {
              type empty;
            }
          }
        }
        container level-2 {
          choice level-choice {
            leaf route-map {
              type string;
            }
            leaf all {
              type empty;
            }
          }
        }
      }
      list tie-break {
        tailf:cli-suppress-mode;
        tailf:cli-delete-when-empty;
        key "level";
        leaf level {
          type enumeration {
            enum "level-1";
            enum "level-2";
          }
        }
        leaf linecard-disjoint {
          type uint8;
        }
        leaf node-protecting {
          type uint8;
        }
        leaf srlg-disjoint {
          type uint8;
        }
      }
      container remote-lfa {
        container level-1 {
          container mpls-ldp {
            tailf:cli-delete-when-empty;
            presence "true";
            leaf maximum-metric {
              type uint32;
            }
          }
        }
        container level-2 {
          container mpls-ldp {
            tailf:cli-delete-when-empty;
            presence "true";
            leaf maximum-metric {
              type uint32;
            }
          }
        }
      }
      list ti-lfa {
        tailf:cli-suppress-mode;
        tailf:cli-delete-when-empty;
        tailf:cli-compact-syntax;
        key "level";
        leaf level {
          type enumeration {
            enum "level-1";
            enum "level-2";
          }
        }
        leaf maximum-metric {
          type uint32;
        }
      }
    }
    container mpls {
      container ldp {
        leaf sync-igp-shortcuts {
          type empty;
        }
        leaf sync {
          type empty;
        }
        container ac-igp-shortcuts {
          tailf:cli-delete-when-empty;
          presence "true";
          leaf level {
            tailf:cli-drop-node-name;
            type enumeration {
              enum "level-1";
              enum "level-2";
            }
          }
        }
        container autoconfig {
          tailf:cli-delete-when-empty;
          presence "true";
          choice level-choice {
            leaf level-1 {
              type empty;
            }
            leaf level-2 {
              type empty;
            }
          }
        }
      }
      container traffic-eng {
        leaf level-1 {
          type empty;
        }
        leaf level-2 {
          type empty;
        }
        leaf multicast-intact {
          type empty;
        }
        container router-id {
          uses interface-name-grouping;
        }
        container scanner {
          tailf:cli-compact-syntax;
          tailf:cli-delete-when-empty;
          presence "true";
          leaf interval {
            type uint8;
          }
          leaf max-flash {
            type uint8;
          }
        }
      }
    }
    uses passive-interface-grouping;
    uses router-distribute-list-grouping;
    container router-id {
      uses interface-name-grouping;
    }
    container redistribute {
      container maximum-prefix {
        tailf:cli-compact-syntax;
        tailf:cli-sequence-commands;
        leaf number {
          tailf:cli-drop-node-name;
          type uint32;
        }
        leaf threshold-value {
          tailf:cli-drop-node-name;
          tailf:cli-break-sequence-commands;
          type uint32;
        }
        leaf warning-only {
          type empty;
        }
        leaf withdraw {
          type empty;
        }
      }
      container connected {
        tailf:cli-compact-syntax;
        tailf:cli-delete-when-empty;
        presence "true";
        uses router-isis-redistribute-grouping;
      }
      container static {
        tailf:cli-compact-syntax;
        tailf:cli-delete-when-empty;
        presence "true";
        container clns {
          tailf:cli-delete-when-empty;
          presence "true";
          leaf route-map {
            type string;
          }
        }
        container ip {
          tailf:cli-compact-syntax;
          tailf:cli-delete-when-empty;
          presence "true";
          uses router-isis-redistribute-grouping;
        }
      }
      container odr {
        tailf:cli-compact-syntax;
        tailf:cli-delete-when-empty;
        presence "true";
        uses router-isis-redistribute-grouping;
      }
      container rip {
        tailf:cli-compact-syntax;
        tailf:cli-delete-when-empty;
        presence "true";
        uses router-isis-redistribute-grouping;
      }
      list bgp {
        tailf:cli-suppress-mode;
        tailf:cli-delete-when-empty;
        tailf:cli-compact-syntax;
        key "as-no";
        leaf as-no {
          tailf:cli-suppress-range;
          type bgp-as-no-type;
        }
        container clns {
          tailf:cli-delete-when-empty;
          presence "true";
          leaf route-map {
            type string;
          }
        }
        uses router-isis-redistribute-grouping;
      }
      list ospf {
        tailf:cli-suppress-mode;
        tailf:cli-delete-when-empty;
        tailf:cli-compact-syntax;
        key "id";
        leaf id {
          tailf:cli-suppress-range;
          type uint16;
        }
        uses redistribute-ospf-match-grouping;
        uses router-isis-redistribute-grouping;
      }
      container isis {
        tailf:cli-compact-syntax;
        list isis-area-list {
          tailf:cli-drop-node-name;
          tailf:cli-suppress-mode;
          tailf:cli-delete-when-empty;
          tailf:cli-compact-syntax;
          key "area-tag";
          leaf area-tag {
            type string;
          }
          leaf ip {
            type empty;
          }
          leaf metric {
            type uint32;
          }
          leaf route-map {
            type string;
          }
        }
        list ip {
          tailf:cli-suppress-mode;
          tailf:cli-delete-when-empty;
          tailf:cli-compact-syntax;
          key "from into";
          leaf from {
            type enumeration {
              enum "level-1";
              enum "level-2";
            }
          }
          leaf into {
            tailf:cli-expose-key-name;
            type enumeration {
              enum "level-1";
              enum "level-2";
            }
          }
          leaf distribute-list {
            type uint8;
          }
          leaf route-map {
            type string;
          }
        }
      }
      list eigrp {
        tailf:cli-suppress-mode;
        tailf:cli-delete-when-empty;
        tailf:cli-compact-syntax;
        key "as-no";
        leaf as-no {
          type eigrp-as-no-type;
        }
        uses router-isis-redistribute-grouping;
      }
      container iso-igrp {
        presence "IGRP for OSI networks";
        tailf:cli-compact-syntax;
        tailf:cli-sequence-commands;
        choice iso-igrp-choice {
          container area-tag-route-map-container {
            tailf:cli-drop-node-name;
            tailf:cli-flatten-container;
            tailf:cli-compact-syntax;
            tailf:cli-sequence-commands;
            leaf area-tag {
              tailf:cli-drop-node-name;
              type string;
            }
            leaf route-map {
              type string;
            }
          }
          leaf route-map {
            type string;
          }
        }
        uses redist-level-grouping;
        leaf metric {
          type uint32;
        }
        leaf metric-type {
          type enumeration {
            enum "external";
            enum "internal";
          }
        }
      }
      container mobile {
        tailf:cli-compact-syntax;
        presence "Mobile routes";
        uses router-isis-redistribute-grouping;
      }
    }
    list summary-address {
      tailf:cli-suppress-mode;
      tailf:cli-delete-when-empty;
      tailf:cli-compact-syntax;
      key "ip mask";
      leaf ip {
        type inet:ipv4-address;
      }
      leaf mask {
        type inet:ipv4-address;
      }
      leaf level {
        tailf:cli-drop-node-name;
        type enumeration {
          enum "level-1";
          enum "level-1-2";
          enum "level-2";
        }
      }
      leaf tag {
        type uint32;
      }
      leaf metric {
        type uint32;
      }
    }
    uses router-isis-af-late-grouping;
    container address-family {
      container ipv6 {
        tailf:cli-add-mode;
        leaf af {
          tailf:cli-drop-node-name;
          tailf:cli-hide-in-submode;
          type enumeration {
            enum "unicast";
          }
        }
        uses router-isis-af-early-grouping;
        container router-id {
          uses interface-name-grouping;
        }
        container advertise {
          leaf passive-only {
            type empty;
          }
        }
        container ipv6 {
          container route {
            container priority {
              container high {
                leaf tag {
                  type uint32;
                }
              }
            }
          }
        }
        container segment-routing {
          container srv6 {
            tailf:cli-add-mode;
            presence "true";
            list locator {
              key "name";
              leaf name {
                type string;
              }
              choice level-choice {
                leaf level-1 {
                  type empty;
                }
                leaf level-2 {
                  type empty;
                }
              }
            }
          }
        }
        container bfd {
          leaf all-interfaces {
            type empty;
          }
        }
        list summary-prefix {
          tailf:cli-suppress-mode;
          tailf:cli-delete-when-empty;
          tailf:cli-compact-syntax;
          key "prefix";
          leaf prefix {
            type ipv6-prefix;
          }
          leaf level {
            tailf:cli-drop-node-name;
            type enumeration {
              enum "level-1";
              enum "level-1-2";
              enum "level-2";
            }
          }
          leaf tag {
            type uint32;
          }
        }
        leaf distance {
          type uint32;
        }
        container multi-topology {
          presence "true";
          leaf transition {
            type empty;
          }
        }
        container redistribute {
          container connected {
            tailf:cli-compact-syntax;
            tailf:cli-delete-when-empty;
            presence "Connected";
            uses router-isis-af-redistribute-grouping;
          }
          container static {
            tailf:cli-compact-syntax;
            tailf:cli-delete-when-empty;
            presence "Static routes";
            uses router-isis-redistribute-grouping;
          }
          container bgp {
            tailf:cli-compact-syntax;
            leaf as-no {
              tailf:cli-drop-node-name;
              type bgp-as-no-type;
            }
            uses router-isis-af-redistribute-grouping;
          }
          list ospf {
            tailf:cli-suppress-mode;
            tailf:cli-delete-when-empty;
            tailf:cli-compact-syntax;
            key "id";
            leaf id {
              tailf:cli-suppress-range;
              type uint16;
            }
            uses redistribute-ospf-match-grouping;
            uses router-isis-af-redistribute-grouping;
          }
          list rip {
            tailf:cli-suppress-mode;
            tailf:cli-delete-when-empty;
            tailf:cli-compact-syntax;
            key "process";
            leaf process {
              type string;
            }
            uses router-isis-af-redistribute-grouping;
          }
          list eigrp {
            tailf:cli-suppress-mode;
            tailf:cli-delete-when-empty;
            tailf:cli-compact-syntax;
            key "as-no";
            leaf as-no {
              type eigrp-as-no-type;
            }
            uses router-isis-af-redistribute-grouping;
          }
          container isis {
            tailf:cli-compact-syntax;
            list isis-list {
              tailf:cli-drop-node-name;
              tailf:cli-suppress-mode;
              tailf:cli-delete-when-empty;
              tailf:cli-compact-syntax;
              key "from into";
              leaf from {
                type enumeration {
                  enum "level-1";
                  enum "level-2";
                }
              }
              leaf into {
                tailf:cli-expose-key-name;
                type enumeration {
                  enum "level-1";
                  enum "level-2";
                }
              }
              leaf distribute-list {
                type string;
              }
              leaf route-map {
                type string;
              }
            }
          }
          container nemo {
            tailf:cli-compact-syntax;
            tailf:cli-delete-when-empty;
            uses router-isis-af-redistribute-grouping;
          }
        }
        uses router-isis-af-late-grouping;
      }
    }
  }

  grouping router-lisp-loc-reach-algorithm-grouping {
    container loc-reach-algorithm {
      leaf lsb-reports {
        type enumeration {
          enum "ignore";
        }
      }
      leaf rloc-probing {
        type empty;
      }
    }
  }

  grouping router-lisp-route-import-grouping {
    list static-list {
      tailf:cli-drop-node-name;
      tailf:cli-suppress-mode;
      tailf:cli-delete-when-empty;
      tailf:cli-compact-syntax;
      tailf:cli-sequence-commands {
        tailf:cli-reset-siblings;
      }
      key "protocol";
      leaf protocol {
        tailf:cli-suppress-range;
        type enumeration {
          enum "connected";
          enum "static";
          enum "rip";
        }
      }
      leaf route-map {
        tailf:cli-optional-in-sequence;
        type string;
      }
      leaf locator-set {
        type string;
      }
    }
    list id-list {
      tailf:cli-drop-node-name;
      tailf:cli-suppress-mode;
      tailf:cli-delete-when-empty;
      tailf:cli-compact-syntax;
      tailf:cli-sequence-commands {
        tailf:cli-reset-siblings;
      }
      key "protocol id";
      leaf protocol {
        tailf:cli-suppress-range;
        type enumeration {
          enum "bgp";
          enum "eigrp";
          enum "isis";
          enum "ospf";
          enum "ospfv3";
          enum "rip";
        }
      }
      leaf id {
        type string;
      }
      leaf route-map {
        tailf:cli-optional-in-sequence;
        type string;
      }
      leaf locator-set {
        type string;
      }
    }
  }

  grouping router-lisp-database-mapping-grouping {
    list database-mapping {
      tailf:cli-suppress-mode;
      tailf:cli-delete-when-empty;
      key "prefix";
      leaf prefix {
        type union {
          type ios:ipv4-prefix;
          type ios:ipv6-prefix;
        }
      }
      leaf auto-discover-rlocs {
        type empty;
      }
      leaf locator-set {
        type string;
      }
    }
    container database-mapping-address {
      tailf:cli-drop-node-name;
      list database-mapping {
        tailf:cli-suppress-mode;
        tailf:cli-delete-when-empty;
        tailf:cli-compact-syntax;
        tailf:cli-sequence-commands {
          tailf:cli-reset-siblings;
        }
        key "prefix rloc-address";
        leaf prefix {
          type union {
            type ios:ipv4-prefix;
            type ios:ipv6-prefix;
          }
        }
        leaf rloc-address {
          type union {
            type inet:ipv4-address;
            type inet:ipv6-address;
          }
        }
        leaf priority {
          type uint8;
        }
        leaf weight {
          type uint8;
        }
      }
    }
    container database-mapping-interface {
      tailf:cli-drop-node-name;
      list database-mapping {
        tailf:cli-suppress-mode;
        tailf:cli-delete-when-empty;
        tailf:cli-compact-syntax;
        tailf:cli-sequence-commands {
          tailf:cli-reset-siblings;
        }
        key "prefix rloc-interface";
        leaf prefix {
          type union {
            type ios:ipv4-prefix;
            type ios:ipv6-prefix;
          }
        }
        leaf af {
          tailf:cli-drop-node-name;
          tailf:cli-prefix-key {
            tailf:cli-before-key "2";
          }
          type enumeration {
            enum "IPv4-interface";
            enum "IPv6-interface";
          }
        }
        leaf rloc-interface {
          type string;
        }
        leaf priority {
          type uint8;
        }
        leaf weight {
          type uint8;
        }
      }
    }
    container database-mapping-conf {
      tailf:cli-drop-node-name;
      container database-mapping {
        container mac {
          leaf locator-set {
            type string;
          }
        }
        container limit {
          leaf dynamic {
            type uint16;
          }
        }
      }
    }
  }

  grouping router-lisp-af4-common-grouping {
    leaf map-request-source {
      type inet:ipv4-address;
    }
    container proxy-itr {
      tailf:cli-compact-syntax;
      tailf:cli-sequence-commands {
        tailf:cli-reset-siblings;
      }
      leaf ipv4-local-locator {
        tailf:cli-drop-node-name;
        tailf:cli-optional-in-sequence;
        type inet:ipv4-address;
      }
      leaf ipv6-local-locator {
        tailf:cli-drop-node-name;
        type inet:ipv6-address;
      }
    }
  }

  grouping router-lisp-af6-common-grouping {
    leaf map-request-source {
      type inet:ipv6-address;
    }
    container proxy-itr {
      tailf:cli-compact-syntax;
      leaf ipv6-local-locator {
        tailf:cli-drop-node-name;
        type inet:ipv6-address;
      }
      leaf ipv4-local-locator {
        tailf:cli-drop-node-name;
        type inet:ipv4-address;
      }
    }
  }

  grouping router-lisp-af-grouping {
    leaf map-resolver {
      type empty;
    }
    container map-resolver-conf {
      tailf:cli-drop-node-name;
      container map-resolver {
        container map-request {
          container validate {
            container source {
              tailf:cli-compact-syntax;
              leaf registered {
                tailf:cli-optional-in-sequence;
                type empty;
              }
              container list {
                choice list-choice {
                  leaf ipv4 {
                    type string;
                  }
                  leaf ipv6 {
                    type string;
                  }
                }
              }
            }
          }
        }
      }
    }
    container itr {
      list map-resolver {
        tailf:cli-suppress-mode;
        tailf:cli-delete-when-empty;
        key "address";
        leaf address {
          type union {
            type inet:ipv4-address;
            type inet:ipv6-address;
          }
        }
      }
      leaf enable {
        tailf:cli-drop-node-name;
        type empty;
      }
    }
    container etr {
      list map-server {
        tailf:cli-suppress-mode;
        tailf:cli-delete-when-empty;
        key "address";
        leaf address {
          type union {
            type inet:ipv4-address;
            type inet:ipv6-address;
          }
        }
        container key {
          tailf:cli-compact-syntax;
          tailf:cli-sequence-commands;
          uses crypto-key-grouping {
            refine "secret";
          }
          leaf hash-function {
            type enumeration {
              enum "sha1";
              enum "sha2";
            }
          }
        }
        leaf proxy-reply {
          type empty;
        }
      }
      container accept-map-request-mapping {
        tailf:cli-delete-when-empty;
        presence "true";
        leaf verify {
          type empty;
        }
      }
      leaf enable {
        tailf:cli-drop-node-name;
        type empty;
      }
    }
    leaf map-cache-limit {
      type uint32;
    }
    container map-cache-persistent {
      presence "true";
      leaf interval {
        type uint16;
      }
    }
    container route-import {
      container map-cache {
        container maximum-prefix {
          tailf:cli-compact-syntax;
          tailf:cli-sequence-commands {
            tailf:cli-reset-siblings;
          }
          leaf value {
            tailf:cli-drop-node-name;
            type uint16;
          }
          leaf warning-only {
            type empty;
          }
        }
        uses router-lisp-route-import-grouping;
      }
      container database {
        uses router-lisp-route-import-grouping;
      }
    }
    container route-export {
      leaf site-registration {
        type empty;
      }
      leaf site-registrations {
        type empty;
      }
    }
    container distance {
      leaf site-registrations {
        type uint8;
      }
    }
    container map-cache {
      list prefix-list {
        tailf:cli-drop-node-name;
        tailf:cli-suppress-mode;
        tailf:cli-delete-when-empty;
        key "prefix";
        leaf prefix {
          type union {
            type ios:ipv4-prefix;
            type ios:ipv6-prefix;
          }
        }
        choice map-cache-choice {
          leaf map-request {
            type empty;
          }
          leaf native-forward {
            type empty;
          }
          leaf drop {
            type empty;
          }
        }
      }
      leaf site-registration {
        type empty;
      }
    }
    leaf proxy-etr {
      type empty;
    }
    list use-petr {
      tailf:cli-suppress-mode;
      tailf:cli-delete-when-empty;
      tailf:cli-compact-syntax;
      tailf:cli-sequence-commands;
      key "address";
      leaf address {
        type union {
          type inet:ipv4-address;
          type inet:ipv6-address;
        }
      }
      leaf priority {
        type uint8;
      }
      leaf weight {
        type uint8;
      }
    }
    leaf map-server {
      type empty;
    }
    container locator {
      container reachability {
        leaf exclude-default {
          type empty;
        }
      }
    }
  }

  grouping router-lisp-eid-table-grouping {
    leaf instance-id {
      tailf:cli-hide-in-submode;
      type uint32;
    }
    list map-cache {
      tailf:cli-suppress-mode;
      tailf:cli-delete-when-empty;
      tailf:cli-compact-syntax;
      tailf:cli-sequence-commands;
      key "prefix";
      leaf prefix {
        type union {
          type ios:ipv4-prefix;
          type ios:ipv6-prefix;
        }
      }
      choice map-cache-choice {
        case locator {
          leaf locator {
            tailf:cli-drop-node-name;
            type union {
              type inet:ipv4-address;
              type inet:ipv6-address;
            }
          }
          leaf priority {
            type uint8;
          }
          leaf weight {
            type uint8;
          }
        }
        leaf map-request {
          type empty;
        }
        leaf native-forward {
          type empty;
        }
        leaf drop {
          type empty;
        }
      }
    }
    uses router-lisp-database-mapping-grouping;
    uses router-lisp-loc-reach-algorithm-grouping;
    container ipv4 {
      uses router-lisp-af-grouping;
      uses router-lisp-af4-common-grouping;
    }
    container ipv6 {
      uses router-lisp-af-grouping;
      uses router-lisp-af6-common-grouping;
    }
  }

  grouping router-lisp-service-af-grouping {
    container eid-table {
      leaf default {
        type empty;
      }
      leaf vrf {
        type string;
      }
      leaf vlan {
        type uint16;
      }
    }
    uses router-lisp-database-mapping-grouping;
    leaf sgt {
      type empty;
    }
    leaf encapsulation {
      type enumeration {
        enum "lisp";
        enum "vxlan";
      }
    }
  }

  grouping router-lisp-service-grouping {
    uses router-lisp-loc-reach-algorithm-grouping;
    leaf disable-ttl-propagate {
      type empty;
    }
    container service {
      container ipv4 {
        tailf:cli-add-mode;
        presence "true";
        uses router-lisp-service-af-grouping;
        uses router-lisp-af-grouping;
        uses router-lisp-af4-common-grouping;
      }
      container ipv6 {
        tailf:cli-add-mode;
        presence "true";
        uses router-lisp-service-af-grouping;
        uses router-lisp-af-grouping;
        uses router-lisp-af6-common-grouping;
      }
      container ethernet {
        tailf:cli-add-mode;
        presence "true";
        uses router-lisp-service-af-grouping;
        uses router-lisp-af-grouping;
      }
    }
  }

  grouping router-lisp-grouping {
    container syslog {
      leaf verbose {
        type empty;
      }
      container session {
        leaf changes {
          type empty;
        }
      }
    }
    leaf site-id {
      type uint32;
    }
    container etr {
      container map-server {
        container source-address {
          uses interface-name-grouping;
        }
      }
    }
    container locator-table {
      choice locator-table-choice {
        leaf default {
          type empty;
        }
        leaf vrf {
          type string;
        }
      }
    }
    list locator-set {
      key "name";
      leaf name {
        type string;
      }
      list IPv4-address {
        tailf:cli-drop-node-name;
        tailf:cli-suppress-mode;
        tailf:cli-delete-when-empty;
        tailf:cli-compact-syntax;
        tailf:cli-sequence-commands;
        key "name";
        leaf name {
          type inet:ipv4-address;
        }
        leaf priority {
          type uint8;
        }
        leaf weight {
          type uint8;
        }
      }
      list IPv6-address {
        tailf:cli-drop-node-name;
        tailf:cli-suppress-mode;
        tailf:cli-delete-when-empty;
        tailf:cli-compact-syntax;
        tailf:cli-sequence-commands;
        key "name";
        leaf name {
          type inet:ipv6-address;
        }
        leaf priority {
          type uint8;
        }
        leaf weight {
          type uint8;
        }
      }
      list IPv4-interface {
        tailf:cli-suppress-mode;
        tailf:cli-delete-when-empty;
        tailf:cli-compact-syntax;
        tailf:cli-sequence-commands;
        key "name";
        leaf name {
          type string;
        }
        leaf priority {
          type uint8;
        }
        leaf weight {
          type uint8;
        }
      }
      list IPv6-interface {
        tailf:cli-suppress-mode;
        tailf:cli-delete-when-empty;
        tailf:cli-compact-syntax;
        tailf:cli-sequence-commands;
        key "name";
        leaf name {
          type string;
        }
        leaf priority {
          type uint8;
        }
        leaf weight {
          type uint8;
        }
      }
      leaf auto-discover-rlocs {
        type empty;
      }
    }
    container locator {
      leaf default-set {
        type string;
      }
    }
    uses router-lisp-service-grouping {
      refine "service/ipv4";
      refine "service/ipv6";
    }
    container map-request {
      leaf itr-rlocs {
        type string;
      }
    }
    container eid-table {
      list default-vrf {
        tailf:cli-drop-node-name;
        key "name";
        leaf name {
          type enumeration {
            enum "default";
          }
        }
        uses router-lisp-eid-table-grouping;
      }
      list vrf {
        key "name";
        leaf name {
          tailf:cli-suppress-range;
          type string;
        }
        uses router-lisp-eid-table-grouping;
      }
    }
    list site {
      key "name";
      leaf name {
        tailf:cli-suppress-range;
        type string;
      }
      leaf description {
        tailf:cli-multi-value;
        type string;
      }
      container authentication-key {
        tailf:cli-compact-syntax;
        tailf:cli-sequence-commands;
        uses crypto-key-grouping {
          refine "secret";
        }
      }
      container eid-record {
        list instance-list {
          tailf:cli-drop-node-name;
          tailf:cli-suppress-mode;
          tailf:cli-delete-when-empty;
          tailf:cli-compact-syntax;
          key "instance-id prefix";
          leaf instance-id {
            tailf:cli-expose-key-name;
            type uint32;
          }
          leaf prefix {
            type union {
              type ios:ipv4-prefix;
              type ios:ipv6-prefix;
              type enumeration {
                enum "any-mac";
              }
            }
          }
          leaf route-tag {
            type uint32;
          }
          leaf accept-more-specifics {
            type empty;
          }
        }
      }
      list eid-prefix {
        tailf:cli-suppress-mode;
        tailf:cli-delete-when-empty;
        tailf:cli-compact-syntax;
        key "prefix";
        leaf prefix {
          type union {
            type ios:ipv4-prefix;
            type ios:ipv6-prefix;
          }
        }
        leaf route-tag {
          type uint32;
        }
        leaf accept-more-specifics {
          type empty;
        }
      }
      container eid-prefix-instance {
        tailf:cli-drop-node-name;
        list eid-prefix {
          tailf:cli-suppress-mode;
          tailf:cli-delete-when-empty;
          tailf:cli-compact-syntax;
          key "instance-id prefix";
          leaf instance-id {
            tailf:cli-expose-key-name;
            type uint32;
          }
          leaf prefix {
            type union {
              type ios:ipv4-prefix;
              type ios:ipv6-prefix;
            }
          }
          leaf route-tag {
            type uint32;
          }
          leaf accept-more-specifics {
            type empty;
          }
        }
      }
      list allowed-locator {
        tailf:cli-suppress-mode;
        tailf:cli-delete-when-empty;
        key "rloc";
        leaf rloc {
          type union {
            type inet:ipv4-address;
            type inet:ipv6-address;
          }
        }
      }
    }
    container ipv4 {
      uses router-lisp-af-grouping {
        refine "map-cache-persistent";
      }
      uses router-lisp-af4-common-grouping;
    }
    container ipv6 {
      uses router-lisp-af-grouping {
        refine "map-cache-persistent";
      }
      uses router-lisp-af6-common-grouping;
    }
    list instance-id {
      key "id";
      leaf id {
        tailf:cli-suppress-range;
        type uint32;
      }
      container remote-rloc-probe {
        leaf on-route-change {
          type boolean;
        }
        leaf on-membership-change {
          type boolean;
        }
      }
      list dynamic-eid {
        key "name";
        leaf name {
          type string;
        }
        uses router-lisp-database-mapping-grouping;
      }
      uses router-lisp-service-grouping;
    }
    container map-server {
      container session {
        leaf passive-open {
          type string;
        }
      }
    }
    container encapsulation {
      leaf vxlan {
        type empty;
      }
    }
  }

  grouping ip-nat-outside-source-grouping {
    leaf redundancy {
      tailf:cli-break-sequence-commands;
      type uint8;
    }
    leaf mapping-id {
      type uint32;
    }
    leaf match-in-vrf {
      type empty;
    }
    leaf overload {
      type empty;
    }
    leaf add-route {
      type empty;
    }
    leaf no-payload {
      type empty;
    }
  }

  grouping ip-nat-source-static-grouping {
    leaf route-map {
      tailf:cli-break-sequence-commands;
      type string;
    }
    leaf redundancy {
      type union {
        type uint8;
        type string;
      }
    }
    leaf mapping-id {
      type uint32;
    }
    leaf extendable {
      type empty;
    }
    leaf no-alias {
      type empty;
    }
    leaf no-payload {
      type empty;
    }
    leaf add-route {
      type empty;
    }
    leaf reversible {
      type empty;
    }
    leaf match-in-vrf {
      type empty;
    }
    leaf forced {
      type empty;
    }
    leaf overload {
      type empty;
    }
  }

  grouping ip-nat-inside-options-grouping {
    leaf no-payload {
      tailf:cli-break-sequence-commands;
      type empty;
    }
    leaf reversible {
      type empty;
    }
    leaf overload {
      type empty;
    }
    leaf oer {
      type empty;
    }
  }

  grouping ip-nat-inside-grouping {
    leaf pool {
      tailf:cli-optional-in-sequence;
      type string;
    }
    leaf redundancy {
      tailf:cli-optional-in-sequence;
      type uint8;
    }
    leaf mapping-id {
      tailf:cli-optional-in-sequence;
      type uint32;
    }
    leaf interface {
      tailf:cli-optional-in-sequence;
      type string;
    }
  }

  grouping ip-nat-inside-vrf-grouping {
    leaf pool {
      tailf:cli-prefix-key {
        tailf:cli-before-key "2";
      }
      tailf:cli-optional-in-sequence;
      type string;
    }
    leaf redundancy {
      tailf:cli-prefix-key {
        tailf:cli-before-key "2";
      }
      tailf:cli-optional-in-sequence;
      type uint8;
    }
    leaf mapping-id {
      tailf:cli-prefix-key {
        tailf:cli-before-key "2";
      }
      tailf:cli-optional-in-sequence;
      type uint32;
    }
    leaf interface {
      tailf:cli-prefix-key {
        tailf:cli-before-key "2";
      }
      tailf:cli-optional-in-sequence;
      type string;
    }
    leaf vrf {
      tailf:cli-expose-key-name;
      type string;
    }
    leaf match-in-vrf {
      tailf:cli-optional-in-sequence;
      type empty;
    }
  }

  grouping mobile-ip-spi-grouping {
    choice spi-type-choice {
      leaf hex {
        tailf:cli-drop-node-name;
        type string;
      }
      leaf decimal {
        type uint32;
      }
    }
  }

  grouping xconnect-if-grouping {
    choice xconnect-choice {
      container xconnect {
        tailf:cli-add-mode;
        tailf:cli-compact-syntax;
        tailf:cli-sequence-commands;
        tailf:cli-delete-when-empty;
        presence "true";
        leaf address {
          tailf:cli-drop-node-name;
          tailf:cli-hide-in-submode;
          type inet:ipv4-address;
        }
        leaf vcid {
          tailf:cli-drop-node-name;
          tailf:cli-hide-in-submode;
          type uint32;
        }
        leaf encapsulation {
          tailf:cli-hide-in-submode;
          tailf:cli-optional-in-sequence;
          type enumeration {
            enum "mpls";
            enum "l2tpv3";
          }
        }
        leaf manual {
          tailf:cli-optional-in-sequence;
          tailf:cli-hide-in-submode;
          type empty;
        }
        leaf pw-class {
          tailf:cli-optional-in-sequence;
          tailf:cli-hide-in-submode;
          type string;
        }
        leaf sequencing {
          tailf:cli-hide-in-submode;
          type enumeration {
            enum "both";
            enum "receive";
            enum "transmit";
          }
        }
        container backup {
          tailf:cli-break-sequence-commands;
          container peer {
            tailf:cli-compact-syntax;
            tailf:cli-sequence-commands {
              tailf:cli-reset-siblings;
            }
            leaf peer-router-ip-addr {
              tailf:cli-drop-node-name;
              type inet:ipv4-address;
            }
            leaf vcid {
              tailf:cli-drop-node-name;
              type uint32;
            }
            leaf pw-class {
              tailf:cli-optional-in-sequence;
              type string;
            }
            leaf priority {
              type uint8;
            }
          }
          container delay {
            tailf:cli-compact-syntax;
            tailf:cli-sequence-commands;
            leaf enable-delay {
              tailf:cli-drop-node-name;
              type uint8;
            }
            leaf disable-delay {
              tailf:cli-drop-node-name;
              type union {
                type uint8;
                type enumeration {
                  enum "never";
                }
              }
            }
          }
        }
        container mpls {
          container label {
            tailf:cli-compact-syntax;
            tailf:cli-sequence-commands;
            leaf local {
              tailf:cli-drop-node-name;
              type uint32;
            }
            leaf remote {
              tailf:cli-drop-node-name;
              type uint32;
            }
          }
          leaf control-word {
            type empty;
          }
        }
        leaf mtu {
          type uint16;
        }
        container remote {
          container link {
            container failure {
              leaf notification {
                type boolean;
              }
            }
          }
        }
        container l2tp {
          container id {
            tailf:cli-compact-syntax;
            tailf:cli-sequence-commands;
            leaf local {
              tailf:cli-drop-node-name;
              type uint32;
            }
            leaf remote {
              tailf:cli-drop-node-name;
              type uint32;
            }
          }
          container cookie {
            container local {
              tailf:cli-compact-syntax;
              tailf:cli-sequence-commands;
              leaf cookie {
                tailf:cli-drop-node-name;
                type enumeration {
                  enum "4";
                  enum "8";
                }
              }
              leaf low-value {
                tailf:cli-drop-node-name;
                type uint32;
              }
            }
            container remote {
              tailf:cli-compact-syntax;
              tailf:cli-sequence-commands;
              leaf cookie {
                tailf:cli-drop-node-name;
                type enumeration {
                  enum "4";
                  enum "8";
                }
              }
              leaf low-value {
                tailf:cli-drop-node-name;
                type uint32;
              }
            }
          }
          leaf hello {
            type string;
          }
        }
      }
      container xconnect-vfi {
        tailf:cli-drop-node-name;
        container xconnect {
          leaf vfi {
            type string;
          }
        }
      }
    }
  }

  grouping xconnect-grouping {
    container xconnect {
      tailf:cli-add-mode;
      tailf:cli-compact-syntax;
      tailf:cli-sequence-commands;
      tailf:cli-delete-when-empty;
      presence "true";
      leaf address {
        tailf:cli-drop-node-name;
        tailf:cli-hide-in-submode;
        type inet:ipv4-address;
      }
      leaf vcid {
        tailf:cli-drop-node-name;
        tailf:cli-hide-in-submode;
        type uint32;
      }
      leaf encapsulation {
        tailf:cli-hide-in-submode;
        tailf:cli-optional-in-sequence;
        type enumeration {
          enum "mpls";
          enum "l2tpv3";
        }
      }
      leaf manual {
        tailf:cli-optional-in-sequence;
        tailf:cli-hide-in-submode;
        type empty;
      }
      leaf pw-class {
        tailf:cli-optional-in-sequence;
        tailf:cli-hide-in-submode;
        type string;
      }
      leaf sequencing {
        tailf:cli-hide-in-submode;
        type enumeration {
          enum "both";
          enum "receive";
          enum "transmit";
        }
      }
      container backup {
        tailf:cli-break-sequence-commands;
        container peer {
          tailf:cli-compact-syntax;
          tailf:cli-sequence-commands {
            tailf:cli-reset-siblings;
          }
          leaf peer-router-ip-addr {
            tailf:cli-drop-node-name;
            type inet:ipv4-address;
          }
          leaf vcid {
            tailf:cli-drop-node-name;
            type uint32;
          }
          leaf pw-class {
            tailf:cli-optional-in-sequence;
            type string;
          }
          leaf priority {
            type uint8;
          }
        }
        container delay {
          tailf:cli-compact-syntax;
          tailf:cli-sequence-commands;
          leaf enable-delay {
            tailf:cli-drop-node-name;
            type uint8;
          }
          leaf disable-delay {
            tailf:cli-drop-node-name;
            type union {
              type uint8;
              type enumeration {
                enum "never";
              }
            }
          }
        }
      }
      container udp {
        container port {
          tailf:cli-compact-syntax;
          tailf:cli-sequence-commands {
            tailf:cli-reset-siblings;
          }
          leaf local {
            type uint16;
          }
          leaf remote {
            type uint16;
          }
        }
      }
    }
  }

  grouping ip-pim-grouping {
    container mpls {
      container source {
        uses interface-name-grouping;
      }
    }
    container ssm {
      choice ip-pim-ssm-choice {
        leaf default {
          type empty;
        }
        leaf range {
          type union {
            type uint16;
            type string;
          }
        }
      }
    }
    leaf register-rate-limit {
      type uint32;
    }
    container register-source {
      uses interface-name-grouping;
    }
    container accept-rp {
      list list {
        tailf:cli-drop-node-name;
        tailf:cli-suppress-mode;
        tailf:cli-delete-when-empty;
        key "address";
        leaf address {
          type inet:ipv4-address;
        }
        leaf access-list {
          tailf:cli-drop-node-name;
          type std-acl-type;
        }
      }
      container auto-rp {
        tailf:cli-delete-when-empty;
        presence "true";
        leaf acl {
          tailf:cli-drop-node-name;
          type std-acl-type;
        }
      }
    }
    container accept-register {
      leaf list {
        type ext-acl-type;
      }
    }
    leaf snooping {
      type empty;
    }
    leaf bidir-enable {
      type empty;
    }
    list bsr-candidate {
      tailf:cli-suppress-mode;
      tailf:cli-delete-when-empty;
      tailf:cli-compact-syntax;
      tailf:cli-sequence-commands;
      key "name";
      leaf name {
        type string;
      }
      leaf hash-mask-length {
        tailf:cli-drop-node-name;
        type uint8;
      }
      leaf priority {
        tailf:cli-drop-node-name;
        type uint8;
      }
      leaf accept-rp-candidate {
        type exp-ip-acl-type;
      }
    }
    container send-rp-announce {
      tailf:cli-compact-syntax;
      container interface {
        tailf:cli-drop-node-name;
        tailf:cli-flatten-container;
        tailf:cli-compact-syntax;
        uses interface-name-grouping;
      }
      leaf scope {
        type uint8;
      }
      leaf group-list {
        type union {
          type uint16;
          type string;
        }
      }
      leaf interval {
        type uint16;
      }
    }
    container send-rp-discovery {
      tailf:cli-compact-syntax;
      container interface {
        tailf:cli-drop-node-name;
        tailf:cli-flatten-container;
        tailf:cli-compact-syntax;
        uses interface-name-grouping;
      }
      container scope {
        tailf:cli-flatten-container;
        tailf:cli-compact-syntax;
        tailf:cli-sequence-commands {
          tailf:cli-reset-siblings;
        }
        leaf ttl {
          tailf:cli-drop-node-name;
          type uint8;
        }
        leaf interval {
          type uint16;
        }
      }
    }
    list rp-address {
      tailf:cli-suppress-mode;
      tailf:cli-delete-when-empty;
      tailf:cli-compact-syntax;
      tailf:cli-sequence-commands {
        tailf:cli-reset-siblings;
      }
      key "address";
      leaf address {
        type inet:ipv4-address;
      }
      leaf access-list {
        tailf:cli-drop-node-name;
        tailf:cli-optional-in-sequence;
        type std-acl-type;
      }
      leaf override {
        type empty;
      }
    }
    list rp-candidate {
      tailf:cli-suppress-mode;
      tailf:cli-delete-when-empty;
      tailf:cli-compact-syntax;
      key "name";
      leaf name {
        type string;
      }
      leaf bidir {
        type empty;
      }
      leaf group-list {
        type union {
          type uint8;
          type string;
        }
      }
      leaf interval {
        type uint16;
      }
      leaf priority {
        type uint8;
      }
    }
    container spt-threshold {
      leaf value {
        tailf:cli-drop-node-name;
        type union {
          type enumeration {
            enum "infinity";
          }
          type uint32;
        }
      }
      list group-list {
        tailf:cli-drop-node-name;
        tailf:cli-suppress-mode;
        tailf:cli-delete-when-empty;
        tailf:cli-compact-syntax;
        tailf:cli-sequence-commands;
        key "group-list";
        leaf value {
          tailf:cli-drop-node-name;
          tailf:cli-prefix-key;
          type union {
            type enumeration {
              enum "infinity";
            }
            type uint32;
          }
        }
        leaf group-list {
          tailf:cli-expose-key-name;
          type std-acl-type;
        }
      }
    }
    choice autorp-choice {
      leaf autorp {
        type boolean;
      }
      container conf {
        tailf:cli-drop-node-name;
        container autorp {
          leaf listener {
            type empty;
          }
        }
      }
    }
    leaf dm-fallback {
      type empty;
    }
    leaf v1-rp-reachability {
      type boolean;
    }
  }

  grouping event-manager-applet-event-grouping {
    container none {
      tailf:cli-delete-when-empty;
      tailf:cli-compact-syntax;
      presence "true";
      leaf default {
        type uint32;
      }
      leaf maxrun {
        type uint32;
      }
      leaf sync {
        type enumeration {
          enum "no";
          enum "yes";
        }
      }
    }
    container snmp-notification {
      tailf:cli-compact-syntax;
      leaf oid {
        type string;
      }
      leaf oid-val {
        type string;
      }
      leaf op {
        type operator-type;
      }
      leaf src-ip-address {
        type union {
          type inet:ipv4-address;
          type inet:ipv6-address;
        }
      }
      leaf dest-ip-address {
        type union {
          type inet:ipv4-address;
          type inet:ipv6-address;
        }
      }
    }
    container syslog {
      tailf:cli-compact-syntax;
      tailf:cli-sequence-commands {
        tailf:cli-reset-siblings;
      }
      leaf serverity {
        tailf:cli-drop-node-name;
        tailf:cli-optional-in-sequence;
        type enumeration {
          enum "severity-debugging";
          enum "severity-notification";
          enum "severity-minor";
          enum "severity-normal";
          enum "severity-warning";
          enum "severity-major";
          enum "severity-fatal";
          enum "severity-critical";
        }
      }
      leaf pattern {
        tailf:cli-optional-in-sequence;
        type string;
      }
      leaf facility {
        tailf:cli-optional-in-sequence;
        type string;
      }
      leaf period {
        tailf:cli-optional-in-sequence;
        type uint32;
      }
      leaf maxrun {
        type uint32;
      }
    }
    container cli {
      tailf:cli-compact-syntax;
      container pattern {
        tailf:cli-compact-syntax;
        tailf:cli-sequence-commands {
          tailf:cli-reset-siblings;
        }
        leaf regular-expression {
          tailf:cli-drop-node-name;
          type string;
        }
        leaf sync {
          tailf:cli-optional-in-sequence;
          type enumeration {
            enum "no";
            enum "yes";
          }
        }
        leaf skip {
          type enumeration {
            enum "no";
            enum "yes";
          }
        }
      }
    }
    container track {
      tailf:cli-compact-syntax;
      tailf:cli-sequence-commands;
      leaf object-number {
        tailf:cli-drop-node-name;
        type uint16;
      }
      leaf state {
        tailf:cli-optional-in-sequence;
        type enumeration {
          enum "any";
          enum "down";
          enum "up";
        }
      }
      leaf maxrun {
        type uint32;
      }
    }
    container neighbor-discovery {
      tailf:cli-compact-syntax;
      container interface {
        tailf:cli-flatten-container;
        leaf regexp {
          type string;
        }
      }
      leaf cdp {
        type enumeration {
          enum "add";
          enum "all";
          enum "delete";
          enum "update";
        }
      }
    }
    container timer {
      tailf:cli-compact-syntax;
      leaf trigger {
        tailf:cli-drop-node-name;
        type enumeration {
          enum "absolute";
          enum "countdown";
          enum "watchdog";
          enum "cron";
        }
      }
      leaf name {
        type string;
      }
      leaf cron-entry {
        type string;
      }
      leaf time {
        type uint32;
      }
      leaf maxrun {
        type uint32;
      }
      leaf ratelimit {
        type uint32;
      }
    }
    container snmp {
      tailf:cli-compact-syntax;
      tailf:cli-sequence-commands {
        tailf:cli-reset-siblings;
      }
      leaf oid {
        type string;
      }
      leaf get-type {
        tailf:cli-break-sequence-commands;
        type enumeration {
          enum "exact";
          enum "next";
        }
      }
      leaf entry-op {
        type operator-type;
      }
      leaf entry-val {
        type string;
      }
      leaf exit-time {
        type uint32;
      }
      leaf exit-op {
        type operator-type;
      }
      leaf exit-val {
        type string;
      }
      leaf poll-interval {
        type uint32;
      }
      leaf maxrun {
        type uint32;
      }
    }
    container ipsla {
      tailf:cli-compact-syntax;
      leaf operation-id {
        type uint32;
      }
      leaf reaction-type {
        type string;
      }
      leaf maxrun {
        type uint32;
      }
    }
    container config {
      tailf:cli-compact-syntax;
      tailf:cli-sequence-commands {
        tailf:cli-reset-siblings;
      }
      leaf maxrun {
        tailf:cli-optional-in-sequence;
        type uint32;
      }
      leaf ratelimit {
        type uint32;
      }
    }
  }

  grouping route-target-grouping {
    list export {
      tailf:cli-suppress-mode;
      tailf:cli-delete-when-empty;
      key "asn-ip";
      leaf asn-ip {
        type asn-ip-type;
      }
    }
    list import {
      tailf:cli-suppress-mode;
      tailf:cli-delete-when-empty;
      key "asn-ip";
      leaf asn-ip {
        type asn-ip-type;
      }
    }
  }

  grouping route-target-stitching-grouping {
    container stitching {
      tailf:cli-drop-node-name;
      list export {
        tailf:cli-suppress-mode;
        tailf:cli-delete-when-empty;
        key "asn-ip";
        leaf asn-ip {
          type asn-ip-type;
        }
        leaf stitching {
          type empty;
        }
      }
      list import {
        tailf:cli-suppress-mode;
        tailf:cli-delete-when-empty;
        key "asn-ip";
        leaf asn-ip {
          type asn-ip-type;
        }
        leaf stitching {
          type empty;
        }
      }
    }
  }

  grouping vrf-definition-af-grouping {
    container import {
      container ipv4 {
        container unicast {
          leaf map {
            type string;
          }
        }
      }
      leaf map {
        type string;
      }
    }
    container export {
      container ipv4 {
        container unicast {
          leaf map {
            type string;
          }
        }
      }
      leaf map {
        type string;
      }
    }
    container route-target {
      uses route-target-grouping;
      uses route-target-stitching-grouping;
    }
    container maximum {
      container routes {
        tailf:cli-compact-syntax;
        tailf:cli-sequence-commands {
          tailf:cli-reset-siblings;
        }
        leaf limit {
          tailf:cli-drop-node-name;
          type uint32;
        }
        choice action {
          case a {
            leaf warning-only {
              type empty;
            }
          }
          case b {
            leaf warn-threshold {
              tailf:cli-drop-node-name;
              type uint8;
            }
            leaf reinstall {
              type uint8;
            }
          }
        }
      }
    }
    container bgp {
      container next-hop {
        leaf Loopback {
          tailf:cli-allow-join-with-value;
          type uint32;
        }
      }
    }
    uses snmp-context-grouping;
    container mdt {
      container auto-discovery {
        container mldp {
          tailf:cli-compact-syntax;
          tailf:cli-sequence-commands {
            tailf:cli-reset-siblings;
          }
          presence "true";
          leaf inter-as {
            tailf:cli-optional-in-sequence;
            type empty;
          }
          leaf pim-tlv-announce {
            tailf:cli-optional-in-sequence;
            type empty;
          }
          leaf mdt-hello-enable {
            type empty;
          }
        }
      }
      container strict-rpf {
        leaf interface {
          type empty;
        }
      }
      container partitioned {
        container mldp {
          leaf p2mp {
            type empty;
          }
        }
      }
      container default {
        leaf address {
          tailf:cli-drop-node-name;
          type inet:ipv4-address;
        }
        container mpls {
          list mldp {
            tailf:cli-suppress-mode;
            tailf:cli-delete-when-empty;
            key "address";
            leaf address {
              type inet:ipv4-address;
            }
          }
        }
      }
      container data {
        list multicast {
          tailf:cli-drop-node-name;
          tailf:cli-suppress-mode;
          tailf:cli-delete-when-empty;
          key "address wildcard";
          leaf address {
            type inet:ipv4-address;
          }
          leaf wildcard {
            type inet:ipv4-address;
          }
        }
        leaf list {
          type ext-acl-type;
        }
        container mpls {
          list mldp {
            tailf:cli-suppress-mode;
            tailf:cli-delete-when-empty;
            tailf:cli-compact-syntax;
            tailf:cli-sequence-commands {
              tailf:cli-reset-siblings;
            }
            key "id";
            leaf id {
              type uint16;
            }
            leaf list {
              tailf:cli-optional-in-sequence;
              type ext-acl-type;
            }
            leaf scope {
              tailf:cli-optional-in-sequence;
              type uint8;
            }
            leaf immediate-switch {
              type empty;
            }
          }
        }
        leaf threshold {
          type uint32;
        }
      }
      container overlay {
        container use-bgp {
          tailf:cli-delete-when-empty;
          presence "true";
          leaf spt-only {
            type empty;
          }
        }
      }
      leaf log-reuse {
        type empty;
      }
      leaf-list preference {
        tailf:cli-flat-list-syntax;
        type enumeration {
          enum "mldp";
          enum "pim";
        }
      }
    }
  }

  grouping snmp-server-host-grouping {
    leaf message-type {
      type enumeration {
        enum "informs";
        enum "traps";
      }
    }
    container version {
      tailf:cli-optional-in-sequence;
      tailf:cli-flatten-container;
      tailf:cli-compact-syntax;
      leaf version {
        tailf:cli-drop-node-name;
        type enumeration {
          enum "1";
          enum "2c";
          enum "3";
        }
      }
      leaf security-level {
        tailf:cli-drop-node-name;
        type enumeration {
          enum "auth";
          enum "noauth";
          enum "priv";
        }
      }
    }
    leaf community-string {
      tailf:cli-drop-node-name;
      type string;
    }
    leaf udp-port {
      tailf:cli-optional-in-sequence;
      type uint16;
    }
    leaf-list allowed-traps {
      tailf:cli-drop-node-name;
      tailf:cli-flat-list-syntax;
      type snmp-traps-type;
    }
  }

  grouping snmp-server-host-new-grouping {
    leaf message-type {
      type enumeration {
        enum "informs";
        enum "traps";
      }
    }
    leaf version {
      tailf:cli-expose-key-name;
      type enumeration {
        enum "1";
        enum "2c";
        enum "3";
      }
    }
    leaf security-level {
      tailf:cli-drop-node-name;
      tailf:cli-optional-in-sequence;
      tailf:cli-prefix-key {
        tailf:cli-before-key "4";
      }
      type enumeration {
        enum "auth";
        enum "noauth";
        enum "priv";
      }
    }
    leaf community-string {
      type string;
    }
    leaf udp-port {
      tailf:cli-optional-in-sequence;
      type uint16;
    }
    leaf-list allowed-traps {
      tailf:cli-drop-node-name;
      tailf:cli-flat-list-syntax;
      type snmp-traps-type;
    }
  }

  grouping snmp-server-group-grouping {
    leaf match {
      tailf:cli-optional-in-sequence;
      type enumeration {
        enum "exact";
        enum "prefix";
      }
    }
    leaf read {
      tailf:cli-optional-in-sequence;
      type string;
    }
    leaf write {
      tailf:cli-optional-in-sequence;
      type string;
    }
    leaf notify {
      tailf:cli-optional-in-sequence;
      type string;
    }
    leaf access {
      type empty;
    }
    leaf ipv6 {
      tailf:cli-optional-in-sequence;
      type string;
    }
    leaf acl {
      tailf:cli-drop-node-name;
      type union {
        type uint8;
        type string;
      }
    }
  }

  grouping snmp-server-user-grouping {
    choice security-model {
      leaf v1 {
        type empty;
      }
      leaf v2c {
        type empty;
      }
      case v3 {
        leaf v3 {
          type empty;
        }
        leaf encrypted {
          tailf:cli-drop-node-name;
          tailf:cli-optional-in-sequence;
          type enumeration {
            enum "encrypted";
          }
        }
        leaf auth {
          tailf:cli-optional-in-sequence;
          type enumeration {
            enum "md5";
            enum "sha";
            enum "sha-2";
          }
        }
        leaf auth-bits {
          tailf:cli-drop-node-name;
          type enumeration {
            enum "256";
            enum "384";
            enum "512";
          }
        }
        leaf auth-password {
          tailf:cli-drop-node-name;
          type string;
        }
        leaf priv {
          tailf:cli-optional-in-sequence;
          type enumeration {
            enum "3des";
            enum "aes";
            enum "des";
          }
        }
        leaf bits {
          tailf:cli-drop-node-name;
          type enumeration {
            enum "128";
            enum "192";
            enum "256";
          }
        }
        leaf priv-password {
          tailf:cli-drop-node-name;
          type string;
        }
      }
    }
    container access {
      tailf:cli-flatten-container;
      choice access-choice {
        leaf access-list-std {
          tailf:cli-drop-node-name;
          type uint16;
        }
        leaf access-list-named {
          tailf:cli-drop-node-name;
          type string;
        }
        leaf ipv6 {
          type string;
        }
      }
    }
  }

  grouping new-aaa-list-syntax-grouping {
    leaf-list method {
      tailf:cli-drop-node-name;
      tailf:cli-flat-list-syntax;
      ordered-by user;
      type union {
        type enumeration {
          enum "none";
          enum "if-needed";
          enum "local";
          enum "local-case";
          enum "line";
          enum "enable";
          enum "krb5";
          enum "krb5-instance";
          enum "tacacs+";
          enum "if-authenticated";
        }
        type string;
        type string;
      }
    }
  }

  grouping aaa-authentication-method-grouping {
    uses new-aaa-list-syntax-grouping;
    leaf cache {
      type aaa-group-type;
    }
    leaf group {
      type aaa-group-type;
    }
    container group2 {
      tailf:cli-drop-node-name;
      tailf:cli-flatten-container;
      tailf:cli-compact-syntax;
      leaf group {
        type aaa-group-type;
      }
    }
    container group3 {
      tailf:cli-drop-node-name;
      tailf:cli-flatten-container;
      tailf:cli-compact-syntax;
      leaf group {
        type aaa-group-type;
      }
    }
    leaf krb5 {
      type empty;
    }
    choice local-choice {
      leaf local {
        type empty;
      }
      leaf local-case {
        type empty;
      }
    }
    leaf tacacsplus {
      tailf:alt-name "tacacs+";
      type empty;
    }
    leaf line {
      type empty;
    }
    leaf enable {
      type empty;
    }
    leaf none {
      type empty;
    }
  }

  grouping aaa-authorization-method-grouping {
    uses new-aaa-list-syntax-grouping;
    leaf cache {
      type aaa-group-type;
    }
    leaf group {
      type aaa-group-type;
    }
    container group2 {
      tailf:cli-drop-node-name;
      tailf:cli-flatten-container;
      tailf:cli-compact-syntax;
      leaf group {
        type aaa-group-type;
      }
    }
    container group3 {
      tailf:cli-drop-node-name;
      tailf:cli-flatten-container;
      tailf:cli-compact-syntax;
      leaf group {
        type aaa-group-type;
      }
    }
    leaf krb5-instance {
      type empty;
    }
    leaf tacacsplus {
      tailf:alt-name "tacacs+";
      type empty;
    }
    leaf local {
      type empty;
    }
    leaf if-authenticated {
      type empty;
    }
    leaf none {
      type empty;
    }
  }

  grouping aaa-accounting-method-grouping {
    leaf action-type {
      tailf:cli-drop-node-name;
      type enumeration {
        enum "none";
        enum "start-stop";
        enum "stop-only";
      }
    }
    leaf broadcast {
      type empty;
    }
    leaf group {
      type aaa-group-type;
    }
    container group2 {
      tailf:cli-drop-node-name;
      tailf:cli-flatten-container;
      tailf:cli-compact-syntax;
      tailf:cli-optional-in-sequence;
      leaf group {
        type string;
      }
    }
    container group3 {
      tailf:cli-drop-node-name;
      tailf:cli-flatten-container;
      tailf:cli-compact-syntax;
      leaf group {
        type aaa-group-type;
      }
    }
  }

  grouping cable-modulation-profile-grouping {
    leaf fec-tbytes {
      tailf:cli-drop-node-name;
      type uint8;
    }
    leaf fec-len {
      tailf:cli-drop-node-name;
      type uint8;
    }
    leaf burst-len {
      tailf:cli-drop-node-name;
      type uint8;
    }
    leaf guard-t {
      tailf:cli-drop-node-name;
      type uint8;
    }
    leaf mod {
      tailf:cli-drop-node-name;
      type enumeration {
        enum "8qam";
        enum "16qam";
        enum "32qam";
        enum "64qam";
        enum "qpsk";
      }
    }
    leaf scrambler {
      tailf:cli-drop-node-name;
      type enumeration {
        enum "no-scrambler";
        enum "scrambler";
      }
    }
    leaf seed {
      tailf:cli-drop-node-name;
      type string;
    }
    leaf diff {
      tailf:cli-drop-node-name;
      type enumeration {
        enum "diff";
        enum "no-diff";
      }
    }
    leaf pre-len {
      tailf:cli-drop-node-name;
      type uint16;
    }
    leaf last-cw {
      tailf:cli-drop-node-name;
      type enumeration {
        enum "fixed";
        enum "shortened";
      }
    }
    leaf preamble {
      tailf:cli-drop-node-name;
      type enumeration {
        enum "qpsk0";
        enum "qpsk1";
      }
    }
    leaf rs-interleave-depth {
      tailf:cli-drop-node-name;
      type uint8;
    }
    leaf rs-interleave-block {
      tailf:cli-drop-node-name;
      type uint16;
    }
  }

  grouping cable-modulation-profile-list-grouping {
    container request {
      tailf:cli-compact-syntax;
      tailf:cli-sequence-commands {
        tailf:cli-reset-all-siblings;
      }
      uses cable-modulation-profile-grouping;
    }
    container initial {
      tailf:cli-compact-syntax;
      tailf:cli-sequence-commands {
        tailf:cli-reset-all-siblings;
      }
      uses cable-modulation-profile-grouping;
    }
    container station {
      tailf:cli-compact-syntax;
      tailf:cli-sequence-commands {
        tailf:cli-reset-all-siblings;
      }
      uses cable-modulation-profile-grouping;
    }
    container short {
      tailf:cli-compact-syntax;
      tailf:cli-sequence-commands {
        tailf:cli-reset-all-siblings;
      }
      uses cable-modulation-profile-grouping;
    }
    container long {
      tailf:cli-compact-syntax;
      tailf:cli-sequence-commands {
        tailf:cli-reset-all-siblings;
      }
      uses cable-modulation-profile-grouping;
    }
    container a-short {
      tailf:cli-compact-syntax;
      tailf:cli-sequence-commands {
        tailf:cli-reset-all-siblings;
      }
      uses cable-modulation-profile-grouping;
    }
    container a-long {
      tailf:cli-compact-syntax;
      tailf:cli-sequence-commands {
        tailf:cli-reset-all-siblings;
      }
      uses cable-modulation-profile-grouping;
    }
    container a-ugs {
      tailf:cli-compact-syntax;
      tailf:cli-sequence-commands {
        tailf:cli-reset-all-siblings;
      }
      uses cable-modulation-profile-grouping;
    }
  }

  grouping cable-load-balance-docsis-group-grouping {
    leaf restricted {
      type empty;
    }
    container downstream {
      list Modular-Cable {
        tailf:cli-allow-join-with-key;
        tailf:cli-suppress-mode;
        tailf:cli-delete-when-empty;
        key "name";
        leaf name {
          type string;
        }
        leaf rf-channel {
          tailf:cli-multi-value;
          type string;
        }
      }
      list Integrated-Cable {
        tailf:cli-allow-join-with-key;
        tailf:cli-suppress-mode;
        tailf:cli-delete-when-empty;
        key "name";
        leaf name {
          type string;
        }
        leaf rf-channel {
          tailf:cli-multi-value;
          type string;
        }
      }
      list Downstream-Cable {
        tailf:cli-allow-join-with-key;
        tailf:cli-suppress-mode;
        tailf:cli-delete-when-empty;
        key "name";
        leaf name {
          type string;
        }
        leaf rf-channel {
          tailf:cli-multi-value;
          type string;
        }
      }
    }
    container upstream {
      list Upstream-Cable {
        tailf:cli-allow-join-with-key;
        tailf:cli-suppress-mode;
        tailf:cli-delete-when-empty;
        key "name";
        leaf name {
          type string;
        }
        leaf us-channel {
          tailf:cli-multi-value;
          type string;
        }
      }
      list Cable {
        tailf:cli-allow-join-with-key;
        tailf:cli-suppress-mode;
        tailf:cli-delete-when-empty;
        key "name";
        leaf name {
          type string;
        }
        leaf upstream-list {
          tailf:cli-drop-node-name;
          type string;
        }
      }
    }
    container method {
      tailf:cli-compact-syntax;
      tailf:cli-sequence-commands {
        tailf:cli-reset-siblings;
      }
      leaf type {
        tailf:cli-drop-node-name;
        type enumeration {
          enum "modems";
          enum "utilization";
        }
      }
      leaf us-method {
        type enumeration {
          enum "modems";
          enum "utilization";
        }
      }
    }
    container threshold {
      container load {
        leaf percentage {
          tailf:cli-drop-node-name;
          type uint8;
        }
        leaf minimum {
          type uint8;
        }
      }
      leaf stability {
        type uint8;
      }
    }
    leaf policy {
      type enumeration {
        enum "pcmm";
        enum "pure-ds-load";
        enum "ugs";
        enum "us-across-ds";
      }
    }
    leaf interval {
      type uint16;
    }
    container init-tech-list {
      tailf:cli-compact-syntax;
      tailf:cli-sequence-commands {
        tailf:cli-reset-siblings;
      }
      leaf grouplist {
        tailf:cli-drop-node-name;
        type string;
      }
      leaf ucc {
        type empty;
      }
    }
    leaf docsis-policy {
      type uint32;
    }
    list tag {
      tailf:cli-suppress-mode;
      tailf:cli-delete-when-empty;
      key "name";
      leaf name {
        type string;
      }
    }
  }

  grouping cable-submgmt-default-filter-group-grouping {
    leaf upstream {
      type uint8;
    }
    leaf downstream {
      type uint8;
    }
  }

  grouping facility-alarm-grouping {
    container major {
      leaf temperature {
        tailf:cli-drop-node-name;
        type uint8;
      }
    }
    container minor {
      leaf temperature {
        tailf:cli-drop-node-name;
        type uint8;
      }
    }
    container critical {
      leaf exceed-action {
        type enumeration {
          enum "shutdown";
        }
      }
      leaf temperature {
        tailf:cli-drop-node-name;
        type uint8;
      }
    }
  }

  grouping process-cpu-threshold-grouping {
    leaf rising {
      type uint8;
    }
    leaf interval {
      type uint32;
    }
    leaf falling {
      type uint8;
    }
    container falling-interval {
      tailf:cli-flatten-container;
      tailf:cli-drop-node-name;
      leaf interval {
        type uint32;
      }
    }
  }

  grouping logging-host-grouping {
    list transport {
      tailf:cli-suppress-mode;
      tailf:cli-delete-when-empty;
      tailf:cli-compact-syntax;
      key "protocol port";
      leaf protocol {
        tailf:cli-suppress-range;
        type enumeration {
          enum "beep";
          enum "tcp";
          enum "udp";
        }
      }
      leaf port {
        tailf:cli-expose-key-name;
        type uint16;
      }
      uses logging-host-grouping-options;
    }
    uses logging-host-grouping-options;
  }

  grouping logging-host-grouping-options {
    leaf discriminator {
      type string;
    }
    leaf xxml {
      tailf:alt-name "xml";
      type empty;
    }
    container session-id {
      tailf:cli-flatten-container;
      tailf:cli-compact-syntax;
      choice session-id-choice {
        leaf hostname {
          type empty;
        }
        leaf ipv4 {
          type empty;
        }
        leaf ipv6 {
          type empty;
        }
        leaf string {
          type string;
        }
      }
    }
    leaf sequence-num-session {
      type empty;
    }
  }

  grouping logging-discriminator-pattern-grouping {
    choice pattern-choice {
      leaf drops {
        type string;
      }
      leaf includes {
        type string;
      }
    }
  }

  grouping crypto-ikev2-profile-aaa-authorization-group-list {
    container list {
      tailf:cli-compact-syntax;
      tailf:cli-sequence-commands {
        tailf:cli-reset-siblings;
      }
      leaf list-name {
        tailf:cli-drop-node-name;
        type string;
      }
      leaf aaa-username {
        tailf:cli-break-sequence-commands;
        tailf:cli-drop-node-name;
        type string;
      }
      leaf name-mangler {
        type string;
      }
      container password {
        tailf:cli-flatten-container;
        tailf:cli-compact-syntax;
        tailf:cli-sequence-commands;
        uses crypto-key-grouping {
          refine "secret";
        }
      }
    }
  }

  grouping parameter-map-aggressive-aging-grouping {
    container aggressive-aging {
      tailf:cli-flatten-container;
      tailf:cli-compact-syntax;
      tailf:cli-sequence-commands {
        tailf:cli-reset-siblings;
      }
      container high {
        tailf:cli-flatten-container;
        tailf:cli-compact-syntax;
        choice high-choice {
          leaf value {
            tailf:cli-drop-node-name;
            type uint32;
          }
          leaf percent {
            type uint8;
          }
        }
      }
      container low {
        tailf:cli-flatten-container;
        tailf:cli-compact-syntax;
        choice low-choice {
          leaf value {
            tailf:cli-drop-node-name;
            type uint32;
          }
          leaf percent {
            type uint8;
          }
        }
      }
    }
  }

  grouping parameter-map-max-incomplete-grouping {
    container half-open-sessions {
      tailf:cli-drop-node-name;
      tailf:cli-compact-syntax;
      tailf:cli-sequence-commands {
        tailf:cli-reset-siblings;
      }
      leaf number {
        tailf:cli-drop-node-name;
        type uint32;
      }
      uses parameter-map-aggressive-aging-grouping;
    }
    leaf tcp {
      type uint32;
    }
    leaf udp {
      type uint32;
    }
    leaf icmp {
      type uint32;
    }
  }

  grouping parameter-map-grouping {
    leaf alert {
      type enumeration {
        enum "off";
        enum "on";
      }
    }
    leaf audit-trail {
      type enumeration {
        enum "off";
        enum "on";
      }
    }
    leaf dns-timeout {
      type uint32;
    }
    container icmp {
      tailf:cli-compact-syntax;
      tailf:cli-sequence-commands {
        tailf:cli-reset-siblings;
      }
      leaf idle-time {
        type uint32;
      }
      leaf ageout-time {
        type uint32;
      }
    }
    leaf max-destination {
      type uint32;
    }
    container one-minute {
      leaf high {
        type uint32;
      }
      leaf low {
        type uint32;
      }
    }
    container session {
      leaf packet {
        type uint16;
      }
      container total {
        tailf:cli-compact-syntax;
        tailf:cli-sequence-commands {
          tailf:cli-reset-siblings;
        }
        leaf number {
          tailf:cli-drop-node-name;
          type uint32;
        }
        container aggressive-aging {
          tailf:cli-flatten-container;
          tailf:cli-compact-syntax;
          tailf:cli-sequence-commands;
          leaf high {
            type uint32;
          }
          leaf low {
            type uint32;
          }
        }
      }
    }
    container sessions {
      leaf maximum {
        type uint32;
      }
    }
    container log {
      container flow-export {
        container v9 {
          container udp {
            container destination {
              tailf:cli-compact-syntax;
              tailf:cli-sequence-commands {
                tailf:cli-reset-siblings;
              }
              leaf address {
                tailf:cli-drop-node-name;
                type inet:ipv4-address;
              }
              leaf port {
                tailf:cli-drop-node-name;
                type uint16;
              }
            }
          }
        }
        container template {
          leaf timeout-rate {
            type uint16;
          }
        }
      }
      leaf dropped-packets {
        type empty;
      }
    }
    container lisp {
      leaf inner-packet-inspection {
        type empty;
      }
    }
    leaf multi-tenancy {
      type empty;
    }
    leaf icmp-unreachable-allow {
      type empty;
    }
    container tcp {
      container finwait-time {
        tailf:cli-compact-syntax;
        tailf:cli-sequence-commands {
          tailf:cli-reset-siblings;
        }
        leaf seconds {
          tailf:cli-drop-node-name;
          type uint32;
        }
        leaf ageout-time {
          type uint32;
        }
      }
      container idle-time {
        tailf:cli-compact-syntax;
        tailf:cli-sequence-commands {
          tailf:cli-reset-siblings;
        }
        leaf seconds {
          tailf:cli-drop-node-name;
          type uint32;
        }
        leaf ageout-time {
          type uint32;
        }
      }
      container max-incomplete {
        leaf host {
          type uint32;
        }
      }
      container synwait-time {
        tailf:cli-compact-syntax;
        tailf:cli-sequence-commands {
          tailf:cli-reset-siblings;
        }
        leaf seconds {
          tailf:cli-drop-node-name;
          type uint32;
        }
        leaf ageout-time {
          type uint32;
        }
      }
      container syn-flood {
        leaf limit {
          type uint32;
        }
        container rate {
          leaf per-destination {
            type uint32;
          }
        }
      }
      container window-scale-enforcement {
        leaf loose {
          type empty;
        }
      }
    }
    container udp {
      container idle-time {
        tailf:cli-compact-syntax;
        tailf:cli-sequence-commands {
          tailf:cli-reset-siblings;
        }
        leaf seconds {
          tailf:cli-drop-node-name;
          type uint32;
        }
        leaf ageout-time {
          type uint32;
        }
      }
      container half-open {
        container idle-time {
          tailf:cli-compact-syntax;
          tailf:cli-sequence-commands {
            tailf:cli-reset-siblings;
          }
          leaf seconds {
            tailf:cli-drop-node-name;
            type uint32;
          }
          leaf ageout-time {
            type uint32;
          }
        }
      }
    }
    container application-inspect {
      list no-list {
        tailf:cli-suppress-mode;
        tailf:cli-delete-when-empty;
        key "name";
        leaf name {
          type enumeration {
            enum "all";
            enum "dns";
            enum "exec";
            enum "ftp";
            enum "gtp";
            enum "h323";
            enum "http";
            enum "imap";
            enum "login";
            enum "msrpc";
            enum "netbios";
            enum "pop3";
            enum "rtsp";
            enum "shell";
            enum "sip";
            enum "skinny";
            enum "smtp";
            enum "sunrpc";
            enum "tftp";
          }
        }
      }
    }
    container max-incomplete {
      leaf high {
        type uint32;
      }
      leaf low {
        type uint32;
      }
      uses parameter-map-max-incomplete-grouping;
    }
    uses parameter-map-aggressive-aging-grouping;
    container inspect {
      leaf name {
        tailf:cli-drop-node-name;
        type string;
      }
      list vrf {
        tailf:cli-suppress-mode;
        tailf:cli-delete-when-empty;
        key "id";
        leaf id {
          type string;
        }
        leaf name {
          tailf:cli-drop-node-name;
          type string;
        }
      }
    }
    container threat-detection {
      leaf basic-threat {
        type empty;
      }
      container rate {
        container syn-attack {
          tailf:cli-compact-syntax;
          tailf:cli-sequence-commands {
            tailf:cli-reset-siblings;
          }
          leaf average-time-frame {
            type uint16;
          }
          leaf average-threshold {
            type uint32;
          }
          leaf burst-threshold {
            type uint32;
          }
        }
        container inspect-drop {
          tailf:cli-compact-syntax;
          tailf:cli-sequence-commands {
            tailf:cli-reset-siblings;
          }
          leaf average-time-frame {
            type uint16;
          }
          leaf average-threshold {
            type uint32;
          }
          leaf burst-threshold {
            type uint32;
          }
        }
        container fw-drop {
          tailf:cli-compact-syntax;
          tailf:cli-sequence-commands {
            tailf:cli-reset-siblings;
          }
          leaf average-time-frame {
            type uint16;
          }
          leaf average-threshold {
            type uint32;
          }
          leaf burst-threshold {
            type uint32;
          }
        }
      }
    }
    container per-box {
      container tcp {
        container syn-flood {
          leaf limit {
            type uint32;
          }
        }
      }
      uses parameter-map-aggressive-aging-grouping;
      container max-incomplete {
        uses parameter-map-max-incomplete-grouping;
      }
    }
    list vrf {
      tailf:cli-suppress-mode;
      tailf:cli-delete-when-empty;
      key "vrf";
      leaf vrf {
        type string;
      }
      leaf inspect {
        type string;
      }
    }
    container zone-mismatch {
      leaf drop {
        type empty;
      }
    }
  }

  grouping cos-value-0-7-grouping {
    leaf cos-value0 {
      tailf:cli-drop-node-name;
      type uint8;
    }
    leaf cos-value1 {
      tailf:cli-drop-node-name;
      type uint8;
    }
    leaf cos-value2 {
      tailf:cli-drop-node-name;
      type uint8;
    }
    leaf cos-value3 {
      tailf:cli-drop-node-name;
      type uint8;
    }
    leaf cos-value4 {
      tailf:cli-drop-node-name;
      type uint8;
    }
    leaf cos-value5 {
      tailf:cli-drop-node-name;
      type uint8;
    }
    leaf cos-value6 {
      tailf:cli-drop-node-name;
      type uint8;
    }
    leaf cos-value7 {
      tailf:cli-drop-node-name;
      type uint8;
    }
  }

  grouping controller-modular-cable-rf-channel-grouping {
    list rf-channel {
      tailf:cli-suppress-mode;
      tailf:cli-delete-when-empty;
      key "rf-port";
      leaf rf-port {
        type uint8;
      }
      leaf description {
        tailf:cli-multi-value;
        type string;
      }
      container cable {
        container downstream {
          leaf channel-id {
            type uint8;
          }
        }
      }
      container frequency {
        tailf:cli-compact-syntax;
        tailf:cli-sequence-commands {
          tailf:cli-reset-siblings;
        }
        leaf freq {
          tailf:cli-drop-node-name;
          type union {
            type uint32;
            type enumeration {
              enum "none";
            }
          }
        }
        leaf annex {
          type enumeration {
            enum "A";
            enum "B";
          }
        }
        leaf modulation {
          type enumeration {
            enum "256qam";
            enum "64qam";
          }
        }
        leaf interleave {
          type enumeration {
            enum "128";
            enum "16";
            enum "32";
            enum "64";
            enum "8";
            enum "12";
          }
        }
      }
      container ip-address {
        tailf:cli-compact-syntax;
        tailf:cli-sequence-commands {
          tailf:cli-reset-siblings;
        }
        leaf ip-address {
          tailf:cli-drop-node-name;
          type inet:ipv4-address;
        }
        leaf mac-address {
          type string;
        }
        leaf depi-remote-id {
          type uint32;
        }
        leaf eqam-headroom {
          type uint8;
        }
      }
      container network-delay {
        choice network-delay-choice {
          leaf usec {
            tailf:cli-drop-node-name;
            type uint16;
          }
          container auto {
            tailf:cli-delete-when-empty;
            presence "true";
            leaf sampling-rate {
              type uint16;
            }
          }
        }
      }
      container depi-tunnel {
        tailf:cli-compact-syntax;
        tailf:cli-sequence-commands {
          tailf:cli-reset-siblings;
        }
        leaf depi-tunnel-name {
          tailf:cli-drop-node-name;
          type string;
        }
        leaf tsid {
          type uint16;
        }
      }
      leaf rf-power {
        type string;
      }
      leaf rf-shutdown {
        type boolean;
      }
    }
  }

  grouping controller-integrated-cable-rf-chan-grouping {
    leaf shutdown {
      type empty;
    }
    container type {
      tailf:cli-compact-syntax;
      tailf:cli-sequence-commands {
        tailf:cli-reset-siblings;
      }
      leaf value {
        tailf:cli-drop-node-name;
        type enumeration {
          enum "DOCSIS";
          enum "VIDEO";
        }
      }
      leaf mode {
        tailf:cli-drop-node-name;
        type enumeration {
          enum "ASYNC";
          enum "SYNC";
        }
      }
    }
    leaf frequency {
      type uint32;
    }
    leaf rf-output {
      type enumeration {
        enum "ALT";
        enum "CW";
        enum "NORMAL";
        enum "PRBS";
      }
    }
    leaf power-adjust {
      type string;
    }
    leaf qam-profile {
      type uint8;
    }
    leaf docsis-channel-id {
      type uint8;
    }
    container ofdm {
      container channel-profile {
        tailf:cli-compact-syntax;
        tailf:cli-sequence-commands {
          tailf:cli-reset-siblings;
        }
        leaf id {
          tailf:cli-drop-node-name;
          type uint8;
        }
        leaf start-frequency {
          type uint32;
        }
        leaf width {
          type uint32;
        }
        leaf plc {
          type uint32;
        }
      }
    }
  }

  grouping cable-video-logical-edge-device-protocol-grouping {
    leaf mgmt-ip {
      type inet:ipv4-address;
    }
    leaf mac-address {
      type string;
    }
    list server {
      tailf:cli-suppress-mode;
      tailf:cli-delete-when-empty;
      ordered-by user;
      key "address";
      leaf address {
        type inet:ipv4-address;
      }
    }
    container keepalive {
      tailf:cli-compact-syntax;
      tailf:cli-sequence-commands {
        tailf:cli-reset-siblings;
      }
      leaf retry {
        type uint8;
      }
      leaf interval {
        type uint8;
      }
    }
    container reset {
      leaf interval {
        type uint16;
      }
      leaf on-active {
        type empty;
      }
    }
    leaf event-profile {
      type string;
    }
    leaf create-session-response-max-delay {
      type uint16;
    }
    leaf udp-port-mapping-method {
      type enumeration {
        enum "10-6";
      }
    }
    list virtual-edge-input-ip {
      tailf:cli-suppress-mode;
      tailf:cli-delete-when-empty;
      tailf:cli-compact-syntax;
      key "ip-address";
      leaf ip-address {
        type inet:ipv4-address;
      }
      leaf vrf {
        type string;
      }
      leaf input-port-number {
        type uint16;
      }
    }
    leaf-list vcg {
      type string;
    }
    container discovery-protocol {
      container d6 {
        tailf:cli-add-mode;
        presence "true";
        leaf mgmt-ip {
          type inet:ipv4-address;
        }
        leaf vendor-string {
          type string;
        }
        leaf streaming-zone {
          type string;
        }
        leaf component-name {
          type string;
        }
        container d6-server {
          container fqdn {
            tailf:cli-compact-syntax;
            tailf:cli-sequence-commands {
              tailf:cli-reset-siblings;
            }
            leaf domain-name {
              tailf:cli-drop-node-name;
              type string;
            }
            leaf port {
              tailf:cli-drop-node-name;
              type uint16;
            }
          }
          container address {
            tailf:cli-drop-node-name;
            tailf:cli-compact-syntax;
            tailf:cli-sequence-commands {
              tailf:cli-reset-siblings;
            }
            leaf ip {
              tailf:cli-drop-node-name;
              type inet:ipv4-address;
            }
            leaf port {
              tailf:cli-drop-node-name;
              type uint16;
            }
          }
        }
        leaf timeout {
          type uint8;
        }
        leaf holdtime {
          type uint16;
        }
        leaf report-output-port-number {
          type empty;
        }
        container input-group {
          list led {
            tailf:cli-suppress-mode;
            tailf:cli-delete-when-empty;
            tailf:cli-compact-syntax;
            tailf:cli-sequence-commands {
              tailf:cli-reset-siblings;
            }
            key "vei-ip";
            leaf vei-ip {
              tailf:cli-expose-key-name;
              type inet:ipv4-address;
            }
            leaf group-name {
              type string;
            }
            leaf bandwidth {
              type uint32;
            }
          }
        }
        leaf enable {
          type empty;
        }
      }
    }
    leaf pmv {
      type empty;
    }
    leaf active {
      type empty;
    }
  }

  grouping cable-rpd-core-if-grouping {
    leaf principal {
      type empty;
    }
    list rpd-ds {
      tailf:cli-suppress-mode;
      tailf:cli-delete-when-empty;
      key "port name id";
      leaf port {
        type uint8;
      }
      leaf name {
        type string;
      }
      leaf id {
        type string;
      }
      leaf profile {
        type uint32;
      }
    }
    list rpd-us {
      tailf:cli-suppress-mode;
      tailf:cli-delete-when-empty;
      key "port name id";
      leaf port {
        type uint8;
      }
      leaf name {
        type string;
      }
      leaf id {
        type string;
      }
      leaf profile {
        type uint32;
      }
    }
    container static-pseudowire-video {
      tailf:cli-drop-node-name;
      list rpd-ds {
        tailf:cli-suppress-mode;
        tailf:cli-delete-when-empty;
        tailf:cli-compact-syntax;
        tailf:cli-sequence-commands;
        key "port profile";
        leaf port {
          type uint8;
        }
        leaf name {
          tailf:cli-drop-node-name;
          tailf:cli-prefix-key {
            tailf:cli-before-key "2";
          }
          type enumeration {
            enum "static-pseudowire-video";
          }
        }
        leaf profile {
          tailf:cli-expose-key-name;
          type uint32;
        }
      }
    }
    container network-delay {
      container dlm {
        tailf:cli-compact-syntax;
        tailf:cli-sequence-commands {
          tailf:cli-reset-siblings;
        }
        leaf seconds {
          tailf:cli-drop-node-name;
          type uint16;
        }
        leaf measure-only {
          type empty;
        }
      }
      leaf static {
        type uint32;
      }
    }
  }

  grouping cable-map-advance-grouping {
    container map-advance {
      choice map-advance-choice {
        leaf static {
          type uint16;
        }
        container dynamic {
          tailf:cli-compact-syntax;
          tailf:cli-sequence-commands;
          leaf safety {
            tailf:cli-drop-node-name;
            type uint16;
          }
          leaf max-delay {
            tailf:cli-drop-node-name;
            type uint16;
          }
        }
      }
    }
  }

  grouping object-group-service-protocol-match {
    choice match-choice {
      leaf eq {
        tailf:cli-prefix-key;
        type empty;
      }
      leaf gt {
        tailf:cli-prefix-key;
        type empty;
      }
      leaf lt {
        tailf:cli-prefix-key;
        type empty;
      }
    }
  }

  grouping arp-grouping {
    list arp-list {
      tailf:cli-drop-node-name;
      tailf:cli-suppress-mode;
      tailf:cli-delete-when-empty;
      tailf:cli-compact-syntax;
      tailf:cli-sequence-commands {
        tailf:cli-reset-siblings;
      }
      key "ip-address";
      leaf ip-address {
        type inet:ipv4-address;
      }
      leaf hardware-address {
        tailf:cli-drop-node-name;
        type string;
      }
      leaf type {
        tailf:cli-drop-node-name;
        type enumeration {
          enum "ARPA";
          enum "SAP";
          enum "SMDS";
          enum "SNAP";
          enum "SRP-A";
          enum "SRP-B";
        }
      }
      leaf alias {
        type empty;
      }
    }
  }

  grouping interface-encryption-mode-grouping {
    container mode {
      container ciphers {
        tailf:cli-flatten-container;
        tailf:cli-compact-syntax;
        choice suite-choice {
          leaf ckip {
            type empty;
          }
          leaf ckip-cmic {
            type empty;
          }
          leaf cmic {
            type empty;
          }
          case a {
            leaf aes-ccm {
              type empty;
            }
            leaf tkip {
              type empty;
            }
            leaf wep {
              tailf:cli-drop-node-name;
              type enumeration {
                enum "wep128";
                enum "wep40";
              }
            }
          }
        }
      }
    }
  }

  grouping ip-ssh-algorithm-grouping {
    container algorithm {
      leaf-list mac {
        tailf:cli-flat-list-syntax;
        ordered-by user;
        type enumeration {
          enum "hmac-sha1";
          enum "hmac-sha1-96";
          enum "hmac-sha2-256";
          enum "hmac-sha2-512";
          enum "hmac-sha2-256-etm@openssh.com";
          enum "hmac-sha2-512-etm@openssh.com";
        }
      }
      leaf-list encryption {
        tailf:cli-flat-list-syntax;
        ordered-by user;
        type enumeration {
          enum "3des-cbc";
          enum "aes128-cbc";
          enum "aes128-ctr";
          enum "aes192-cbc";
          enum "aes192-ctr";
          enum "aes256-cbc";
          enum "aes256-ctr";
          enum "aes256-gcm";
          enum "aes128-gcm";
        }
      }
      leaf-list hostkey {
        tailf:cli-flat-list-syntax;
        ordered-by user;
        type enumeration {
          enum "ssh-rsa";
          enum "rsa-sha2-256";
          enum "rsa-sha2-512";
          enum "x509v3-ssh-rsa";
        }
      }
      leaf-list authentication {
        tailf:cli-flat-list-syntax;
        ordered-by user;
        type enumeration {
          enum "password";
          enum "keyboard";
          enum "publickey";
        }
      }
      leaf-list kex {
        tailf:cli-flat-list-syntax;
        ordered-by user;
        type enumeration {
          enum "diffie-hellman-group14-sha1";
          enum "diffie-hellman-group-exchange-sha1";
          enum "ecdh-sha2-nistp256";
          enum "ecdh-sha2-nistp384";
          enum "ecdh-sha2-nistp521";
          enum "diffie-hellman-group14-sha256";
          enum "diffie-hellman-group16-sha512";
          enum "curve25519-sha256";
          enum "curve25519-sha256@libssh.org";
        }
      }
      leaf-list publickey {
        tailf:cli-flat-list-syntax;
        ordered-by user;
        type enumeration {
          enum "ecdsa-sha2-nistp256";
          enum "ecdsa-sha2-nistp384";
          enum "ecdsa-sha2-nistp521";
          enum "rsa-sha2-256";
          enum "rsa-sha2-512";
          enum "ssh-rsa";
          enum "x509v3-ecdsa-sha2-nistp256";
          enum "x509v3-ecdsa-sha2-nistp384";
          enum "x509v3-ecdsa-sha2-nistp521";
          enum "x509v3-ssh-rsa";
          enum "x509v3-rsa2048-sha256";
          enum "ssh-ed25519";
        }
      }
    }
  }

  grouping bandwidth-remaining-account-grouping {
    container account {
      tailf:cli-flatten-container;
      tailf:cli-compact-syntax;
      tailf:cli-sequence-commands;
      choice account-choice {
        case dot1q-qing {
          leaf bras-side {
            tailf:cli-drop-node-name;
            type enumeration {
              enum "dot1q";
              enum "qinq";
            }
          }
          leaf aal {
            tailf:cli-drop-node-name;
            type enumeration {
              enum "aal3";
              enum "aal5";
            }
          }
          leaf subscriber-encapsulation {
            tailf:cli-drop-node-name;
            type enumeration {
              enum "mux-1483routed";
              enum "mux-dot1q-rbe";
              enum "mux-pppoa";
              enum "mux-rbe";
              enum "snap-1483routed";
              enum "snap-dot1q-rbe";
              enum "snap-pppoa";
              enum "snap-rbe";
            }
          }
        }
        leaf user-defined {
          type int8;
        }
      }
    }
  }

  grouping result-type-method-grouping {
    leaf authoritative {
      type empty;
    }
    leaf agent-not-found {
      type empty;
    }
    leaf none {
      type empty;
    }
    leaf success {
      type empty;
    }
    leaf method-timeout {
      type empty;
    }
    leaf aaa-timeout {
      type empty;
    }
  }

  grouping interface-vrrp-grouping {
    leaf name {
      type string;
    }
    leaf description {
      tailf:cli-multi-value;
      type string;
    }
    container vrrs {
      list leader {
        tailf:cli-suppress-mode;
        tailf:cli-delete-when-empty;
        key "name";
        leaf name {
          type string;
        }
      }
    }
    container preempt {
      container delay {
        leaf minimum {
          type uint16;
        }
      }
    }
    leaf vrrpv2 {
      type empty;
    }
    leaf priority {
      type uint8;
    }
    container timers {
      container advertise {
        leaf seconds {
          tailf:cli-drop-node-name;
          type uint16;
        }
        leaf msec {
          type uint16;
        }
      }
      leaf learn {
        type empty;
      }
    }
    list track {
      tailf:cli-suppress-mode;
      tailf:cli-delete-when-empty;
      key "name";
      leaf name {
        type uint16;
      }
      leaf decrement {
        type uint16;
      }
    }
    leaf shutdown {
      type empty;
    }
  }

  grouping ip-dns-view-grouping {
    container domain {
      container name-server {
        list vrf-default {
          tailf:cli-drop-node-name;
          tailf:cli-suppress-mode;
          tailf:cli-delete-when-empty;
          ordered-by user;
          key "address";
          leaf address {
            type union {
              type inet:ipv4-address;
              type inet:ipv6-address;
            }
          }
        }
        list vrf {
          tailf:cli-suppress-mode;
          tailf:cli-delete-when-empty;
          ordered-by user;
          key "name address";
          leaf name {
            type string;
          }
          leaf address {
            type union {
              type inet:ipv4-address;
              type inet:ipv6-address;
            }
          }
        }
        container interface {
          uses interface-name-grouping;
        }
      }
      container resolver {
        container source-interface {
          uses interface-name-grouping;
        }
      }
    }
    container dns {
      container forwarding {
        container source-interface {
          uses interface-name-grouping;
        }
      }
    }
  }

  grouping ip-igmp-grouping {
    leaf limit {
      type uint16;
    }
    container ssm-map {
      leaf enable {
        type empty;
      }
      container query {
        leaf dns {
          type boolean;
        }
      }
      list static {
        tailf:cli-suppress-mode;
        tailf:cli-delete-when-empty;
        key "access-list source-address";
        leaf access-list {
          type std-ip-acl-type;
        }
        leaf source-address {
          type inet:ipv4-address;
        }
      }
    }
  }

  grouping ip-msdp-grouping {
    list peer {
      tailf:cli-suppress-mode;
      tailf:cli-delete-when-empty;
      tailf:cli-compact-syntax;
      key "address";
      leaf address {
        type inet:host;
      }
      container connect-source {
        tailf:cli-flatten-container;
        tailf:cli-compact-syntax;
        uses interface-name-grouping;
      }
      leaf remote-as {
        type uint16;
      }
    }
    list description {
      tailf:cli-suppress-mode;
      tailf:cli-delete-when-empty;
      key "address";
      leaf address {
        type inet:host;
      }
      leaf text {
        tailf:cli-drop-node-name;
        tailf:cli-multi-value;
        type string;
      }
    }
    list keepalive {
      tailf:cli-suppress-mode;
      tailf:cli-delete-when-empty;
      tailf:cli-compact-syntax;
      key "address";
      leaf address {
        type inet:host;
      }
      leaf keepalive-interval {
        tailf:cli-drop-node-name;
        type uint8;
      }
      leaf hold-time-interval {
        tailf:cli-drop-node-name;
        type uint8;
      }
    }
    list sa-filter {
      tailf:cli-suppress-mode;
      tailf:cli-delete-when-empty;
      tailf:cli-compact-syntax;
      key "direction address";
      leaf direction {
        type enumeration {
          enum "in";
          enum "out";
        }
      }
      leaf address {
        type inet:host;
      }
      choice list-choice {
        leaf list {
          type ext-acl-type;
        }
        leaf route-map {
          type string;
        }
        leaf rp-list {
          type union {
            type uint16;
            type string;
          }
        }
        leaf rp-route-map {
          type string;
        }
      }
    }
    list sa-limit {
      tailf:cli-suppress-mode;
      tailf:cli-delete-when-empty;
      key "address";
      leaf address {
        type inet:host;
      }
      leaf value {
        tailf:cli-drop-node-name;
        type uint32;
      }
    }
    container password {
      list peer {
        tailf:cli-suppress-mode;
        tailf:cli-delete-when-empty;
        key "address";
        leaf address {
          type inet:host;
        }
        container password {
          tailf:cli-drop-node-name;
          tailf:cli-flatten-container;
          tailf:cli-compact-syntax;
          tailf:cli-sequence-commands;
          uses password-grouping {
            refine "secret";
          }
        }
      }
    }
    container rpf {
      leaf rfc3618 {
        type empty;
      }
    }
    container originator-id {
      uses interface-name-grouping;
    }
    container mesh-group {
      tailf:cli-compact-syntax;
      tailf:cli-sequence-commands {
        tailf:cli-reset-siblings;
      }
      leaf name {
        tailf:cli-drop-node-name;
        type string;
      }
      leaf address {
        tailf:cli-drop-node-name;
        type inet:host;
      }
    }
    container redistribute {
      leaf list {
        type ext-acl-type;
      }
    }
    leaf timer {
      type uint8;
    }
  }

  grouping if-srv-encapsulation-dot1q-grouping {
    leaf-list id {
      tailf:cli-drop-node-name;
      tailf:cli-range-list-syntax;
      type uint16;
    }
    leaf second-dot1q {
      tailf:cli-break-sequence-commands;
      type union {
        type uint16;
        type string;
      }
    }
    leaf cos {
      type uint8;
    }
    leaf etype {
      type enumeration {
        enum "ipv4";
        enum "ipv6";
        enum "pppoe-all";
        enum "pppoe-discovery";
        enum "pppoe-session";
      }
    }
  }

  grouping ip-wccp-grouping {
    container source-interface {
      uses interface-name-grouping;
    }
    container web-cache {
      presence "true";
    }
    list wccp-list {
      tailf:cli-drop-node-name;
      tailf:cli-suppress-mode;
      tailf:cli-delete-when-empty;
      tailf:cli-compact-syntax;
      tailf:cli-sequence-commands {
        tailf:cli-reset-all-siblings;
      }
      key "service-number";
      leaf service-number {
        tailf:cli-suppress-range;
        type uint8;
      }
      leaf redirect-list {
        tailf:cli-break-sequence-commands;
        type exp-ip-acl-type;
      }
      leaf group-list {
        type std-acl-type;
      }
      container password {
        tailf:cli-flatten-container;
        tailf:cli-compact-syntax;
        tailf:cli-sequence-commands;
        uses password-grouping {
          refine "secret";
        }
      }
    }
  }

  grouping interface-ip-wccp-grouping {
    container redirect {
      container exclude {
        leaf in {
          type empty;
        }
      }
    }
    list wccp-list {
      tailf:cli-drop-node-name;
      tailf:cli-suppress-mode;
      tailf:cli-delete-when-empty;
      key "service-number";
      leaf service-number {
        tailf:cli-suppress-range;
        type uint8;
      }
      container redirect {
        leaf in {
          type empty;
        }
        leaf out {
          type empty;
        }
      }
    }
  }

  grouping spanning-tree-portfast-grouping {
    leaf default {
      type empty;
    }
    container bpdufilter {
      leaf default {
        type empty;
      }
    }
    container bpduguard {
      leaf default {
        type empty;
      }
    }
  }

  grouping domain-path-preference-grouping {
    container path-preference {
      tailf:cli-compact-syntax;
      tailf:cli-sequence-commands {
        tailf:cli-reset-siblings;
      }
      leaf path1 {
        tailf:cli-drop-node-name;
        type string;
      }
      leaf path2 {
        tailf:cli-optional-in-sequence;
        tailf:cli-drop-node-name;
        type string;
      }
      leaf path3 {
        tailf:cli-optional-in-sequence;
        tailf:cli-drop-node-name;
        type string;
      }
      leaf fallback {
        type empty;
      }
      leaf fallback-path1 {
        tailf:cli-optional-in-sequence;
        tailf:cli-drop-node-name;
        type string;
      }
      leaf fallback-path2 {
        tailf:cli-optional-in-sequence;
        tailf:cli-drop-node-name;
        type string;
      }
      leaf fallback-path3 {
        tailf:cli-optional-in-sequence;
        tailf:cli-drop-node-name;
        type string;
      }
      leaf next-fallback {
        tailf:cli-optional-in-sequence;
        type empty;
      }
      leaf blackhole {
        tailf:cli-optional-in-sequence;
        type empty;
      }
      leaf routing {
        tailf:cli-optional-in-sequence;
        type empty;
      }
      leaf next-fallback-path1 {
        tailf:cli-drop-node-name;
        type string;
      }
      leaf next-fallback-path2 {
        tailf:cli-drop-node-name;
        type string;
      }
      leaf next-fallback-path3 {
        tailf:cli-drop-node-name;
        type string;
      }
    }
  }

  grouping lifetime-grouping {
    leaf start-time {
      tailf:cli-drop-node-name;
      type hhmm-type;
    }
    leaf start-month {
      tailf:cli-drop-node-name;
      type month-type;
    }
    leaf start-date {
      tailf:cli-drop-node-name;
      type uint8;
    }
    leaf start-year {
      tailf:cli-drop-node-name;
      type uint16;
    }
    leaf duration {
      tailf:cli-optional-in-sequence;
      type uint32;
    }
    leaf infinite {
      tailf:cli-optional-in-sequence;
      type empty;
    }
    leaf stop-time {
      tailf:cli-drop-node-name;
      type hhmm-type;
    }
    leaf stop-month {
      tailf:cli-drop-node-name;
      type month-type;
    }
    leaf stop-date {
      tailf:cli-drop-node-name;
      type uint8;
    }
    leaf stop-year {
      tailf:cli-drop-node-name;
      type uint16;
    }
  }

  grouping us-channel-grouping {
    list us-channel {
      tailf:cli-suppress-mode;
      tailf:cli-delete-when-empty;
      key "id";
      leaf id {
        type uint8;
      }
      uses description-grouping;
      leaf spectrum-group {
        type uint8;
      }
      leaf chan-class-id {
        type string;
      }
      leaf frequency {
        type uint32;
      }
      container channel-width {
        tailf:cli-compact-syntax;
        tailf:cli-sequence-commands {
          tailf:cli-reset-siblings;
        }
        leaf first-choice-width {
          tailf:cli-drop-node-name;
          type uint32;
        }
        leaf last-choice-width {
          tailf:cli-drop-node-name;
          type uint32;
        }
      }
      leaf ingress-noise-cancellation {
        type boolean;
      }
      container threshold {
        container snr-profiles {
          tailf:cli-compact-syntax;
          tailf:cli-sequence-commands {
            tailf:cli-reset-siblings;
          }
          leaf snr-threshold1 {
            tailf:cli-drop-node-name;
            type uint8;
          }
          leaf snr-threshold2 {
            tailf:cli-drop-node-name;
            type uint8;
          }
        }
        leaf corr-fec {
          type uint8;
        }
        leaf hysteresis {
          type uint8;
        }
      }
      leaf power-level {
        type int8;
      }
      container hop-priority {
        container modulation {
          container frequency {
            leaf channel-width {
              type empty;
            }
          }
        }
      }
      leaf docsis-mode {
        type enumeration {
          enum "atdma";
          enum "scdma";
          enum "tdma";
          enum "tdma-atdma";
          enum "ofdma";
        }
      }
      container frequency-range {
        tailf:cli-compact-syntax;
        tailf:cli-sequence-commands {
          tailf:cli-reset-siblings;
        }
        leaf lower {
          tailf:cli-drop-node-name;
          type uint32;
        }
        leaf higher {
          tailf:cli-drop-node-name;
          type uint32;
        }
      }
      leaf initial-rng-frequency-start {
        type uint32;
      }
      leaf subcarrier-spacing {
        type enumeration {
          enum "25KHz";
          enum "50KHz";
        }
      }
      leaf symbols-per-frame {
        type uint8;
      }
      container cyclic-prefix {
        tailf:cli-compact-syntax;
        tailf:cli-sequence-commands {
          tailf:cli-reset-siblings;
        }
        leaf value {
          tailf:cli-drop-node-name;
          type uint16;
        }
        leaf roll-off-period {
          type uint8;
        }
      }
      leaf minislot-size {
        type uint8;
      }
      container modulation-profile {
        tailf:cli-compact-syntax;
        tailf:cli-sequence-commands {
          tailf:cli-reset-siblings;
        }
        leaf primary-profile-number {
          tailf:cli-drop-node-name;
          type uint16;
        }
        leaf secondary-profile-number {
          tailf:cli-drop-node-name;
          type uint16;
        }
        leaf tertiary-profile-number {
          tailf:cli-drop-node-name;
          type uint16;
        }
      }
      leaf equalization-coefficient {
        type empty;
      }
      list data-iuc {
        tailf:cli-suppress-mode;
        tailf:cli-delete-when-empty;
        tailf:cli-compact-syntax;
        tailf:cli-sequence-commands {
          tailf:cli-reset-siblings;
        }
        key "id band";
        leaf id {
          type uint8;
        }
        leaf band {
          tailf:cli-expose-key-name;
          type uint32;
        }
        leaf band-higher {
          tailf:cli-drop-node-name;
          type uint32;
        }
        leaf modulation {
          type enumeration {
            enum "8-QAM";
            enum "16-QAM";
            enum "32-QAM";
            enum "64-QAM";
            enum "128-QAM";
            enum "256-QAM";
            enum "512-QAM";
            enum "1024-QAM";
            enum "2048-QAM";
            enum "4096-QAM";
            enum "BPSK";
            enum "NONE";
            enum "QPSK";
          }
        }
        leaf pilot-pattern {
          type uint8;
        }
      }
      leaf shutdown {
        type empty;
      }
    }
  }

  grouping ip-explicit-path-grouping {
    list index {
      tailf:cli-suppress-mode;
      tailf:cli-delete-when-empty;
      tailf:cli-compact-syntax;
      key "id";
      leaf id {
        type uint16;
      }
      choice address-choice {
        leaf next-address {
          type inet:ipv4-address;
        }
        container next-address-loose {
          tailf:cli-drop-node-name;
          container next-address {
            leaf loose {
              type inet:ipv4-address;
            }
          }
        }
        leaf exclude-address {
          type inet:ipv4-address;
        }
        leaf next-label {
          type uint32;
        }
      }
    }
  }

  grouping radius-server-grouping {
    leaf auth-port {
      type uint16;
    }
    leaf acct-port {
      type uint16;
    }
    leaf timeout {
      type uint16;
    }
    leaf retransmit {
      type uint8;
    }
    container test {
      tailf:cli-flatten-container;
      leaf username {
        type string;
      }
    }
    leaf ignore-auth-port {
      type empty;
    }
    leaf ignore-acct-port {
      type empty;
    }
    leaf idle-time {
      type uint16;
    }
    leaf probe-on {
      type empty;
    }
    container key {
      tailf:cli-flatten-container;
      tailf:cli-compact-syntax;
      tailf:cli-sequence-commands;
      uses password-grouping {
        refine "secret";
      }
    }
  }

  grouping domain-advanced-smart-probes-burst-grouping {
    container burst {
      container burst {
        tailf:cli-drop-node-name;
        tailf:cli-compact-syntax;
        tailf:cli-sequence-commands;
        leaf number {
          tailf:cli-drop-node-name;
          type uint8;
        }
        leaf packets {
          type empty;
        }
        leaf every {
          type empty;
        }
        leaf interval {
          tailf:cli-drop-node-name;
          type uint8;
        }
        leaf seconds {
          type empty;
        }
        leaf only-burst {
          type empty;
        }
      }
      container quick {
        tailf:cli-compact-syntax;
        tailf:cli-sequence-commands;
        leaf number {
          tailf:cli-drop-node-name;
          type uint8;
        }
        leaf packets {
          type empty;
        }
        leaf every {
          type empty;
        }
        leaf interval {
          tailf:cli-drop-node-name;
          type uint8;
        }
        leaf seconds {
          type empty;
        }
        leaf only-burst {
          type empty;
        }
      }
    }
  }

  grouping domain-advanced-smart-probes-grouping {
    container smart-probes {
      uses domain-advanced-smart-probes-burst-grouping;
      list profile {
        tailf:cli-drop-node-name;
        tailf:cli-suppress-mode;
        tailf:cli-delete-when-empty;
        key "id";
        leaf id {
          type uint8;
        }
        uses domain-advanced-smart-probes-burst-grouping;
      }
    }
  }

  grouping domain-master-grouping {
    list master {
      tailf:cli-sequence-commands;
      key "type";
      leaf type {
        type enumeration {
          enum "branch";
          enum "hub";
          enum "regional-hub";
          enum "transit";
        }
      }
      leaf pop-id {
        tailf:cli-drop-node-name;
        tailf:cli-hide-in-submode;
        type uint8;
      }
      container source-interface {
        tailf:cli-break-sequence-commands;
        uses interface-name-grouping;
      }
      container site-prefixes {
        leaf prefix-list {
          type string;
        }
      }
      leaf hub {
        type inet:ipv4-address;
      }
      container collector {
        tailf:cli-compact-syntax;
        tailf:cli-sequence-commands {
          tailf:cli-reset-siblings;
        }
        leaf ip-address {
          tailf:cli-drop-node-name;
          type inet:ipv4-address;
        }
        leaf port {
          type uint16;
        }
      }
      container load-balance {
        tailf:cli-add-mode;
        leaf option {
          tailf:cli-drop-node-name;
          tailf:cli-hide-in-submode;
          type enumeration {
            enum "advanced";
          }
        }
        uses domain-path-preference-grouping;
      }
      container password {
        tailf:cli-compact-syntax;
        tailf:cli-sequence-commands;
        uses password-grouping {
          refine "secret";
        }
      }
      container enterprise-prefix {
        leaf prefix-list {
          type string;
        }
      }
      list monitor-interval {
        tailf:cli-suppress-mode;
        tailf:cli-delete-when-empty;
        key "seconds dscp";
        leaf seconds {
          type uint16;
        }
        leaf dscp {
          tailf:cli-expose-key-name;
          type dscp-type;
        }
      }
      container advanced {
        tailf:cli-add-mode;
        presence "true";
        uses domain-advanced-smart-probes-grouping;
        leaf channel-unreachable-timer {
          type uint16;
        }
        leaf inter-dc {
          type empty;
        }
      }
      list class {
        tailf:cli-sequence-commands;
        key "name";
        leaf name {
          type string;
        }
        leaf sequence {
          tailf:cli-hide-in-submode;
          type uint16;
        }
        container match {
          tailf:cli-break-sequence-commands;
          list dscp {
            tailf:cli-suppress-mode;
            tailf:cli-delete-when-empty;
            key "services-value";
            leaf services-value {
              type dscp-type;
            }
            leaf policy {
              type enumeration {
                enum "best-effort";
                enum "bulk-data";
                enum "custom";
                enum "low-latency-data";
                enum "real-time-video";
                enum "scavenger";
                enum "voice";
              }
            }
          }
          list application {
            tailf:cli-suppress-mode;
            tailf:cli-delete-when-empty;
            key "services-value";
            leaf services-value {
              type string;
            }
            leaf policy {
              type enumeration {
                enum "best-effort";
                enum "bulk-data";
                enum "custom";
                enum "low-latency-data";
                enum "real-time-video";
                enum "scavenger";
                enum "voice";
              }
            }
          }
        }
        uses domain-path-preference-grouping;
        leaf path-last-resort {
          type string;
        }
      }
    }
  }

  grouping domain-border-grouping {
    container border {
      tailf:cli-add-mode;
      presence "true";
      leaf master {
        type union {
          type inet:ipv4-address;
          type enumeration {
            enum "local";
          }
        }
      }
      container source-interface {
        uses interface-name-grouping;
      }
      container password {
        tailf:cli-compact-syntax;
        tailf:cli-sequence-commands;
        uses password-grouping {
          refine "secret";
        }
      }
    }
  }

  grouping carrier-delay-grouping {
    choice delay-choice {
      leaf seconds {
        tailf:cli-drop-node-name;
        type uint8;
      }
      leaf msec {
        type uint16;
      }
    }
  }

  grouping crypto-pki-server-lifetime-grouping {
    leaf days {
      tailf:cli-drop-node-name;
      type uint16;
    }
    leaf hours {
      tailf:cli-drop-node-name;
      type uint16;
    }
    leaf minutes {
      tailf:cli-drop-node-name;
      type uint16;
    }
  }

  grouping crypto-gdoi-local-server-grouping {
    leaf split-resilency {
      type boolean;
    }
    leaf gdoi {
      type boolean;
    }
    leaf gikev2 {
      type string;
    }
    container rekey {
      container lifetime {
        choice lifetime-choice {
          leaf seconds {
            type uint32;
          }
          leaf days {
            type uint32;
          }
        }
      }
      container algorithm {
        tailf:cli-compact-syntax;
        tailf:cli-sequence-commands {
          tailf:cli-reset-siblings;
        }
        leaf encryption {
          tailf:cli-drop-node-name;
          type enumeration {
            enum "3des-cbc";
            enum "des-cbc";
            enum "aes";
          }
        }
        leaf bits {
          tailf:cli-drop-node-name;
          type enumeration {
            enum "128";
            enum "192";
            enum "256";
          }
        }
      }
      container sig-hash {
        leaf algorithm {
          type enumeration {
            enum "sha";
            enum "sha256";
            enum "sha384";
            enum "sha512";
          }
        }
      }
      container retransmit {
        tailf:cli-compact-syntax;
        tailf:cli-sequence-commands {
          tailf:cli-reset-siblings;
        }
        leaf number-of-seconds {
          tailf:cli-drop-node-name;
          type uint8;
        }
        choice retransmit-choice {
          leaf number {
            type uint8;
          }
          leaf periodic {
            type empty;
          }
        }
      }
      container authentication {
        tailf:cli-compact-syntax;
        tailf:cli-sequence-commands {
          tailf:cli-reset-siblings;
        }
        choice authentication-choice {
          leaf mypubkey {
            type empty;
          }
          leaf pubkey {
            type empty;
          }
        }
        leaf rsa {
          type string;
        }
      }
      container transport {
        leaf unicast {
          type empty;
        }
      }
    }
    container identifier {
      tailf:cli-add-mode;
      container range {
        tailf:cli-compact-syntax;
        tailf:cli-sequence-commands;
        leaf lowest {
          tailf:cli-drop-node-name;
          type uint8;
        }
        leaf hyphen {
          tailf:alt-name "-";
          type empty;
        }
        leaf highest {
          tailf:cli-drop-node-name;
          type uint8;
        }
      }
    }
    container authorization {
      container address {
        leaf ipv4 {
          type union {
            type uint8;
            type string;
          }
        }
      }
      leaf identity {
        type string;
      }
    }
    container replay {
      container time {
        leaf window-size {
          type uint32;
        }
      }
    }
    container sa {
      leaf receive-only {
        type empty;
      }
      container d3p {
        container window {
          choice window-choice {
            leaf msec {
              type uint32;
            }
            leaf sec {
              type uint8;
            }
          }
        }
      }
      list ipsec {
        key "id";
        leaf id {
          type uint32;
        }
        leaf profile {
          type string;
        }
        container match {
          container address {
            choice address-choice {
              leaf ipv4 {
                type ext-ip-acl-type;
              }
              leaf ipv6 {
                type string;
              }
            }
          }
        }
        container replay {
          choice replay-choice {
            container time {
              leaf window-size {
                type uint8;
              }
            }
            container counter {
              leaf window-size {
                type ipsec-window-size-type;
              }
            }
          }
        }
        choice tag-choice {
          container tag {
            container cts {
              leaf sgt {
                type empty;
              }
            }
          }
          container tag-enable {
            tailf:cli-drop-node-name;
            leaf tag {
              type boolean;
            }
          }
        }
      }
    }
    container address {
      leaf ipv4 {
        type union {
          type inet:ipv4-address;
          type string;
        }
      }
    }
    container redundancy {
      tailf:cli-add-mode;
      container local {
        tailf:cli-delete-when-empty;
        presence "true";
        leaf priority {
          type uint8;
        }
      }
      container peer {
        container address {
          leaf-list ipv4 {
            ordered-by user;
            type inet:ipv4-address;
          }
        }
      }
      container protocol {
        leaf version {
          type enumeration {
            enum "base";
            enum "optimize";
          }
        }
      }
    }
    leaf pfs {
      type boolean;
    }
  }

  grouping crypto-pki-certificate-grouping {
    list certificate {
      tailf:cli-delete-when-empty;
      tailf:cli-compact-syntax;
      tailf:cli-sequence-commands;
      key "serial";
      leaf serial {
        type string;
      }
      leaf cert-type {
        tailf:cli-optional-in-sequence;
        tailf:cli-drop-node-name;
        tailf:cli-prefix-key;
        type enumeration {
          enum "ca";
          enum "ra-encrypt";
          enum "ra-general";
          enum "ra-sign";
          enum "rollover";
          enum "self-signed";
        }
      }
      leaf rollover {
        tailf:cli-optional-in-sequence;
        tailf:cli-prefix-key;
        type empty;
      }
      leaf cert {
        tailf:cli-drop-node-name;
        type string;
      }
    }
  }

  grouping mpls-label-mode-grouping {
    container protocol {
      choice protocol-choice {
        leaf all-afs {
          type mpls-label-mode-type;
        }
        case per-af {
          leaf bgp-vpnv4 {
            type mpls-label-mode-type;
          }
          leaf bgp-vpnv6 {
            type mpls-label-mode-type;
          }
        }
      }
    }
  }

  grouping track-timer-grouping {
    choice timer-choice {
      leaf seconds {
        tailf:cli-drop-node-name;
        type uint16;
      }
      leaf msec {
        type uint16;
      }
    }
  }

  grouping utd-web-filter-grouping {
    container web-filter {
      container block {
        container local-server {
          list profile {
            key "id";
            leaf id {
              type string;
            }
            container block-page-interface {
              leaf Loopback {
                tailf:cli-allow-join-with-value;
                type string;
              }
            }
            container content {
              choice content-choice {
                leaf text {
                  type string;
                }
                leaf file {
                  type string;
                }
              }
            }
            leaf http-ports {
              type string;
            }
          }
        }
        container page {
          list profile {
            key "id";
            leaf id {
              type string;
            }
            choice page-choice {
              leaf file {
                type string;
              }
              leaf redirect-url {
                type string;
              }
              leaf text {
                type string;
              }
            }
          }
        }
      }
      container domain;
      list sourcedb {
        key "id";
        leaf id {
          type string;
        }
        container logging {
          leaf level {
            type enumeration {
              enum "debug";
              enum "error";
              enum "info";
              enum "trace";
              enum "warning";
            }
          }
        }
      }
      container url {
        list profile {
          key "id";
          leaf id {
            type string;
          }
          leaf-list alert {
            tailf:cli-flat-list-syntax;
            type enumeration {
              enum "all";
              enum "blacklist";
              enum "categories-reputation";
              enum "whitelist";
            }
          }
          container blacklist {
            tailf:cli-add-mode;
            presence "true";
            container parameter-map {
              leaf regex {
                type string;
              }
            }
          }
          container categories {
            container allow {
              tailf:cli-add-mode;
              presence "true";
              list category {
                tailf:cli-drop-node-name;
                tailf:cli-suppress-mode;
                tailf:cli-delete-when-empty;
                key "name";
                leaf name {
                  tailf:cli-suppress-range;
                  type utd-category-type;
                }
              }
            }
            container block {
              tailf:cli-add-mode;
              presence "true";
              list category {
                tailf:cli-drop-node-name;
                tailf:cli-suppress-mode;
                tailf:cli-delete-when-empty;
                key "name";
                leaf name {
                  tailf:cli-suppress-range;
                  type utd-category-type;
                }
              }
            }
          }
          container block {
            leaf local-server {
              type string;
            }
            leaf page-profile {
              type string;
            }
          }
          container log {
            leaf level {
              type enumeration {
                enum "detailed";
                enum "error";
                enum "info";
              }
            }
          }
          container reputation {
            tailf:cli-add-mode;
            presence "true";
            leaf block-threshold {
              type enumeration {
                enum "high-risk";
                enum "low-risk";
                enum "moderate-risk";
                enum "suspicious";
                enum "trustworthy";
              }
            }
          }
          container sourcedb {
            container fail {
              leaf close {
                type empty;
              }
            }
          }
          container whitelist {
            tailf:cli-add-mode;
            presence "true";
            container parameter-map {
              leaf regex {
                type string;
              }
            }
          }
        }
      }
    }
  }

  grouping utd-engine-standard-grouping {
    container logging {
      list host {
        tailf:cli-suppress-mode;
        tailf:cli-delete-when-empty;
        key "name";
        leaf name {
          tailf:cli-suppress-range;
          type string;
        }
      }
      leaf syslog {
        type empty;
      }
    }
    container threat-inspection {
      tailf:cli-add-mode;
      presence "true";
      container signature {
        container update {
          container server {
            choice server-choice {
              container cisco {
                tailf:cli-compact-syntax;
                tailf:cli-sequence-commands {
                  tailf:cli-reset-siblings;
                }
                leaf username {
                  type string;
                }
                leaf password {
                  type string;
                }
              }
              container url {
                tailf:cli-compact-syntax;
                tailf:cli-sequence-commands {
                  tailf:cli-reset-siblings;
                }
                leaf path {
                  tailf:cli-drop-node-name;
                  type string;
                }
                leaf username {
                  type string;
                }
                leaf password {
                  type string;
                }
              }
            }
          }
          container occur-at {
            tailf:cli-compact-syntax;
            tailf:cli-sequence-commands {
              tailf:cli-reset-siblings;
            }
            choice occur-at-choice {
              leaf daily {
                type empty;
              }
              leaf weekly {
                type string;
              }
              leaf monthly {
                type string;
              }
            }
            leaf hours {
              tailf:cli-drop-node-name;
              type uint8;
            }
            leaf minutes {
              tailf:cli-drop-node-name;
              type uint8;
            }
          }
        }
      }
    }
  }

  grouping utd-engine-threat-inspection-grouping {
    leaf threat {
      type enumeration {
        enum "detection";
        enum "protection";
      }
    }
    leaf policy {
      type enumeration {
        enum "balanced";
        enum "connectivity";
        enum "security";
      }
    }
    container logging {
      leaf level {
        type enumeration {
          enum "emerg" {
            value 1;
          }
          enum "alert" {
            value 2;
          }
          enum "crit" {
            value 3;
          }
          enum "err" {
            value 4;
          }
          enum "warning" {
            value 5;
          }
          enum "notice" {
            value 6;
          }
          enum "info" {
            value 7;
          }
          enum "debug" {
            value 8;
          }
        }
      }
    }
  }

  grouping pseudowire-preferred-path-grouping {
    container preferred-path {
      tailf:cli-compact-syntax;
      tailf:cli-sequence-commands;
      choice path-choice {
        leaf peer {
          type inet:host;
        }
        container interface {
          tailf:cli-compact-syntax;
          tailf:cli-sequence-commands;
          leaf Tunnel {
            tailf:cli-allow-join-with-value;
            type uint32;
          }
          leaf disable-fallback {
            type empty;
          }
        }
        container segment-routing {
          tailf:cli-flatten-container;
          container traffic-eng {
            tailf:cli-flatten-container;
            choice te-choice {
              leaf attribute-set {
                type string;
              }
              leaf policy {
                type string;
              }
            }
          }
        }
      }
      leaf disable-fallback {
        type empty;
      }
    }
  }

  grouping enable-secret-grouping {
    leaf algorithm-type {
      tailf:cli-optional-in-sequence;
      type enumeration {
        enum "md5";
        enum "scrypt";
        enum "sha256";
      }
    }
    leaf type {
      tailf:cli-drop-node-name;
      tailf:cli-optional-in-sequence;
      type enumeration {
        enum "0";
        enum "4";
        enum "5";
        enum "8";
        enum "9";
      }
    }
    leaf secret {
      tailf:cli-drop-node-name;
      type string;
    }
  }

  grouping pppoe-client-grouping {
    container pppoe-client {
      list dial-pool-number {
        tailf:cli-suppress-mode;
        tailf:cli-delete-when-empty;
        tailf:cli-compact-syntax;
        key "id";
        leaf id {
          type uint8;
        }
        leaf dial-on-demand {
          type empty;
        }
        leaf restart {
          type uint16;
        }
        leaf mac-override {
          type empty;
        }
        leaf service-name {
          type string;
        }
      }
      leaf ppp-max-payload {
        type uint16;
      }
    }
  }

  grouping if-tunnel-mpls-traffic-eng-path-option-grouping {
    leaf segment-routing {
      tailf:cli-break-sequence-commands;
      type empty;
    }
    leaf pce {
      type empty;
    }
    leaf attributes {
      type string;
    }
    leaf non-revertive {
      type empty;
    }
    leaf lockdown {
      type empty;
    }
    leaf sticky {
      type empty;
    }
    container bandwidth {
      tailf:cli-flatten-container;
      tailf:cli-compact-syntax;
      tailf:cli-sequence-commands {
        tailf:cli-reset-siblings;
      }
      leaf sub-pool {
        tailf:cli-optional-in-sequence;
        type empty;
      }
      leaf value {
        tailf:cli-drop-node-name;
        type uint32;
      }
    }
    leaf verbatim {
      type empty;
    }
  }

  grouping interface-isdn-outgoing-ie-grouping {
    container codeset_0 {
      tailf:cli-delete-when-empty;
      presence "true";
      container message {
        leaf alerting {
          type empty;
        }
        leaf callproc {
          type empty;
        }
        leaf connect {
          type empty;
        }
        leaf disconnect {
          type empty;
        }
        leaf facility {
          type empty;
        }
        leaf information {
          type empty;
        }
        leaf progress {
          type empty;
        }
        leaf rel_comp {
          type empty;
        }
        leaf release {
          type empty;
        }
        leaf setup {
          type empty;
        }
        leaf setup-ack {
          type empty;
        }
      }
    }
  }

  grouping interface-cem-grouping {
    list cem {
      key "id";
      leaf id {
        type uint16;
      }
      container cem {
        leaf class {
          type string;
        }
      }
      leaf rtp-present {
        type empty;
      }
      container service-policy {
        leaf input {
          type string;
        }
      }
      leaf idle-pattern {
        type string;
      }
      uses xconnect-grouping;
    }
  }

  grouping snmp-context-grouping {
    container snmp {
      list context {
        tailf:cli-suppress-mode;
        tailf:cli-delete-when-empty;
        key "name";
        leaf name {
          type string;
        }
        container community {
          tailf:cli-compact-syntax;
          tailf:cli-sequence-commands {
            tailf:cli-reset-siblings;
          }
          leaf community-string {
            tailf:cli-drop-node-name;
            type string;
          }
          leaf access {
            tailf:cli-drop-node-name;
            tailf:cli-optional-in-sequence;
            type enumeration {
              enum "RO";
              enum "RW";
            }
          }
          leaf ipv6 {
            tailf:cli-optional-in-sequence;
            type string;
          }
          leaf access-list-name {
            tailf:cli-drop-node-name;
            type std-ip-acl-type;
          }
        }
        container user {
          tailf:cli-compact-syntax;
          tailf:cli-sequence-commands {
            tailf:cli-reset-siblings;
          }
          leaf name {
            tailf:cli-drop-node-name;
            type string;
          }
        }
      }
    }
  }

  grouping ptp-clock-domain-grouping {
    leaf profile {
      tailf:cli-hide-in-submode;
      type enumeration {
        enum "g8265.1";
        enum "g8275.1";
        enum "g8275.2";
      }
    }
    leaf local-priority {
      type uint8;
    }
    leaf priority1 {
      type uint8;
    }
    leaf priority2 {
      type uint8;
    }
    container servo {
      leaf tracking-type {
        type enumeration {
          enum "Frequency";
          enum "R-DTI";
        }
      }
    }
    container time-properties {
      container gps {
        tailf:cli-compact-syntax;
        tailf:cli-sequence-commands {
          tailf:cli-reset-siblings;
        }
        leaf timeScale {
          tailf:cli-drop-node-name;
          type enumeration {
            enum "timeScaleFALSE";
            enum "timeScaleTRUE";
          }
        }
        leaf currentUtcOffsetValid {
          tailf:cli-drop-node-name;
          type enumeration {
            enum "currentUtcOffsetValidFALSE";
            enum "currentUtcOffsetValidTRUE";
          }
        }
        leaf leap59 {
          tailf:cli-drop-node-name;
          type enumeration {
            enum "leap59FALSE";
            enum "leap59TRUE";
          }
        }
        leaf leap61 {
          tailf:cli-drop-node-name;
          type enumeration {
            enum "leap61FALSE";
            enum "leap61TRUE";
          }
        }
        leaf currentUtcOffset {
          tailf:cli-drop-node-name;
          type uint16;
        }
      }
    }
    list clock-port {
      key "name";
      leaf name {
        type string;
      }
      leaf mode {
        tailf:cli-drop-node-name;
        tailf:cli-hide-in-submode;
        type enumeration {
          enum "master";
          enum "slave";
        }
      }
      leaf profile {
        tailf:cli-hide-in-submode;
        type enumeration {
          enum "g8265.1";
          enum "g8275.1";
          enum "g8275.2";
        }
      }
      leaf local-priority {
        tailf:cli-hide-in-submode;
        type uint8;
      }
      container delay-req {
        leaf interval {
          type int8;
        }
      }
      container announce {
        leaf interval {
          type int8;
        }
        leaf timeout {
          type uint8;
        }
      }
      container sync {
        leaf interval {
          type int8;
        }
        leaf one-step {
          type empty;
        }
      }
      container transport {
        tailf:cli-compact-syntax;
        tailf:cli-sequence-commands {
          tailf:cli-reset-siblings;
        }
        leaf proto {
          tailf:cli-drop-node-name;
          type enumeration {
            enum "ethernet";
            enum "ipv4";
            enum "ipv6";
          }
        }
        choice af-choice {
          leaf unicast {
            tailf:cli-optional-in-sequence;
            type empty;
          }
          leaf multicast {
            type empty;
          }
        }
        leaf interface {
          tailf:cli-optional-in-sequence;
          type string;
        }
        leaf negotiation {
          tailf:cli-optional-in-sequence;
          type empty;
        }
        leaf single-hop {
          type empty;
        }
      }
      container clock {
        choice source-choice {
          leaf source {
            type string;
          }
          container source-conf {
            tailf:cli-drop-node-name;
            container source {
              leaf ipv6 {
                type inet:ipv6-address;
              }
            }
          }
        }
        list source-priority {
          tailf:cli-drop-node-name;
          tailf:cli-suppress-mode;
          tailf:cli-delete-when-empty;
          tailf:cli-compact-syntax;
          tailf:cli-sequence-commands;
          key "priority";
          leaf source {
            tailf:cli-prefix-key;
            type string;
          }
          leaf priority {
            type uint8;
          }
        }
        leaf destination {
          type string;
        }
      }
    }
  }

  grouping controller-SONET-grouping {
    leaf description {
      tailf:cli-multi-value;
      type string;
    }
    leaf shutdown {
      type empty;
    }
    container snmp {
      container trap {
        leaf link-status {
          type boolean;
        }
      }
    }
    leaf rate {
      type string;
    }
    leaf ais-shut {
      type boolean;
    }
    leaf TU-AIS {
      type boolean;
    }
    leaf alarm-report {
      type enumeration {
        enum "all";
      }
    }
    container threshold {
      leaf sf-ber {
        type uint8;
      }
    }
    leaf framing {
      type enumeration {
        enum "sdh";
        enum "sonet";
      }
    }
    container clock {
      leaf source {
        type enumeration {
          enum "line";
          enum "internal";
        }
      }
    }
    container loopback {
      choice loopback-choice {
        container local {
          presence "true";
        }
        container network {
          presence "true";
        }
      }
    }
    container aug {
      leaf mapping {
        type enumeration {
          enum "au-3";
          enum "au-4";
        }
      }
    }
    container overhead {
      leaf j0 {
        type uint8;
      }
    }
    list au-3 {
      key "id";
      leaf id {
        type uint8;
      }
      container overhead {
        container j1 {
          tailf:cli-compact-syntax;
          leaf length {
            type enumeration {
              enum "16";
              enum "64";
            }
          }
        }
      }
      leaf mode {
        type enumeration {
          enum "c-11";
        }
      }
      list tug-2 {
        tailf:cli-suppress-mode;
        tailf:cli-delete-when-empty;
        key "tug-2 t1";
        leaf tug-2 {
          type uint8;
        }
        leaf t1 {
          tailf:cli-expose-key-name;
          type uint8;
        }
        container clock {
          leaf source {
            type enumeration {
              enum "line";
              enum "internal";
            }
          }
        }
      }
    }
    list au-4 {
      tailf:cli-suppress-mode;
      tailf:cli-delete-when-empty;
      key "id";
      leaf id {
        type uint8;
      }
      container threshold {
        leaf b3-tca {
          type uint8;
        }
      }
      list tug-3 {
        key "id";
        leaf id {
          type uint8;
        }
        leaf mode {
          type enumeration {
            enum "c-12";
          }
        }
        list tug-2 {
          tailf:cli-suppress-mode;
          tailf:cli-delete-when-empty;
          key "tug-2 e1";
          leaf tug-2 {
            type uint8;
          }
          leaf e1 {
            tailf:cli-expose-key-name;
            type uint8;
          }
          container ima-group {
            leaf group-number {
              tailf:cli-drop-node-name;
              type uint8;
            }
          }
          list channel-group {
            tailf:cli-suppress-mode;
            tailf:cli-delete-when-empty;
            key "id";
            leaf id {
              type uint8;
            }
            leaf-list timeslots {
              tailf:cli-range-list-syntax;
              type uint16;
            }
          }
          list cem-group {
            tailf:cli-suppress-mode;
            tailf:cli-delete-when-empty;
            key "id";
            leaf id {
              type uint16;
            }
            leaf unframed {
              type empty;
            }
            leaf-list timeslots {
              tailf:cli-range-list-syntax;
              type uint8;
            }
          }
          leaf framing {
            type enumeration {
              enum "crc4";
              enum "no-crc4";
              enum "unframed";
            }
          }
          leaf unframed {
            type empty;
          }
          container clock {
            leaf source {
              type enumeration {
                enum "line";
                enum "internal";
              }
            }
          }
          uses description-grouping;
        }
      }
    }
    container sts-3c {
      tailf:cli-drop-node-name;
      list sts-1 {
        key "id";
        leaf id {
          type string;
        }
        leaf mode {
          tailf:cli-hide-in-submode;
          type enumeration {
            enum "sts-3c";
          }
        }
        container cem-group {
          tailf:cli-compact-syntax;
          tailf:cli-sequence-commands {
            tailf:cli-reset-siblings;
          }
          leaf id {
            tailf:cli-drop-node-name;
            type uint16;
          }
          leaf cep {
            type empty;
          }
        }
        container clock {
          leaf source {
            type enumeration {
              enum "line";
              enum "internal";
              enum "recovered";
              enum "enhanced";
            }
          }
        }
      }
    }
    list sts-1 {
      key "id";
      leaf id {
        type uint8;
      }
      uses description-grouping;
      container clock {
        leaf source {
          type enumeration {
            enum "line";
            enum "internal";
            enum "recovered";
            enum "enhanced";
          }
        }
      }
      container loopback {
        choice loopback-choice {
          container local {
            presence "true";
          }
          container network {
            tailf:cli-delete-when-empty;
            presence "true";
            leaf line {
              type empty;
            }
          }
        }
      }
      container cem-group {
        tailf:cli-compact-syntax;
        tailf:cli-sequence-commands {
          tailf:cli-reset-siblings;
        }
        leaf id {
          tailf:cli-drop-node-name;
          type uint16;
        }
        leaf unframed {
          tailf:cli-optional-in-sequence;
          type empty;
        }
        leaf cep {
          type empty;
        }
      }
      container t3 {
        container clock {
          leaf source {
            type enumeration {
              enum "line";
              enum "internal";
              enum "recovered";
            }
          }
        }
      }
      list vtg {
        tailf:cli-suppress-mode;
        tailf:cli-delete-when-empty;
        key "id t1";
        leaf id {
          type uint8;
        }
        leaf t1 {
          tailf:cli-expose-key-name;
          type uint8;
        }
        leaf description {
          tailf:cli-multi-value;
          type string;
        }
        container Loopback {
          choice loopback-choice {
            leaf Local {
              type empty;
            }
            container Network {
              tailf:cli-delete-when-empty;
              presence "true";
              leaf line {
                type empty;
              }
            }
          }
        }
        leaf framing {
          type enumeration {
            enum "ESF";
            enum "SF";
            enum "unframed";
          }
        }
        container cem-group {
          tailf:cli-compact-syntax;
          tailf:cli-sequence-commands {
            tailf:cli-reset-siblings;
          }
          leaf id {
            tailf:cli-drop-node-name;
            type uint16;
          }
          leaf unframed {
            tailf:cli-optional-in-sequence;
            type empty;
          }
          leaf-list timeslots {
            tailf:cli-range-list-syntax;
            type uint8;
          }
        }
        list channel-group {
          tailf:cli-suppress-mode;
          tailf:cli-delete-when-empty;
          key "id";
          leaf id {
            type uint8;
          }
          leaf-list timeslots {
            tailf:cli-range-list-syntax;
            type uint8;
          }
        }
      }
      container mode {
        choice mode-choice {
          leaf ct3 {
            type empty;
          }
          leaf ct3-e1 {
            type empty;
          }
          leaf t3 {
            type empty;
          }
          leaf unframed {
            type empty;
          }
          leaf vt-15 {
            type empty;
          }
          leaf vt-2 {
            type empty;
          }
        }
      }
    }
    container aps {
      container group {
        leaf value {
          tailf:cli-drop-node-name;
          type uint8;
        }
        leaf acr {
          type uint8;
        }
      }
      leaf working {
        type uint8;
      }
      container timers {
        tailf:cli-compact-syntax;
        tailf:cli-sequence-commands {
          tailf:cli-reset-siblings;
        }
        leaf seconds1 {
          tailf:cli-drop-node-name;
          type uint8;
        }
        leaf seconds2 {
          tailf:cli-drop-node-name;
          type uint8;
        }
        leaf seconds3 {
          tailf:cli-drop-node-name;
          type uint16;
        }
      }
      leaf authentication {
        type string;
      }
      leaf hspw-icrm-grp {
        type uint32;
      }
      list protect {
        tailf:cli-suppress-mode;
        tailf:cli-delete-when-empty;
        key "id";
        leaf id {
          type uint8;
        }
        leaf address {
          tailf:cli-drop-node-name;
          type inet:ipv4-address;
        }
      }
    }
  }

  grouping mls-rate-limit-grouping {
    leaf pps {
      tailf:cli-drop-node-name;
      type uint32;
    }
    leaf packets-in-burst {
      tailf:cli-drop-node-name;
      type uint8;
    }
  }

  grouping ap-dot11-ghz-grouping {
    leaf shutdown {
      type empty;
    }
    container rrm {
      container monitor {
        leaf channel-list {
          type enumeration {
            enum "all";
            enum "country";
            enum "dca";
          }
        }
      }
      container channel {
        leaf cleanair-event {
          type empty;
        }
        container cleanair-event-conf {
          tailf:cli-drop-node-name;
          container cleanair-event {
            leaf sensitivity {
              type enumeration {
                enum "low";
                enum "medium";
                enum "high";
                enum "custom";
              }
            }
          }
        }
        list dca {
          tailf:cli-suppress-mode;
          tailf:cli-delete-when-empty;
          key "id";
          leaf id {
            type uint8;
          }
          leaf action {
            tailf:cli-drop-node-name;
            tailf:cli-prefix-key;
            type enumeration {
              enum "add";
              enum "remove";
            }
          }
        }
        container dca-conf {
          tailf:cli-drop-node-name;
          container dca {
            container chan-width {
              leaf width-max {
                type string;
              }
              leaf value {
                tailf:cli-drop-node-name;
                type enumeration {
                  enum "20";
                  enum "40";
                  enum "80";
                  enum "80+80";
                  enum "160";
                  enum "best";
                }
              }
            }
            leaf interval {
              type uint8;
            }
          }
        }
      }
      container txpower {
        leaf max {
          type int8;
        }
        leaf min {
          type int8;
        }
      }
      container tpc {
        leaf threshold {
          type int8;
        }
      }
    }
    leaf beamforming {
      type empty;
    }
    container cac {
      container voice {
        container sip {
          presence "true";
        }
        leaf acm {
          type empty;
        }
      }
    }
    leaf exp-bwreq {
      type empty;
    }
    leaf tsm {
      type empty;
    }
    leaf edca-parameters {
      type enumeration {
        enum "custom-voice";
        enum "fastlane";
        enum "optimized-video-voice";
        enum "optimized-voice";
        enum "svp-voice";
        enum "wmm-default";
      }
    }
    container channelswitch-conf {
      tailf:cli-drop-node-name;
      container channelswitch {
        leaf quiet {
          type empty;
        }
      }
    }
    list rate {
      tailf:cli-suppress-mode;
      tailf:cli-delete-when-empty;
      key "name";
      leaf name {
        type string;
      }
      leaf mode {
        tailf:cli-drop-node-name;
        type enumeration {
          enum "disable";
          enum "mandatory";
          enum "supported";
        }
      }
    }
    list rf-profile {
      key "name";
      leaf name {
        type string;
      }
      container channel {
        list add {
          tailf:cli-suppress-mode;
          tailf:cli-delete-when-empty;
          key "id";
          leaf id {
            type uint8;
          }
        }
        list remove {
          tailf:cli-suppress-mode;
          tailf:cli-delete-when-empty;
          key "id";
          leaf id {
            type uint8;
          }
        }
        leaf chan-width {
          type enumeration {
            enum "20";
            enum "40";
            enum "80";
            enum "80+80";
            enum "160";
            enum "best";
          }
        }
      }
      leaf client-network-preference {
        type enumeration {
          enum "connectivity";
          enum "default";
          enum "throughput";
        }
      }
      container coverage {
        container data {
          container rssi {
            leaf threshold {
              type int8;
            }
          }
        }
        leaf level {
          type uint8;
        }
        container voice {
          container rssi {
            leaf threshold {
              type int8;
            }
          }
        }
        leaf exception {
          type uint8;
        }
      }
      leaf description {
        type string;
      }
      container high-density {
        container rx-sop {
          tailf:cli-compact-syntax;
          tailf:cli-sequence-commands {
            tailf:cli-reset-siblings;
          }
          leaf threshold {
            type enumeration {
              enum "auto";
              enum "custom";
              enum "low";
              enum "medium";
              enum "high";
            }
          }
          leaf value {
            tailf:cli-drop-node-name;
            type int8;
          }
        }
      }
      container tx-power {
        leaf max {
          type int8;
        }
        leaf min {
          type int8;
        }
        container v1 {
          leaf threshold {
            type int8;
          }
        }
      }
      list rate {
        tailf:cli-suppress-mode;
        tailf:cli-delete-when-empty;
        key "name";
        leaf name {
          type string;
        }
        leaf mode {
          tailf:cli-drop-node-name;
          type enumeration {
            enum "disable";
            enum "mandatory";
            enum "supported";
          }
        }
      }
      leaf shutdown {
        type boolean;
      }
    }
  }

  grouping bfd-template-grouping {
    container interval {
      tailf:cli-compact-syntax;
      tailf:cli-sequence-commands {
        tailf:cli-reset-siblings;
      }
      leaf min-tx {
        type uint16;
      }
      leaf min-rx {
        tailf:code-name "bfd-template-min-rx";
        type uint16;
      }
      leaf multiplier {
        type uint8;
      }
    }
    container authentication {
      tailf:cli-compact-syntax;
      tailf:cli-sequence-commands;
      leaf algorithm {
        tailf:cli-drop-node-name;
        type enumeration {
          enum "md5";
          enum "meticulous-md5";
          enum "meticulous-sha-1";
          enum "sha-1";
        }
      }
      leaf keychain {
        type string;
      }
    }
    leaf echo {
      type empty;
    }
  }

  grouping l2-vfi-grouping {
    choice neighbor-choice {
      leaf encapsulation {
        tailf:cli-optional-in-sequence;
        tailf:cli-hide-in-submode;
        type enumeration {
          enum "mpls";
          enum "l2tpv3";
        }
      }
      leaf pw-class {
        tailf:cli-hide-in-submode;
        type string;
      }
    }
    leaf no-split-horizon {
      tailf:cli-hide-in-submode;
      type empty;
    }
    container mpls {
      leaf control-word {
        type empty;
      }
      container label {
        tailf:cli-compact-syntax;
        tailf:cli-sequence-commands;
        leaf local {
          tailf:cli-drop-node-name;
          type uint32;
        }
        leaf remote {
          tailf:cli-drop-node-name;
          type uint32;
        }
      }
    }
  }

  grouping bundle-interface-cable-common {
    leaf nd {
      type boolean;
    }
    container conf {
      tailf:cli-drop-node-name;
      leaf arp {
        type boolean;
      }
    }
    leaf proxy-arp {
      type boolean;
    }
    leaf source-verify {
      type empty;
    }
    container source-verify-conf {
      tailf:cli-drop-node-name;
      container source-verify {
        container dhcp {
          presence "true";
          leaf server {
            type inet:ipv4-address;
          }
        }
        container leasequery-filter {
          container upstream {
            tailf:cli-compact-syntax;
            tailf:cli-sequence-commands;
            leaf threshold {
              tailf:cli-drop-node-name;
              type uint8;
            }
            leaf interval {
              tailf:cli-drop-node-name;
              type uint8;
            }
          }
        }
        leaf leasetimer {
          type uint8;
        }
      }
    }
    container ipv6 {
      container source-verify {
        container dhcp {
          presence "true";
          leaf server {
            type inet:ipv6-address;
          }
        }
        container leasequery-filter {
          container upstream {
            tailf:cli-compact-syntax;
            tailf:cli-sequence-commands;
            leaf threshold {
              tailf:cli-drop-node-name;
              type uint8;
            }
            leaf interval {
              tailf:cli-drop-node-name;
              type uint8;
            }
          }
        }
        leaf leasetimer {
          type uint8;
        }
      }
    }
    container dhcp-giaddr {
      choice dhcp-giaddr-choice {
        container policy {
          presence "true";
        }
        leaf primary {
          type empty;
        }
      }
    }
    list helper-address {
      tailf:cli-suppress-mode;
      tailf:cli-delete-when-empty;
      key "IP-address";
      leaf IP-address {
        type inet:ipv4-address;
      }
    }
  }

  grouping ip-sla-reaction-grouping {
    container threshold-value {
      tailf:cli-break-sequence-commands;
      tailf:cli-flatten-container;
      tailf:cli-compact-syntax;
      tailf:cli-sequence-commands;
      leaf upper-threshold {
        tailf:cli-drop-node-name;
        type uint16;
      }
      leaf lower-threshold {
        tailf:cli-drop-node-name;
        type uint16;
      }
    }
    container threshold-type {
      tailf:cli-flatten-container;
      tailf:cli-compact-syntax;
      tailf:cli-sequence-commands {
        tailf:cli-reset-siblings;
      }
      choice threshold-type-choice {
        case average {
          leaf average {
            type empty;
          }
          leaf n {
            tailf:cli-drop-node-name;
            type uint8;
          }
        }
        container average-no-n {
          tailf:cli-drop-node-name;
          tailf:cli-flatten-container;
          tailf:cli-compact-syntax;
          leaf average {
            type empty;
          }
        }
        case consecutive {
          leaf consecutive {
            type empty;
          }
          leaf number {
            tailf:cli-drop-node-name;
            type uint8;
          }
        }
        leaf immediate {
          type empty;
        }
        leaf never {
          type empty;
        }
        container xOfy {
          tailf:cli-flatten-container;
          tailf:cli-compact-syntax;
          tailf:cli-sequence-commands;
          leaf x {
            tailf:cli-drop-node-name;
            type uint8;
          }
          leaf y {
            tailf:cli-drop-node-name;
            type uint8;
          }
        }
      }
    }
    leaf action-type {
      type enumeration {
        enum "none";
        enum "trapAndTrigger";
        enum "trapOnly";
        enum "triggerOnly";
      }
    }
  }

  grouping sr-connected-prefix-sid-map-af-grouping {
    list address-list {
      tailf:cli-drop-node-name;
      tailf:cli-suppress-mode;
      tailf:cli-delete-when-empty;
      tailf:cli-compact-syntax;
      tailf:cli-sequence-commands {
        tailf:cli-reset-siblings;
      }
      key "prefix";
      leaf prefix {
        type ios:ipv4-prefix;
      }
      choice absolute-or-index {
        leaf absolute {
          type uint32;
        }
        leaf index {
          type uint32;
        }
      }
      leaf range {
        type uint32;
      }
    }
  }

  grouping segment-routing-preference-grouping {
    container explicit {
      list segment-list {
        tailf:cli-suppress-mode;
        tailf:cli-delete-when-empty;
        tailf:cli-compact-syntax;
        tailf:cli-sequence-commands {
          tailf:cli-reset-siblings;
        }
        key "name";
        leaf name {
          type string;
        }
        leaf weight {
          type uint32;
        }
      }
    }
    uses description-grouping;
    container constraints {
      tailf:cli-add-mode;
      presence "true";
      leaf bandwidth {
        type uint32;
      }
      container segments {
        tailf:cli-add-mode;
        container dataplane {
          choice dataplane-choice {
            leaf mpls {
              type empty;
            }
            leaf srv6 {
              type empty;
            }
          }
        }
        leaf type {
          type enumeration {
            enum "protected";
            enum "unprotected";
          }
        }
        leaf algorithm {
          type uint8;
        }
      }
      container affinity {
        tailf:cli-add-mode;
        list attribute-list {
          tailf:cli-drop-node-name;
          key "id";
          leaf id {
            type enumeration {
              enum "exclude-any";
              enum "include-all";
              enum "include-any";
            }
          }
          list name {
            tailf:cli-suppress-mode;
            tailf:cli-delete-when-empty;
            key "name";
            leaf name {
              type string;
            }
          }
        }
      }
      container association-group {
        tailf:cli-add-mode;
        leaf identifier {
          type uint16;
        }
        container disjointness {
          leaf type {
            type enumeration {
              enum "link";
              enum "node";
              enum "srlg";
            }
          }
        }
        leaf source {
          type inet:ipv4-address;
        }
      }
    }
    container dynamic {
      tailf:cli-add-mode;
      presence "true";
      leaf pcep {
        type empty;
      }
      container metric {
        tailf:cli-add-mode;
        leaf type {
          type enumeration {
            enum "delay";
            enum "igp";
            enum "te";
          }
        }
        leaf sid-limit {
          type uint8;
        }
        container margin {
          tailf:cli-add-mode;
          leaf absolute {
            type uint32;
          }
          leaf relative {
            type uint8;
          }
        }
      }
    }
    container per-flow {
      tailf:cli-add-mode;
      presence "true";
      list forward-class {
        tailf:cli-suppress-mode;
        tailf:cli-delete-when-empty;
        key "id";
        leaf id {
          type uint8;
        }
        leaf color {
          type uint32;
        }
      }
    }
  }

  grouping ip-sla-distribution-delay-grouping {
    container one-way {
      tailf:cli-compact-syntax;
      tailf:cli-sequence-commands {
        tailf:cli-reset-siblings;
      }
      leaf number-of-bins {
        tailf:cli-drop-node-name;
        type uint8;
      }
      leaf boundary {
        tailf:cli-drop-node-name;
        type string;
      }
    }
    container two-way {
      tailf:cli-compact-syntax;
      tailf:cli-sequence-commands {
        tailf:cli-reset-siblings;
      }
      leaf number-of-bins {
        tailf:cli-drop-node-name;
        type uint8;
      }
      leaf boundary {
        tailf:cli-drop-node-name;
        type string;
      }
    }
  }

  grouping ip-flow-monitor-grouping {
    list monitor {
      tailf:cli-suppress-mode;
      tailf:cli-delete-when-empty;
      tailf:cli-compact-syntax;
      tailf:cli-sequence-commands {
        tailf:cli-reset-siblings;
      }
      key "name direction";
      leaf name {
        type string;
      }
      leaf sampler {
        tailf:cli-prefix-key {
          tailf:cli-before-key "2";
        }
        tailf:cli-optional-in-sequence;
        type string;
      }
      leaf direction {
        type enumeration {
          enum "input";
          enum "output";
        }
      }
    }
  }

  grouping router-bgp-af-ipvx-vrf-advertise-l2vpn-grouping {
    container advertise {
      container l2vpn {
        container evpn {
          tailf:cli-delete-when-empty;
          presence "true";
          leaf limit {
            tailf:cli-drop-node-name;
            type uint32;
          }
        }
      }
    }
  }

  grouping ip-rsvp-policy-local-grouping {
    container local {
      list identity {
        key "name";
        leaf name {
          type string;
        }
        uses ip-rsvp-policy-local-contents-grouping;
      }
      container default {
        tailf:cli-add-mode;
        uses ip-rsvp-policy-local-contents-grouping;
      }
    }
  }

  grouping ip-rsvp-policy-local-contents-grouping {
    container maximum {
      container bandwidth {
        leaf group {
          type uint32;
        }
        leaf ingress {
          type uint32;
        }
        leaf single {
          type uint32;
        }
      }
    }
    container forward {
      choice forward-choice {
        leaf all {
          type empty;
        }
        case messages-case {
          leaf path {
            type empty;
          }
          leaf resv {
            type empty;
          }
          leaf path-error {
            type empty;
          }
          leaf resv-error {
            type empty;
          }
        }
      }
    }
  }

  leaf hostname {
    type string;
  }
  container upgrade {
    container fpd {
      leaf auto {
        type empty;
      }
      leaf path {
        type string;
      }
    }
  }
  leaf version {
    type string;
  }
  container service {
    leaf config {
      type empty;
    }
    leaf exec-callback {
      type empty;
    }
    leaf nagle {
      type empty;
    }
    leaf slave-log {
      type boolean;
    }
    container pad {
      leaf to-xot {
        type empty;
      }
      leaf from-xot {
        type empty;
      }
      leaf cmns {
        type empty;
      }
    }
    container conf {
      tailf:cli-drop-node-name;
      leaf pad {
        type boolean;
      }
    }
    leaf tcp-keepalives-in {
      type empty;
    }
    leaf tcp-keepalives-out {
      type empty;
    }
    container timestamps {
      tailf:cli-compact-syntax;
      tailf:cli-delete-when-empty;
      presence "true";
      container debug {
        choice timestamp-choice {
          leaf uptime {
            type empty;
          }
          container datetime {
            tailf:cli-compact-syntax;
            tailf:cli-delete-when-empty;
            presence "true";
            leaf msec {
              type empty;
            }
            leaf localtime {
              type empty;
            }
            leaf show-timezone {
              type empty;
            }
            leaf year {
              type empty;
            }
          }
        }
      }
      container log {
        choice timestamp-choice {
          leaf uptime {
            type empty;
          }
          container datetime {
            tailf:cli-compact-syntax;
            tailf:cli-delete-when-empty;
            presence "true";
            leaf msec {
              type empty;
            }
            leaf localtime {
              type empty;
            }
            leaf show-timezone {
              type empty;
            }
            leaf year {
              type empty;
            }
          }
        }
      }
    }
    container password-encryption {
      presence "true";
    }
    leaf password-recovery {
      type boolean;
    }
    leaf exec-wait {
      type empty;
    }
    leaf linenumber {
      type empty;
    }
    leaf compress-config {
      type empty;
    }
    leaf udp-small-servers {
      type empty;
    }
    container prompt {
      leaf config {
        type boolean;
      }
    }
    leaf tcp-small-servers {
      type empty;
    }
    leaf old-slip-prompts {
      type empty;
    }
    leaf pt-vty-logging {
      type empty;
    }
    leaf disable-ip-fast-frag {
      type empty;
    }
    leaf sequence-numbers {
      type empty;
    }
    container divert-rate-limit {
      list ip {
        tailf:cli-suppress-mode;
        tailf:cli-delete-when-empty;
        tailf:cli-compact-syntax;
        tailf:cli-sequence-commands;
        key "divert-code";
        leaf divert-code {
          type string;
        }
        leaf rate {
          type uint16;
        }
        leaf limit {
          type uint16;
        }
      }
      list ipv6 {
        tailf:cli-suppress-mode;
        tailf:cli-delete-when-empty;
        tailf:cli-compact-syntax;
        tailf:cli-sequence-commands;
        key "divert-code";
        leaf divert-code {
          type string;
        }
        leaf rate {
          type uint16;
        }
        leaf limit {
          type uint16;
        }
      }
      list trusted-site {
        tailf:cli-suppress-mode;
        tailf:cli-delete-when-empty;
        key "ip-address mask-ip-address tos mask";
        leaf ip-address {
          type inet:ipv4-address;
        }
        leaf mask-ip-address {
          type inet:ipv4-address;
        }
        leaf tos {
          tailf:cli-expose-key-name;
          type string;
        }
        leaf mask {
          tailf:cli-expose-key-name;
          type string;
        }
      }
      list trusted-site-ipv6 {
        tailf:cli-suppress-mode;
        tailf:cli-delete-when-empty;
        key "ip-address traffic-class mask";
        leaf ip-address {
          type ios:ipv6-prefix;
        }
        leaf traffic-class {
          tailf:cli-expose-key-name;
          type string;
        }
        leaf mask {
          tailf:cli-expose-key-name;
          type string;
        }
      }
    }
    container counters {
      container max {
        leaf age {
          type uint8;
        }
      }
    }
    container alignment {
      leaf detection {
        type boolean;
      }
      leaf logging {
        type boolean;
      }
    }
    leaf call-home {
      type empty;
    }
    leaf dhcp {
      type boolean;
    }
    leaf finger {
      type empty;
    }
    container heartbeat {
      leaf fatal-count {
        type uint8;
      }
      leaf interrupt-interval {
        type uint8;
      }
      leaf interrupt-max {
        type uint8;
      }
      leaf transmit-interval {
        type uint8;
      }
      leaf warning-timeout {
        type uint8;
      }
      leaf fatal-timeout {
        type uint8;
      }
      leaf cslipc-timeout {
        type uint16;
      }
      leaf alive-timeout {
        type uint16;
      }
    }
    leaf hide-telnet-addresses {
      type empty;
    }
    leaf unsupported-adapter {
      type empty;
    }
    leaf unsupported-transceiver {
      type empty;
    }
    leaf internal {
      type empty;
    }
    container log {
      leaf backtrace {
        type empty;
      }
    }
    leaf log-hidden {
      type empty;
    }
    container image-version {
      leaf efsu {
        type boolean;
      }
    }
    leaf single-slot-reload-enable {
      type boolean;
    }
  }
  list profile {
    tailf:cli-suppress-mode;
    tailf:cli-delete-when-empty;
    key "start end increment";
    leaf start {
      type string;
    }
    leaf end {
      type string;
    }
    leaf increment {
      type string;
    }
  }
  container environment {
    container router {
      leaf altitude {
        type uint16;
      }
    }
    container temperature-controlled {
      presence "true";
    }
    leaf fan-algorithm {
      type enumeration {
        enum "static";
        enum "dynamic";
      }
    }
  }
  container boot {
    leaf config {
      type string;
    }
    container network {
      list list {
        tailf:cli-drop-node-name;
        tailf:cli-suppress-mode;
        tailf:cli-delete-when-empty;
        key "protocol filename address";
        leaf protocol {
          type enumeration {
            enum "ftp";
            enum "mop";
            enum "rcp";
            enum "tftp";
          }
        }
        leaf filename {
          type string;
        }
        leaf address {
          type inet:host;
        }
      }
      leaf flash {
        type empty;
      }
      container list-flash {
        tailf:cli-drop-node-name;
        list flash {
          tailf:cli-suppress-mode;
          tailf:cli-delete-when-empty;
          key "name";
          leaf name {
            type string;
          }
        }
      }
      leaf remote-url {
        tailf:cli-drop-node-name;
        type string;
      }
    }
    leaf bootldr {
      type string;
    }
  }
  container warm-reboot {
    presence "true";
  }
  container stack-mac {
    container persistent {
      leaf timer {
        type uint8;
      }
    }
  }
  container password {
    container encryption {
      leaf aes {
        type empty;
      }
    }
  }
  container login {
    leaf delay {
      type uint8;
    }
    container block-for {
      tailf:cli-compact-syntax;
      tailf:cli-sequence-commands {
        tailf:cli-reset-siblings;
      }
      leaf seconds {
        tailf:cli-drop-node-name;
        type uint16;
      }
      leaf attempts {
        type uint16;
      }
      leaf within {
        type uint16;
      }
    }
    container on-failure {
      tailf:cli-compact-syntax;
      tailf:cli-sequence-commands {
        tailf:cli-reset-siblings;
      }
      leaf log {
        type empty;
      }
      leaf every {
        type uint16;
      }
    }
    container on-success {
      tailf:cli-compact-syntax;
      tailf:cli-sequence-commands {
        tailf:cli-reset-siblings;
      }
      leaf log {
        type empty;
      }
      leaf every {
        type uint16;
      }
    }
    container quiet-mode {
      tailf:cli-compact-syntax;
      tailf:cli-sequence-commands {
        tailf:cli-reset-siblings;
      }
      leaf access-class {
        type exp-ip-acl-type;
      }
      leaf vrf-also {
        type empty;
      }
    }
  }
  container cdp {
    leaf timer {
      type uint8;
    }
    leaf holdtime {
      type uint8;
    }
    leaf run {
      type boolean;
    }
    leaf advertise-v2 {
      type boolean;
    }
    container tlv {
      leaf location {
        type boolean;
      }
      leaf app {
        type boolean;
      }
    }
    list tlv-list {
      key "name";
      leaf name {
        type string;
      }
      leaf-list tlv {
        tailf:cli-drop-node-name;
        type enumeration {
          enum "address";
          enum "capability";
          enum "cos";
          enum "duplex";
          enum "ext-port-id";
          enum "hello-protocol";
          enum "ip-prefix";
          enum "location";
          enum "location-server";
          enum "mgmt-address";
          enum "native-vlan";
          enum "platform";
          enum "port-id";
          enum "power-available";
          enum "powernet";
          enum "spare-pair-poe";
          enum "trust";
          enum "unidirectional-mode";
          enum "version";
          enum "vtp-mgmt-domain";
          enum "vvid";
        }
      }
    }
    leaf filter-tlv-list {
      type string;
    }
  }
  container platform {
    container acl {
      leaf egress-disable {
        type empty;
      }
    }
    leaf shell {
      type empty;
    }
    leaf console {
      type enumeration {
        enum "auto";
        enum "serial";
        enum "virtual";
      }
    }
    container mpls {
      leaf mtu-enable {
        type empty;
      }
    }
    leaf resource {
      type enumeration {
        enum "control-plane-heavy";
        enum "control-plane-extra-heavy";
        enum "data-plane-normal";
        enum "data-plane-heavy";
        enum "service-plane-medium";
        enum "service-plane-heavy";
      }
    }
    container bfd {
      leaf allow-svi {
        type empty;
      }
    }
    leaf bfd-debug-trace {
      type uint8;
    }
    container enable {
      list controller {
        tailf:cli-suppress-mode;
        tailf:cli-delete-when-empty;
        key "name";
        leaf name {
          tailf:cli-multi-word-key;
          type string;
        }
      }
    }
    container hardware {
      container throughput {
        container level {
          choice throughput-choice {
            leaf MB {
              type union {
                type uint32;
                type enumeration {
                  enum "T0";
                  enum "T1";
                  enum "T2";
                  enum "T3";
                  enum "T4";
                }
              }
            }
            leaf kbps {
              tailf:cli-drop-node-name;
              type uint32;
            }
            leaf boost {
              type empty;
            }
          }
        }
        leaf crypto {
          type enumeration {
            enum "250000";
            enum "50000";
            enum "100M";
            enum "10M";
            enum "15M";
            enum "250M";
            enum "25M";
            enum "50M";
            enum "2.5G";
            enum "5G";
            enum "10G";
            enum "unthrottled";
            enum "T3";
          }
        }
      }
      container crypto-throughput {
        leaf level {
          type enumeration {
            enum "8g";
            enum "8-16g";
            enum "8-25g";
            enum "16-25g";
          }
        }
      }
    }
    container memory {
      leaf add {
        type uint32;
      }
    }
    container ipccl {
      leaf log-history {
        type uint32;
      }
    }
    container ipsla {
      container classify {
        container cpu {
          leaf packets {
            type empty;
          }
        }
      }
    }
    container ip {
      container cef {
        leaf load-sharing {
          type enumeration {
            enum "dst-only";
            enum "full";
            enum "ip-only";
          }
        }
      }
    }
    container ipv4 {
      container pbr {
        container optimize {
          leaf tcam {
            type empty;
          }
        }
      }
    }
    container ipsec {
      leaf flexvpn-bypass-tcam {
        type empty;
      }
      container reassemble {
        leaf transit {
          type empty;
        }
      }
    }
    container ring {
      leaf rx {
        type uint32;
      }
    }
    container vfi {
      leaf dot1q-transparency {
        type empty;
      }
    }
    container tcam-parity-error {
      leaf enable {
        type empty;
      }
    }
    container tcam-threshold {
      leaf alarm-frequency {
        type uint32;
      }
    }
    container multicast {
      container lre {
        leaf off {
          type empty;
        }
      }
    }
    container issu {
      container reload {
        container interface-module {
          leaf-list sequence {
            tailf:cli-flat-list-syntax;
            ordered-by user;
            type uint16;
          }
        }
      }
    }
    leaf expect-single-psu {
      type empty;
    }
    container punt-keepalive {
      leaf disable-kernel-core {
        type boolean;
      }
      container settings {
        leaf transmit-interval {
          type uint8;
        }
        leaf warning-count {
          type uint8;
        }
        leaf fatal-count {
          type uint8;
        }
      }
    }
    list punt-policer {
      tailf:cli-suppress-mode;
      tailf:cli-delete-when-empty;
      key "cause";
      leaf cause {
        type union {
          type uint8;
          type string;
        }
      }
      leaf alerting {
        type empty;
      }
      container values {
        tailf:cli-drop-node-name;
        tailf:cli-compact-syntax;
        tailf:cli-sequence-commands {
          tailf:cli-reset-siblings;
        }
        leaf rate {
          tailf:cli-drop-node-name;
          type uint32;
        }
        leaf burst {
          tailf:cli-drop-node-name;
          type uint32;
        }
      }
    }
    container punt-policer-high {
      tailf:cli-drop-node-name;
      list punt-policer {
        tailf:cli-suppress-mode;
        tailf:cli-delete-when-empty;
        key "cause";
        leaf cause {
          type union {
            type uint8;
            type string;
          }
        }
        container alerting {
          leaf high {
            type empty;
          }
        }
        container values {
          tailf:cli-drop-node-name;
          tailf:cli-compact-syntax;
          tailf:cli-sequence-commands {
            tailf:cli-reset-siblings;
          }
          leaf rate {
            tailf:cli-drop-node-name;
            type uint32;
          }
          leaf burst {
            tailf:cli-drop-node-name;
            tailf:cli-optional-in-sequence;
            type uint32;
          }
          leaf high {
            type empty;
          }
        }
      }
    }
    container punt-sbrl {
      container wan {
        list punt-cause {
          tailf:cli-suppress-mode;
          tailf:cli-delete-when-empty;
          tailf:cli-compact-syntax;
          tailf:cli-sequence-commands {
            tailf:cli-reset-siblings;
          }
          key "name";
          leaf name {
            type string;
          }
          leaf rate-per-1-sec {
            type uint16;
          }
          leaf quarantine-time {
            type uint8;
          }
          leaf burst-factor {
            type uint16;
          }
        }
      }
      container subscriber {
        list punt-cause {
          tailf:cli-suppress-mode;
          tailf:cli-delete-when-empty;
          tailf:cli-compact-syntax;
          tailf:cli-sequence-commands {
            tailf:cli-reset-siblings;
          }
          key "name";
          leaf name {
            type string;
          }
          leaf rate-per-4-sec {
            type union {
              type enumeration {
                enum "no-drop";
              }
              type uint8;
            }
          }
          leaf bucket-size {
            tailf:cli-optional-in-sequence;
            type uint8;
          }
          leaf quarantine-time {
            type uint8;
          }
          leaf burst-factor {
            type uint16;
          }
        }
        leaf rate {
          type uint16;
        }
        leaf ping-bypass {
          type empty;
        }
      }
      leaf ping-bypass {
        type empty;
      }
    }
    container qfp {
      container utilization {
        container monitor {
          leaf load {
            type uint8;
          }
        }
      }
    }
    container qos {
      leaf queueing-only {
        type empty;
      }
      leaf marker-statistics {
        type empty;
      }
      container match-statistics {
        leaf per-filter {
          type empty;
        }
        leaf per-ace {
          type empty;
        }
      }
      leaf performance-monitor {
        type empty;
      }
      leaf punt-path-matching {
        type empty;
      }
      leaf-list port-channel-aggregate {
        type uint8;
      }
    }
    container qos-adjust-policer {
      leaf enable {
        type empty;
      }
    }
    list qos-port-channel_multiple_active {
      tailf:cli-suppress-mode;
      tailf:cli-delete-when-empty;
      key "id";
      leaf id {
        type uint32;
      }
    }
    list qos-port-channel_aggregator {
      tailf:cli-suppress-mode;
      tailf:cli-delete-when-empty;
      key "id";
      leaf id {
        type uint32;
      }
    }
    container power {
      container redundancy-mode {
        leaf nplus1 {
          type empty;
        }
      }
    }
    container rate-limit {
      container unicast {
        container acl {
          leaf vacl_log {
            type boolean;
          }
        }
      }
    }
    container hw-module {
      container configuration {
        tailf:cli-add-mode;
        presence "true";
        list hw-module {
          tailf:cli-suppress-mode;
          tailf:cli-delete-when-empty;
          tailf:cli-compact-syntax;
          tailf:cli-sequence-commands {
            tailf:cli-reset-siblings;
          }
          key "slot";
          leaf slot {
            type string;
          }
          leaf im-type {
            tailf:cli-drop-node-name;
            type string;
          }
          leaf mode {
            type string;
          }
        }
      }
    }
    container time-source {
      container ntp {
        tailf:cli-delete-when-empty;
        presence "true";
        leaf time-scale {
          type enumeration {
            enum "epoch-1900";
            enum "epoch-1970";
          }
        }
      }
    }
    container xconnect {
      container load-balance-hash-algo {
        leaf mac-ip-instanceid {
          type empty;
        }
      }
    }
    container smart-sfp {
      list interface {
        tailf:cli-suppress-mode;
        tailf:cli-delete-when-empty;
        tailf:cli-compact-syntax;
        key "name";
        leaf name {
          type string;
        }
        leaf type {
          type string;
        }
      }
    }
    container feature-manager {
      container capture {
        leaf rate-limit {
          type uint32;
        }
      }
    }
    container l2vpn {
      leaf hdlc-pass-through {
        type empty;
      }
    }
    container cos-mark {
      list protocol {
        tailf:cli-suppress-mode;
        tailf:cli-delete-when-empty;
        key "name";
        leaf name {
          type string;
        }
        leaf cos-value {
          type uint8;
        }
      }
    }
  }
  container boot-marker {
    tailf:cli-drop-node-name;
    container boot {
      list system {
        tailf:cli-suppress-mode;
        tailf:cli-delete-when-empty;
        ordered-by user;
        key "entry";
        leaf entry {
          tailf:cli-multi-word-key;
          type string;
        }
      }
    }
  }
  container shell {
    choice processing-choice {
      leaf processing {
        type boolean;
      }
      container processing-full {
        tailf:cli-drop-node-name;
        container processing {
          leaf full {
            type empty;
          }
        }
      }
    }
  }
  container aqm-register-fnf {
    presence "true";
  }
  container service-module {
    list wlan-ap {
      tailf:cli-suppress-mode;
      tailf:cli-delete-when-empty;
      tailf:cli-compact-syntax;
      tailf:cli-sequence-commands {
        tailf:cli-reset-siblings;
      }
      key "interface-number";
      leaf interface-number {
        type uint8;
      }
      leaf bootimage {
        type enumeration {
          enum "autonomous";
          enum "unified";
        }
      }
    }
  }
  container vrf {
    list definition {
      unique "rd";
      key "name";
      leaf name {
        type string;
      }
      leaf description {
        tailf:cli-multi-value;
        type string;
      }
      container rd-auto-enable {
        tailf:cli-drop-node-name;
        leaf rd-auto {
          type empty;
        }
      }
      container rd-auto {
        leaf disable {
          type empty;
        }
      }
      leaf rd {
        type rd-type;
      }
      container vpn {
        leaf id {
          type vpn-id-type;
        }
      }
      container ipv4 {
        container multicast {
          leaf multitopology {
            type empty;
          }
        }
      }
      container route-target {
        uses route-target-grouping;
      }
      container address-family {
        container ipv4 {
          tailf:cli-add-mode;
          presence "true";
          uses vrf-definition-af-grouping;
        }
        container ipv4-multicast {
          tailf:cli-drop-node-name;
          container ipv4 {
            container multicast {
              tailf:cli-add-mode;
              presence "true";
              uses vrf-definition-af-grouping;
            }
          }
        }
        container ipv6 {
          tailf:cli-add-mode;
          presence "true";
          uses vrf-definition-af-grouping;
        }
      }
    }
  }
  container security {
    container passwords {
      leaf min-length {
        type uint8;
      }
    }
    container authentication {
      container failure {
        tailf:cli-compact-syntax;
        tailf:cli-sequence-commands {
          tailf:cli-reset-siblings;
        }
        leaf rate {
          type uint16;
        }
        leaf log {
          type empty;
        }
      }
    }
  }
  container enable {
    container password {
      tailf:cli-compact-syntax;
      tailf:cli-sequence-commands;
      uses password-grouping {
        refine "secret";
      }
    }
    container password-conf {
      tailf:cli-drop-node-name;
      container password {
        list level {
          tailf:cli-suppress-mode;
          tailf:cli-delete-when-empty;
          tailf:cli-compact-syntax;
          tailf:cli-sequence-commands;
          key "level";
          leaf level {
            type uint8;
          }
          uses password-grouping {
            refine "secret";
          }
        }
      }
    }
    leaf last-resort {
      type enumeration {
        enum "password";
        enum "succeed";
      }
    }
    container secret {
      tailf:cli-compact-syntax;
      tailf:cli-sequence-commands;
      uses enable-secret-grouping;
    }
    container secret-conf {
      tailf:cli-drop-node-name;
      container secret {
        list level {
          tailf:cli-suppress-mode;
          tailf:cli-delete-when-empty;
          tailf:cli-compact-syntax;
          tailf:cli-sequence-commands;
          key "level";
          leaf level {
            tailf:cli-suppress-range;
            type uint8;
          }
          uses enable-secret-grouping;
        }
      }
    }
    leaf use-tacacs {
      type empty;
    }
  }
  container aaa {
    leaf new-model {
      type empty;
    }
    container password {
      leaf restriction {
        type empty;
      }
    }
    container local {
      container authentication {
        container default {
          leaf authorization {
            type string;
          }
        }
        container attempts {
          leaf max-fail {
            type uint16;
          }
        }
      }
    }
    container group {
      container server {
        list radius {
          key "name";
          leaf name {
            type string;
          }
          container server {
            list name {
              tailf:cli-suppress-mode;
              tailf:cli-delete-when-empty;
              ordered-by user;
              key "name";
              leaf name {
                type string;
              }
            }
            list direct {
              tailf:cli-drop-node-name;
              tailf:cli-compact-syntax;
              tailf:cli-suppress-mode;
              key "name";
              leaf name {
                type inet:host;
              }
              leaf auth-port {
                type uint16;
              }
              leaf acct-port {
                type uint16;
              }
            }
          }
          list server-private {
            tailf:cli-suppress-mode;
            tailf:cli-delete-when-empty;
            tailf:cli-compact-syntax;
            key "name";
            leaf name {
              type inet:host;
            }
            uses radius-server-grouping;
          }
          container backoff {
            container exponential {
              tailf:cli-delete-when-empty;
              presence "true";
              leaf max-delay {
                type uint8;
              }
              leaf backoff-retry {
                type uint8;
              }
            }
          }
          container ip {
            container vrf {
              leaf forwarding {
                type string;
              }
            }
            container radius {
              container source-interface {
                uses interface-name-grouping;
              }
            }
          }
          container ipv6 {
            container vrf {
              leaf forwarding {
                type string;
              }
            }
            container radius {
              container source-interface {
                uses interface-name-grouping;
              }
            }
          }
          leaf deadtime {
            type uint16;
          }
          container throttle {
            tailf:cli-compact-syntax;
            tailf:cli-sequence-commands {
              tailf:cli-reset-siblings;
            }
            leaf accounting {
              tailf:cli-optional-in-sequence;
              type uint16;
            }
            leaf access {
              type uint16;
            }
            leaf access-timeout {
              type uint8;
            }
          }
          leaf retransmit {
            type uint8;
          }
          leaf timeout {
            type uint16;
          }
          container load-balance {
            container method {
              container least-outstanding {
                tailf:cli-delete-when-empty;
                presence "true";
                leaf batch-size {
                  type uint32;
                }
              }
            }
          }
          container attribute {
            container nas-port {
              tailf:cli-compact-syntax;
              tailf:cli-sequence-commands {
                tailf:cli-reset-siblings;
              }
              choice attr-choice {
                leaf none {
                  type empty;
                }
                case format {
                  leaf format {
                    type enumeration {
                      enum "a";
                      enum "b";
                      enum "c";
                      enum "d";
                      enum "e";
                    }
                  }
                  leaf string {
                    tailf:cli-drop-node-name;
                    type string;
                  }
                }
              }
            }
          }
        }
        list tacacs-plus {
          tailf:alt-name "tacacs+";
          key "name";
          leaf name {
            type string;
          }
          container server {
            list name {
              tailf:cli-suppress-mode;
              tailf:cli-delete-when-empty;
              ordered-by user;
              key "name";
              leaf name {
                type string;
              }
            }
            list server-list {
              tailf:cli-drop-node-name;
              tailf:cli-suppress-mode;
              tailf:cli-delete-when-empty;
              key "name";
              leaf name {
                type inet:host;
              }
            }
          }
          list server-private {
            tailf:cli-suppress-mode;
            tailf:cli-delete-when-empty;
            tailf:cli-compact-syntax;
            tailf:cli-sequence-commands {
              tailf:cli-reset-all-siblings;
            }
            ordered-by user;
            key "name";
            leaf name {
              type inet:host;
            }
            leaf port {
              tailf:cli-break-sequence-commands;
              type uint16;
            }
            leaf timeout {
              type uint16;
            }
            container key {
              tailf:cli-flatten-container;
              tailf:cli-compact-syntax;
              tailf:cli-sequence-commands;
              uses password-grouping {
                refine "secret";
              }
            }
          }
          container ip {
            container vrf {
              leaf forwarding {
                type string;
              }
            }
            container tacacs {
              container source-interface {
                uses interface-name-grouping;
              }
            }
          }
          container ipv6 {
            container vrf {
              leaf forwarding {
                type string;
              }
            }
            container tacacs {
              container source-interface {
                uses interface-name-grouping;
              }
            }
          }
          leaf timeout {
            type uint16;
          }
        }
      }
    }
    container authentication {
      leaf banner {
        type string;
      }
      leaf fail-message {
        type string;
      }
      container attempts {
        leaf login {
          type uint8;
        }
      }
      leaf username-prompt {
        type string;
      }
      leaf password-prompt {
        type string;
      }
      list dot1x {
        tailf:cli-suppress-mode;
        tailf:cli-delete-when-empty;
        tailf:cli-compact-syntax;
        key "name";
        leaf name {
          type aaa-authentication-name-type;
        }
        uses aaa-authentication-method-grouping;
      }
      list login {
        tailf:cli-suppress-mode;
        tailf:cli-delete-when-empty;
        tailf:cli-compact-syntax;
        key "name";
        leaf name {
          type aaa-authentication-name-type;
        }
        uses aaa-authentication-method-grouping;
      }
      container enable {
        container default {
          tailf:cli-compact-syntax;
          uses aaa-authentication-method-grouping;
        }
      }
      list ppp {
        tailf:cli-suppress-mode;
        tailf:cli-delete-when-empty;
        tailf:cli-compact-syntax;
        key "name";
        leaf name {
          type aaa-authentication-name-type;
        }
        uses aaa-authentication-method-grouping;
      }
    }
    container authorization {
      leaf console {
        type empty;
      }
      container suppress {
        leaf null-username {
          type empty;
        }
      }
      leaf config-commands {
        type empty;
      }
      list exec {
        tailf:cli-suppress-mode;
        tailf:cli-delete-when-empty;
        tailf:cli-compact-syntax;
        key "name";
        leaf name {
          type aaa-authorization-name-type;
        }
        uses aaa-authorization-method-grouping;
      }
      list commands {
        tailf:cli-suppress-mode;
        tailf:cli-delete-when-empty;
        tailf:cli-compact-syntax;
        key "level name";
        leaf level {
          type uint8;
        }
        leaf name {
          type aaa-authorization-name-type;
        }
        uses aaa-authorization-method-grouping;
      }
      list eventmanager {
        tailf:cli-suppress-mode;
        tailf:cli-delete-when-empty;
        tailf:cli-compact-syntax;
        key "name";
        leaf name {
          type aaa-authorization-name-type;
        }
        uses aaa-authorization-method-grouping;
      }
      list network {
        tailf:cli-suppress-mode;
        tailf:cli-delete-when-empty;
        tailf:cli-compact-syntax;
        key "name";
        leaf name {
          type aaa-authorization-name-type;
        }
        uses aaa-authorization-method-grouping;
      }
      list auth-proxy {
        tailf:cli-suppress-mode;
        tailf:cli-delete-when-empty;
        tailf:cli-compact-syntax;
        key "name";
        leaf name {
          type aaa-authorization-name-type;
        }
        uses aaa-authorization-method-grouping;
      }
      list subscriber-service {
        tailf:cli-suppress-mode;
        tailf:cli-delete-when-empty;
        tailf:cli-compact-syntax;
        key "name";
        leaf name {
          type aaa-authorization-name-type;
        }
        uses aaa-authorization-method-grouping;
      }
      list reverse-access {
        tailf:cli-suppress-mode;
        tailf:cli-delete-when-empty;
        tailf:cli-compact-syntax;
        key "name";
        leaf name {
          type aaa-authorization-name-type;
        }
        uses aaa-authorization-method-grouping;
      }
      list credential-download {
        tailf:cli-suppress-mode;
        tailf:cli-delete-when-empty;
        tailf:cli-compact-syntax;
        key "name";
        leaf name {
          type aaa-authorization-name-type;
        }
        uses aaa-authorization-method-grouping;
      }
    }
    container accounting {
      container send {
        container stop-record {
          container authentication {
            leaf failure {
              type empty;
            }
            container failure-vrf {
              tailf:cli-drop-node-name;
              container failure {
                list vrf {
                  tailf:cli-suppress-mode;
                  tailf:cli-delete-when-empty;
                  key "name";
                  leaf name {
                    type string;
                  }
                }
              }
            }
          }
        }
      }
      container nested {
        tailf:cli-delete-when-empty;
        presence "true";
        container suppress {
          leaf stop {
            type empty;
          }
        }
      }
      list commands {
        tailf:cli-suppress-mode;
        tailf:cli-delete-when-empty;
        tailf:cli-compact-syntax;
        key "level name";
        leaf level {
          type uint8;
        }
        leaf name {
          type aaa-accounting-name-type;
        }
        uses aaa-accounting-method-grouping;
      }
      list exec {
        tailf:cli-suppress-mode;
        tailf:cli-delete-when-empty;
        tailf:cli-compact-syntax;
        key "name";
        leaf name {
          type aaa-accounting-name-type;
        }
        uses aaa-accounting-method-grouping;
      }
      list network {
        tailf:cli-suppress-mode;
        tailf:cli-delete-when-empty;
        tailf:cli-compact-syntax;
        key "name";
        leaf name {
          type aaa-accounting-name-type;
        }
        uses aaa-accounting-method-grouping;
      }
      list auth-proxy {
        tailf:cli-suppress-mode;
        tailf:cli-delete-when-empty;
        tailf:cli-compact-syntax;
        key "name";
        leaf name {
          type aaa-accounting-name-type;
        }
        uses aaa-accounting-method-grouping;
      }
      list identity {
        tailf:cli-suppress-mode;
        tailf:cli-delete-when-empty;
        tailf:cli-compact-syntax;
        key "name";
        leaf name {
          type aaa-accounting-name-type;
        }
        uses aaa-accounting-method-grouping;
      }
      list connection {
        tailf:cli-suppress-mode;
        tailf:cli-delete-when-empty;
        tailf:cli-compact-syntax;
        key "name";
        leaf name {
          type aaa-accounting-name-type;
        }
        uses aaa-accounting-method-grouping;
      }
      list dot1x {
        tailf:cli-suppress-mode;
        tailf:cli-delete-when-empty;
        tailf:cli-compact-syntax;
        key "name";
        leaf name {
          type aaa-accounting-name-type;
        }
        uses aaa-accounting-method-grouping;
      }
      container multicast {
        container default {
          tailf:cli-compact-syntax;
          tailf:cli-delete-when-empty;
          presence "true";
          uses aaa-accounting-method-grouping;
        }
      }
      container onep {
        container default {
          tailf:cli-compact-syntax;
          tailf:cli-delete-when-empty;
          presence "true";
          uses aaa-accounting-method-grouping;
        }
      }
      container system {
        container default {
          tailf:cli-compact-syntax;
          tailf:cli-delete-when-empty;
          presence "true";
          uses aaa-accounting-method-grouping;
        }
        leaf guarantee-first {
          type boolean;
        }
      }
      container suppress {
        leaf null-username {
          type empty;
        }
      }
      container session-duration {
        leaf ntp-adjusted {
          type empty;
        }
      }
      container jitter {
        leaf maximum {
          type uint32;
        }
      }
      container update {
        tailf:cli-compact-syntax;
        leaf newinfo {
          type empty;
        }
        leaf periodic {
          type uint32;
        }
        container jitter {
          tailf:cli-flatten-container;
          leaf maximum {
            type uint32;
          }
        }
      }
      container delay-start {
        presence "true";
        leaf all {
          type empty;
        }
      }
    }
    container common-criteria {
      list policy {
        key "name";
        leaf name {
          type string;
        }
        leaf min-length {
          type uint8;
        }
        leaf max-length {
          type uint8;
        }
        leaf numeric-count {
          type uint8;
        }
        leaf special-case {
          type uint8;
        }
        leaf char-changes {
          type uint8;
        }
        leaf upper-case {
          type uint8;
        }
        leaf lower-case {
          type uint8;
        }
      }
    }
    leaf session-id {
      type enumeration {
        enum "common";
        enum "unique";
      }
    }
    container policy {
      container interface-config {
        leaf allow-subinterface {
          type empty;
        }
      }
    }
    container attribute {
      list list {
        key "name";
        leaf name {
          type string;
        }
        container attribute {
          container type {
            list interface-config {
              tailf:cli-suppress-mode;
              tailf:cli-delete-when-empty;
              ordered-by user;
              key "line";
              leaf line {
                type string;
              }
            }
            list list {
              tailf:cli-drop-node-name;
              tailf:cli-suppress-mode;
              tailf:cli-delete-when-empty;
              key "name";
              leaf name {
                type string;
              }
              list attributes {
                tailf:cli-drop-node-name;
                tailf:cli-suppress-mode;
                tailf:cli-delete-when-empty;
                ordered-by user;
                key "line";
                leaf line {
                  type string;
                }
              }
            }
          }
        }
      }
    }
    container server {
      container radius {
        container dynamic-author {
          tailf:cli-add-mode;
          list client {
            tailf:cli-suppress-mode;
            tailf:cli-delete-when-empty;
            ordered-by user;
            key "address";
            leaf address {
              type inet:host;
            }
            container server-key {
              tailf:cli-flatten-container;
              tailf:cli-compact-syntax;
              tailf:cli-sequence-commands;
              uses password-grouping {
                refine "secret";
              }
            }
          }
          container client-vrf {
            tailf:cli-drop-node-name;
            list client {
              tailf:cli-suppress-mode;
              tailf:cli-delete-when-empty;
              ordered-by user;
              key "address vrf";
              leaf address {
                type inet:host;
              }
              leaf vrf {
                tailf:cli-expose-key-name;
                type string;
              }
              container server-key {
                tailf:cli-flatten-container;
                tailf:cli-compact-syntax;
                tailf:cli-sequence-commands;
                uses password-grouping {
                  refine "secret";
                }
              }
            }
          }
          leaf port {
            type uint16;
          }
          leaf auth-type {
            type enumeration {
              enum "all";
              enum "any";
              enum "session-key";
            }
          }
          container server-key {
            tailf:cli-compact-syntax;
            tailf:cli-sequence-commands;
            uses password-grouping {
              refine "secret";
            }
          }
          container ignore {
            leaf session-key {
              type empty;
            }
            leaf server-key {
              type empty;
            }
            leaf retransmission {
              type empty;
            }
          }
        }
      }
    }
  }
  container eap {
    list profile {
      key "name";
      leaf name {
        type string;
      }
      container method {
        leaf tls {
          type empty;
        }
      }
      leaf pki-trustpoint {
        type string;
      }
    }
  }
  container ppp {
    container packet {
      container throttle {
        tailf:cli-compact-syntax;
        tailf:cli-sequence-commands {
          tailf:cli-reset-siblings;
        }
        leaf N {
          tailf:cli-drop-node-name;
          type uint32;
        }
        leaf T1 {
          tailf:cli-drop-node-name;
          type uint16;
        }
        leaf T2 {
          tailf:cli-drop-node-name;
          type uint16;
        }
      }
    }
  }
  container pppoe {
    container intermediate-agent {
      container format-type {
        container circuit-id {
          choice circuit-id-choice {
            container hostname {
              leaf portname {
                type empty;
              }
            }
            leaf string {
              type string;
            }
          }
        }
      }
    }
    container intermediate-agent-enable {
      tailf:cli-drop-node-name;
      leaf intermediate-agent {
        type empty;
      }
    }
  }
  container svclc {
    list vlan-group {
      tailf:cli-suppress-mode;
      tailf:cli-delete-when-empty;
      key "id";
      leaf id {
        tailf:cli-suppress-range;
        type uint16;
      }
      leaf-list vlan {
        tailf:cli-drop-node-name;
        tailf:cli-range-list-syntax;
        type uint16;
      }
    }
  }
  container wan {
    leaf mode {
      type enumeration {
        enum "dsl";
        enum "ethernet";
      }
    }
  }
  container cisp {
    leaf enable {
      type empty;
    }
  }
  container switch {
    container virtual {
      list domain {
        key "id";
        leaf id {
          tailf:cli-suppress-range;
          type uint8;
        }
        container switch {
          list list {
            tailf:cli-drop-node-name;
            tailf:cli-suppress-mode;
            tailf:cli-delete-when-empty;
            key "id";
            leaf id {
              type uint8;
            }
            leaf priority {
              type uint8;
            }
          }
          container mode {
            leaf virtual {
              type empty;
            }
          }
        }
        leaf mac-address {
          type union {
            type string;
            type enumeration {
              enum "chassis";
              enum "use-virtual";
            }
          }
        }
        container dual-active {
          container detection {
            container pagp {
              container trust {
                list channel-group {
                  tailf:cli-suppress-mode;
                  tailf:cli-delete-when-empty;
                  key "id";
                  leaf id {
                    type uint16;
                  }
                }
              }
            }
          }
        }
      }
    }
    list list {
      tailf:cli-drop-node-name;
      tailf:cli-suppress-mode;
      tailf:cli-delete-when-empty;
      key "id";
      leaf id {
        type uint8;
      }
      leaf provision {
        type string;
      }
    }
  }
  container stackwise-virtual {
    tailf:cli-add-mode;
    presence "true";
    leaf domain {
      type uint8;
    }
  }
  container resource {
    container policy {
      tailf:cli-add-mode;
      presence "true";
      list policy {
        key "name";
        leaf name {
          type string;
        }
        leaf global {
          tailf:cli-hide-in-submode;
          type empty;
        }
        leaf system {
          type empty;
        }
      }
    }
  }
  container cns {
    container aaa {
      leaf enable {
        type boolean;
      }
    }
    list trusted-server {
      tailf:cli-suppress-mode;
      tailf:cli-delete-when-empty;
      key "agent name";
      leaf agent {
        type enumeration {
          enum "all-agents";
          enum "config";
          enum "event";
          enum "exec";
          enum "image";
        }
      }
      leaf name {
        type string;
      }
    }
    container id {
      leaf string {
        type string;
      }
      container id-services-list {
        tailf:cli-drop-node-name;
        list string {
          tailf:cli-suppress-mode;
          tailf:cli-delete-when-empty;
          tailf:cli-compact-syntax;
          tailf:cli-sequence-commands;
          key "service";
          leaf string {
            tailf:cli-prefix-key;
            tailf:cli-drop-node-name;
            type string;
          }
          leaf service {
            type enumeration {
              enum "event";
              enum "image";
            }
          }
        }
      }
    }
    list event {
      tailf:cli-suppress-mode;
      tailf:cli-delete-when-empty;
      tailf:cli-compact-syntax;
      key "name";
      leaf name {
        type string;
      }
      leaf port-number {
        tailf:cli-drop-node-name;
        type uint16;
      }
      container source {
        tailf:cli-flatten-container;
        tailf:cli-compact-syntax;
        uses interface-name-grouping;
      }
      container keepalive {
        tailf:cli-flatten-container;
        tailf:cli-compact-syntax;
        tailf:cli-sequence-commands;
        leaf seconds {
          tailf:cli-drop-node-name;
          type uint16;
        }
        leaf retry-count {
          tailf:cli-drop-node-name;
          type uint16;
        }
      }
    }
    container image {
      container server {
        tailf:cli-compact-syntax;
        tailf:cli-sequence-commands {
          tailf:cli-reset-siblings;
        }
        leaf server-url {
          tailf:cli-drop-node-name;
          type string;
        }
        leaf status {
          type string;
        }
      }
    }
    container config {
      container notify {
        tailf:cli-compact-syntax;
        tailf:cli-sequence-commands {
          tailf:cli-reset-siblings;
        }
        leaf capture {
          tailf:cli-drop-node-name;
          type enumeration {
            enum "all";
            enum "diff";
          }
        }
        leaf interval {
          type uint16;
        }
      }
      container initial {
        tailf:cli-compact-syntax;
        tailf:cli-sequence-commands {
          tailf:cli-reset-siblings;
        }
        leaf host {
          tailf:cli-drop-node-name;
          type inet:host;
        }
        leaf port-number {
          tailf:cli-drop-node-name;
          type uint16;
        }
      }
      container partial {
        tailf:cli-compact-syntax;
        tailf:cli-sequence-commands {
          tailf:cli-reset-siblings;
        }
        leaf host {
          tailf:cli-drop-node-name;
          type inet:host;
        }
        leaf port-number {
          tailf:cli-drop-node-name;
          type uint16;
        }
      }
    }
    list exec {
      tailf:cli-suppress-mode;
      tailf:cli-delete-when-empty;
      tailf:cli-compact-syntax;
      tailf:cli-sequence-commands {
        tailf:cli-reset-siblings;
      }
      key "port-number";
      leaf encrypt {
        tailf:cli-prefix-key;
        tailf:cli-optional-in-sequence;
        type empty;
      }
      leaf port-number {
        type uint16;
      }
      container source {
        tailf:cli-flatten-container;
        tailf:cli-compact-syntax;
        uses interface-name-grouping;
      }
    }
    leaf dhcp {
      type empty;
    }
    container image-enable {
      tailf:cli-drop-node-name;
      leaf image {
        type empty;
      }
    }
  }
  container epm {
    leaf access-control {
      type enumeration {
        enum "Open";
      }
    }
    leaf logging {
      type empty;
    }
  }
  container clock {
    container timezone {
      tailf:cli-compact-syntax;
      tailf:cli-sequence-commands {
        tailf:cli-reset-siblings;
      }
      leaf zone {
        tailf:cli-drop-node-name;
        type string;
      }
      leaf offset {
        tailf:cli-drop-node-name;
        tailf:cli-optional-in-sequence;
        type enumeration {
          enum "+";
          enum "-";
        }
      }
      leaf hours {
        tailf:cli-drop-node-name;
        type int8;
      }
      leaf minutes {
        tailf:cli-drop-node-name;
        type int8;
      }
    }
    container summer-time {
      tailf:cli-compact-syntax;
      tailf:cli-sequence-commands {
        tailf:cli-reset-siblings;
      }
      leaf zone {
        tailf:cli-drop-node-name;
        type string;
      }
      choice summer-choice {
        case date-case {
          leaf date {
            type empty;
          }
          leaf date-start-month {
            tailf:cli-drop-node-name;
            type month-type;
          }
          leaf date-start-date {
            tailf:cli-drop-node-name;
            type uint8;
          }
          leaf date-start-year {
            tailf:cli-drop-node-name;
            type uint16;
          }
          leaf date-start-time {
            tailf:cli-drop-node-name;
            type hhmm-type;
          }
          leaf date-end-month {
            tailf:cli-drop-node-name;
            type month-type;
          }
          leaf date-end-date {
            tailf:cli-drop-node-name;
            type uint8;
          }
          leaf date-end-year {
            tailf:cli-drop-node-name;
            type uint16;
          }
          leaf date-end-time {
            tailf:cli-drop-node-name;
            type hhmm-type;
          }
          leaf date-offset {
            tailf:cli-drop-node-name;
            type uint16;
          }
        }
        case recurring-case {
          leaf recurring {
            type empty;
          }
          leaf start {
            tailf:cli-drop-node-name;
            type union {
              type uint8;
              type enumeration {
                enum "first";
                enum "last";
              }
            }
          }
          leaf start-day {
            tailf:cli-drop-node-name;
            type weekday-type;
          }
          leaf start-month {
            tailf:cli-drop-node-name;
            type month-type;
          }
          leaf start-time {
            tailf:cli-drop-node-name;
            type hhmm-type;
          }
          leaf end {
            tailf:cli-drop-node-name;
            type union {
              type uint8;
              type enumeration {
                enum "first";
                enum "last";
              }
            }
          }
          leaf end-day {
            tailf:cli-drop-node-name;
            type weekday-type;
          }
          leaf end-month {
            tailf:cli-drop-node-name;
            type month-type;
          }
          leaf end-time {
            tailf:cli-drop-node-name;
            type hhmm-type;
          }
          leaf offset {
            tailf:cli-drop-node-name;
            type uint16;
          }
        }
      }
    }
    container calendar-valid {
      presence "true";
    }
  }
  container software {
    container auto-upgrade {
      leaf enable {
        type boolean;
      }
      container source {
        leaf url {
          type string;
        }
      }
    }
  }
  container device-sensor {
    container filter-list {
      container cdp {
        list list {
          key "name";
          leaf name {
            type string;
          }
          container tlv {
            leaf-list name {
              type string;
            }
          }
        }
      }
      container lldp {
        list list {
          key "name";
          leaf name {
            type string;
          }
          container tlv {
            leaf-list name {
              type string;
            }
          }
        }
      }
      container dhcp {
        list list {
          key "name";
          leaf name {
            type string;
          }
          container option {
            leaf-list name {
              type string;
            }
          }
        }
      }
    }
    container filter-spec {
      container dhcp {
        tailf:cli-compact-syntax;
        tailf:cli-sequence-commands {
          tailf:cli-reset-siblings;
        }
        leaf type {
          tailf:cli-drop-node-name;
          type enumeration {
            enum "exclude";
            enum "include";
          }
        }
        choice list-choice {
          leaf all {
            type empty;
          }
          leaf list {
            type string;
          }
        }
      }
      container lldp {
        tailf:cli-compact-syntax;
        tailf:cli-sequence-commands {
          tailf:cli-reset-siblings;
        }
        leaf type {
          tailf:cli-drop-node-name;
          type enumeration {
            enum "exclude";
            enum "include";
          }
        }
        choice list-choice {
          leaf all {
            type empty;
          }
          leaf list {
            type string;
          }
        }
      }
      container cdp {
        tailf:cli-compact-syntax;
        tailf:cli-sequence-commands {
          tailf:cli-reset-siblings;
        }
        leaf type {
          tailf:cli-drop-node-name;
          type enumeration {
            enum "exclude";
            enum "include";
          }
        }
        choice list-choice {
          leaf all {
            type empty;
          }
          leaf list {
            type string;
          }
        }
      }
    }
    leaf accounting {
      type empty;
    }
    leaf notify {
      type enumeration {
        enum "all-changes";
        enum "new-tlvs";
      }
    }
  }
  container process-restart {
    tailf:cli-add-mode;
    leaf lcha-preferred {
      type boolean;
    }
  }
  container call-home {
    tailf:cli-add-mode;
    leaf contact-email-addr {
      type string;
    }
    leaf site-id {
      type string;
    }
    leaf contract-id {
      type string;
    }
    leaf customer-id {
      type string;
    }
    container data-privacy {
      leaf level {
        type enumeration {
          enum "normal";
          enum "high";
        }
      }
    }
    leaf phone-number {
      type string;
    }
    leaf rate-limit {
      type uint8;
    }
    container sender {
      leaf from {
        type string;
      }
      leaf reply-to {
        type string;
      }
    }
    list mail-server {
      tailf:cli-suppress-mode;
      tailf:cli-delete-when-empty;
      key "host";
      leaf host {
        type inet:host;
      }
      leaf priority {
        type uint8;
      }
    }
    container source-interface {
      uses interface-name-grouping;
    }
    leaf vrf {
      type string;
    }
    container http-proxy {
      tailf:cli-compact-syntax;
      tailf:cli-sequence-commands {
        tailf:cli-reset-siblings;
      }
      leaf server {
        tailf:cli-drop-node-name;
        type string;
      }
      leaf port {
        type uint16;
      }
    }
    container http {
      container resolve-hostname {
        leaf ipv4-first {
          type empty;
        }
      }
      container secure {
        leaf server-identity-check {
          type boolean;
        }
      }
    }
    list profile {
      key "name";
      leaf name {
        type string;
      }
      leaf active {
        type boolean;
      }
      leaf anonymous-reporting-only {
        type empty;
      }
      container reporting {
        leaf smart-call-home-data {
          type boolean;
        }
        leaf smart-licensing-data {
          type boolean;
        }
      }
      container destination {
        container transport-method {
          leaf http {
            type empty;
          }
          leaf email {
            type boolean;
          }
        }
        container address {
          leaf-list http {
            type string;
          }
          leaf-list email {
            type string;
          }
        }
      }
    }
  }
  container opflex {
    container agent {
      tailf:cli-add-mode;
      presence "true";
      container service {
        container vxlan-evpn {
          tailf:cli-add-mode;
          presence "true";
          leaf nve-id {
            type uint16;
          }
          container bdi-ip {
            tailf:cli-compact-syntax;
            tailf:cli-sequence-commands;
            leaf address {
              tailf:cli-drop-node-name;
              type inet:ipv4-address;
            }
            leaf mask {
              tailf:cli-drop-node-name;
              type inet:ipv4-address;
            }
          }
        }
      }
      list domain {
        key "name";
        leaf name {
          type string;
        }
        leaf identity {
          type string;
        }
        list peer {
          tailf:cli-suppress-mode;
          tailf:cli-delete-when-empty;
          tailf:cli-compact-syntax;
          tailf:cli-sequence-commands {
            tailf:cli-reset-siblings;
          }
          key "name";
          leaf name {
            type string;
          }
          leaf ip-address {
            type inet:ipv4-address;
          }
          leaf tcp-port {
            type uint16;
          }
          leaf src-ip-address {
            type inet:ipv4-address;
          }
        }
      }
    }
  }
  container facility-alarm {
    container core-temperature {
      uses facility-alarm-grouping;
    }
    container outlet-temperature {
      uses facility-alarm-grouping;
    }
    container intake-temperature {
      uses facility-alarm-grouping;
    }
    container critical {
      leaf exceed-action {
        type enumeration {
          enum "shutdown";
        }
      }
    }
  }
  container cef {
    container table {
      container output-chain {
        container build {
          leaf favor {
            type enumeration {
              enum "convergence-speed";
              enum "memory-utilization";
            }
          }
        }
      }
    }
  }
  container ipdr {
    list session {
      tailf:cli-suppress-mode;
      tailf:cli-delete-when-empty;
      tailf:cli-compact-syntax;
      tailf:cli-sequence-commands {
        tailf:cli-reset-siblings;
      }
      key "session-id";
      leaf session-id {
        type uint8;
      }
      leaf session-name {
        tailf:cli-drop-node-name;
        type string;
      }
      leaf session-descr {
        tailf:cli-drop-node-name;
        tailf:cli-multi-value;
        type string;
      }
    }
    list type {
      tailf:cli-suppress-mode;
      tailf:cli-delete-when-empty;
      tailf:cli-compact-syntax;
      key "session-id";
      leaf session-id {
        type uint8;
      }
      choice type-choice {
        leaf ad-hoc {
          type empty;
        }
        leaf event {
          type empty;
        }
        leaf time-interval {
          type uint16;
        }
      }
    }
    list collector {
      tailf:cli-suppress-mode;
      tailf:cli-delete-when-empty;
      tailf:cli-compact-syntax;
      tailf:cli-sequence-commands {
        tailf:cli-reset-siblings;
      }
      key "name";
      leaf name {
        type string;
      }
      leaf ip-addr {
        tailf:cli-drop-node-name;
        type inet:ipv4-address;
      }
      leaf port {
        tailf:cli-drop-node-name;
        type uint16;
      }
    }
    list associate {
      tailf:cli-suppress-mode;
      tailf:cli-delete-when-empty;
      tailf:cli-compact-syntax;
      tailf:cli-sequence-commands {
        tailf:cli-reset-siblings;
      }
      key "session-id";
      leaf session-id {
        type uint8;
      }
      leaf collector-name {
        tailf:cli-drop-node-name;
        type string;
      }
      leaf priority {
        tailf:cli-drop-node-name;
        type uint8;
      }
    }
    list template {
      tailf:cli-suppress-mode;
      tailf:cli-delete-when-empty;
      tailf:cli-compact-syntax;
      tailf:cli-sequence-commands {
        tailf:cli-reset-siblings;
      }
      key "session-id";
      leaf session-id {
        type uint8;
      }
      leaf template-name {
        tailf:cli-drop-node-name;
        type string;
      }
    }
    container exporter {
      leaf start {
        type empty;
      }
      leaf keepalive {
        type uint16;
      }
    }
  }
  container qos-conf {
    tailf:cli-drop-node-name;
    leaf qos {
      type empty;
    }
  }
  container qos {
    container dbl {
      presence "true";
      container exceed-action {
        leaf ecn {
          type empty;
        }
        leaf probability {
          type uint8;
        }
      }
    }
    container map {
      container dscp {
        list dscp-to-tq-queue {
          tailf:cli-drop-node-name;
          tailf:cli-suppress-mode;
          tailf:cli-delete-when-empty;
          tailf:cli-compact-syntax;
          tailf:cli-sequence-commands;
          key "dscp";
          leaf dscp {
            type uint8;
          }
          leaf to {
            type empty;
          }
          leaf tx-queue {
            type uint8;
          }
        }
        list dscp-to-cos {
          tailf:cli-drop-node-name;
          tailf:cli-suppress-mode;
          tailf:cli-delete-when-empty;
          tailf:cli-compact-syntax;
          tailf:cli-sequence-commands;
          key "dscp";
          leaf dscp {
            type uint8;
          }
          leaf to {
            type empty;
          }
          leaf cos {
            type uint8;
          }
        }
        list policed {
          tailf:cli-suppress-mode;
          tailf:cli-delete-when-empty;
          tailf:cli-compact-syntax;
          tailf:cli-sequence-commands;
          key "value";
          leaf value {
            type uint8;
          }
          leaf to {
            type empty;
          }
          leaf dscp {
            type uint8;
          }
        }
      }
      container cos {
        list cos-to-dscp {
          tailf:cli-drop-node-name;
          tailf:cli-suppress-mode;
          tailf:cli-delete-when-empty;
          tailf:cli-compact-syntax;
          tailf:cli-sequence-commands;
          key "cos";
          leaf cos {
            type uint8;
          }
          leaf to {
            type empty;
          }
          leaf dscp {
            type uint8;
          }
        }
      }
    }
    container account {
      container layer2 {
        container encapsulation {
          leaf length {
            type uint8;
          }
        }
      }
    }
    container rewrite {
      container ip {
        leaf dscp {
          type boolean;
        }
      }
    }
    list aggregate-policer {
      tailf:cli-suppress-mode;
      tailf:cli-delete-when-empty;
      tailf:cli-compact-syntax;
      tailf:cli-sequence-commands {
        tailf:cli-reset-all-siblings;
      }
      key "name";
      leaf name {
        type string;
      }
      leaf rate {
        tailf:cli-drop-node-name;
        type uint64;
      }
      leaf xps {
        tailf:cli-drop-node-name;
        tailf:cli-optional-in-sequence;
        type enumeration {
          enum "pps";
          enum "bps";
        }
      }
      leaf burst {
        tailf:cli-drop-node-name;
        type uint32;
      }
      leaf burst-type {
        tailf:cli-drop-node-name;
        tailf:cli-optional-in-sequence;
        type enumeration {
          enum "byte";
        }
      }
      container conform-action {
        tailf:cli-optional-in-sequence;
        tailf:cli-flatten-container;
        tailf:cli-compact-syntax;
        choice action-choice {
          leaf drop {
            type empty;
          }
          leaf transmit {
            type empty;
          }
        }
      }
      leaf exceed-action {
        tailf:cli-optional-in-sequence;
        type enumeration {
          enum "drop";
          enum "policed-dscp-transmit";
          enum "transmit";
        }
      }
    }
    leaf queue-softmax-multiplier {
      type uint16;
    }
    leaf wireless-default-untrust {
      type empty;
    }
  }
  container card {
    list card-slot {
      tailf:cli-drop-node-name;
      tailf:cli-suppress-mode;
      tailf:cli-delete-when-empty;
      tailf:cli-compact-syntax;
      key "slot card-type";
      leaf slot {
        type uint8;
      }
      leaf card-type {
        type enumeration {
          enum "4jacket-1";
        }
      }
    }
    list card-slot-subslot {
      tailf:cli-drop-node-name;
      tailf:cli-suppress-mode;
      tailf:cli-delete-when-empty;
      tailf:cli-compact-syntax;
      tailf:cli-sequence-commands {
        tailf:cli-reset-siblings;
      }
      key "slot-subslot card-type";
      leaf slot-subslot {
        type string;
      }
      leaf card-type {
        type union {
          type enumeration {
            enum "24rfchannel-spa-1";
            enum "2cable-dtcc";
            enum "2cable-tccplus";
            enum "SPA-1XTENGE-XFP-V2";
            enum "SPA-2X1GE-V2";
            enum "SPA-5X1GE-V2";
            enum "SPA-8X1GE-V2";
            enum "SPA-DOCSIS-HD-V1";
            enum "ubr10k-clc-3g60";
            enum "ubr10k-clc-mc2020v";
            enum "1gigethernet-1";
            enum "1gigethernet-hh-1";
            enum "cBR-CCAP-LC-40G";
            enum "sup-pic-8x10g";
          }
          type string;
        }
      }
      leaf SPA-DOCSIS-HD-V1-port {
        tailf:cli-drop-node-name;
        type enumeration {
          enum "1x10GE";
          enum "3x1GE";
        }
      }
      leaf r-phy {
        tailf:cli-optional-in-sequence;
        type empty;
      }
      leaf license {
        type string;
      }
    }
    container type {
      list t1 {
        tailf:cli-suppress-mode;
        tailf:cli-delete-when-empty;
        tailf:cli-compact-syntax;
        key "slot";
        leaf slot {
          type uint8;
        }
      }
      container t1-bay {
        tailf:cli-drop-node-name;
        list t1 {
          tailf:cli-suppress-mode;
          tailf:cli-delete-when-empty;
          tailf:cli-compact-syntax;
          key "slot bay";
          leaf slot {
            type uint8;
          }
          leaf bay {
            type uint8;
          }
        }
      }
      container t3-slot {
        tailf:cli-drop-node-name;
        list t3 {
          tailf:cli-suppress-mode;
          tailf:cli-delete-when-empty;
          key "slot";
          leaf slot {
            type uint8;
          }
        }
      }
      list t3 {
        tailf:cli-suppress-mode;
        tailf:cli-delete-when-empty;
        key "slot subslot";
        leaf slot {
          type uint8;
        }
        leaf subslot {
          type uint8;
        }
      }
      container e1-slot {
        tailf:cli-drop-node-name;
        list e1 {
          tailf:cli-suppress-mode;
          tailf:cli-delete-when-empty;
          key "slot";
          leaf slot {
            type uint8;
          }
        }
      }
      list e1 {
        tailf:cli-suppress-mode;
        tailf:cli-delete-when-empty;
        key "slot bay";
        leaf slot {
          type uint8;
        }
        leaf bay {
          type uint8;
        }
      }
      list e3 {
        tailf:cli-suppress-mode;
        tailf:cli-delete-when-empty;
        key "slot subslot";
        leaf slot {
          type uint8;
        }
        leaf subslot {
          type uint8;
        }
      }
    }
  }
  list card-protection {
    key "id";
    leaf id {
      type uint8;
    }
    container primary {
      tailf:cli-compact-syntax;
      tailf:cli-sequence-commands {
        tailf:cli-reset-siblings;
      }
      leaf slot {
        type uint8;
      }
      leaf bay {
        type uint8;
      }
    }
    container backup {
      tailf:cli-compact-syntax;
      tailf:cli-sequence-commands {
        tailf:cli-reset-siblings;
      }
      leaf slot {
        type uint8;
      }
      leaf bay {
        type uint8;
      }
    }
  }
  container kron {
    list occurrence {
      tailf:cli-sequence-commands {
        tailf:cli-reset-siblings;
      }
      key "name";
      leaf name {
        type string;
      }
      choice occurrence-choice {
        case at {
          leaf at {
            tailf:cli-hide-in-submode;
            type string;
          }
          leaf month {
            tailf:cli-drop-node-name;
            tailf:cli-optional-in-sequence;
            tailf:cli-hide-in-submode;
            type month-type;
          }
          leaf day-of-week {
            tailf:cli-drop-node-name;
            tailf:cli-optional-in-sequence;
            tailf:cli-hide-in-submode;
            type weekday-type;
          }
          leaf day-of-month {
            tailf:cli-drop-node-name;
            tailf:cli-optional-in-sequence;
            tailf:cli-hide-in-submode;
            type uint8;
          }
        }
        leaf in {
          tailf:cli-hide-in-submode;
          type string;
        }
      }
      choice when-choice {
        leaf oneshot {
          tailf:cli-hide-in-submode;
          type empty;
        }
        case recurring {
          leaf recurring {
            tailf:cli-hide-in-submode;
            type empty;
          }
          leaf system-startup {
            tailf:cli-hide-in-submode;
            type empty;
          }
        }
      }
      leaf-list policy-list {
        type string;
      }
    }
    list policy-list {
      key "name";
      leaf name {
        type string;
      }
      leaf conditional {
        tailf:cli-hide-in-submode;
        type empty;
      }
      list cli {
        tailf:cli-suppress-mode;
        tailf:cli-delete-when-empty;
        key "name";
        leaf name {
          tailf:cli-suppress-range;
          type string;
        }
      }
    }
  }
  container hw-module {
    list bay {
      tailf:cli-suppress-mode;
      tailf:cli-delete-when-empty;
      tailf:cli-compact-syntax;
      tailf:cli-sequence-commands {
        tailf:cli-reset-siblings;
      }
      key "name";
      leaf name {
        type string;
      }
      leaf shutdown {
        type empty;
      }
      choice power-choice {
        leaf powered {
          type empty;
        }
        leaf unpowered {
          type empty;
        }
      }
    }
    list ism {
      tailf:cli-suppress-mode;
      tailf:cli-delete-when-empty;
      key "name";
      leaf name {
        type string;
      }
    }
    list pvdm {
      tailf:cli-suppress-mode;
      tailf:cli-delete-when-empty;
      key "name";
      leaf name {
        type string;
      }
    }
    list sm {
      tailf:cli-suppress-mode;
      tailf:cli-delete-when-empty;
      key "name";
      leaf name {
        type string;
      }
    }
    list slot {
      tailf:cli-suppress-mode;
      tailf:cli-delete-when-empty;
      key "name";
      leaf name {
        type uint32;
      }
      container memory {
        container test {
          leaf full {
            type empty;
          }
        }
      }
      leaf process-max-time {
        type uint16;
      }
      container sp {
        leaf process-max-time {
          type uint16;
        }
      }
      container rp {
        leaf process-max-time {
          type uint16;
        }
      }
      leaf ipv6-hbh-rl {
        type uint32;
      }
    }
    list breakout {
      tailf:cli-suppress-mode;
      tailf:cli-delete-when-empty;
      key "module port switch";
      leaf module {
        tailf:cli-expose-key-name;
        tailf:cli-suppress-range;
        type uint8;
      }
      leaf port {
        tailf:cli-expose-key-name;
        tailf:cli-suppress-range;
        type uint8;
      }
      leaf switch {
        tailf:cli-expose-key-name;
        tailf:cli-suppress-range;
        type uint8;
      }
    }
    container module {
      list module-list {
        tailf:cli-drop-node-name;
        tailf:cli-suppress-mode;
        tailf:cli-delete-when-empty;
        tailf:cli-compact-syntax;
        key "name port-group";
        leaf name {
          type uint8;
        }
        leaf port-group {
          tailf:cli-expose-key-name;
          type uint8;
        }
        leaf select {
          type enumeration {
            enum "gigabitethernet";
            enum "tengigabitethernet";
          }
        }
      }
      list module-list-mode {
        tailf:cli-drop-node-name;
        tailf:cli-suppress-mode;
        tailf:cli-delete-when-empty;
        tailf:cli-compact-syntax;
        key "name";
        leaf name {
          type uint8;
        }
        leaf mode {
          type uint8;
        }
      }
      list no-list {
        tailf:cli-suppress-mode;
        tailf:cli-delete-when-empty;
        key "name";
        leaf name {
          type uint8;
        }
        container logging {
          leaf onboard {
            type empty;
          }
        }
      }
    }
    container usb {
      leaf disable {
        type empty;
      }
    }
    container uplink {
      leaf select {
        type enumeration {
          enum "all";
          enum "gigabitethernet";
          enum "tengigabitethernet";
        }
      }
    }
    container system {
      leaf max-queue-limit {
        type uint16;
      }
    }
  }
  container cable {
    container profile {
      list mac-domain {
        key "name";
        leaf name {
          type string;
        }
        container cable {
          container dynamic-secret {
            tailf:cli-compact-syntax;
            tailf:cli-sequence-commands {
              tailf:cli-reset-siblings;
            }
            leaf option {
              tailf:cli-drop-node-name;
              type enumeration {
                enum "lock";
                enum "mark";
                enum "reject";
              }
            }
            leaf nocrypt {
              type empty;
            }
          }
          container privacy {
            leaf mandatory {
              type empty;
            }
            leaf skip-validity-period {
              type empty;
            }
            leaf bpi-plus-policy {
              type enumeration {
                enum "capable-enforcement";
                enum "d11-enabled-enforcement";
                enum "d11-enforcement";
                enum "total-enforcement";
              }
            }
          }
          container cm-status {
            leaf-list enable {
              tailf:cli-range-list-syntax;
              type uint8;
            }
          }
          uses cable-map-advance-grouping;
          container upstream {
            list cable-upstream-list {
              tailf:cli-drop-node-name;
              tailf:cli-suppress-mode;
              tailf:cli-delete-when-empty;
              key "id";
              leaf id {
                type uint8;
              }
              leaf attribute-mask {
                type string;
              }
              container power-adjust {
                leaf threshold {
                  type uint8;
                }
                leaf continue {
                  type uint8;
                }
                leaf noise {
                  type uint8;
                }
              }
            }
            leaf balance-scheduling {
              type empty;
            }
          }
          container enable-trap {
            leaf cmonoff-notification {
              type empty;
            }
            leaf cmonoff-interval {
              type uint32;
            }
          }
        }
        leaf load-interval {
          type uint16;
        }
      }
      list wideband-interface {
        key "name";
        leaf name {
          type string;
        }
        container cable {
          container downstream {
            leaf attribute-mask {
              type string;
            }
          }
        }
        leaf load-interval {
          type uint16;
        }
        uses description-grouping;
      }
      list downstream {
        key "name";
        leaf name {
          type string;
        }
        container cable {
          container rf-bandwidth-percent {
            leaf percent-value {
              tailf:cli-drop-node-name;
              type uint8;
            }
          }
          leaf attribute-mask {
            type string;
          }
        }
      }
      list load-balance {
        key "name";
        leaf name {
          type string;
        }
        leaf restricted {
          type empty;
        }
        container method {
          tailf:cli-compact-syntax;
          tailf:cli-sequence-commands {
            tailf:cli-reset-siblings;
          }
          leaf method {
            tailf:cli-drop-node-name;
            type enumeration {
              enum "modems";
              enum "utilization";
            }
          }
          leaf us-method {
            type enumeration {
              enum "modems";
              enum "utilization";
            }
          }
        }
        container threshold {
          container load {
            leaf value {
              tailf:cli-drop-node-name;
              type uint8;
            }
            leaf minimum {
              type uint8;
            }
          }
          leaf stability {
            type uint8;
          }
        }
        container policy {
          leaf ugs {
            type empty;
          }
          leaf pure-ds-load {
            type empty;
          }
        }
        leaf init-tech-list {
          type string;
        }
        leaf docsis-policy {
          type uint32;
        }
        leaf interval {
          type uint16;
        }
        list tag {
          tailf:cli-suppress-mode;
          tailf:cli-delete-when-empty;
          key "name";
          leaf name {
            type string;
          }
        }
      }
      list service-group {
        key "name";
        leaf name {
          type string;
        }
        container cable {
          leaf bundle {
            type uint8;
          }
        }
        list mac-domain {
          tailf:cli-sequence-commands;
          key "id";
          leaf id {
            type uint8;
          }
          leaf profile {
            tailf:cli-hide-in-submode;
            type string;
          }
          container downstream {
            tailf:cli-break-sequence-commands;
            tailf:cli-compact-syntax;
            tailf:cli-sequence-commands;
            list sg-channel {
              tailf:cli-suppress-mode;
              tailf:cli-delete-when-empty;
              tailf:cli-compact-syntax;
              tailf:cli-sequence-commands;
              key "profile";
              leaf profile {
                tailf:cli-expose-key-name;
                tailf:cli-suppress-range;
                type string;
              }
              leaf-list id {
                tailf:cli-drop-node-name;
                tailf:cli-prefix-key;
                tailf:cli-range-list-syntax;
                type uint8;
              }
              leaf upstream {
                type string;
              }
            }
          }
          container cable {
            container downstream {
              container dsg {
                leaf timer {
                  type uint16;
                }
                leaf chan-list {
                  type uint16;
                }
                list tg {
                  tailf:cli-suppress-mode;
                  tailf:cli-delete-when-empty;
                  key "tgid";
                  leaf tgid {
                    type uint16;
                  }
                }
              }
            }
          }
          list upstream {
            tailf:cli-suppress-mode;
            tailf:cli-delete-when-empty;
            key "id";
            leaf id {
              type uint16;
            }
            leaf sg-channel {
              type uint8;
            }
          }
          list us-bonding-group {
            key "id";
            leaf id {
              type uint16;
            }
            container admission-control {
              leaf max-reserved-bandwidth {
                type uint32;
              }
            }
            list upstream {
              tailf:cli-suppress-mode;
              tailf:cli-delete-when-empty;
              key "id";
              leaf id {
                type uint8;
              }
            }
          }
        }
        list load-balance {
          key "docsis-group profile";
          leaf docsis-group {
            tailf:cli-expose-key-name;
            type uint8;
          }
          leaf profile {
            tailf:cli-expose-key-name;
            type string;
          }
          container downstream {
            leaf-list sg-channel {
              tailf:cli-range-list-syntax;
              type uint8;
            }
          }
          list upstream {
            tailf:cli-suppress-mode;
            tailf:cli-delete-when-empty;
            key "id";
            leaf id {
              type uint16;
            }
            leaf sg-channel {
              type uint8;
            }
          }
        }
        list wideband-interface {
          key "id";
          leaf id {
            type uint8;
          }
          leaf profile {
            tailf:cli-hide-in-submode;
            type string;
          }
          container cable {
            leaf ds-resiliency {
              type empty;
            }
          }
          container downstream {
            list sg-channel {
              tailf:cli-suppress-mode;
              tailf:cli-delete-when-empty;
              key "id";
              leaf id {
                tailf:cli-multi-word-key;
                tailf:cli-suppress-range;
                type string;
              }
              leaf rf-bandwidth-percent {
                type uint8;
              }
            }
          }
        }
      }
      list rpd-event {
        key "id";
        leaf id {
          type uint8;
        }
        list priority {
          tailf:cli-suppress-mode;
          tailf:cli-delete-when-empty;
          key "name";
          leaf name {
            type enumeration {
              enum "emergency";
              enum "alert";
              enum "critical";
              enum "error";
              enum "warning";
              enum "notice";
              enum "informational";
              enum "debug";
            }
          }
          leaf flags {
            tailf:cli-drop-node-name;
            type string;
          }
        }
        leaf enable-notify {
          type empty;
        }
      }
      list ssd {
        key "id";
        leaf id {
          type uint8;
        }
        uses description-grouping;
        container ssd {
          tailf:cli-compact-syntax;
          tailf:cli-sequence-commands {
            tailf:cli-reset-siblings;
          }
          leaf address {
            tailf:cli-drop-node-name;
            type union {
              type inet:ipv4-address;
              type inet:ipv6-address;
            }
          }
          choice file-choice {
            leaf http {
              type string;
            }
            leaf tftp {
              type string;
            }
          }
          leaf m-cvc-c {
            tailf:cli-optional-in-sequence;
            type string;
          }
          leaf c-cvc-c {
            type string;
          }
        }
      }
    }
    container depi {
      container multicast {
        list pool {
          key "id";
          leaf id {
            type uint8;
          }
          uses description-grouping;
          container ip {
            tailf:cli-compact-syntax;
            tailf:cli-sequence-commands;
            leaf address {
              type inet:ipv4-address;
            }
            leaf mask {
              tailf:cli-drop-node-name;
              type inet:ipv4-address;
            }
          }
          container ipv6 {
            leaf address {
              type ios:ipv6-prefix;
            }
          }
        }
      }
      leaf fragment {
        type enumeration {
          enum "off";
          enum "on";
        }
      }
    }
    container dynamic-bonding-group-enable {
      tailf:cli-drop-node-name;
      leaf dynamic-bonding-group {
        type empty;
      }
    }
    container dynamic-punt {
      leaf enable {
        type empty;
      }
    }
    container downstream {
      list freq-profile {
        key "name";
        leaf name {
          type string;
        }
        list lane {
          key "id";
          leaf id {
            type uint8;
          }
          leaf start-freq {
            tailf:cli-hide-in-submode;
            type uint32;
          }
          list block {
            tailf:cli-suppress-mode;
            tailf:cli-delete-when-empty;
            key "id";
            leaf id {
              type uint8;
            }
            leaf start-freq {
              type uint32;
            }
          }
        }
      }
      list rf-profile {
        key "name";
        leaf name {
          type string;
        }
        container cable {
          container downstream {
            leaf annex {
              type enumeration {
                enum "A";
                enum "B";
                enum "C";
              }
            }
            leaf modulation {
              type enumeration {
                enum "256";
                enum "64";
              }
            }
            container interleaver-depth {
              tailf:cli-compact-syntax;
              tailf:cli-sequence-commands {
                tailf:cli-reset-siblings;
              }
              leaf option1 {
                type cable-downstream-interleaver-depth-option;
              }
              leaf option2 {
                type cable-downstream-interleaver-depth-option;
              }
            }
            leaf symbol-rate {
              type uint32;
            }
          }
        }
      }
      list qam-profile {
        key "name";
        leaf name {
          type string;
        }
        container annex {
          tailf:cli-compact-syntax;
          tailf:cli-sequence-commands {
            tailf:cli-reset-siblings;
          }
          leaf format {
            tailf:cli-drop-node-name;
            type enumeration {
              enum "A";
              enum "B";
              enum "C";
            }
          }
          leaf freq-spacing {
            tailf:cli-drop-node-name;
            type enumeration {
              enum "6MHZ";
              enum "7MHZ";
            }
          }
        }
        leaf modulation {
          type enumeration {
            enum "256";
            enum "64";
          }
        }
        leaf interleaver-depth {
          type enumeration {
            enum "I12-J17";
            enum "I128-J1";
            enum "I128-J2";
            enum "I128-J3";
            enum "I128-J4";
            enum "I128-J5";
            enum "I128-J6";
            enum "I128-J7";
            enum "I128-J8";
            enum "I16-J8";
            enum "I32-J4";
            enum "I64-J2";
            enum "I8-J16";
          }
        }
        leaf symbol-rate {
          type uint32;
        }
        leaf spectrum-inversion {
          type enumeration {
            enum "off";
            enum "on";
          }
        }
        uses description-grouping;
      }
      list controller-profile {
        key "id";
        leaf id {
          type uint8;
        }
        leaf mode {
          tailf:cli-drop-node-name;
          tailf:cli-hide-in-submode;
          type enumeration {
            enum "I-CMTS";
            enum "RPHY";
            enum "Video";
            enum "SPW-Video";
          }
        }
        leaf shutdown {
          type empty;
        }
        uses description-grouping;
        leaf broadcast {
          type empty;
        }
        leaf max-carrier {
          type uint8;
        }
        leaf max-ofdm-spectrum {
          type uint32;
        }
        leaf base-channel-power {
          type uint8;
        }
        container rf-chan {
          list rf-chan {
            tailf:cli-drop-node-name;
            key "start";
            leaf start {
              type uint8;
            }
            leaf end {
              tailf:cli-drop-node-name;
              tailf:cli-hide-in-submode;
              type uint8;
            }
            uses controller-integrated-cable-rf-chan-grouping;
          }
        }
        leaf multicast-pool {
          type uint8;
        }
      }
      list ofdm-modulation-profile {
        key "id";
        leaf id {
          type uint8;
        }
        uses description-grouping;
        leaf subcarrier-spacing {
          type enumeration {
            enum "25KHz";
            enum "50KHz";
            enum "25KHZ";
            enum "50KHZ";
          }
        }
        leaf width {
          type uint32;
        }
        leaf start-freq {
          type uint32;
        }
        container assign {
          leaf modulation-default {
            type qam-modulation-type9;
          }
          container modulation {
            list modulation-range-subcarriers {
              tailf:cli-drop-node-name;
              tailf:cli-suppress-mode;
              tailf:cli-delete-when-empty;
              tailf:cli-compact-syntax;
              tailf:cli-sequence-commands {
                tailf:cli-reset-siblings;
              }
              key "name freq-abs";
              leaf name {
                type qam-modulation-type9;
              }
              leaf range-subcarriers {
                tailf:cli-prefix-key {
                  tailf:cli-before-key "2";
                }
                type empty;
              }
              leaf freq-abs {
                tailf:cli-expose-key-name;
                type uint32;
              }
              leaf width {
                type uint32;
              }
            }
            list modulation-range-subcarriers-offset {
              tailf:cli-drop-node-name;
              tailf:cli-suppress-mode;
              tailf:cli-delete-when-empty;
              tailf:cli-compact-syntax;
              tailf:cli-sequence-commands {
                tailf:cli-reset-siblings;
              }
              key "name freq-offset";
              leaf name {
                type qam-modulation-type9;
              }
              leaf range-subcarriers {
                tailf:cli-prefix-key {
                  tailf:cli-before-key "2";
                }
                type empty;
              }
              leaf freq-offset {
                tailf:cli-expose-key-name;
                type uint32;
              }
              leaf width {
                type uint32;
              }
            }
          }
        }
      }
      list ofdm-chan-profile {
        key "id";
        leaf id {
          type uint8;
        }
        uses description-grouping;
        leaf cyclic-prefix {
          type enumeration {
            enum "192";
            enum "256";
            enum "512";
            enum "768";
            enum "1024";
          }
        }
        leaf interleaver-depth {
          type uint8;
        }
        leaf pilot-scaling {
          type uint8;
        }
        leaf roll-off {
          type enumeration {
            enum "64";
            enum "128";
            enum "192";
            enum "256";
          }
        }
        leaf subcarrier-spacing {
          type enumeration {
            enum "25KHz";
            enum "50KHz";
            enum "25KHZ";
            enum "50KHZ";
          }
        }
        container profile-control {
          leaf modulation-default {
            type qam-modulation-type;
          }
        }
        container profile-ncp {
          leaf modulation-default {
            type enumeration {
              enum "16-QAM";
              enum "64-QAM";
              enum "QPSK";
            }
          }
        }
        leaf guardband-override {
          type uint32;
        }
        list profile-data {
          tailf:cli-suppress-mode;
          tailf:cli-delete-when-empty;
          key "id";
          leaf id {
            type uint8;
          }
          choice modulation-choice {
            leaf modulation-default {
              type qam-modulation-type;
            }
            leaf modulation-profile {
              type uint8;
            }
          }
        }
      }
      list ofdm-power-profile {
        key "id";
        leaf id {
          type uint8;
        }
        uses description-grouping;
        leaf ofdm-channel-width {
          type uint32;
        }
        leaf power-adjust-default {
          type string;
        }
        leaf power-tilt-linear {
          type string;
        }
      }
      container ofdm-prof-mgmt {
        leaf prof-dwngrd-auto {
          type empty;
        }
        leaf exempt-sc-pct {
          type uint8;
        }
        leaf unfit-profile-age {
          type uint16;
        }
        leaf mer-margin-qdb {
          type uint8;
        }
        leaf rxmer-poll-interval {
          type uint16;
        }
      }
      container ofdm-flow-to-profile {
        list profile-data {
          tailf:cli-suppress-mode;
          tailf:cli-delete-when-empty;
          key "id";
          leaf id {
            type uint8;
          }
          leaf mac-address {
            type string;
          }
        }
      }
    }
    container downstream-pilot-tone {
      list profile {
        key "id";
        leaf id {
          type uint16;
        }
        list rf-chan {
          key "id";
          leaf id {
            type uint16;
          }
          leaf frequency {
            type uint32;
          }
          leaf mute {
            type boolean;
          }
        }
      }
    }
    container upstream {
      container rate-adapt {
        tailf:cli-compact-syntax;
        leaf priority {
          type uint8;
        }
        leaf rate {
          type uint32;
        }
        leaf local {
          type empty;
        }
      }
      container resiliency {
        container recover {
          tailf:cli-compact-syntax;
          tailf:cli-sequence-commands {
            tailf:cli-reset-siblings;
          }
          leaf delay {
            type uint32;
          }
          leaf retries {
            type uint8;
          }
        }
      }
      container ofdma-prof-mgmt {
        leaf exempt-mslot-pct {
          type uint8;
        }
        leaf prof-upgrade-auto {
          type boolean;
        }
        leaf rxmer-poll-interval {
          type uint16;
        }
        leaf eq-poll-interval {
          type uint16;
        }
        container downgrade {
          leaf enable {
            type empty;
          }
          leaf interval {
            type uint16;
          }
          leaf threshold {
            type uint16;
          }
          leaf hold-down {
            type uint16;
          }
          leaf min-cws {
            type uint16;
          }
          leaf partial-threshold {
            type uint32;
          }
          leaf partial-hold-down {
            type uint16;
          }
          leaf rxmer-enable {
            type empty;
          }
          leaf rxmer-exempt-mslot-pct {
            type uint16;
          }
        }
      }
      list controller-profile {
        key "name";
        leaf name {
          type uint16;
        }
        uses description-grouping;
        container cable {
          container ofdma-frequency-exclusion-band {
            tailf:cli-compact-syntax;
            tailf:cli-sequence-commands;
            leaf start-value {
              tailf:cli-drop-node-name;
              type uint32;
            }
            leaf end-value {
              tailf:cli-drop-node-name;
              type uint32;
            }
          }
        }
        uses us-channel-grouping;
      }
    }
    list mod-profile-ofdma {
      key "id";
      leaf id {
        type uint16;
      }
      leaf subcarrier-spacing {
        type enumeration {
          enum "25KHz";
          enum "50KHz";
        }
      }
      leaf initial-rng-subcarrier {
        type uint8;
      }
      leaf initial-rng-preamble {
        type uint8;
      }
      leaf fine-rng-subcarrier {
        type uint16;
      }
      list data-iuc {
        tailf:cli-suppress-mode;
        tailf:cli-delete-when-empty;
        tailf:cli-compact-syntax;
        tailf:cli-sequence-commands {
          tailf:cli-reset-siblings;
        }
        key "id";
        leaf id {
          type uint8;
        }
        leaf modulation {
          type enumeration {
            enum "8-QAM";
            enum "16-QAM";
            enum "32-QAM";
            enum "64-QAM";
            enum "128-QAM";
            enum "256-QAM";
            enum "512-QAM";
            enum "1024-QAM";
            enum "2048-QAM";
            enum "4096-QAM";
            enum "BPSK";
            enum "NONE";
            enum "QPSK";
          }
        }
        leaf pilot-pattern {
          type uint8;
        }
      }
    }
    list linecard {
      tailf:cli-suppress-mode;
      tailf:cli-delete-when-empty;
      tailf:cli-compact-syntax;
      tailf:cli-sequence-commands;
      key "id";
      leaf id {
        type uint8;
      }
      leaf encryption {
        type enumeration {
          enum "clear";
          enum "dual-crypt";
          enum "dvb";
          enum "pkey";
          enum "pme";
        }
      }
      leaf scrambler {
        type enumeration {
          enum "none";
          enum "csa";
          enum "des";
        }
      }
    }
    container admission-control {
      container preempt {
        leaf priority-voice {
          type empty;
        }
      }
    }
    container flap-list {
      leaf size {
        type uint16;
      }
      leaf aging {
        type uint32;
      }
      container power-adjust {
        leaf threshold {
          type uint8;
        }
      }
      leaf miss-threshold {
        type uint8;
      }
    }
    container source-verify {
      list group {
        key "name";
        leaf name {
          type string;
        }
      }
      leaf enable-sav-static {
        type empty;
      }
      container leasequery-filter {
        container downstream {
          tailf:cli-compact-syntax;
          tailf:cli-sequence-commands;
          leaf threshold {
            tailf:cli-drop-node-name;
            type uint8;
          }
          leaf interval {
            tailf:cli-drop-node-name;
            type uint8;
          }
        }
      }
    }
    container modem {
      container remote-query {
        container gather {
          tailf:cli-drop-node-name;
          tailf:cli-compact-syntax;
          tailf:cli-sequence-commands;
          leaf polling-interval {
            tailf:cli-drop-node-name;
            type uint32;
          }
          leaf community-string {
            tailf:cli-drop-node-name;
            type string;
          }
        }
        leaf src-ip {
          type inet:ipv4-address;
        }
      }
      leaf max-cpe {
        type union {
          type uint8;
          type enumeration {
            enum "unlimited";
          }
        }
      }
      leaf v6-max-cpe-prefix {
        type uint16;
      }
      list vendor {
        tailf:cli-suppress-mode;
        tailf:cli-delete-when-empty;
        key "oui";
        leaf oui {
          type string;
        }
        leaf vendor-name {
          tailf:cli-drop-node-name;
          type string;
        }
      }
    }
    container modulation-profile {
      list modulation-profile-list {
        tailf:cli-drop-node-name;
        tailf:cli-suppress-mode;
        tailf:cli-delete-when-empty;
        key "profile";
        leaf profile {
          type string;
        }
        container atdma {
          uses cable-modulation-profile-list-grouping;
        }
        container tdma {
          uses cable-modulation-profile-list-grouping;
        }
        container mixed {
          uses cable-modulation-profile-list-grouping;
        }
        uses cable-modulation-profile-list-grouping;
      }
    }
    list tag {
      key "id";
      leaf id {
        type uint16;
      }
      leaf name {
        type string;
      }
      leaf service-type-id {
        type string;
      }
      leaf docsis-version {
        type enumeration {
          enum "docsis10";
          enum "docsis11";
          enum "docsis20";
          enum "docsis30";
        }
      }
      leaf service-class {
        type string;
      }
    }
    container service {
      list class {
        tailf:cli-suppress-mode;
        tailf:cli-delete-when-empty;
        key "class-index";
        leaf class-index {
          type uint16;
        }
        leaf name {
          type string;
        }
        choice direction-choice {
          leaf downstream {
            type empty;
          }
          leaf upstream {
            type empty;
          }
        }
        leaf peak-rate {
          type uint32;
        }
        leaf max-concat-burst {
          type uint16;
        }
        container tos-overwrite {
          tailf:cli-compact-syntax;
          tailf:cli-sequence-commands;
          leaf and-mask {
            tailf:cli-drop-node-name;
            type string;
          }
          leaf or-mask {
            tailf:cli-drop-node-name;
            type string;
          }
        }
        leaf req-trans-policy {
          type string;
        }
        leaf max-rate {
          type uint32;
        }
        leaf max-burst {
          type uint32;
        }
        leaf min-rate {
          type uint32;
        }
        leaf min-packet-size {
          type uint16;
        }
        leaf max-latency {
          type uint32;
        }
        leaf req-attr-mask {
          type string;
        }
        leaf admission-timeout {
          type uint16;
        }
        leaf activity-timeout {
          type uint16;
        }
        leaf priority {
          type uint8;
        }
        leaf sched-type {
          type enumeration {
            enum "2";
            enum "3";
            enum "4";
            enum "5";
            enum "6";
          }
        }
      }
      list type {
        tailf:cli-suppress-mode;
        tailf:cli-delete-when-empty;
        key "id";
        leaf id {
          tailf:cli-suppress-range;
          type string;
        }
        leaf ds-frequency {
          type uint32;
        }
      }
      container attribute {
        container ds-bonded {
          container downstream-type {
            container bonding-enabled {
              tailf:cli-delete-when-empty;
              presence "true";
              leaf enforce {
                type empty;
              }
            }
          }
        }
        container withhold-tlvs {
          leaf peak-rate {
            type empty;
          }
        }
      }
      container flow {
        leaf activity-timeout {
          type uint16;
        }
      }
    }
    container qos {
      container permission {
        leaf create {
          type empty;
        }
        leaf update {
          type empty;
        }
        leaf modems {
          type empty;
        }
      }
      list profile {
        tailf:cli-suppress-mode;
        key "id";
        leaf id {
          type uint16;
        }
        leaf max-burst {
          type uint16;
        }
        leaf max-downstream {
          type uint32;
        }
        leaf max-upstream {
          type uint32;
        }
        leaf priority {
          type uint8;
        }
        leaf privacy {
          type empty;
        }
      }
    }
    container multicast {
      container mdf-disable {
        leaf WB-Incapable-CM {
          type empty;
        }
        leaf DSG {
          type empty;
        }
      }
    }
    container filter {
      list group {
        tailf:cli-suppress-mode;
        tailf:cli-delete-when-empty;
        tailf:cli-compact-syntax;
        key "group-id";
        leaf group-id {
          type uint8;
        }
        list index {
          tailf:cli-suppress-mode;
          tailf:cli-delete-when-empty;
          key "index-num";
          leaf index-num {
            type uint8;
          }
          leaf src-ip {
            type inet:ipv4-address;
          }
          leaf src-mask {
            type inet:ipv4-address;
          }
          leaf dest-ip {
            type inet:ipv4-address;
          }
          leaf dest-mask {
            type inet:ipv4-address;
          }
          leaf v6-src-address {
            type inet:ipv6-address;
          }
          leaf v6-src-pfxlen {
            type uint8;
          }
          leaf v6-dest-address {
            type inet:ipv6-address;
          }
          leaf v6-dest-pfxlen {
            type uint8;
          }
          leaf v6-flow-label {
            type uint32;
          }
          leaf ip-proto {
            type uint16;
          }
          container ip-tos {
            tailf:cli-compact-syntax;
            tailf:cli-sequence-commands;
            leaf tos-mask {
              tailf:cli-drop-node-name;
              type string;
            }
            leaf tos-value {
              tailf:cli-drop-node-name;
              type string;
            }
          }
          leaf src-port {
            type uint16;
          }
          leaf dest-port {
            type uint16;
          }
          leaf ip-version {
            type enumeration {
              enum "IPv4";
              enum "IPv6";
            }
          }
          container tcp-flags {
            tailf:cli-compact-syntax;
            tailf:cli-sequence-commands;
            leaf flags-mask {
              tailf:cli-drop-node-name;
              type string;
            }
            leaf flags-value {
              tailf:cli-drop-node-name;
              type string;
            }
          }
          leaf match-action {
            type enumeration {
              enum "accept";
              enum "drop";
            }
          }
          leaf status {
            type enumeration {
              enum "active";
              enum "inactive";
            }
          }
        }
      }
    }
    container monitor {
      tailf:cli-add-mode;
      list sniff {
        tailf:cli-suppress-mode;
        tailf:cli-delete-when-empty;
        key "card param";
        leaf card {
          tailf:cli-expose-key-name;
          type uint8;
        }
        leaf param {
          tailf:cli-multi-word-key;
          type string;
        }
      }
    }
    container submgmt {
      container default {
        container filter-group {
          container cm {
            uses cable-submgmt-default-filter-group-grouping;
          }
          container cpe {
            uses cable-submgmt-default-filter-group-grouping;
          }
          container mta {
            uses cable-submgmt-default-filter-group-grouping;
          }
          container stb {
            uses cable-submgmt-default-filter-group-grouping;
          }
          container ps {
            uses cable-submgmt-default-filter-group-grouping;
          }
        }
        leaf active {
          type empty;
        }
      }
    }
    container logging {
      container badipsource {
        tailf:cli-delete-when-empty;
        presence "true";
        leaf buffer-size {
          tailf:cli-drop-node-name;
          type uint32;
        }
      }
      container layer2events {
        tailf:cli-delete-when-empty;
        presence "true";
        leaf buffer-size {
          tailf:cli-drop-node-name;
          type uint32;
        }
      }
      container overlapip {
        tailf:cli-delete-when-empty;
        presence "true";
        leaf buffer-size {
          tailf:cli-drop-node-name;
          type uint32;
        }
      }
      container ironbus {
        tailf:cli-delete-when-empty;
        presence "true";
        leaf buffer-size {
          tailf:cli-drop-node-name;
          type uint32;
        }
      }
      container downstream-index {
        tailf:cli-delete-when-empty;
        presence "true";
        leaf buffer-size {
          tailf:cli-drop-node-name;
          type uint32;
        }
      }
    }
    leaf us-freq-use-cm-cap {
      type empty;
    }
    container default-tos-qos10 {
      container tos-overwrite {
        tailf:cli-compact-syntax;
        tailf:cli-sequence-commands;
        leaf tos-and {
          tailf:cli-drop-node-name;
          type string;
        }
        leaf tos-or {
          tailf:cli-drop-node-name;
          type string;
        }
      }
    }
    container primary-sflow-qos11 {
      leaf keep {
        type enumeration {
          enum "all";
          enum "snmp-only";
        }
      }
    }
    container sflog {
      container max-entry {
        tailf:cli-compact-syntax;
        tailf:cli-sequence-commands;
        leaf value {
          tailf:cli-drop-node-name;
          type uint16;
        }
        leaf entry-duration {
          type uint32;
        }
      }
      leaf stop-record-time-overwrite {
        type empty;
      }
    }
    list trust {
      tailf:cli-suppress-mode;
      tailf:cli-delete-when-empty;
      key "address";
      leaf address {
        type string;
      }
    }
    container dynamic-secret {
      container exclude {
        leaf modem {
          type string;
        }
        leaf oui {
          type string;
        }
      }
      container tftp {
        leaf insert-upgrade-server {
          type empty;
        }
      }
    }
    container snmp {
      leaf cm-rcs {
        type enumeration {
          enum "bonding-group";
          enum "service-group";
        }
      }
      container trap {
        leaf detailed-alarm {
          type empty;
        }
      }
    }
    container docsis30-voice {
      container downstream {
        tailf:cli-compact-syntax;
        tailf:cli-sequence-commands;
        leaf req-attr-mask {
          type string;
        }
        leaf forb-attr-mask {
          type string;
        }
      }
    }
    leaf util-interval {
      type uint32;
    }
    container clock {
      leaf dti {
        type empty;
      }
      leaf dti-server-type {
        type enumeration {
          enum "polylink";
          enum "symmetricom";
        }
      }
    }
    container bgsync {
      leaf active {
        type boolean;
      }
      leaf ptime {
        type uint32;
      }
      leaf itime {
        type uint32;
      }
    }
    container privacy {
      leaf encrypt-alg-priority {
        type enumeration {
          enum "aes128-des40-des56";
          enum "aes128-des56-des40";
          enum "des40-aes128-des56";
          enum "des40-des56-aes128";
          enum "des56-aes128-des40";
          enum "des56-des40-aes128";
        }
      }
      container hotlist {
        list cm {
          tailf:cli-suppress-mode;
          tailf:cli-delete-when-empty;
          key "address";
          leaf address {
            type string;
          }
        }
      }
    }
    container dsg {
      list client-list {
        tailf:cli-suppress-mode;
        tailf:cli-delete-when-empty;
        tailf:cli-compact-syntax;
        key "client-list-id";
        leaf client-list-id {
          type uint16;
        }
        list id-index {
          tailf:cli-suppress-mode;
          tailf:cli-delete-when-empty;
          key "id";
          leaf id {
            type uint16;
          }
          choice parameter-choice {
            leaf application-id {
              type string;
            }
            leaf broadcast {
              type uint16;
            }
            leaf ca-system-id {
              type string;
            }
            leaf mac-addr {
              type string;
            }
          }
        }
      }
      list tg {
        tailf:cli-suppress-mode;
        tailf:cli-delete-when-empty;
        key "group-id";
        leaf group-id {
          type uint16;
        }
        list channel {
          tailf:cli-suppress-mode;
          tailf:cli-delete-when-empty;
          tailf:cli-compact-syntax;
          key "channel-id";
          leaf channel-id {
            type uint16;
          }
          leaf priority {
            type uint8;
          }
          leaf status {
            tailf:cli-drop-node-name;
            type enumeration {
              enum "disable";
              enum "enable";
            }
          }
        }
      }
      list tunnel {
        tailf:cli-suppress-mode;
        tailf:cli-delete-when-empty;
        tailf:cli-compact-syntax;
        tailf:cli-sequence-commands;
        key "tunnel-id";
        leaf tunnel-id {
          type uint16;
        }
        leaf mac-addr {
          type string;
        }
        leaf tg {
          type uint16;
        }
        leaf clients {
          type uint16;
        }
        leaf status {
          tailf:cli-drop-node-name;
          type enumeration {
            enum "disable";
            enum "enable";
          }
        }
      }
      list cfr {
        tailf:cli-suppress-mode;
        tailf:cli-delete-when-empty;
        tailf:cli-compact-syntax;
        tailf:cli-sequence-commands;
        key "index";
        leaf index {
          type uint16;
        }
        leaf dest-ip {
          type string;
        }
        leaf tunnel {
          tailf:cli-break-sequence-commands;
          type uint16;
        }
        leaf priority {
          type uint8;
        }
        leaf src-ip {
          type string;
        }
        leaf in-dcd {
          type enumeration {
            enum "ignore";
            enum "no";
            enum "yes";
          }
        }
      }
      list timer {
        tailf:cli-suppress-mode;
        tailf:cli-delete-when-empty;
        tailf:cli-compact-syntax;
        key "index";
        leaf index {
          type uint16;
        }
        leaf Tdsg1 {
          type uint16;
        }
        leaf Tdsg2 {
          type uint16;
        }
        leaf Tdsg3 {
          type uint16;
        }
        leaf Tdsg4 {
          type uint16;
        }
      }
      list chan-list {
        tailf:cli-suppress-mode;
        tailf:cli-delete-when-empty;
        tailf:cli-compact-syntax;
        tailf:cli-sequence-commands {
          tailf:cli-reset-siblings;
        }
        key "id index";
        leaf id {
          type uint16;
        }
        leaf index {
          tailf:cli-expose-key-name;
          type uint16;
        }
        leaf freq {
          type uint32;
        }
      }
    }
    container load-balance {
      leaf docsis-enable {
        type empty;
      }
      container docsis30-enable {
        tailf:cli-delete-when-empty;
        presence "true";
        leaf downstream-only {
          type empty;
        }
        container dynamic {
          leaf downstream {
            type empty;
          }
        }
      }
      container method-utilization {
        leaf min-threshold {
          type uint8;
        }
      }
      container us-attribute-mask {
        leaf force-check {
          type empty;
        }
      }
      leaf fixed-primary-channel {
        type empty;
      }
      container modem {
        leaf max-failures {
          type uint8;
        }
      }
      list rule {
        tailf:cli-suppress-mode;
        tailf:cli-delete-when-empty;
        tailf:cli-compact-syntax;
        tailf:cli-sequence-commands;
        key "rule-id";
        leaf rule-id {
          type uint32;
        }
        choice status-choice {
          container ds {
            tailf:cli-drop-node-name;
            container disable-throughput-lowerbound {
              leaf ds {
                type uint32;
              }
            }
          }
          container us {
            tailf:cli-drop-node-name;
            container disable-throughput-lowerbound {
              leaf us {
                type uint32;
              }
            }
          }
          leaf disabled {
            type empty;
          }
          leaf enabled {
            type empty;
          }
        }
      }
      list docsis-policy {
        tailf:cli-suppress-mode;
        tailf:cli-delete-when-empty;
        key "policy-id";
        leaf policy-id {
          type uint32;
        }
        list rule {
          tailf:cli-suppress-mode;
          tailf:cli-delete-when-empty;
          key "rule-id";
          leaf rule-id {
            type uint32;
          }
        }
        list tag {
          tailf:cli-suppress-mode;
          tailf:cli-delete-when-empty;
          key "name";
          leaf name {
            type string;
          }
          leaf override {
            type empty;
          }
        }
      }
      container d20-ggrp-default {
        leaf init-tech-list {
          type string;
        }
        container method {
          container utilization {
            presence "true";
          }
        }
        container policy {
          leaf pure-ds-load {
            type empty;
          }
        }
        container threshold {
          container load {
            leaf value {
              tailf:cli-drop-node-name;
              type uint8;
            }
          }
        }
      }
      container d30-ggrp-default {
        leaf disable {
          type empty;
        }
        leaf init-tech-list {
          type string;
        }
        leaf docsis-policy {
          type uint32;
        }
        leaf policy {
          type enumeration {
            enum "pcmm";
            enum "pure-ds-load";
            enum "ugs";
            enum "us-across-ds";
          }
        }
        container threshold {
          container load {
            leaf load-value {
              tailf:cli-drop-node-name;
              type uint8;
            }
            leaf minimum {
              type uint8;
            }
          }
        }
        container method {
          tailf:cli-compact-syntax;
          tailf:cli-sequence-commands {
            tailf:cli-reset-siblings;
          }
          leaf value {
            tailf:cli-drop-node-name;
            type enumeration {
              enum "utilization";
              enum "modems";
            }
          }
          leaf primary-distributed {
            tailf:cli-optional-in-sequence;
            type empty;
          }
          leaf us-method {
            type enumeration {
              enum "utilization";
              enum "modems";
            }
          }
        }
      }
      container docsis-group {
        list FN {
          key "fn-id";
          leaf fn-id {
            type uint16;
          }
          container MD {
            tailf:cli-hide-in-submode;
            tailf:cli-flatten-container;
            leaf Cable {
              tailf:cli-allow-join-with-value;
              tailf:cli-hide-in-submode;
              type string;
            }
          }
          uses cable-load-balance-docsis-group-grouping;
        }
        list docsis-group-list {
          tailf:cli-drop-node-name;
          key "docsis-group-id";
          leaf docsis-group-id {
            type uint32;
          }
          uses cable-load-balance-docsis-group-grouping;
        }
      }
      list group {
        tailf:cli-suppress-mode;
        tailf:cli-delete-when-empty;
        key "id";
        leaf id {
          type uint16;
        }
      }
      container exclude {
        list modem {
          tailf:cli-suppress-mode;
          tailf:cli-delete-when-empty;
          key "address";
          leaf address {
            type string;
          }
        }
        list oui {
          tailf:cli-suppress-mode;
          tailf:cli-delete-when-empty;
          tailf:cli-compact-syntax;
          key "word";
          leaf word {
            type string;
          }
          leaf assignment {
            type empty;
          }
          leaf enforce {
            type empty;
          }
          leaf static {
            type empty;
          }
          leaf strict {
            type empty;
          }
        }
      }
    }
    container metering {
      choice cable-metering-choice {
        container destination {
          tailf:cli-compact-syntax;
          tailf:cli-sequence-commands {
            tailf:cli-reset-siblings;
          }
          leaf ip-address {
            tailf:cli-drop-node-name;
            type inet:ipv4-address;
          }
          leaf port {
            tailf:cli-drop-node-name;
            type uint16;
          }
          leaf ip-address2 {
            tailf:cli-drop-node-name;
            tailf:cli-optional-in-sequence;
            type inet:ipv4-address;
          }
          leaf port2 {
            tailf:cli-drop-node-name;
            type uint16;
          }
          leaf retries {
            tailf:cli-drop-node-name;
            type uint8;
          }
          leaf minutes {
            tailf:cli-drop-node-name;
            type uint16;
          }
          leaf security {
            tailf:cli-drop-node-name;
            type enumeration {
              enum "non-secure";
              enum "secure";
            }
          }
          leaf flow-aggregate {
            tailf:cli-break-sequence-commands;
            type empty;
          }
          leaf cpe-list-suppress {
            type empty;
          }
          leaf full-records {
            type empty;
          }
        }
        container ipdr-d3 {
          container session {
            tailf:cli-compact-syntax;
            tailf:cli-sequence-commands {
              tailf:cli-reset-siblings;
            }
            leaf session-id {
              tailf:cli-drop-node-name;
              type uint8;
            }
            leaf type {
              type uint8;
            }
            leaf flow-aggregate {
              tailf:cli-optional-in-sequence;
              type empty;
            }
            leaf full-records {
              type empty;
            }
          }
        }
      }
      container ipdr {
        tailf:cli-compact-syntax;
        tailf:cli-sequence-commands {
          tailf:cli-reset-siblings;
        }
        leaf interval {
          tailf:cli-drop-node-name;
          type uint16;
        }
        leaf session {
          type uint8;
        }
        leaf flow-aggregate {
          tailf:cli-optional-in-sequence;
          type empty;
        }
        leaf full-records {
          type empty;
        }
      }
      container source-interface {
        uses interface-name-grouping;
      }
      container data-per-session {
        tailf:cli-compact-syntax;
        tailf:cli-sequence-commands;
        leaf data-per-session {
          tailf:cli-drop-node-name;
          type uint8;
        }
        leaf timer {
          type uint16;
        }
      }
    }
    container rf-change-trigger {
      tailf:cli-compact-syntax;
      leaf percent {
        type uint8;
      }
      leaf count {
        type uint16;
      }
      leaf secondary {
        type empty;
      }
    }
    container ofdm-rf-change-trigger {
      tailf:cli-compact-syntax;
      leaf percent {
        type uint8;
      }
      leaf count {
        type uint16;
      }
    }
    leaf rf-change-dampen-time {
      type uint16;
    }
    leaf rf-change-up-multiplier {
      type uint8;
    }
    container resiliency {
      leaf ds-bonding {
        type empty;
      }
      leaf free-interval {
        type uint16;
      }
    }
    list cm-status {
      tailf:cli-suppress-mode;
      tailf:cli-delete-when-empty;
      tailf:cli-compact-syntax;
      key "id";
      leaf id {
        type uint8;
      }
      leaf holdoff {
        type uint16;
      }
      leaf reports {
        type uint8;
      }
    }
    container throttle-modem {
      tailf:cli-compact-syntax;
      tailf:cli-sequence-commands {
        tailf:cli-reset-siblings;
      }
      leaf init-rate {
        type uint16;
      }
      leaf holdoff-time {
        type uint8;
      }
      leaf flush-rate {
        type uint16;
      }
    }
    container ds-max-burst {
      tailf:cli-delete-when-empty;
      presence "true";
      choice optional {
        leaf burst-threshold {
          type uint32;
        }
        leaf peak-rate {
          type uint32;
        }
      }
    }
    container acfe {
      leaf enable {
        type empty;
      }
      leaf period {
        type uint8;
      }
    }
    container l2-vpn-service {
      container xconnect {
        container extended-mtu {
          tailf:cli-delete-when-empty;
          presence "true";
          leaf value {
            tailf:cli-drop-node-name;
            type uint16;
          }
        }
        container nsi {
          container dot1q {
            presence "true";
            container interface {
              uses interface-name-grouping;
            }
          }
          container mpls {
            presence "true";
          }
        }
      }
    }
    list dot1q-vc-map {
      tailf:cli-suppress-mode;
      tailf:cli-delete-when-empty;
      tailf:cli-compact-syntax;
      tailf:cli-sequence-commands;
      key "mac-address";
      leaf mac-address {
        type string;
      }
      container ethernet-interface {
        tailf:cli-drop-node-name;
        tailf:cli-flatten-container;
        tailf:cli-compact-syntax;
        uses interface-name-grouping;
      }
      leaf vlan-id {
        tailf:cli-drop-node-name;
        type uint16;
      }
      leaf cust-name {
        tailf:cli-drop-node-name;
        type string;
      }
    }
    list l2vpn {
      tailf:cli-sequence-commands;
      key "mac-address";
      leaf mac-address {
        type string;
      }
      leaf customer-name {
        tailf:cli-drop-node-name;
        tailf:cli-hide-in-submode;
        type string;
      }
      container service {
        tailf:cli-break-sequence-commands;
        list instance {
          tailf:cli-sequence-commands;
          key "id";
          leaf id {
            type uint16;
          }
          leaf ethernet {
            tailf:cli-hide-in-submode;
            type empty;
          }
          container xconnect {
            tailf:cli-break-sequence-commands;
            tailf:cli-add-mode;
            tailf:cli-compact-syntax;
            tailf:cli-sequence-commands;
            tailf:cli-delete-when-empty;
            presence "true";
            leaf address {
              tailf:cli-drop-node-name;
              tailf:cli-hide-in-submode;
              type inet:ipv4-address;
            }
            leaf vcid {
              tailf:cli-drop-node-name;
              tailf:cli-hide-in-submode;
              type uint32;
            }
            leaf encapsulation {
              tailf:cli-hide-in-submode;
              type enumeration {
                enum "mpls";
              }
            }
            leaf pw-type {
              tailf:cli-optional-in-sequence;
              tailf:cli-hide-in-submode;
              type uint8;
            }
            container backup {
              tailf:cli-break-sequence-commands;
              list peer {
                tailf:cli-suppress-mode;
                tailf:cli-delete-when-empty;
                tailf:cli-compact-syntax;
                key "peer-router-ip-addr vcid";
                leaf peer-router-ip-addr {
                  type inet:ipv4-address;
                }
                leaf vcid {
                  type uint32;
                }
                leaf priority {
                  type uint8;
                }
              }
              container delay {
                tailf:cli-compact-syntax;
                tailf:cli-sequence-commands;
                leaf enable-delay {
                  tailf:cli-drop-node-name;
                  type uint8;
                }
                leaf disable-delay {
                  tailf:cli-drop-node-name;
                  type union {
                    type uint8;
                    type enumeration {
                      enum "never";
                    }
                  }
                }
              }
            }
          }
          container cable {
            container set {
              leaf mpls-experimental {
                type uint8;
              }
            }
          }
        }
      }
    }
    container wideband {
      leaf auto-reset {
        type empty;
      }
      leaf rphy-auto-reset {
        type empty;
      }
    }
    list rcc-template {
      key "index";
      leaf index {
        type uint8;
      }
      leaf rcp-id {
        tailf:cli-multi-value;
        type string;
      }
      list receive-module {
        tailf:cli-suppress-mode;
        tailf:cli-delete-when-empty;
        tailf:cli-compact-syntax;
        tailf:cli-sequence-commands;
        key "index";
        leaf index {
          type uint8;
        }
        leaf first-center-frequency {
          type uint32;
        }
        leaf connected-receive-module {
          type uint8;
        }
      }
      list receive-channel {
        tailf:cli-suppress-mode;
        tailf:cli-delete-when-empty;
        tailf:cli-compact-syntax;
        tailf:cli-sequence-commands;
        key "index";
        leaf index {
          type uint8;
        }
        leaf center-frequency {
          type uint32;
        }
        leaf connected-receive-module {
          type uint8;
        }
        leaf primary {
          type empty;
        }
      }
    }
    list virtual-service-group {
      tailf:cli-suppress-mode;
      tailf:cli-delete-when-empty;
      tailf:cli-compact-syntax;
      tailf:cli-sequence-commands;
      key "name";
      leaf name {
        type string;
      }
      choice cable-choice {
        leaf downstream-cable {
          type string;
        }
        leaf upstream-cable {
          type string;
        }
        leaf downstream-video {
          type string;
        }
      }
      leaf profile {
        type uint16;
      }
    }
    container oob {
      tailf:cli-add-mode;
      presence "true";
      list virtual-om {
        key "id";
        leaf id {
          type uint8;
        }
        container ip {
          tailf:cli-compact-syntax;
          tailf:cli-sequence-commands {
            tailf:cli-reset-siblings;
          }
          leaf address {
            tailf:cli-drop-node-name;
            type inet:ipv4-address;
          }
          leaf mask {
            tailf:cli-drop-node-name;
            type inet:ipv4-address;
          }
        }
        container join-group {
          tailf:cli-compact-syntax;
          tailf:cli-sequence-commands {
            tailf:cli-reset-siblings;
          }
          leaf group-ip {
            tailf:cli-drop-node-name;
            type inet:ipv4-address;
          }
          leaf source-ip {
            type inet:ipv4-address;
          }
          leaf out-group {
            type inet:ipv4-address;
          }
        }
      }
      list virtual-arpd {
        key "id";
        leaf id {
          type uint8;
        }
        container ip {
          tailf:cli-compact-syntax;
          tailf:cli-sequence-commands {
            tailf:cli-reset-siblings;
          }
          leaf address {
            tailf:cli-drop-node-name;
            type inet:ipv4-address;
          }
          leaf mask {
            tailf:cli-drop-node-name;
            type inet:ipv4-address;
          }
        }
        container nc {
          tailf:cli-compact-syntax;
          tailf:cli-sequence-commands {
            tailf:cli-reset-siblings;
          }
          leaf address {
            tailf:cli-drop-node-name;
            type inet:ipv4-address;
          }
          leaf udp-port {
            type uint16;
          }
        }
        leaf source-id {
          type uint32;
        }
      }
      list static-pseudowire {
        key "name";
        leaf name {
          type string;
        }
        leaf type {
          tailf:cli-hide-in-submode;
          type enumeration {
            enum "ndf";
            enum "ndr";
          }
        }
        leaf id {
          tailf:cli-hide-in-submode;
          type uint32;
        }
        container dest-source {
          tailf:cli-drop-node-name;
          tailf:cli-compact-syntax;
          tailf:cli-sequence-commands {
            tailf:cli-reset-siblings;
          }
          leaf dest-ip {
            type union {
              type inet:ipv4-address;
              type inet:ipv6-address;
            }
          }
          leaf source-ip {
            type union {
              type inet:ipv4-address;
              type inet:ipv6-address;
            }
          }
        }
        leaf server-ip {
          type union {
            type inet:ipv4-address;
            type inet:ipv6-address;
          }
        }
        leaf session-id {
          type string;
        }
      }
    }
    container rphy {
      list ccap-core-event {
        tailf:cli-suppress-mode;
        tailf:cli-delete-when-empty;
        key "name";
        leaf name {
          type enumeration {
            enum "evt-66080102";
            enum "evt-66080100";
            enum "evt-66080101";
            enum "evt-66080104";
            enum "evt-66080105";
            enum "evt-66080200";
            enum "evt-66080201";
            enum "evt-66080400";
          }
        }
        leaf enable {
          type empty;
        }
      }
      container link {
        leaf redundancy {
          type enumeration {
            enum "cold";
            enum "hot";
          }
        }
      }
      container statistics {
        container session {
          leaf update-freq {
            type uint32;
          }
        }
      }
    }
    container video {
      tailf:cli-add-mode;
      presence "true";
      container multicast-uplink {
        tailf:cli-compact-syntax;
        tailf:cli-sequence-commands {
          tailf:cli-reset-siblings;
        }
        uses interface-name-grouping;
        leaf access-list {
          type string;
        }
        leaf access-list-global {
          tailf:cli-optional-in-sequence;
          type string;
        }
        leaf rp {
          type inet:ipv4-address;
        }
      }
      leaf default-onid {
        type uint16;
      }
      leaf default-psi-interval {
        type uint16;
      }
      leaf use-pcr-fo {
        type empty;
      }
      leaf pcr-based-source-switch {
        type empty;
      }
      leaf default-nit-reference {
        type uint16;
      }
      container mgmt-intf {
        leaf VirtualPortGroup {
          type uint8;
        }
      }
      list service-distribution-group {
        key "name";
        leaf name {
          type string;
        }
        leaf id {
          tailf:cli-hide-in-submode;
          type uint16;
        }
        container rpd {
          leaf downstream-cable {
            type string;
          }
        }
        leaf onid {
          type uint16;
        }
        leaf psi-interval {
          type uint16;
        }
        container rf-port {
          list integrated-cable {
            tailf:cli-suppress-mode;
            tailf:cli-delete-when-empty;
            key "name";
            leaf name {
              type string;
            }
          }
        }
        leaf serving-area {
          type uint16;
        }
      }
      list virtual-carrier-group {
        key "name";
        leaf name {
          type string;
        }
        leaf id {
          tailf:cli-hide-in-submode;
          type uint16;
        }
        list virtual-edge-input-ip {
          tailf:cli-suppress-mode;
          tailf:cli-delete-when-empty;
          tailf:cli-compact-syntax;
          tailf:cli-sequence-commands {
            tailf:cli-reset-siblings;
          }
          key "address";
          leaf address {
            type inet:ipv4-address;
          }
          leaf vrf {
            tailf:cli-optional-in-sequence;
            type string;
          }
          leaf input-port-number {
            type uint16;
          }
        }
        leaf low-latency {
          type empty;
        }
        leaf encrypt {
          type empty;
        }
        leaf service-type {
          type enumeration {
            enum "broadcast";
            enum "narrowcast";
          }
        }
        leaf override-tsid {
          type uint16;
        }
        container rf-channel {
          tailf:cli-compact-syntax;
          tailf:cli-sequence-commands;
          leaf channel {
            tailf:cli-drop-node-name;
            type string;
          }
          leaf tsid {
            type string;
          }
          leaf output-port-number {
            type string;
          }
        }
      }
      container bind-vcg {
        tailf:cli-add-mode;
        list vcg {
          tailf:cli-suppress-mode;
          tailf:cli-delete-when-empty;
          key "name sdg";
          leaf name {
            type string;
          }
          leaf sdg {
            tailf:cli-expose-key-name;
            type string;
          }
        }
      }
      list announce-event-profile {
        key "name";
        unique "id";
        leaf name {
          type string;
        }
        leaf id {
          tailf:cli-hide-in-submode;
          type uint16;
        }
        leaf ack-timeout {
          type uint8;
        }
        leaf filter {
          type enumeration {
            enum "2104";
            enum "4400";
            enum "4401";
            enum "5200";
            enum "5401";
            enum "5404";
            enum "5405";
            enum "5406";
            enum "5502";
            enum "5602";
            enum "all-events";
          }
        }
      }
      list logical-edge-device {
        key "name";
        leaf name {
          type string;
        }
        leaf id {
          tailf:cli-hide-in-submode;
          type uint8;
        }
        container protocol {
          container gqi {
            tailf:cli-add-mode;
            presence "true";
            uses cable-video-logical-edge-device-protocol-grouping;
          }
          container table-based {
            tailf:cli-add-mode;
            presence "true";
            uses cable-video-logical-edge-device-protocol-grouping;
          }
        }
      }
      container table-based {
        tailf:cli-add-mode;
        list multicast-label {
          tailf:cli-suppress-mode;
          tailf:cli-delete-when-empty;
          tailf:cli-compact-syntax;
          tailf:cli-sequence-commands {
            tailf:cli-reset-siblings;
          }
          key "name";
          leaf name {
            type string;
          }
          leaf group {
            type inet:ipv4-address;
          }
          leaf source {
            type inet:ipv4-address;
          }
          leaf source2 {
            type inet:ipv4-address;
          }
          leaf source3 {
            type inet:ipv4-address;
          }
          leaf source4 {
            type inet:ipv4-address;
          }
        }
        list vcg {
          key "name";
          leaf name {
            type string;
          }
          list rf-channel {
            key "name";
            leaf name {
              tailf:cli-suppress-range;
              type string;
            }
            list session {
              tailf:cli-suppress-mode;
              tailf:cli-delete-when-empty;
              tailf:cli-compact-syntax;
              tailf:cli-sequence-commands {
                tailf:cli-reset-siblings;
              }
              key "name";
              leaf name {
                type string;
              }
              choice session-id-choice {
                leaf input-port {
                  type uint16;
                }
                leaf multicast-label {
                  type string;
                }
                leaf group {
                  type inet:ipv4-address;
                }
              }
              leaf source {
                tailf:cli-optional-in-sequence;
                type inet:ipv4-address;
              }
              leaf start-udp-port {
                tailf:cli-optional-in-sequence;
                type uint16;
              }
              leaf num-sessions-per-qam {
                tailf:cli-optional-in-sequence;
                type uint8;
              }
              leaf increment-by {
                tailf:cli-optional-in-sequence;
                type uint8;
              }
              leaf processing-type {
                type enumeration {
                  enum "data";
                  enum "passthru";
                  enum "remap";
                  enum "remux";
                }
              }
              leaf input-program-num {
                tailf:cli-optional-in-sequence;
                type uint16;
              }
              leaf output-program-num {
                tailf:cli-optional-in-sequence;
                type uint16;
              }
              leaf start-program {
                tailf:cli-optional-in-sequence;
                type uint16;
              }
              leaf bit-rate {
                tailf:cli-optional-in-sequence;
                type uint32;
              }
              leaf repeat {
                tailf:cli-optional-in-sequence;
                type empty;
              }
              choice bit-rate-choice {
                leaf cbr {
                  tailf:cli-optional-in-sequence;
                  type empty;
                }
                leaf vbr {
                  tailf:cli-optional-in-sequence;
                  type empty;
                }
              }
              leaf master-slave {
                tailf:cli-optional-in-sequence;
                type empty;
              }
              leaf pcr-pid {
                tailf:cli-optional-in-sequence;
                type uint16;
              }
              leaf psip {
                tailf:cli-optional-in-sequence;
                type empty;
              }
              leaf eas {
                type empty;
              }
            }
          }
        }
      }
      container timeout {
        leaf off-session {
          type uint16;
        }
      }
      container report-stream-error {
        container cc-error {
          tailf:cli-compact-syntax;
          tailf:cli-delete-when-empty;
          presence "true";
          leaf report-interval {
            type uint16;
          }
          leaf threshold {
            type uint16;
          }
          leaf syslog {
            type enumeration {
              enum "disable";
              enum "enable";
            }
          }
        }
      }
    }
    list fiber-node {
      key "fiber-node-id";
      leaf fiber-node-id {
        type uint16;
      }
      leaf description {
        tailf:cli-multi-value;
        type string;
      }
      container downstream {
        list Downstream-Cable {
          tailf:cli-allow-join-with-key;
          tailf:cli-suppress-mode;
          tailf:cli-delete-when-empty;
          key "name";
          leaf name {
            type string;
          }
          leaf rf-channel {
            type string;
          }
        }
        list Modular-Cable {
          tailf:cli-allow-join-with-key;
          tailf:cli-suppress-mode;
          tailf:cli-delete-when-empty;
          key "name";
          leaf name {
            type string;
          }
          leaf rf-channel {
            type string;
          }
        }
        list Integrated-Cable {
          tailf:cli-allow-join-with-key;
          tailf:cli-suppress-mode;
          tailf:cli-delete-when-empty;
          key "name";
          leaf name {
            type string;
          }
          leaf rf-channel {
            type string;
          }
        }
        list sg-channel {
          tailf:cli-suppress-mode;
          tailf:cli-delete-when-empty;
          tailf:cli-compact-syntax;
          tailf:cli-sequence-commands;
          key "low";
          leaf low {
            tailf:cli-suppress-range;
            type uint8;
          }
          leaf high {
            tailf:cli-drop-node-name;
            tailf:cli-optional-in-sequence;
            type uint8;
          }
          choice cable-choice {
            leaf downstream-Cable {
              type string;
            }
            leaf integrated-Cable {
              type string;
            }
            leaf downstream-cable {
              type string;
            }
            leaf integrated-cable {
              type string;
            }
          }
          leaf rf-channel {
            type uint8;
          }
          leaf rf-channel-high {
            tailf:cli-drop-node-name;
            type uint8;
          }
        }
      }
      container upstream {
        list Upstream-Cable {
          tailf:cli-allow-join-with-key;
          tailf:cli-suppress-mode;
          tailf:cli-delete-when-empty;
          key "name";
          leaf name {
            type string;
          }
          leaf connector {
            type string;
          }
        }
        list Cable {
          tailf:cli-allow-join-with-key;
          tailf:cli-suppress-mode;
          tailf:cli-delete-when-empty;
          key "name";
          leaf name {
            type string;
          }
          leaf connector {
            type string;
          }
        }
        list sg-channel {
          tailf:cli-suppress-mode;
          tailf:cli-delete-when-empty;
          tailf:cli-compact-syntax;
          tailf:cli-sequence-commands {
            tailf:cli-reset-siblings;
          }
          key "id";
          leaf id {
            type uint8;
          }
          leaf peer-node-us {
            tailf:cli-optional-in-sequence;
            type empty;
          }
          leaf Upstream-Cable {
            type string;
          }
          leaf us-channel {
            type uint8;
          }
        }
      }
      container service-group {
        list managed {
          tailf:cli-suppress-mode;
          tailf:cli-delete-when-empty;
          key "md";
          leaf md {
            tailf:cli-expose-key-name;
            type uint8;
          }
          leaf Cable {
            tailf:cli-allow-join-with-value;
            type string;
          }
        }
        leaf profile {
          type string;
        }
      }
    }
    list rpd {
      key "name";
      leaf name {
        type string;
      }
      uses description-grouping;
      leaf identifier {
        type string;
      }
      leaf type {
        type enumeration {
          enum "node";
          enum "shelf";
        }
      }
      leaf ssd {
        type uint8;
      }
      container sbfd {
        leaf enable {
          type empty;
        }
      }
      list rpd-us {
        tailf:cli-suppress-mode;
        tailf:cli-delete-when-empty;
        key "port";
        leaf port {
          type uint8;
        }
        leaf description {
          tailf:cli-multi-value;
          type string;
        }
        leaf base-power-rx-level-1_6Mhz {
          type int8;
        }
      }
      list rpd-ds {
        tailf:cli-suppress-mode;
        tailf:cli-delete-when-empty;
        key "port";
        leaf port {
          type uint8;
        }
        leaf max-carrier {
          type uint8;
        }
        leaf base-power {
          type decimal64 {
            fraction-digits 1;
          }
        }
        container downstream-pilot-tone {
          leaf profile {
            type uint16;
          }
        }
        leaf tilt-slope {
          type decimal64 {
            fraction-digits 1;
          }
        }
        leaf tilt-pivot-freq {
          type uint32;
        }
        list rf-channel {
          tailf:cli-suppress-mode;
          tailf:cli-delete-when-empty;
          key "name";
          leaf name {
            tailf:cli-suppress-range;
            type string;
          }
          leaf power-adjust {
            type string;
          }
          leaf mute {
            type empty;
          }
        }
        leaf mute {
          type empty;
        }
        leaf shutdown {
          type empty;
        }
      }
      container core-interface {
        list Te {
          tailf:cli-allow-join-with-key;
          key "name";
          leaf name {
            type string;
          }
          uses cable-rpd-core-if-grouping;
        }
        list Hu {
          tailf:cli-allow-join-with-key;
          key "name";
          leaf name {
            type string;
          }
          uses cable-rpd-core-if-grouping;
        }
      }
      leaf r-dti {
        type uint8;
      }
      container rpd-event {
        leaf profile {
          type uint8;
        }
      }
      container rpd-55d1-us-event {
        leaf profile {
          type uint8;
        }
      }
      container ptp {
        leaf profile {
          type uint8;
        }
      }
      list external-core {
        tailf:cli-suppress-mode;
        tailf:cli-delete-when-empty;
        key "address";
        leaf address {
          type union {
            type inet:ipv4-address;
            type inet:ipv6-address;
          }
        }
      }
      container location {
        leaf description {
          tailf:cli-multi-value;
          type string;
        }
        leaf latitude {
          type string;
        }
        leaf longitude {
          type string;
        }
      }
    }
    container ipv6 {
      container pd-route {
        tailf:cli-compact-syntax;
        tailf:cli-sequence-commands;
        leaf prefix {
          tailf:cli-drop-node-name;
          type ios:ipv6-prefix;
        }
        leaf Bundle {
          tailf:cli-allow-join-with-value;
          type uint8;
        }
      }
      container source-verify {
        container leasequery-filter {
          container downstream {
            tailf:cli-compact-syntax;
            tailf:cli-sequence-commands;
            leaf threshold {
              tailf:cli-drop-node-name;
              type uint8;
            }
            leaf interval {
              tailf:cli-drop-node-name;
              type uint8;
            }
          }
        }
      }
    }
    container reconcilation {
      leaf enable {
        type empty;
      }
      leaf time {
        type uint8;
      }
    }
  }
  container l2tp {
    leaf congestion-control {
      type empty;
    }
  }
  list l2tp-class {
    key "l2tp-class-name";
    leaf l2tp-class-name {
      type string;
    }
    leaf authentication {
      type empty;
    }
    leaf hello {
      type uint16;
    }
    container password {
      tailf:cli-compact-syntax;
      tailf:cli-sequence-commands;
      uses password-grouping {
        refine "secret";
      }
    }
    container retransmit {
      leaf retries {
        type uint16;
      }
      container timeout {
        choice timeout-choice {
          leaf max {
            type uint8;
          }
          leaf min {
            type uint8;
          }
        }
      }
      container initial {
        leaf retries {
          type uint16;
        }
      }
    }
    container digest {
      container secret {
        tailf:cli-compact-syntax;
        tailf:cli-sequence-commands;
        uses password-grouping {
          refine "secret";
        }
      }
    }
    container timeout {
      leaf setup {
        type uint16;
      }
    }
    container cookie {
      leaf size {
        type enumeration {
          enum "4";
          enum "8";
        }
      }
    }
  }
  container packetcable {
    leaf element-id {
      type uint32;
    }
    container timer {
      leaf T0 {
        type uint32;
      }
      leaf T1 {
        type uint32;
      }
    }
    container authorize {
      leaf vanilla-docsis-mta {
        type empty;
      }
    }
    leaf multimedia {
      type empty;
    }
    container gate {
      leaf send-subscriberID {
        type empty;
      }
    }
  }
  container packetcable-enable {
    tailf:cli-drop-node-name;
    leaf packetcable {
      type empty;
    }
  }
  list depi-class {
    key "depi-class-name";
    leaf depi-class-name {
      type string;
    }
    container mode {
      leaf mpt {
        type empty;
      }
    }
    leaf l2tp-class {
      type string;
    }
  }
  list depi-tunnel {
    key "depi-tunnel-name";
    leaf depi-tunnel-name {
      type string;
    }
    leaf dest-ip {
      type inet:ipv4-address;
    }
    leaf l2tp-class {
      type string;
    }
    leaf depi-class {
      type string;
    }
    leaf protect-tunnel {
      type string;
    }
  }
  list chat-script {
    tailf:cli-suppress-mode;
    tailf:cli-delete-when-empty;
    key "name";
    leaf name {
      type string;
    }
    leaf line {
      tailf:cli-drop-node-name;
      type string;
    }
  }
  container auto {
    container qos {
      container global {
        leaf compact {
          type empty;
        }
      }
    }
  }
  container autonomic {
    container registrar {
      tailf:cli-add-mode;
      leaf domain-id {
        type string;
      }
      container CA {
        choice CA-choice {
          leaf local {
            type empty;
          }
          leaf url {
            type string;
          }
        }
      }
      leaf whitelist {
        type string;
      }
      leaf shut {
        type boolean;
      }
    }
  }
  container autonomic-enable {
    tailf:cli-drop-node-name;
    leaf autonomic {
      type empty;
    }
  }
  container recovered-clock {
    list clock-list {
      tailf:cli-drop-node-name;
      key "slot subslot";
      leaf slot {
        type uint8;
      }
      leaf subslot {
        type uint8;
      }
      container clock {
        list recovered {
          tailf:cli-compact-syntax;
          tailf:cli-suppress-mode;
          tailf:cli-delete-when-empty;
          tailf:cli-sequence-commands {
            tailf:cli-reset-siblings;
          }
          key "id";
          leaf id {
            type uint16;
          }
          leaf type {
            tailf:cli-drop-node-name;
            type enumeration {
              enum "adaptive";
              enum "differential";
            }
          }
          container cem {
            tailf:cli-flatten-container;
            tailf:cli-compact-syntax;
            tailf:cli-sequence-commands {
              tailf:cli-reset-siblings;
            }
            leaf port {
              tailf:cli-drop-node-name;
              type uint8;
            }
            leaf cem-group {
              tailf:cli-drop-node-name;
              type uint16;
            }
          }
        }
      }
    }
  }
  container controller {
    list controller-tx-ex-list {
      tailf:cli-drop-node-name;
      key "name number";
      leaf name {
        type enumeration {
          enum "T1";
          enum "E1";
          enum "T3";
        }
      }
      leaf number {
        type string;
      }
      leaf secondary-admin-state {
        type enumeration {
          enum "auto-in-service";
          enum "maintenance";
          enum "normal";
        }
      }
      leaf ais-shut {
        type boolean;
      }
      container attach {
        leaf profile {
          type string;
        }
      }
      container forward-alarm {
        leaf ais {
          type empty;
        }
        leaf rai {
          type empty;
        }
      }
      container threshold {
        leaf sd-ber {
          type uint8;
        }
        leaf sf-ber {
          type uint8;
        }
      }
      leaf framing {
        type string;
      }
      leaf service-type {
        type enumeration {
          enum "data";
          enum "ccs-voice";
          enum "cas-voice";
        }
      }
      leaf fdl {
        type enumeration {
          enum "ansi";
          enum "att";
          enum "both";
        }
      }
      list cem-group {
        tailf:cli-suppress-mode;
        tailf:cli-delete-when-empty;
        key "id";
        leaf id {
          type uint8;
        }
        choice type-choice {
          leaf framed {
            type empty;
          }
          leaf unframed {
            type empty;
          }
          leaf cep {
            type empty;
          }
        }
        leaf-list timeslots {
          tailf:cli-range-list-syntax;
          type uint8;
        }
      }
      container clock {
        container source {
          choice source-choice {
            container line {
              tailf:cli-delete-when-empty;
              presence "true";
              leaf line-mode {
                tailf:cli-drop-node-name;
                type enumeration {
                  enum "primary";
                  enum "secondary";
                  enum "bits";
                  enum "independent";
                }
              }
            }
            leaf internal {
              type empty;
            }
            leaf loop-timed {
              type empty;
            }
            leaf free-running {
              type empty;
            }
            leaf recovered {
              type uint16;
            }
          }
        }
      }
      leaf linecode {
        type enumeration {
          enum "ami";
          enum "b8zs";
          enum "hdb3";
        }
      }
      container loopback {
        choice loopback-choice {
          leaf diag {
            type empty;
          }
          container local {
            tailf:cli-delete-when-empty;
            presence "true";
            leaf payload {
              type empty;
            }
          }
        }
      }
      container cablelength {
        choice cablelength-choice {
          leaf value {
            tailf:cli-drop-node-name;
            type uint32;
          }
          leaf long {
            type string;
          }
          leaf short {
            type string;
          }
          container short-novalue {
            tailf:cli-drop-node-name;
            leaf short {
              type empty;
            }
          }
          container long-novalue {
            tailf:cli-drop-node-name;
            leaf long {
              type empty;
            }
          }
        }
      }
      container pri-group {
        list timeslots {
          tailf:cli-suppress-mode;
          tailf:cli-delete-when-empty;
          tailf:cli-compact-syntax;
          tailf:cli-range-list-syntax;
          key "id";
          leaf id {
            type uint8;
          }
          leaf nfas_d {
            type enumeration {
              enum "primary";
              enum "backup";
              enum "none";
            }
          }
          leaf nfas_int {
            type uint32;
          }
          leaf nfas_group {
            type uint8;
          }
          leaf service {
            type enumeration {
              enum "mgcp";
            }
          }
        }
      }
      list channel-group {
        tailf:cli-suppress-mode;
        tailf:cli-delete-when-empty;
        key "number";
        leaf number {
          type uint8;
        }
        leaf unframed {
          type empty;
        }
        leaf-list timeslots {
          tailf:cli-range-list-syntax;
          type uint16;
        }
      }
      leaf description {
        tailf:cli-multi-value;
        type string;
      }
      list t1 {
        tailf:cli-suppress-mode;
        tailf:cli-delete-when-empty;
        key "id";
        leaf id {
          type uint8;
        }
        leaf description {
          tailf:cli-multi-value;
          type string;
        }
        list cem-group {
          tailf:cli-suppress-mode;
          tailf:cli-delete-when-empty;
          key "id";
          leaf id {
            type uint16;
          }
          choice type-choice {
            leaf framed {
              type empty;
            }
            leaf unframed {
              type empty;
            }
            leaf-list timeslots {
              tailf:cli-range-list-syntax;
              type uint8;
            }
          }
        }
        list channel-group {
          tailf:cli-suppress-mode;
          tailf:cli-delete-when-empty;
          key "id";
          leaf id {
            type uint8;
          }
          leaf-list timeslots {
            tailf:cli-range-list-syntax;
            type uint8;
          }
        }
        leaf framing {
          type enumeration {
            enum "SF";
          }
        }
        leaf speed {
          type enumeration {
            enum "56";
            enum "64";
          }
        }
        container clock {
          tailf:cli-compact-syntax;
          tailf:cli-sequence-commands {
            tailf:cli-reset-siblings;
          }
          leaf source {
            type enumeration {
              enum "line";
              enum "internal";
              enum "Recovered";
            }
          }
          leaf id {
            tailf:cli-drop-node-name;
            type uint16;
          }
        }
      }
      container ima-group {
        tailf:cli-compact-syntax;
        tailf:cli-sequence-commands {
          tailf:cli-reset-siblings;
        }
        leaf group-number {
          tailf:cli-drop-node-name;
          type uint8;
        }
        leaf scrambling-payload {
          type empty;
        }
      }
      leaf shutdown {
        type empty;
      }
      container snmp {
        container trap {
          leaf link-status {
            type boolean;
          }
        }
      }
    }
    container BITS {
      container input {
        container applique {
          container E1 {
            tailf:cli-compact-syntax;
            tailf:cli-sequence-commands;
            choice E1-choice {
              case clock-case {
                leaf clock-if {
                  tailf:cli-drop-node-name;
                  type enumeration {
                    enum "2048KHz";
                  }
                }
              }
              case framing-case {
                leaf framing {
                  type enumeration {
                    enum "fas_crc4";
                    enum "fas_nocrc";
                    enum "mfas_crc4";
                    enum "mfas_nocrc";
                  }
                }
                leaf linecode {
                  type enumeration {
                    enum "ami";
                    enum "b8zs";
                    enum "hdb3";
                  }
                }
              }
            }
          }
        }
      }
    }
    list Cellular {
      key "id";
      leaf id {
        type string;
      }
      leaf description {
        tailf:cli-multi-value;
        type string;
      }
      container lte {
        container gps {
          leaf enable {
            type empty;
          }
          container mode {
            leaf standalone {
              type empty;
            }
          }
          container nmea {
            choice nmea-choice {
              container ip {
                presence "true";
              }
              container serial {
                presence "true";
                leaf streaming {
                  tailf:cli-drop-node-name;
                  type enumeration {
                    enum "38400";
                    enum "4800";
                    enum "line-config";
                  }
                }
              }
            }
          }
        }
        container modem {
          container link-recovery {
            leaf enable {
              type empty;
            }
            container rssi {
              leaf onset-threshold {
                type int8;
              }
            }
            leaf monitor-timer {
              type uint8;
            }
            leaf wait-timer {
              type uint8;
            }
            leaf debounce-count {
              type uint8;
            }
          }
        }
      }
    }
    list VDSL {
      key "id";
      leaf id {
        type string;
      }
      leaf description {
        tailf:cli-multi-value;
        type string;
      }
      leaf shutdown {
        type empty;
      }
      container firmware {
        leaf filename {
          type string;
        }
      }
    }
    list Upstream-Cable {
      key "name";
      leaf name {
        type string;
      }
      uses description-grouping;
      container cable {
        leaf spectrum-group {
          type uint8;
        }
      }
      uses us-channel-grouping;
    }
    list Downstream-Cable {
      key "name";
      leaf name {
        type string;
      }
      uses description-grouping;
    }
    list Modular-Cable {
      key "name";
      leaf name {
        type string;
      }
      uses description-grouping;
      leaf ip-address {
        type inet:ipv4-address;
      }
      container modular-host {
        leaf subslot {
          type string;
        }
      }
      uses controller-modular-cable-rf-channel-grouping;
    }
    list Integrated-Cable {
      key "name";
      leaf name {
        type string;
      }
      uses description-grouping;
      leaf max-ofdm-spectrum {
        type uint32;
      }
      leaf max-carrier {
        type uint8;
      }
      leaf base-channel-power {
        type uint8;
      }
      container power-tilt {
        tailf:cli-compact-syntax;
        tailf:cli-sequence-commands {
          tailf:cli-reset-siblings;
        }
        leaf mode {
          tailf:cli-drop-node-name;
          type enumeration {
            enum "cable-loss-approx";
            enum "linear";
          }
        }
        leaf loss {
          tailf:cli-drop-node-name;
          type string;
        }
        leaf max-frequency {
          type uint32;
        }
      }
      leaf shutdown {
        type empty;
      }
      leaf freq-profile {
        type uint8;
      }
      container rf-chan {
        list rf-chan {
          tailf:cli-drop-node-name;
          key "start";
          leaf start {
            type uint8;
          }
          uses controller-integrated-cable-rf-chan-grouping;
        }
        list rf-chan-range {
          tailf:cli-drop-node-name;
          key "start end";
          leaf start {
            type uint8;
          }
          leaf end {
            type uint8;
          }
          uses controller-integrated-cable-rf-chan-grouping;
        }
      }
    }
    list upstream-oob {
      key "name id";
      leaf name {
        type string;
      }
      leaf id {
        type uint32;
      }
      list us-channel {
        tailf:cli-suppress-mode;
        tailf:cli-delete-when-empty;
        key "id";
        leaf id {
          type uint8;
        }
        leaf shutdown {
          type empty;
        }
        leaf frequency {
          type uint32;
        }
        container varpd {
          tailf:cli-drop-node-name;
          tailf:cli-compact-syntax;
          tailf:cli-sequence-commands {
            tailf:cli-reset-siblings;
          }
          leaf varpd-portid {
            type uint8;
          }
          leaf varpd-demodid {
            type uint8;
          }
        }
      }
    }
    container upstream-oob-id {
      tailf:cli-drop-node-name;
      list upstream-oob {
        key "name id";
        leaf name {
          type string;
        }
        leaf id {
          tailf:cli-expose-key-name;
          type uint32;
        }
        list us-channel {
          tailf:cli-suppress-mode;
          tailf:cli-delete-when-empty;
          key "id";
          leaf id {
            type uint8;
          }
          leaf shutdown {
            type empty;
          }
          leaf width {
            type uint32;
          }
          leaf frequency {
            type uint32;
          }
        }
      }
    }
    list downstream-oob {
      key "name id";
      leaf name {
        type string;
      }
      leaf id {
        type uint32;
      }
      list ds-channel {
        tailf:cli-suppress-mode;
        tailf:cli-delete-when-empty;
        key "id";
        leaf id {
          type uint8;
        }
        leaf rf-mute {
          type empty;
        }
        leaf shutdown {
          type empty;
        }
        leaf frequency {
          type uint32;
        }
        leaf poweradjust {
          type uint8;
        }
        leaf sf-mute {
          type empty;
        }
        leaf sf-shutdown {
          type empty;
        }
        leaf second-frequency {
          type uint32;
        }
        leaf sf-poweradjust {
          type uint8;
        }
      }
    }
    container downstream-oob-id {
      tailf:cli-drop-node-name;
      list downstream-oob {
        key "name id";
        leaf name {
          type string;
        }
        leaf id {
          tailf:cli-expose-key-name;
          type uint32;
        }
        list ds-channel {
          tailf:cli-suppress-mode;
          tailf:cli-delete-when-empty;
          key "id";
          leaf id {
            type uint8;
          }
          leaf shutdown {
            type empty;
          }
          leaf width {
            type uint32;
          }
          leaf frequency {
            type uint32;
          }
        }
      }
    }
    list wanphy {
      key "name";
      leaf name {
        type string;
      }
    }
    list dwdm {
      key "name";
      leaf name {
        type string;
      }
      leaf shutdown {
        type empty;
      }
      container g709 {
        leaf fec {
          type enumeration {
            enum "enhanced";
            enum "standard";
          }
        }
      }
      container transport-mode {
        choice mode-choice {
          leaf lanwan {
            tailf:cli-drop-node-name;
            type enumeration {
              enum "lan";
              enum "wan";
            }
          }
          leaf otn {
            type enumeration {
              enum "otu3";
              enum "otu4";
            }
          }
        }
      }
    }
    list SONET {
      key "name";
      leaf name {
        type string;
      }
      uses controller-SONET-grouping;
    }
    list SONET-ACR {
      key "name";
      leaf name {
        type uint8;
      }
      uses controller-SONET-grouping;
    }
    list SDH {
      key "name";
      leaf name {
        type string;
      }
      container snmp {
        container trap {
          leaf link-status {
            type boolean;
          }
        }
      }
      leaf rate {
        type enumeration {
          enum "STM1";
          enum "STM4";
          enum "STM16";
        }
      }
      leaf ais-shut {
        type boolean;
      }
      leaf alarm-report {
        type enumeration {
          enum "all";
        }
      }
      leaf shutdown {
        type empty;
      }
      container clock {
        leaf source {
          type enumeration {
            enum "line";
            enum "internal";
          }
        }
      }
      container overhead {
        leaf s1s0 {
          type uint8;
        }
      }
      container aug {
        leaf mapping {
          type enumeration {
            enum "au-3";
            enum "au-4";
          }
        }
      }
      list au-4 {
        key "id";
        leaf id {
          type uint8;
        }
        container clock {
          leaf source {
            type enumeration {
              enum "line";
              enum "internal";
            }
          }
        }
        container overhead {
          leaf c2 {
            type uint8;
          }
        }
        leaf mode {
          type enumeration {
            enum "tug-3";
            enum "vc4";
          }
        }
        leaf channel-group {
          type uint8;
        }
        list tug-3 {
          key "id";
          leaf id {
            type uint8;
          }
          leaf mode {
            tailf:cli-case-insensitive;
            type enumeration {
              enum "ce3";
              enum "ct3";
              enum "ct3-e1";
              enum "e3";
              enum "t3";
              enum "vc1x";
              enum "vc3";
            }
          }
          list tug-2 {
            key "id";
            leaf id {
              type uint8;
            }
            leaf payload {
              tailf:cli-hide-in-submode;
              tailf:cli-case-insensitive;
              type enumeration {
                enum "vc11";
                enum "vc12";
              }
            }
            list e1 {
              tailf:cli-suppress-mode;
              tailf:cli-delete-when-empty;
              key "id";
              leaf id {
                type uint8;
              }
              container cem-group {
                tailf:cli-flatten-container;
                tailf:cli-compact-syntax;
                tailf:cli-sequence-commands {
                  tailf:cli-reset-siblings;
                }
                leaf id {
                  tailf:cli-drop-node-name;
                  type uint16;
                }
                leaf unframed {
                  type empty;
                }
              }
              uses description-grouping;
              leaf framing {
                type enumeration {
                  enum "crc4";
                  enum "no-crc4";
                  enum "unframed";
                }
              }
            }
            list vc {
              tailf:cli-suppress-mode;
              tailf:cli-delete-when-empty;
              key "id";
              leaf id {
                type uint8;
              }
              container overhead {
                leaf v5 {
                  type uint8;
                }
              }
            }
          }
          container t3 {
            leaf framing {
              type enumeration {
                enum "g751";
                enum "g832";
                enum "c-bit";
              }
            }
            container clock {
              leaf source {
                type enumeration {
                  enum "line";
                  enum "internal";
                }
              }
            }
          }
          list e1 {
            tailf:cli-suppress-mode;
            tailf:cli-delete-when-empty;
            key "id";
            leaf id {
              type uint8;
            }
            container cem-group {
              tailf:cli-flatten-container;
              tailf:cli-compact-syntax;
              tailf:cli-sequence-commands {
                tailf:cli-reset-siblings;
              }
              leaf id {
                tailf:cli-drop-node-name;
                type uint16;
              }
              leaf unframed {
                type empty;
              }
            }
            leaf framing {
              type enumeration {
                enum "crc4";
                enum "no-crc4";
                enum "unframed";
              }
            }
          }
        }
      }
    }
    list SHDSL {
      key "name";
      leaf name {
        type string;
      }
      uses description-grouping;
      leaf termination {
        type enumeration {
          enum "cpe";
          enum "co";
        }
      }
      leaf mode {
        type enumeration {
          enum "atm";
          enum "efm";
        }
      }
      list dsl-group {
        key "id";
        leaf id {
          type uint8;
        }
        leaf pairs {
          tailf:cli-hide-in-submode;
          type string;
        }
        leaf efm-bond {
          tailf:cli-hide-in-submode;
          type empty;
        }
        container shdsl {
          container annex {
            tailf:cli-compact-syntax;
            tailf:cli-sequence-commands {
              tailf:cli-reset-siblings;
            }
            leaf standard {
              tailf:cli-drop-node-name;
              type enumeration {
                enum "A";
                enum "A-F";
                enum "B";
                enum "B-G";
                enum "F";
                enum "G";
              }
            }
            leaf coding {
              type enumeration {
                enum "4-TCPAM";
                enum "8-TCPAM";
                enum "16-TCPAM";
                enum "32-TCPAM";
                enum "64-TCPAM";
                enum "128-TCPAM";
              }
            }
          }
          container rate {
            tailf:cli-compact-syntax;
            tailf:cli-sequence-commands {
              tailf:cli-reset-siblings;
            }
            leaf enhanced {
              tailf:cli-optional-in-sequence;
              type empty;
            }
            leaf value {
              tailf:cli-drop-node-name;
              type union {
                type enumeration {
                  enum "auto";
                }
                type uint16;
              }
            }
          }
        }
        container ignore {
          leaf crc {
            type union {
              type uint8;
              type enumeration {
                enum "always";
              }
            }
          }
        }
        leaf handshake {
          type enumeration {
            enum "itut";
            enum "ieee";
          }
        }
        leaf shutdown {
          type empty;
        }
      }
    }
    list ISA {
      key "name";
      leaf name {
        type string;
      }
    }
    list nid {
      key "name";
      leaf name {
        type string;
      }
    }
    list MediaType {
      key "name";
      leaf name {
        type string;
      }
      uses description-grouping;
      leaf mode {
        type enumeration {
          enum "ethernet";
          enum "sonet";
          enum "t3";
          enum "e1";
          enum "t1";
          enum "sdh";
        }
      }
    }
  }
  container vc-class {
    list atm {
      key "name";
      leaf name {
        type string;
      }
      container vbr-nrt {
        tailf:cli-compact-syntax;
        tailf:cli-sequence-commands {
          tailf:cli-reset-siblings;
        }
        leaf pcr {
          tailf:cli-drop-node-name;
          type uint16;
        }
        leaf scr {
          tailf:cli-drop-node-name;
          type uint16;
        }
        leaf mbs {
          tailf:cli-drop-node-name;
          type uint16;
        }
      }
    }
  }
  container fhrp {
    container version {
      leaf vrrp {
        type enumeration {
          enum "v2";
          enum "v3";
        }
      }
    }
  }
  container coap {
    container http {
      leaf enable {
        type empty;
      }
    }
  }
  container iox {
    presence "true";
  }
  container ip {
    leaf subnet-zero {
      type boolean;
    }
    leaf source-route {
      type boolean;
    }
    leaf host-routing {
      type empty;
    }
    leaf routing {
      type boolean;
    }
    container routing-conf {
      tailf:cli-drop-node-name;
      container routing {
        container protocol {
          container purge {
            leaf interface {
              type boolean;
            }
          }
        }
      }
    }
    container reflexive-list {
      leaf timeout {
        type uint32;
      }
    }
    container options {
      choice options-choice {
        leaf drop {
          type empty;
        }
        leaf ignore {
          type empty;
        }
      }
    }
    leaf identd {
      type empty;
    }
    container audit {
      container notify {
        leaf log {
          type empty;
        }
      }
      container po {
        leaf max-events {
          type uint16;
        }
      }
    }
    container auth-proxy {
      leaf max-login-attempts {
        type uint32;
      }
      leaf max-nodata-conns {
        type uint16;
      }
      container watch-list {
        leaf expiry-time {
          type uint16;
        }
      }
    }
    container admission {
      leaf max-login-attempts {
        type uint32;
      }
      leaf max-nodata-conns {
        type uint16;
      }
      container watch-list {
        leaf expiry-time {
          type uint32;
        }
      }
    }
    container arp {
      container proxy {
        leaf disable {
          type empty;
        }
      }
      container inspection {
        leaf-list bridge-domain {
          tailf:cli-range-list-syntax;
          type uint16;
        }
        container bridge-domain-list {
          tailf:cli-drop-node-name;
          list bridge-domain {
            tailf:cli-suppress-mode;
            tailf:cli-delete-when-empty;
            tailf:cli-compact-syntax;
            key "id";
            leaf id {
              type uint16;
            }
            container logging {
              tailf:cli-flatten-container;
              choice logging-choice {
                leaf acl-match {
                  type enumeration {
                    enum "matchlog";
                    enum "none";
                  }
                }
                leaf dhcp-bindings {
                  type enumeration {
                    enum "all";
                    enum "none";
                    enum "permit";
                  }
                }
              }
            }
          }
        }
        leaf-list validate {
          tailf:cli-flat-list-syntax;
          type enumeration {
            enum "src-mac";
            enum "dst-mac";
            enum "ip";
          }
        }
        container log-buffer {
          leaf entries {
            type uint16;
          }
          container logs {
            tailf:cli-compact-syntax;
            tailf:cli-sequence-commands;
            leaf number {
              tailf:cli-drop-node-name;
              type uint16;
            }
            leaf interval {
              type uint32;
            }
          }
        }
        leaf-list vlan {
          tailf:cli-range-list-syntax;
          type uint16;
        }
        list filter {
          tailf:cli-suppress-mode;
          tailf:cli-delete-when-empty;
          tailf:cli-compact-syntax;
          key "name";
          leaf name {
            type string;
          }
          leaf-list vlan {
            tailf:cli-range-list-syntax;
            type uint16;
          }
        }
      }
      container entry {
        leaf learn {
          type uint32;
        }
      }
    }
    choice gratuitous-arps-choice {
      container gratuitous-arps-conf {
        tailf:cli-drop-node-name;
        leaf gratuitous-arps {
          type boolean;
        }
      }
      container gratuitous-arps {
        leaf non-local {
          type boolean;
        }
      }
    }
    container cef-conf {
      tailf:cli-drop-node-name;
      leaf cef {
        type empty;
      }
    }
    container cef {
      leaf distributed {
        type empty;
      }
      container optimize {
        container neighbor {
          leaf resolution {
            type boolean;
          }
        }
      }
      container load-sharing {
        container algorithm {
          choice algorithm-choice {
            leaf original {
              type empty;
            }
            container universal {
              tailf:cli-delete-when-empty;
              presence "true";
              leaf id {
                tailf:cli-drop-node-name;
                type string;
              }
            }
            container include-ports {
              tailf:cli-compact-syntax;
              tailf:cli-sequence-commands {
                tailf:cli-reset-siblings;
              }
              leaf source {
                tailf:cli-optional-in-sequence;
                type empty;
              }
              leaf destination {
                type empty;
              }
              leaf destination-id {
                tailf:cli-drop-node-name;
                tailf:cli-optional-in-sequence;
                type string;
              }
            }
          }
        }
      }
      container accounting {
        tailf:cli-compact-syntax;
        leaf per-prefix {
          type empty;
        }
        leaf non-recursive {
          type empty;
        }
        leaf prefix-length {
          type empty;
        }
        leaf load-balance-hash {
          type empty;
        }
      }
    }
    list vrf {
      key "name";
      leaf name {
        type string;
      }
      leaf description {
        tailf:cli-multi-value;
        type string;
      }
      leaf rd {
        type rd-type;
      }
      container vpn {
        leaf id {
          type vpn-id-type;
        }
      }
      container snmp {
        leaf context {
          type string;
        }
      }
      leaf context {
        type string;
      }
      container import {
        leaf map {
          type string;
        }
        container ipv4 {
          tailf:cli-compact-syntax;
          tailf:cli-sequence-commands;
          leaf ipv4-type {
            tailf:cli-drop-node-name;
            type enumeration {
              enum "unicast";
              enum "multicast";
            }
          }
          leaf upper-limit {
            tailf:cli-break-sequence-commands;
            tailf:cli-drop-node-name;
            type uint32;
          }
          leaf map {
            type string;
          }
        }
      }
      container export {
        leaf map {
          type string;
        }
        container ipv4 {
          tailf:cli-compact-syntax;
          tailf:cli-sequence-commands;
          leaf ipv4-type {
            tailf:cli-drop-node-name;
            type enumeration {
              enum "unicast";
              enum "multicast";
            }
          }
          leaf upper-limit {
            tailf:cli-break-sequence-commands;
            tailf:cli-drop-node-name;
            type uint32;
          }
          leaf map {
            type string;
          }
        }
      }
      container maximum {
        tailf:cli-compact-syntax;
        tailf:cli-sequence-commands;
        presence "true";
        leaf routes {
          type uint32;
        }
        choice maximum-choice {
          case threshold-case {
            leaf threshold {
              tailf:cli-drop-node-name;
              type uint16;
            }
            leaf reinstall {
              type uint16;
            }
          }
          case warning-case {
            leaf warning-only {
              type empty;
            }
          }
        }
      }
      container bgp {
        container next-hop {
          leaf Loopback {
            tailf:cli-allow-join-with-value;
            type uint32;
          }
        }
      }
      container mdt {
        presence "true";
        leaf default {
          type inet:ipv4-address;
        }
        container data {
          tailf:cli-compact-syntax;
          tailf:cli-sequence-commands;
          leaf mulicast-address {
            tailf:cli-drop-node-name;
            type inet:ipv4-address;
          }
          leaf wildcard-bits {
            tailf:cli-drop-node-name;
            type inet:ipv4-address;
          }
          choice mdt-data-choice {
            case mdt-data-threshold {
              leaf threshold {
                type uint32;
              }
              leaf threshold-list {
                tailf:alt-name "list";
                type ext-acl-type;
              }
            }
            case mdt-data-list {
              leaf list {
                type ext-acl-type;
              }
            }
          }
        }
        leaf log-reuse {
          type empty;
        }
        leaf mtu {
          type uint16;
        }
      }
      container route-target {
        uses route-target-grouping;
      }
    }
    container dhcp-server {
      list dhcp-server-list {
        tailf:cli-drop-node-name;
        tailf:cli-suppress-mode;
        tailf:cli-delete-when-empty;
        tailf:cli-compact-syntax;
        key "server";
        leaf server {
          type inet:host;
        }
      }
      container query {
        container lease {
          leaf timeout {
            type uint8;
          }
        }
      }
    }
    container dhcp-relay {
      container source-interface {
        tailf:cli-flatten-container;
        tailf:cli-compact-syntax;
        uses interface-name-grouping;
      }
      container information {
        container option {
          leaf server-override {
            type empty;
          }
        }
      }
    }
    container ddns {
      container update {
        list method {
          key "name";
          leaf name {
            type string;
          }
          container DDNS {
            presence "true";
            tailf:cli-delete-when-empty;
            leaf both {
              type empty;
            }
          }
          container interval {
            container maximum {
              tailf:cli-sequence-commands;
              tailf:cli-compact-syntax;
              leaf days {
                tailf:cli-drop-node-name;
                type uint16;
              }
              leaf hours {
                tailf:cli-drop-node-name;
                type uint8;
              }
              leaf minutes {
                tailf:cli-drop-node-name;
                type uint8;
              }
              leaf seconds {
                tailf:cli-drop-node-name;
                type uint8;
              }
            }
            container minimum {
              tailf:cli-sequence-commands;
              tailf:cli-compact-syntax;
              leaf days {
                tailf:cli-drop-node-name;
                type uint16;
              }
              leaf hours {
                tailf:cli-drop-node-name;
                type uint8;
              }
              leaf minutes {
                tailf:cli-drop-node-name;
                type uint8;
              }
              leaf seconds {
                tailf:cli-drop-node-name;
                type uint8;
              }
            }
          }
        }
      }
    }
    list host-list {
      key "name";
      leaf name {
        type string;
      }
      leaf-list host {
        tailf:cli-flat-list-syntax;
        ordered-by user;
        type inet:ipv4-address;
      }
    }
    container dhcp {
      leaf smart-relay {
        type empty;
      }
      container use {
        container vrf {
          leaf connected {
            type boolean;
          }
          leaf remote {
            type empty;
          }
        }
      }
      container compatibility {
        container suboption {
          leaf link-selection {
            type enumeration {
              enum "cisco";
              enum "standard";
            }
          }
        }
      }
      container binding {
        container cleanup {
          leaf interval {
            type uint16;
          }
        }
      }
      container conflict {
        leaf logging {
          type boolean;
        }
      }
      container excluded-address {
        uses ip-dhcp-excluded-address-grouping;
        list vrf {
          tailf:cli-suppress-mode;
          tailf:cli-delete-when-empty;
          tailf:cli-compact-syntax;
          key "name";
          leaf name {
            type string;
          }
          uses ip-dhcp-excluded-address-grouping;
        }
      }
      list pool {
        key "id";
        leaf id {
          tailf:cli-multi-word-key;
          type string;
        }
        leaf vrf {
          type string;
        }
        container import {
          leaf all {
            type empty;
          }
        }
        leaf bootfile {
          type string;
        }
        container host {
          tailf:cli-compact-syntax;
          tailf:cli-sequence-commands {
            tailf:cli-reset-siblings;
          }
          leaf address {
            tailf:cli-drop-node-name;
            type inet:ipv4-address;
          }
          leaf mask {
            tailf:cli-drop-node-name;
            type inet:ipv4-address;
          }
        }
        choice hardware-or-client {
          leaf hardware-address {
            type string;
          }
          leaf client-identifier {
            type string;
          }
        }
        leaf client-name {
          type string;
        }
        container network {
          tailf:cli-compact-syntax;
          tailf:cli-sequence-commands {
            tailf:cli-reset-siblings;
          }
          leaf network-number {
            tailf:cli-drop-node-name;
            type inet:ipv4-address;
          }
          leaf mask {
            tailf:cli-drop-node-name;
            type inet:ipv4-address;
          }
        }
        container network-secondary {
          tailf:cli-drop-node-name;
          list network {
            tailf:cli-sequence-commands;
            key "network-number";
            leaf network-number {
              type inet:ipv4-address;
            }
            leaf mask {
              tailf:cli-drop-node-name;
              tailf:cli-hide-in-submode;
              type inet:ipv4-address;
            }
            leaf secondary {
              tailf:cli-hide-in-submode;
              type empty;
            }
            container override {
              leaf default-router {
                type inet:host;
              }
            }
          }
        }
        leaf-list next-server {
          tailf:cli-flat-list-syntax;
          ordered-by user;
          type inet:host;
        }
        leaf-list netbios-name-server {
          tailf:cli-flat-list-syntax;
          ordered-by user;
          type inet:host;
        }
        leaf-list dns-server {
          tailf:cli-flat-list-syntax;
          ordered-by user;
          type inet:host;
        }
        leaf-list default-router {
          tailf:cli-flat-list-syntax;
          ordered-by user;
          type inet:host;
        }
        leaf domain-name {
          type string;
        }
        list option {
          tailf:cli-suppress-mode;
          tailf:cli-delete-when-empty;
          key "code";
          leaf code {
            type uint8;
          }
          choice option-config {
            leaf ascii {
              tailf:cli-multi-value;
              type string;
            }
            leaf hex {
              type union {
                type string;
                type enumeration {
                  enum "none";
                }
              }
            }
            leaf-list ip {
              tailf:cli-flat-list-syntax;
              type inet:host;
            }
          }
          list instance {
            tailf:cli-suppress-mode;
            tailf:cli-delete-when-empty;
            key "option-instance";
            leaf option-instance {
              type uint8;
            }
            choice option-config {
              leaf ascii {
                tailf:cli-multi-value;
                type string;
              }
              leaf hex {
                type union {
                  type string;
                  type enumeration {
                    enum "none";
                  }
                }
              }
              leaf-list ip {
                tailf:cli-flat-list-syntax;
                type inet:host;
              }
            }
          }
        }
        container lease {
          tailf:cli-compact-syntax;
          tailf:cli-sequence-commands {
            tailf:cli-reset-all-siblings;
          }
          choice lease-choice {
            case a {
              leaf infinite {
                type empty;
              }
            }
            case b {
              leaf days {
                tailf:cli-drop-node-name;
                type uint16;
              }
              leaf hours {
                tailf:cli-drop-node-name;
                type uint16;
              }
              leaf minutes {
                tailf:cli-drop-node-name;
                type uint16;
              }
            }
          }
        }
        container update {
          leaf arp {
            type empty;
          }
        }
        leaf accounting {
          type string;
        }
        list class {
          key "name";
          leaf name {
            type string;
          }
          container address {
            container range {
              tailf:cli-compact-syntax;
              tailf:cli-sequence-commands {
                tailf:cli-reset-siblings;
              }
              leaf start-ip {
                tailf:cli-drop-node-name;
                type inet:ipv4-address;
              }
              leaf end-ip {
                tailf:cli-drop-node-name;
                type inet:ipv4-address;
              }
            }
          }
        }
        leaf netbios-node-type {
          type union {
            type enumeration {
              enum "b-node";
              enum "h-node";
              enum "m-node";
              enum "p-node";
            }
            type string;
          }
        }
      }
      list class {
        key "id";
        leaf id {
          type string;
        }
        leaf remark {
          tailf:cli-multi-value;
          type string;
        }
        container relay {
          container agent {
            container information {
              tailf:cli-add-mode;
              presence "true";
            }
          }
        }
      }
      container snooping {
        leaf-list bridge-domain {
          tailf:cli-range-list-syntax;
          tailf:cli-suppress-list-no;
          type uint16;
        }
        container information {
          container option-conf {
            tailf:cli-drop-node-name;
            leaf option {
              type boolean;
            }
          }
          container option {
            leaf allow-untrusted {
              type empty;
            }
            container format {
              leaf snmp-ifindex {
                type empty;
              }
              container remote-id {
                choice remote-id-choice {
                  leaf hostname {
                    type empty;
                  }
                  leaf string {
                    type string;
                  }
                }
              }
            }
          }
        }
        container database {
          leaf url {
            tailf:cli-drop-node-name;
            type string;
          }
          leaf write-delay {
            type uint32;
          }
        }
        container track {
          leaf host {
            type empty;
          }
        }
        container verify {
          leaf mac-address {
            type boolean;
          }
          leaf no-relay-agent-address {
            type empty;
          }
        }
        leaf glean {
          type empty;
        }
        leaf-list vlan {
          tailf:cli-range-list-syntax;
          type uint16;
        }
      }
      container snooping-conf {
        tailf:cli-drop-node-name;
        leaf snooping {
          type empty;
        }
      }
      container relay {
        container information {
          container option-conf {
            tailf:cli-drop-node-name;
            container option {
              leaf vpn {
                type empty;
              }
            }
          }
          container option {
            presence "true";
          }
          leaf check {
            type boolean;
          }
          leaf trust-all {
            type empty;
          }
        }
        container override {
          container giaddr {
            leaf link-selection {
              type empty;
            }
          }
        }
        container prefer {
          leaf known-good-server {
            type empty;
          }
        }
      }
      container bootp {
        leaf ignore {
          type empty;
        }
      }
    }
    container bootp {
      leaf server {
        type boolean;
      }
    }
    container domain {
      leaf round-robin {
        type empty;
      }
      container list-vrf {
        tailf:cli-drop-node-name;
        container list {
          list vrf {
            tailf:cli-suppress-mode;
            tailf:cli-delete-when-empty;
            key "name domain-name";
            leaf name {
              type string;
            }
            leaf domain-name {
              type string;
            }
          }
        }
      }
      list list {
        tailf:cli-suppress-mode;
        tailf:cli-delete-when-empty;
        key "name";
        leaf name {
          type string;
        }
      }
      leaf retry {
        type uint8;
      }
      leaf timeout {
        type uint16;
      }
      container lookup-conf {
        tailf:cli-drop-node-name;
        leaf lookup {
          type boolean;
        }
      }
      container lookup {
        leaf nsap {
          type boolean;
        }
        leaf recursive {
          type empty;
        }
        container vrf-source-interface {
          tailf:cli-drop-node-name;
          list vrf {
            tailf:cli-suppress-mode;
            tailf:cli-delete-when-empty;
            tailf:cli-compact-syntax;
            key "name";
            leaf name {
              type string;
            }
            container source-interface {
              tailf:cli-flatten-container;
              tailf:cli-compact-syntax;
              uses interface-name-grouping;
            }
          }
        }
        container source-interface {
          uses interface-name-grouping;
        }
        leaf vrf {
          type string;
        }
      }
      container name-vrf {
        tailf:cli-drop-node-name;
        container name {
          list vrf {
            tailf:cli-suppress-mode;
            tailf:cli-delete-when-empty;
            tailf:cli-compact-syntax;
            key "name";
            leaf name {
              type string;
            }
            leaf domain-name {
              tailf:cli-drop-node-name;
              type string;
            }
          }
        }
      }
      leaf name {
        type string;
      }
      leaf multicast {
        type string;
      }
      container recursive {
        leaf retry {
          type uint8;
        }
        leaf allow-soa {
          type empty;
        }
      }
    }
    container host {
      uses ip-host-grouping;
      list vrf {
        tailf:cli-suppress-mode;
        tailf:cli-delete-when-empty;
        tailf:cli-compact-syntax;
        key "name";
        leaf name {
          type string;
        }
        uses ip-host-grouping;
      }
    }
    container name-server {
      uses ip-name-server-grouping;
      list vrf {
        tailf:cli-suppress-mode;
        tailf:cli-delete-when-empty;
        tailf:cli-compact-syntax;
        key "name";
        leaf name {
          type string;
        }
        uses ip-name-server-grouping;
      }
    }
    container mcr-conf {
      tailf:cli-drop-node-name;
      leaf multicast-routing {
        type empty;
      }
    }
    container multicast-routing {
      list vrf {
        tailf:cli-suppress-list-no;
        tailf:cli-suppress-mode;
        tailf:cli-delete-when-empty;
        tailf:cli-compact-syntax;
        key "name";
        leaf name {
          type string;
        }
        leaf distributed {
          type empty;
        }
      }
      leaf distributed {
        type empty;
      }
    }
    container multicast {
      leaf group-range {
        type ip-acl-type;
      }
      container route-limit {
        tailf:cli-compact-syntax;
        tailf:cli-sequence-commands;
        leaf limit {
          tailf:cli-drop-node-name;
          type uint32;
        }
        leaf threshold {
          tailf:cli-drop-node-name;
          type uint32;
        }
      }
      container multipath {
        tailf:cli-delete-when-empty;
        presence "true";
        leaf s-g-hash {
          type enumeration {
            enum "basic";
            enum "next-hop-based";
          }
        }
      }
      container mpls {
        leaf mldp {
          type empty;
        }
      }
      list vrf {
        tailf:cli-suppress-mode;
        tailf:cli-delete-when-empty;
        key "name";
        leaf name {
          type string;
        }
        container route-limit {
          tailf:cli-compact-syntax;
          tailf:cli-sequence-commands;
          leaf limit {
            tailf:cli-drop-node-name;
            type uint32;
          }
          leaf threshold {
            tailf:cli-drop-node-name;
            type uint32;
          }
        }
        container multipath {
          presence "true";
        }
        container rpf {
          container select {
            container global {
              list group-list {
                tailf:cli-suppress-mode;
                tailf:cli-delete-when-empty;
                key "id";
                leaf id {
                  type union {
                    type uint16;
                    type string;
                  }
                }
              }
            }
          }
        }
      }
      container hardware-switching {
        leaf replication-mode {
          type enumeration {
            enum "egress";
            enum "ingress";
          }
        }
      }
      container rpf {
        leaf multitopology {
          type empty;
        }
      }
    }
    container icmp {
      container rate-limit {
        container unreachable {
          tailf:cli-compact-syntax;
          tailf:cli-sequence-commands {
            tailf:cli-reset-siblings;
          }
          leaf ms {
            tailf:cli-drop-node-name;
            type uint32;
          }
          leaf log {
            type empty;
          }
          leaf packets {
            tailf:cli-drop-node-name;
            type uint32;
          }
          leaf interval-ms {
            tailf:cli-drop-node-name;
            type uint32;
          }
        }
        container unreachable-DF {
          tailf:cli-drop-node-name;
          container unreachable {
            container DF {
              tailf:cli-compact-syntax;
              tailf:cli-sequence-commands {
                tailf:cli-reset-siblings;
              }
              leaf ms {
                tailf:cli-drop-node-name;
                type uint32;
              }
              leaf log {
                type empty;
              }
              leaf packets {
                tailf:cli-drop-node-name;
                type uint32;
              }
              leaf interval-ms {
                tailf:cli-drop-node-name;
                type uint32;
              }
            }
          }
        }
      }
      leaf redirect {
        type enumeration {
          enum "subnet";
          enum "host";
        }
      }
    }
    container igmp {
      uses ip-igmp-grouping;
      container snooping-conf {
        tailf:cli-drop-node-name;
        container snooping {
          leaf l2-entry-limit {
            type uint32;
          }
          leaf last-member-query-interval {
            type uint16;
          }
          container source-only-learning {
            leaf age-timer {
              type uint32;
            }
          }
          leaf report-suppression {
            type boolean;
          }
          container querier-conf {
            tailf:cli-drop-node-name;
            container querier {
              leaf version {
                type uint8;
              }
              container timer {
                leaf expiry {
                  type uint16;
                }
              }
            }
          }
          leaf querier {
            type empty;
          }
        }
      }
      leaf snooping {
        type boolean;
      }
      container snooping-vlan {
        tailf:cli-drop-node-name;
        container snooping {
          container vlan {
            list no-list {
              tailf:cli-suppress-mode;
              tailf:cli-delete-when-empty;
              key "id";
              leaf id {
                type uint16;
              }
              leaf querier {
                type empty;
              }
              container check {
                leaf ttl {
                  type empty;
                }
                leaf rtr-alert-option {
                  type empty;
                }
              }
            }
            list list {
              tailf:cli-drop-node-name;
              tailf:cli-suppress-mode;
              tailf:cli-delete-when-empty;
              key "id";
              leaf id {
                tailf:cli-suppress-range;
                type uint16;
              }
              container querier {
                leaf address {
                  type inet:ipv4-address;
                }
                leaf query-interval {
                  type uint16;
                }
              }
              container mrouter {
                leaf learn {
                  type enumeration {
                    enum "pim-dvmrp";
                    enum "cgmp";
                  }
                }
                list interface {
                  tailf:cli-suppress-mode;
                  tailf:cli-delete-when-empty;
                  key "name";
                  leaf name {
                    type string;
                  }
                }
              }
              leaf immediate-leave {
                type empty;
              }
            }
            list static-list {
              tailf:cli-drop-node-name;
              tailf:cli-suppress-mode;
              tailf:cli-delete-when-empty;
              key "id static interface";
              leaf id {
                type uint16;
              }
              leaf static {
                tailf:cli-expose-key-name;
                type string;
              }
              leaf interface {
                tailf:cli-expose-key-name;
                type string;
              }
            }
          }
        }
      }
      list profile {
        key "id";
        leaf id {
          type uint32;
        }
      }
      leaf filter {
        type boolean;
      }
      list vrf {
        tailf:cli-suppress-mode;
        tailf:cli-delete-when-empty;
        key "name";
        leaf name {
          type string;
        }
        uses ip-igmp-grouping;
      }
    }
    container msdp {
      uses ip-msdp-grouping;
      list vrf {
        tailf:cli-suppress-mode;
        tailf:cli-delete-when-empty;
        key "name";
        leaf name {
          type string;
        }
        uses ip-msdp-grouping;
      }
    }
    container sap {
      leaf cache-timeout {
        type uint32;
      }
    }
    container device {
      container tracking {
        tailf:cli-delete-when-empty;
        presence "true";
        container probe {
          leaf count {
            type uint8;
          }
          container auto-source {
            tailf:cli-compact-syntax;
            tailf:cli-delete-when-empty;
            presence "true";
            container fallback {
              tailf:cli-flatten-container;
              tailf:cli-compact-syntax;
              tailf:cli-sequence-commands {
                tailf:cli-reset-siblings;
              }
              leaf address {
                tailf:cli-drop-node-name;
                type inet:ipv4-address;
              }
              leaf mask {
                tailf:cli-drop-node-name;
                type inet:ipv4-address;
              }
            }
            leaf override {
              type empty;
            }
          }
          leaf delay {
            type uint8;
          }
          leaf interval {
            type uint32;
          }
        }
      }
    }
    container slb {
      list probe {
        key "name";
        leaf name {
          type string;
        }
        choice probe-choice {
          leaf tcp {
            tailf:cli-hide-in-submode;
            type empty;
          }
          leaf dns {
            tailf:cli-hide-in-submode;
            type empty;
          }
          leaf ping {
            tailf:cli-hide-in-submode;
            type empty;
          }
          leaf custom {
            tailf:cli-hide-in-submode;
            type enumeration {
              enum "udp";
            }
          }
        }
        leaf lookup {
          type string;
        }
        leaf port {
          type uint16;
        }
        leaf interval {
          type uint16;
        }
      }
      list serverfarm {
        key "name";
        leaf name {
          type string;
        }
        container nat {
          choice nat-choice {
            leaf server {
              type empty;
            }
            leaf client {
              type string;
            }
          }
        }
        container predictor {
          leaf leastconns {
            type empty;
          }
        }
        list probe {
          key "name";
          leaf name {
            type string;
          }
        }
        list real {
          key "address";
          leaf address {
            type inet:ipv4-address;
          }
          leaf weight {
            type uint8;
          }
          leaf inservice {
            type empty;
          }
        }
      }
      list vserver {
        key "name";
        leaf name {
          type string;
        }
        container virtual {
          tailf:cli-compact-syntax;
          tailf:cli-sequence-commands {
            tailf:cli-reset-siblings;
          }
          leaf address {
            tailf:cli-drop-node-name;
            type inet:ipv4-address;
          }
          leaf-list protocols {
            tailf:cli-drop-node-name;
            tailf:cli-flat-list-syntax;
            ordered-by user;
            type string;
          }
        }
        leaf serverfarm {
          type string;
        }
        choice advertise-choice {
          container advertise-enable {
            tailf:cli-drop-node-name;
            leaf advertise {
              type boolean;
            }
          }
          container advertise {
            leaf active {
              type empty;
            }
          }
        }
        container delay {
          leaf value {
            tailf:cli-drop-node-name;
            type uint16;
          }
        }
        container replicate {
          container casa {
            tailf:cli-compact-syntax;
            tailf:cli-sequence-commands {
              tailf:cli-reset-siblings;
            }
            leaf listen-ip {
              tailf:cli-drop-node-name;
              type inet:ipv4-address;
            }
            leaf remote-ip {
              tailf:cli-drop-node-name;
              type inet:ipv4-address;
            }
            leaf port {
              tailf:cli-drop-node-name;
              type uint16;
            }
          }
        }
        container inservice {
          tailf:cli-delete-when-empty;
          presence "true";
          leaf standby {
            type string;
          }
        }
      }
    }
    container finger {
      presence "true";
      leaf rfc-compliant {
        type empty;
      }
    }
    container tcp {
      leaf selective-ack {
        type empty;
      }
      leaf timestamp {
        type empty;
      }
      leaf mss {
        type uint16;
      }
      container path-mtu-discovery {
        presence "true";
        leaf age-timer {
          type union {
            type enumeration {
              enum "infinite";
            }
            type uint8;
          }
        }
      }
      leaf window-size {
        type uint32;
      }
      leaf chunk-size {
        type uint16;
      }
      leaf queuemax {
        type uint8;
      }
      leaf synwait-time {
        type uint16;
      }
      container intercept {
        leaf connection-timeout {
          type uint32;
        }
      }
    }
    container telnet {
      leaf tos {
        type string;
      }
      container source-interface {
        uses interface-name-grouping;
      }
      leaf quiet {
        type empty;
      }
    }
    container ftp {
      leaf passive {
        type boolean;
      }
      container source-interface {
        uses interface-name-grouping;
      }
      leaf username {
        type string;
      }
      container password {
        tailf:cli-compact-syntax;
        tailf:cli-sequence-commands;
        uses password-grouping {
          refine "secret";
        }
      }
    }
    container tftp {
      container source-interface {
        tailf:cli-compact-syntax;
        uses interface-name-grouping;
      }
      container boot-interface {
        uses interface-name-grouping;
      }
      leaf blocksize {
        type uint16;
      }
    }
    container ssh {
      leaf bulk-mode {
        type uint32;
      }
      leaf time-out {
        type uint8;
      }
      list port {
        tailf:cli-suppress-mode;
        tailf:cli-delete-when-empty;
        tailf:cli-compact-syntax;
        tailf:cli-sequence-commands;
        key "port";
        leaf port {
          type uint16;
        }
        leaf rotary {
          type uint8;
        }
        leaf rotary-high {
          tailf:cli-drop-node-name;
          type uint8;
        }
      }
      leaf break-string {
        type string;
      }
      leaf authentication-retries {
        type uint8;
      }
      leaf dscp {
        type uint8;
      }
      container logging {
        leaf events {
          type empty;
        }
      }
      leaf version {
        type uint8;
      }
      leaf precedence {
        type uint8;
      }
      leaf stricthostkeycheck {
        type empty;
      }
      leaf maxstartups {
        type uint8;
      }
      container source-interface {
        uses interface-name-grouping;
      }
      container dh {
        container min {
          leaf size {
            type enumeration {
              enum "1024";
              enum "2048";
              enum "4096";
            }
          }
        }
      }
      leaf window-size {
        type uint32;
      }
      container server {
        container authenticate {
          container user {
            leaf publickey {
              type boolean;
            }
            leaf keyboard {
              type boolean;
            }
            leaf password {
              type boolean;
            }
          }
        }
        uses ip-ssh-algorithm-grouping;
      }
      container client {
        uses ip-ssh-algorithm-grouping;
      }
      container rsa {
        leaf keypair-name {
          type string;
        }
      }
      container pubkey-chain {
        tailf:cli-add-mode;
        list username {
          key "name";
          leaf name {
            type string;
          }
          list key-hash {
            tailf:cli-suppress-mode;
            tailf:cli-delete-when-empty;
            tailf:cli-compact-syntax;
            tailf:cli-sequence-commands {
              tailf:cli-reset-siblings;
            }
            key "key-type";
            leaf key-type {
              type union {
                type enumeration {
                  enum "ssh-rsa";
                }
                type string;
              }
            }
            leaf key-name {
              tailf:cli-drop-node-name;
              type string;
            }
            leaf key-comment {
              tailf:cli-drop-node-name;
              type string;
            }
          }
        }
      }
    }
    container scp {
      container server {
        leaf enable {
          type empty;
        }
      }
      leaf remote-username {
        type string;
      }
    }
    container local {
      container policy {
        leaf route-map {
          type string;
        }
      }
      list pool {
        tailf:cli-suppress-mode;
        tailf:cli-delete-when-empty;
        tailf:cli-compact-syntax;
        tailf:cli-sequence-commands {
          tailf:cli-reset-siblings;
        }
        key "id start";
        leaf id {
          type union {
            type string;
            type enumeration {
              enum "default";
            }
          }
        }
        leaf start {
          type inet:ipv4-address;
        }
        leaf last {
          tailf:cli-drop-node-name;
          tailf:cli-optional-in-sequence;
          type inet:ipv4-address;
        }
        leaf group {
          tailf:cli-optional-in-sequence;
          type string;
        }
        leaf cache-size {
          type uint8;
        }
      }
    }
    leaf default-gateway {
      type inet:ipv4-address;
    }
    leaf-list default-network {
      type inet:ipv4-address;
    }
    leaf classless {
      type boolean;
    }
    container forward-protocol {
      leaf nd {
        type empty;
      }
      leaf sdns {
        type boolean;
      }
      leaf turbo-flood {
        type boolean;
      }
      container spanning-tree {
        presence "true";
        leaf any-local-broadcast {
          type empty;
        }
      }
      choice udp-choice {
        leaf udp {
          type boolean;
        }
        container udp-conf {
          tailf:cli-drop-node-name;
          container udp {
            list service {
              tailf:cli-drop-node-name;
              tailf:cli-suppress-mode;
              tailf:cli-delete-when-empty;
              tailf:cli-suppress-list-no;
              key "name";
              leaf name {
                type string;
              }
              leaf disabled {
                type empty;
              }
            }
          }
        }
      }
    }
    container rcmd {
      leaf domain-lookup {
        type boolean;
      }
      leaf rcp-enable {
        type empty;
      }
      leaf rsh-enable {
        type empty;
      }
      list remote-host {
        tailf:cli-suppress-mode;
        tailf:cli-delete-when-empty;
        key "local-username host remote-username";
        leaf local-username {
          type string;
        }
        leaf host {
          type inet:host;
        }
        leaf remote-username {
          type string;
        }
        leaf enable {
          type empty;
        }
      }
      container source-interface {
        uses interface-name-grouping;
      }
    }
    container http {
      leaf port {
        type uint16;
      }
      leaf server {
        type boolean;
      }
      choice access-class-choice {
        leaf access-class {
          type uint8;
        }
        container access-class-ipv4 {
          tailf:cli-drop-node-name;
          container access-class {
            leaf ipv4 {
              type base-acl-type;
            }
          }
        }
      }
      container access-class-ipv6 {
        tailf:cli-drop-node-name;
        container access-class {
          leaf ipv6 {
            type base-acl-type;
          }
        }
      }
      container authentication {
        choice authentication-choice {
          container aaa {
            presence "true";
            leaf login-authentication {
              type string;
            }
            leaf exec-authorization {
              type string;
            }
          }
          leaf local {
            type empty;
          }
        }
      }
      container ctc {
        leaf authentication {
          type boolean;
        }
      }
      leaf secure-server {
        type boolean;
      }
      leaf secure-trustpoint {
        type string;
      }
      leaf-list secure-ciphersuite {
        tailf:cli-flat-list-syntax;
        ordered-by user;
        type enumeration {
          enum "3des-ede-cbc-sha";
          enum "aes-128-cbc-sha";
          enum "aes-256-cbc-sha";
          enum "dhe-aes-128-cbc-sha";
          enum "dhe-aes-cbc-sha2";
          enum "dhe-aes-gcm-sha2";
          enum "ecdhe-rsa-3des-ede-cbc-sha";
          enum "ecdhe-rsa-aes-cbc-sha2";
          enum "ecdhe-rsa-aes-gcm-sha2";
          enum "rsa-aes-cbc-sha2";
          enum "rsa-aes-gcm-sha2";
        }
      }
      container secure-active-session-modules {
        choice modules-choice {
          leaf name {
            tailf:cli-drop-node-name;
            type string;
          }
          leaf all {
            type empty;
          }
          leaf none {
            type empty;
          }
        }
      }
      container active-session-modules {
        choice modules-choice {
          leaf name {
            tailf:cli-drop-node-name;
            type string;
          }
          leaf all {
            type empty;
          }
          leaf none {
            type empty;
          }
        }
      }
      leaf max-connections {
        type uint8;
      }
      container timeout-policy {
        tailf:cli-compact-syntax;
        tailf:cli-sequence-commands {
          tailf:cli-reset-siblings;
        }
        leaf idle {
          type uint16;
        }
        leaf life {
          type uint32;
        }
        leaf requests {
          type uint32;
        }
      }
      container timeout-policy-linger {
        tailf:cli-drop-node-name;
        container timeout-policy {
          leaf linger {
            type uint16;
          }
        }
      }
      container client {
        container source-interface {
          uses interface-name-grouping;
        }
        leaf username {
          type string;
        }
        container password {
          tailf:cli-flatten-container;
          tailf:cli-compact-syntax;
          tailf:cli-sequence-commands {
            tailf:cli-reset-siblings;
          }
          leaf type {
            tailf:cli-drop-node-name;
            tailf:cli-optional-in-sequence;
            type enumeration {
              enum "0";
              enum "7";
            }
          }
          leaf secret {
            tailf:cli-drop-node-name;
            type string;
          }
        }
        container proxy-server {
          tailf:cli-compact-syntax;
          tailf:cli-sequence-commands;
          leaf address {
            tailf:cli-drop-node-name;
            type inet:host;
          }
          leaf proxy-port {
            type uint16;
          }
        }
      }
      leaf path {
        type string;
      }
      leaf help-path {
        type string;
      }
      leaf tls-version {
        type enumeration {
          enum "TLSv1.0";
          enum "TLSv1.1";
          enum "TLSv1.2";
        }
      }
    }
    container ospf {
      leaf name-lookup {
        type empty;
      }
    }
    container bgp-community {
      leaf new-format {
        type empty;
      }
    }
    container community-list {
      list number {
        tailf:cli-drop-node-name;
        tailf:cli-suppress-mode;
        tailf:cli-delete-when-empty;
        key "no";
        leaf no {
          type union {
            type uint16;
            type uint16;
          }
        }
        uses ip-community-list-grouping;
      }
      list standard {
        tailf:cli-suppress-mode;
        tailf:cli-delete-when-empty;
        key "name";
        leaf name {
          type string;
        }
        uses ip-community-list-grouping;
      }
      list expanded {
        tailf:cli-suppress-mode;
        tailf:cli-delete-when-empty;
        key "name";
        leaf name {
          type string;
        }
        uses ip-community-list-grouping;
      }
    }
    container extcommunity-list {
      list number {
        tailf:cli-drop-node-name;
        tailf:cli-suppress-mode;
        tailf:cli-delete-when-empty;
        key "no";
        leaf no {
          type union {
            type uint16;
            type uint16;
          }
        }
        uses ip-extcommunity-list-grouping;
      }
      container standard {
        list no-mode-list {
          tailf:cli-drop-node-name;
          tailf:cli-suppress-mode;
          tailf:cli-delete-when-empty;
          key "name";
          leaf name {
            type string;
          }
          uses ip-extcommunity-list-grouping;
        }
        list mode-list {
          tailf:cli-drop-node-name;
          key "name";
          leaf name {
            type string;
          }
          list entry {
            tailf:cli-drop-node-name;
            tailf:cli-suppress-mode;
            tailf:cli-delete-when-empty;
            key "id";
            leaf id {
              type uint32;
            }
            leaf expr {
              tailf:cli-drop-node-name;
              tailf:cli-multi-value;
              type string;
            }
          }
        }
      }
      container expanded {
        list no-mode-list {
          tailf:cli-drop-node-name;
          tailf:cli-suppress-mode;
          tailf:cli-delete-when-empty;
          key "name";
          leaf name {
            type string;
          }
          uses ip-extcommunity-list-grouping;
        }
        list mode-list {
          tailf:cli-drop-node-name;
          key "name";
          leaf name {
            type string;
          }
          list entry {
            tailf:cli-drop-node-name;
            tailf:cli-suppress-mode;
            tailf:cli-delete-when-empty;
            key "id";
            leaf id {
              type uint32;
            }
            leaf expr {
              tailf:cli-drop-node-name;
              tailf:cli-multi-value;
              type string;
            }
          }
        }
      }
    }
    list policy-list {
      key "name operation";
      leaf name {
        type string;
      }
      leaf operation {
        type enumeration {
          enum "deny";
          enum "permit";
        }
      }
      container match {
        leaf-list as-path {
          tailf:cli-flat-list-syntax;
          ordered-by user;
          type string;
        }
        leaf-list community {
          tailf:cli-flat-list-syntax;
          ordered-by user;
          type string;
        }
        leaf-list route-type {
          tailf:cli-flat-list-syntax;
          type enumeration {
            enum "local";
            enum "internal";
            enum "level-1";
            enum "level-2";
            enum "external";
            enum "nssa-external";
          }
        }
        container ip {
          container address {
            leaf-list prefix-list {
              tailf:cli-flat-list-syntax;
              type string;
            }
          }
        }
      }
    }
    container as-path {
      list access-list {
        tailf:cli-suppress-mode;
        tailf:cli-delete-when-empty;
        tailf:cli-compact-syntax;
        key "name";
        leaf name {
          type string;
        }
        list as-path-rule {
          tailf:cli-suppress-mode;
          tailf:cli-delete-when-empty;
          tailf:cli-drop-node-name;
          tailf:cli-compact-syntax;
          ordered-by user;
          key "operation rule";
          leaf operation {
            type enumeration {
              enum "deny" {
                tailf:code-name "operation_deny";
              }
              enum "permit" {
                tailf:code-name "operation_permit";
              }
            }
          }
          leaf rule {
            tailf:cli-multi-word-key;
            type string;
          }
        }
      }
    }
    container flow-capture {
      leaf icmp {
        type empty;
      }
      leaf ip-id {
        type empty;
      }
    }
    container flow-egress {
      leaf input-interface {
        type empty;
      }
    }
    container flow-cache {
      leaf entries {
        type uint32;
      }
      container timeout {
        leaf inactive {
          type uint16;
        }
        leaf active {
          type uint16;
        }
      }
    }
    container flow-export {
      container source {
        uses interface-name-grouping;
      }
      container version {
        tailf:cli-compact-syntax;
        tailf:cli-sequence-commands {
          tailf:cli-reset-siblings;
        }
        leaf version {
          tailf:cli-drop-node-name;
          type enumeration {
            enum "1";
            enum "5";
            enum "9";
          }
        }
        choice as-choice {
          leaf origin-as {
            tailf:cli-optional-in-sequence;
            type empty;
          }
          leaf peer-as {
            tailf:cli-optional-in-sequence;
            type empty;
          }
        }
        leaf bgp-nexthop {
          type empty;
        }
      }
      container template {
        container options {
          leaf export-stats {
            type empty;
          }
          leaf timeout-rate {
            type uint16;
          }
          leaf refresh-rate {
            type uint16;
          }
        }
        leaf timeout-rate {
          type uint16;
        }
        leaf refresh-rate {
          type uint16;
        }
      }
      list destination {
        tailf:cli-suppress-mode;
        tailf:cli-delete-when-empty;
        key "ip port";
        leaf ip {
          type inet:host;
        }
        leaf port {
          type uint16;
        }
      }
      container destination-vrf {
        tailf:cli-drop-node-name;
        list destination {
          tailf:cli-suppress-mode;
          tailf:cli-delete-when-empty;
          key "ip port vrf";
          leaf ip {
            type inet:host;
          }
          leaf port {
            type uint16;
          }
          leaf vrf {
            tailf:cli-expose-key-name;
            type string;
          }
        }
      }
    }
    container flow-aggregation {
      list cache {
        key "name";
        leaf name {
          type string;
        }
        container cache {
          container timeout {
            leaf active {
              type uint8;
            }
          }
        }
        container export {
          list destination {
            tailf:cli-suppress-mode;
            tailf:cli-delete-when-empty;
            tailf:cli-compact-syntax;
            key "address";
            leaf address {
              type inet:host;
            }
            leaf port {
              tailf:cli-drop-node-name;
              type uint16;
            }
          }
        }
      }
    }
    container dns {
      list view {
        key "name";
        leaf name {
          type string;
        }
        uses ip-dns-view-grouping;
      }
      container view-vrf {
        tailf:cli-drop-node-name;
        list view {
          key "vrf name";
          leaf vrf {
            tailf:cli-expose-key-name;
            type string;
          }
          leaf name {
            type string;
          }
          uses ip-dns-view-grouping;
        }
      }
      list view-list {
        key "name";
        leaf name {
          type string;
        }
        list view {
          key "name";
          leaf name {
            type string;
          }
          leaf order {
            tailf:cli-drop-node-name;
            tailf:cli-hide-in-submode;
            type uint32;
          }
          container restrict {
            leaf name-group {
              type uint32;
            }
            leaf authenticate {
              type empty;
            }
          }
        }
        container view-vrf {
          tailf:cli-drop-node-name;
          list view {
            key "vrf name";
            leaf vrf {
              tailf:cli-expose-key-name;
              type string;
            }
            leaf name {
              type string;
            }
            leaf order {
              tailf:cli-drop-node-name;
              tailf:cli-hide-in-submode;
              type uint32;
            }
            container restrict {
              leaf name-group {
                type uint32;
              }
              leaf authenticate {
                type empty;
              }
            }
          }
        }
      }
      list name-list {
        tailf:cli-suppress-mode;
        tailf:cli-delete-when-empty;
        key "id";
        leaf id {
          type uint16;
        }
        list regexp-list {
          tailf:cli-drop-node-name;
          tailf:cli-suppress-mode;
          tailf:cli-delete-when-empty;
          ordered-by user;
          key "regexp";
          leaf regexp {
            tailf:cli-multi-word-key;
            type string;
          }
        }
      }
      container server {
        presence "true";
        leaf view-group {
          type string;
        }
      }
      container spoofing {
        presence "true";
      }
    }
    container mobile {
      container secure {
        list home-agent {
          tailf:cli-suppress-mode;
          tailf:cli-delete-when-empty;
          tailf:cli-compact-syntax;
          tailf:cli-sequence-commands {
            tailf:cli-reset-all-siblings;
          }
          key "lower-address";
          leaf lower-address {
            type inet:ipv4-address;
          }
          leaf upper-address {
            tailf:cli-drop-node-name;
            tailf:cli-optional-in-sequence;
            type inet:ipv4-address;
          }
          choice spi-choice {
            case single-spi {
              container spi {
                tailf:cli-flatten-container;
                tailf:cli-compact-syntax;
                uses mobile-ip-spi-grouping;
              }
            }
            case range-spi {
              container inbound-spi {
                tailf:cli-flatten-container;
                tailf:cli-compact-syntax;
                uses mobile-ip-spi-grouping;
              }
              container outbound-spi {
                tailf:cli-flatten-container;
                tailf:cli-compact-syntax;
                uses mobile-ip-spi-grouping;
              }
            }
          }
          container key {
            tailf:cli-flatten-container;
            tailf:cli-compact-syntax;
            choice key-choice {
              leaf ascii {
                type string;
              }
              leaf hex {
                type string;
              }
            }
          }
          container algorithm {
            tailf:cli-break-sequence-commands;
            tailf:cli-flatten-container;
            tailf:cli-compact-syntax;
            choice algorithm-choice {
              leaf hmac-md5 {
                type empty;
              }
              container md5 {
                tailf:cli-flatten-container;
                tailf:cli-compact-syntax;
                container mode {
                  tailf:cli-flatten-container;
                  tailf:cli-compact-syntax;
                  leaf prefix-suffix {
                    type empty;
                  }
                }
              }
            }
          }
          leaf ignore-spi {
            type empty;
          }
        }
      }
      container router {
        tailf:cli-add-mode;
        presence "true";
        container address {
          tailf:cli-compact-syntax;
          tailf:cli-sequence-commands {
            tailf:cli-reset-siblings;
          }
          leaf ipv4-address {
            tailf:cli-drop-node-name;
            type inet:ipv4-address;
          }
          leaf ipv4-mask {
            tailf:cli-drop-node-name;
            type inet:ipv4-address;
          }
        }
        container collocated {
          leaf single-tunnel {
            type empty;
          }
        }
        list home-agent {
          tailf:cli-suppress-mode;
          tailf:cli-delete-when-empty;
          key "address";
          leaf address {
            type inet:ipv4-address;
          }
          leaf priority {
            type uint8;
          }
        }
        list mobile-network {
          tailf:cli-suppress-mode;
          tailf:cli-delete-when-empty;
          key "name";
          leaf name {
            type string;
          }
          container policy {
            leaf mobile-map {
              type string;
            }
          }
        }
        container register {
          container retransmit {
            tailf:cli-compact-syntax;
            tailf:cli-sequence-commands {
              tailf:cli-reset-siblings;
            }
            leaf initial {
              type uint16;
            }
            leaf maximum {
              type uint16;
            }
            leaf retry {
              type uint8;
            }
          }
          container extend {
            tailf:cli-compact-syntax;
            tailf:cli-sequence-commands {
              tailf:cli-reset-siblings;
            }
            leaf expire {
              type uint16;
            }
            leaf retry {
              type uint8;
            }
            leaf interval {
              type uint16;
            }
            leaf reverse-tunnel {
              type empty;
            }
          }
          leaf lifetime {
            type uint16;
          }
        }
        leaf reverse-tunnel {
          type empty;
        }
        container tunnel {
          container mode {
            leaf gre {
              type empty;
            }
          }
        }
        container template {
          leaf Tunnel {
            tailf:cli-allow-join-with-value;
            type uint32;
          }
        }
      }
    }
    container pim {
      uses ip-pim-grouping;
      list vrf {
        tailf:cli-suppress-mode;
        tailf:cli-delete-when-empty;
        key "id";
        leaf id {
          type string;
        }
        uses ip-pim-grouping;
      }
    }
    container rsvp {
      container signalling {
        container refresh {
          container reduction-conf {
            tailf:cli-drop-node-name;
            container reduction {
              leaf ack-delay {
                type uint16;
              }
            }
          }
          leaf reduction {
            type empty;
          }
        }
        container hello-enable {
          tailf:cli-drop-node-name;
          leaf hello {
            type empty;
          }
        }
        container hello-bfd {
          tailf:cli-drop-node-name;
          container hello {
            leaf bfd {
              type empty;
            }
          }
        }
        container hello {
          container graceful-restart {
            leaf mode {
              type enumeration {
                enum "full";
                enum "help-neighbor";
              }
            }
            container refresh {
              leaf interval {
                type uint16;
              }
              leaf misses {
                type uint8;
              }
            }
          }
        }
        choice rate-limit-choice {
          leaf rate-limit {
            type boolean;
          }
          container rate-limit-conf {
            tailf:cli-drop-node-name;
            container rate-limit {
              tailf:cli-compact-syntax;
              leaf period {
                type uint16;
              }
              leaf burst {
                type uint16;
              }
              leaf maxsize {
                type uint16;
              }
              leaf limit {
                type uint16;
              }
            }
          }
        }
      }
      container policy {
        list identity {
          tailf:cli-suppress-mode;
          tailf:cli-delete-when-empty;
          key "name";
          leaf name {
            type string;
          }
          leaf policy-locator {
            type string;
          }
        }
        leaf preempt {
          type empty;
        }
        uses ip-rsvp-policy-local-grouping;
      }
    }
    container nat {
      container settings {
        leaf mode {
          type enumeration {
            enum "cgn";
            enum "default";
          }
        }
        leaf gatekeeper-size {
          type uint32;
        }
        container support {
          container mapping {
            leaf outside {
              type boolean;
            }
          }
        }
        container pap {
          tailf:cli-compact-syntax;
          tailf:cli-sequence-commands {
            tailf:cli-reset-siblings;
          }
          leaf limit {
            tailf:cli-optional-in-sequence;
            type enumeration {
              enum "30";
              enum "60";
              enum "120";
              enum "250";
              enum "500";
              enum "1000";
            }
          }
          choice pap-choice {
            leaf pool {
              tailf:cli-optional-in-sequence;
              type empty;
            }
            case bpa {
              leaf bpa {
                type empty;
              }
              leaf set-size {
                tailf:cli-optional-in-sequence;
                type enumeration {
                  enum "64";
                  enum "128";
                  enum "256";
                  enum "512";
                }
              }
              leaf step-size {
                tailf:cli-optional-in-sequence;
                type enumeration {
                  enum "1";
                  enum "2";
                  enum "4";
                  enum "8";
                }
              }
              leaf single-set {
                type empty;
              }
            }
          }
        }
        leaf nonpatdrop {
          type empty;
        }
      }
      container switchover {
        container replication {
          container http {
            tailf:cli-delete-when-empty;
            presence "true";
            leaf port {
              tailf:cli-drop-node-name;
              type uint16;
            }
          }
        }
      }
      container log {
        container translations {
          container flow-export {
            container v9 {
              container udp {
                list destination {
                  tailf:cli-suppress-mode;
                  tailf:cli-delete-when-empty;
                  tailf:cli-compact-syntax;
                  tailf:cli-sequence-commands {
                    tailf:cli-reset-siblings;
                  }
                  key "address port";
                  leaf address {
                    type inet:host;
                  }
                  leaf port {
                    type uint16;
                  }
                  leaf source {
                    type string;
                  }
                }
                container vrf {
                  tailf:cli-drop-node-name;
                  list destination {
                    tailf:cli-suppress-mode;
                    tailf:cli-delete-when-empty;
                    tailf:cli-compact-syntax;
                    tailf:cli-sequence-commands {
                      tailf:cli-reset-siblings;
                    }
                    key "address port vrf";
                    leaf address {
                      type inet:host;
                    }
                    leaf port {
                      type uint16;
                    }
                    leaf vrf {
                      tailf:cli-expose-key-name;
                      type string;
                    }
                    leaf source {
                      type string;
                    }
                  }
                }
              }
            }
          }
        }
      }
      container translation {
        leaf timeout {
          type ip-nat-timeout-type;
        }
        leaf dns-timeout {
          type ip-nat-timeout-type;
        }
        leaf syn-timeout {
          type ip-nat-timeout-type;
        }
        leaf finrst-timeout {
          type ip-nat-timeout-type;
        }
        leaf icmp-timeout {
          type ip-nat-timeout-type;
        }
        leaf udp-timeout {
          type ip-nat-timeout-type;
        }
        leaf tcp-timeout {
          type ip-nat-timeout-type;
        }
        leaf pptp-timeout {
          type ip-nat-timeout-type;
        }
        leaf routemap-entry-timeout {
          type ip-nat-timeout-type;
        }
        container max-entries {
          leaf number {
            tailf:cli-drop-node-name;
            type uint32;
          }
          leaf all-host {
            type uint32;
          }
          list vrf {
            tailf:cli-suppress-mode;
            tailf:cli-delete-when-empty;
            key "name";
            leaf name {
              type string;
            }
            leaf number {
              tailf:cli-drop-node-name;
              type uint32;
            }
          }
          container list {
            tailf:cli-compact-syntax;
            tailf:cli-sequence-commands {
              tailf:cli-reset-siblings;
            }
            leaf access-list {
              tailf:cli-drop-node-name;
              type exp-ip-acl-type;
            }
            leaf number {
              tailf:cli-drop-node-name;
              type uint32;
            }
          }
        }
      }
      container service {
        leaf dns-reset-ttl {
          type boolean;
        }
        leaf H225 {
          type boolean;
        }
        leaf gatekeeper {
          type boolean;
        }
        container list-ftp-tcp {
          tailf:cli-drop-node-name;
          list list {
            tailf:cli-suppress-mode;
            tailf:cli-delete-when-empty;
            tailf:cli-compact-syntax;
            tailf:cli-sequence-commands {
              tailf:cli-reset-siblings;
            }
            key "access-list port";
            leaf access-list {
              type union {
                type uint16;
                type string;
              }
            }
            leaf ftp {
              tailf:cli-prefix-key {
                tailf:cli-before-key "2";
              }
              type empty;
            }
            leaf tcp {
              tailf:cli-prefix-key {
                tailf:cli-before-key "2";
              }
              type empty;
            }
            leaf port {
              tailf:cli-expose-key-name;
              type uint16;
            }
          }
        }
        container sip {
          container tcp {
            list port {
              tailf:cli-suppress-mode;
              tailf:cli-delete-when-empty;
              key "id";
              leaf id {
                type uint16;
              }
            }
            container default {
              tailf:cli-drop-node-name;
              container port {
                leaf fiftysixty {
                  tailf:alt-name "5060";
                  type boolean;
                }
              }
            }
          }
          container udp {
            list port {
              tailf:cli-suppress-mode;
              tailf:cli-delete-when-empty;
              key "id";
              leaf id {
                type uint16;
              }
            }
            container default {
              tailf:cli-drop-node-name;
              container port {
                leaf fiftysixty {
                  tailf:alt-name "5060";
                  type boolean;
                }
              }
            }
          }
        }
      }
      list pool {
        tailf:cli-suppress-mode;
        tailf:cli-delete-when-empty;
        tailf:cli-compact-syntax;
        tailf:cli-sequence-commands {
          tailf:cli-reset-siblings;
        }
        key "id";
        leaf id {
          type string;
        }
        leaf start-address {
          tailf:cli-drop-node-name;
          tailf:cli-optional-in-sequence;
          type inet:ipv4-address;
        }
        leaf end-address {
          tailf:cli-drop-node-name;
          type inet:ipv4-address;
        }
        choice prefix-choice {
          leaf netmask {
            type inet:ipv4-address;
          }
          leaf prefix-length {
            type uint8;
          }
        }
        leaf accounting {
          tailf:cli-optional-in-sequence;
          type string;
        }
        choice nat-choice {
          leaf arp-ping {
            type empty;
          }
          leaf type {
            type enumeration {
              enum "match-host";
              enum "rotary";
            }
          }
          leaf add-route {
            type empty;
          }
        }
      }
      container inside {
        container source {
          container static {
            list nat-static-interface-list {
              tailf:cli-drop-node-name;
              tailf:cli-suppress-mode;
              tailf:cli-delete-when-empty;
              tailf:cli-compact-syntax;
              tailf:cli-sequence-commands;
              key "interface";
              leaf local-ip {
                tailf:cli-drop-node-name;
                tailf:cli-prefix-key;
                type inet:ipv4-address;
              }
              leaf interface {
                tailf:cli-expose-key-name;
                type string;
              }
            }
            list nat-static-address-list {
              tailf:cli-drop-node-name;
              tailf:cli-suppress-mode;
              tailf:cli-delete-when-empty;
              tailf:cli-compact-syntax;
              tailf:cli-sequence-commands {
                tailf:cli-reset-siblings;
              }
              key "local-ip global-ip";
              leaf local-ip {
                type inet:ipv4-address;
              }
              leaf global-ip {
                type inet:ipv4-address;
              }
              uses ip-nat-source-static-grouping;
            }
            list nat-static-address-list-vrf {
              tailf:cli-drop-node-name;
              tailf:cli-suppress-mode;
              tailf:cli-delete-when-empty;
              tailf:cli-compact-syntax;
              tailf:cli-sequence-commands {
                tailf:cli-reset-siblings;
              }
              key "local-ip global-ip vrf";
              leaf local-ip {
                type inet:ipv4-address;
              }
              leaf global-ip {
                type inet:ipv4-address;
              }
              leaf vrf {
                tailf:cli-expose-key-name;
                type string;
              }
              uses ip-nat-source-static-grouping;
            }
            list nat-static-transport-list {
              tailf:cli-drop-node-name;
              tailf:cli-suppress-mode;
              tailf:cli-delete-when-empty;
              tailf:cli-compact-syntax;
              tailf:cli-sequence-commands {
                tailf:cli-reset-siblings;
              }
              key "proto local-ip local-port global-ip global-port";
              leaf proto {
                type enumeration {
                  enum "tcp";
                  enum "udp";
                }
              }
              leaf local-ip {
                type inet:ipv4-address;
              }
              leaf local-port {
                type uint16;
              }
              leaf global-ip {
                type inet:ipv4-address;
              }
              leaf global-port {
                type uint16;
              }
              uses ip-nat-source-static-grouping;
            }
            list nat-static-transport-list-vrf {
              tailf:cli-drop-node-name;
              tailf:cli-suppress-mode;
              tailf:cli-delete-when-empty;
              tailf:cli-compact-syntax;
              tailf:cli-sequence-commands {
                tailf:cli-reset-siblings;
              }
              key "proto local-ip local-port global-ip global-port vrf";
              leaf proto {
                type enumeration {
                  enum "tcp";
                  enum "udp";
                }
              }
              leaf local-ip {
                type inet:ipv4-address;
              }
              leaf local-port {
                type uint16;
              }
              leaf global-ip {
                type inet:ipv4-address;
              }
              leaf global-port {
                type uint16;
              }
              leaf vrf {
                tailf:cli-expose-key-name;
                type string;
              }
              uses ip-nat-source-static-grouping;
            }
            list nat-static-transport-interface-list {
              tailf:cli-drop-node-name;
              tailf:cli-suppress-mode;
              tailf:cli-delete-when-empty;
              tailf:cli-compact-syntax;
              tailf:cli-sequence-commands {
                tailf:cli-reset-siblings;
              }
              key "proto local-ip local-port";
              leaf proto {
                type enumeration {
                  enum "tcp";
                  enum "udp";
                }
              }
              leaf local-ip {
                type inet:ipv4-address;
              }
              leaf local-port {
                type uint16;
              }
              container interface {
                tailf:cli-flatten-container;
                tailf:cli-compact-syntax;
                uses interface-name-grouping;
              }
              leaf global-port {
                tailf:cli-drop-node-name;
                type uint16;
              }
            }
          }
          list list {
            tailf:cli-suppress-mode;
            tailf:cli-delete-when-empty;
            tailf:cli-compact-syntax;
            tailf:cli-sequence-commands {
              tailf:cli-reset-all-siblings;
            }
            key "id";
            leaf id {
              type union {
                type uint16;
                type string;
              }
            }
            uses ip-nat-inside-grouping;
            uses ip-nat-inside-options-grouping;
          }
          container list-vrf {
            tailf:cli-drop-node-name;
            list list {
              tailf:cli-suppress-mode;
              tailf:cli-delete-when-empty;
              tailf:cli-compact-syntax;
              tailf:cli-sequence-commands {
                tailf:cli-reset-all-siblings;
              }
              key "id vrf";
              leaf id {
                type union {
                  type uint16;
                  type string;
                }
              }
              uses ip-nat-inside-vrf-grouping;
              uses ip-nat-inside-options-grouping;
            }
          }
          list route-map {
            tailf:cli-suppress-mode;
            tailf:cli-delete-when-empty;
            tailf:cli-compact-syntax;
            tailf:cli-sequence-commands {
              tailf:cli-reset-all-siblings;
            }
            key "id";
            leaf id {
              type string;
            }
            uses ip-nat-inside-grouping;
            uses ip-nat-inside-options-grouping;
          }
          container route-map-vrf {
            tailf:cli-drop-node-name;
            list route-map {
              tailf:cli-suppress-mode;
              tailf:cli-delete-when-empty;
              tailf:cli-compact-syntax;
              tailf:cli-sequence-commands {
                tailf:cli-reset-all-siblings;
              }
              key "id vrf";
              leaf id {
                type string;
              }
              uses ip-nat-inside-vrf-grouping;
              uses ip-nat-inside-options-grouping;
            }
          }
        }
        container destination {
          list list {
            tailf:cli-suppress-mode;
            tailf:cli-delete-when-empty;
            tailf:cli-compact-syntax;
            tailf:cli-sequence-commands {
              tailf:cli-reset-siblings;
            }
            key "id";
            leaf id {
              type union {
                type uint16;
                type string;
              }
            }
            leaf pool {
              type string;
            }
            leaf redundancy {
              tailf:cli-optional-in-sequence;
              type uint8;
            }
            leaf mapping-id {
              type uint32;
            }
          }
        }
      }
      container outside {
        container source {
          list list {
            tailf:cli-suppress-mode;
            tailf:cli-delete-when-empty;
            tailf:cli-compact-syntax;
            tailf:cli-sequence-commands {
              tailf:cli-reset-siblings;
            }
            key "id";
            leaf id {
              type union {
                type uint16;
                type string;
              }
            }
            leaf pool {
              type string;
            }
            uses ip-nat-outside-source-grouping;
          }
          container list-vrf {
            tailf:cli-drop-node-name;
            list list {
              tailf:cli-suppress-mode;
              tailf:cli-delete-when-empty;
              tailf:cli-compact-syntax;
              tailf:cli-sequence-commands {
                tailf:cli-reset-all-siblings;
              }
              key "id vrf";
              leaf id {
                type union {
                  type uint16;
                  type string;
                }
              }
              leaf pool {
                tailf:cli-prefix-key {
                  tailf:cli-before-key "2";
                }
                type string;
              }
              leaf vrf {
                tailf:cli-expose-key-name;
                type string;
              }
              uses ip-nat-outside-source-grouping;
            }
          }
          list route-map {
            tailf:cli-suppress-mode;
            tailf:cli-delete-when-empty;
            tailf:cli-compact-syntax;
            tailf:cli-sequence-commands {
              tailf:cli-reset-siblings;
            }
            key "id";
            leaf id {
              type string;
            }
            leaf pool {
              type string;
            }
            uses ip-nat-outside-source-grouping;
          }
          container route-map-vrf {
            tailf:cli-drop-node-name;
            list route-map {
              tailf:cli-suppress-mode;
              tailf:cli-delete-when-empty;
              tailf:cli-compact-syntax;
              tailf:cli-sequence-commands {
                tailf:cli-reset-siblings;
              }
              key "id vrf";
              leaf id {
                type string;
              }
              leaf pool {
                tailf:cli-prefix-key {
                  tailf:cli-before-key "2";
                }
                type string;
              }
              leaf vrf {
                tailf:cli-expose-key-name;
                type string;
              }
              uses ip-nat-outside-source-grouping;
            }
          }
          container static {
            list nat-static-address-list {
              tailf:cli-drop-node-name;
              tailf:cli-suppress-mode;
              tailf:cli-delete-when-empty;
              tailf:cli-compact-syntax;
              tailf:cli-sequence-commands {
                tailf:cli-reset-siblings;
              }
              key "global-ip local-ip";
              leaf global-ip {
                type inet:ipv4-address;
              }
              leaf local-ip {
                type inet:ipv4-address;
              }
              uses ip-nat-source-static-grouping;
            }
            list nat-static-address-list-vrf {
              tailf:cli-drop-node-name;
              tailf:cli-suppress-mode;
              tailf:cli-delete-when-empty;
              tailf:cli-compact-syntax;
              tailf:cli-sequence-commands {
                tailf:cli-reset-siblings;
              }
              key "global-ip local-ip vrf";
              leaf global-ip {
                type inet:ipv4-address;
              }
              leaf local-ip {
                type inet:ipv4-address;
              }
              leaf vrf {
                tailf:cli-expose-key-name;
                type string;
              }
              uses ip-nat-source-static-grouping;
            }
            list nat-static-transport-list {
              tailf:cli-drop-node-name;
              tailf:cli-suppress-mode;
              tailf:cli-delete-when-empty;
              tailf:cli-compact-syntax;
              tailf:cli-sequence-commands {
                tailf:cli-reset-siblings;
              }
              key "proto global-ip global-port local-ip local-port";
              leaf proto {
                type enumeration {
                  enum "tcp";
                  enum "udp";
                }
              }
              leaf global-ip {
                type inet:ipv4-address;
              }
              leaf global-port {
                type uint16;
              }
              leaf local-ip {
                type inet:ipv4-address;
              }
              leaf local-port {
                type uint16;
              }
              uses ip-nat-source-static-grouping;
            }
            list nat-static-transport-list-vrf {
              tailf:cli-drop-node-name;
              tailf:cli-suppress-mode;
              tailf:cli-delete-when-empty;
              tailf:cli-compact-syntax;
              tailf:cli-sequence-commands {
                tailf:cli-reset-siblings;
              }
              key "proto global-ip global-port local-ip local-port vrf";
              leaf proto {
                type enumeration {
                  enum "tcp";
                  enum "udp";
                }
              }
              leaf global-ip {
                type inet:ipv4-address;
              }
              leaf global-port {
                type uint16;
              }
              leaf local-ip {
                type inet:ipv4-address;
              }
              leaf local-port {
                type uint16;
              }
              leaf vrf {
                tailf:cli-expose-key-name;
                type string;
              }
              uses ip-nat-source-static-grouping;
            }
          }
        }
      }
    }
    container mroute {
      container global {
        tailf:cli-drop-node-name;
        tailf:cli-compact-syntax;
        tailf:cli-sequence-commands {
          tailf:cli-reset-siblings;
        }
        uses ip-mroute-grouping;
      }
      list vrf {
        tailf:cli-suppress-mode;
        tailf:cli-delete-when-empty;
        tailf:cli-compact-syntax;
        tailf:cli-sequence-commands {
          tailf:cli-reset-siblings;
        }
        key "name";
        leaf name {
          type string;
        }
        uses ip-mroute-grouping;
      }
    }
    container route {
      container static {
        leaf adjust-time {
          type uint8;
        }
        leaf inter-vrf {
          type boolean;
        }
        container bfd {
          list ip-route-bfd-forwarding-list {
            tailf:cli-drop-node-name;
            tailf:cli-suppress-mode;
            tailf:cli-delete-when-empty;
            tailf:cli-compact-syntax;
            key "interface ip-address";
            leaf interface {
              type string;
            }
            leaf ip-address {
              type union {
                type inet:ipv4-address;
                type enumeration {
                  enum "multicast";
                }
              }
            }
            leaf group {
              type string;
            }
            leaf log {
              type empty;
            }
          }
          list vrf {
            tailf:cli-suppress-mode;
            tailf:cli-delete-when-empty;
            tailf:cli-compact-syntax;
            key "name dst-ip vrf src-ip";
            leaf name {
              type string;
            }
            leaf dst-ip {
              type inet:ipv4-address;
            }
            leaf vrf {
              tailf:cli-expose-key-name;
              type string;
            }
            leaf src-ip {
              type inet:ipv4-address;
            }
            leaf group {
              type string;
            }
            leaf log {
              type empty;
            }
          }
        }
        leaf install-routes-recurse-via-nexthop {
          type empty;
        }
        container install-routes-recurse-via-nexthop-vrf {
          tailf:cli-drop-node-name;
          container install-routes-recurse-via-nexthop {
            list vrf {
              tailf:cli-suppress-mode;
              tailf:cli-delete-when-empty;
              key "name";
              leaf name {
                type string;
              }
            }
          }
        }
      }
      leaf profile {
        type empty;
      }
      uses ip-route-grouping;
      list vrf {
        tailf:cli-suppress-mode;
        tailf:cli-delete-when-empty;
        tailf:cli-compact-syntax;
        key "name";
        leaf name {
          type string;
        }
        uses ip-route-grouping;
      }
    }
    container explicit-path {
      list identifier {
        key "number";
        leaf number {
          tailf:cli-suppress-range;
          type uint16;
        }
        leaf mode {
          tailf:cli-drop-node-name;
          tailf:cli-hide-in-submode;
          type enumeration {
            enum "enable";
            enum "disable";
          }
        }
        uses ip-explicit-path-grouping;
      }
      list name {
        key "name";
        leaf name {
          tailf:cli-suppress-range;
          type string;
        }
        leaf mode {
          tailf:cli-drop-node-name;
          tailf:cli-hide-in-submode;
          type enumeration {
            enum "enable";
            enum "disable";
          }
        }
        uses ip-explicit-path-grouping;
      }
    }
    container tacacs {
      container source-interface {
        uses interface-name-grouping;
      }
      container source-interface-vrf {
        tailf:cli-drop-node-name;
        list source-interface {
          tailf:cli-suppress-mode;
          tailf:cli-delete-when-empty;
          key "vrf";
          leaf name {
            tailf:cli-drop-node-name;
            tailf:cli-prefix-key;
            type string;
          }
          leaf vrf {
            tailf:cli-expose-key-name;
            type string;
          }
        }
      }
    }
    container access-list {
      tailf:cli-compact-syntax;
      container logging {
        leaf interval {
          type uint32;
        }
        leaf hash-generation {
          type empty;
        }
      }
      leaf persistent {
        type empty;
      }
      container standard {
        list std-named-acl {
          tailf:cli-drop-node-name;
          key "name";
          leaf name {
            tailf:cli-suppress-range;
            type std-ip-acl-type;
          }
          list std-access-list-rule {
            tailf:cli-drop-node-name;
            tailf:cli-suppress-mode;
            tailf:cli-delete-when-empty;
            tailf:cli-compact-syntax;
            ordered-by user;
            key "rule";
            leaf rule {
              tailf:cli-suppress-range;
              tailf:cli-multi-word-key;
              type string;
            }
          }
        }
      }
      container extended {
        list ext-named-acl {
          tailf:cli-drop-node-name;
          key "name";
          leaf name {
            tailf:cli-suppress-range;
            type ext-acl-type;
          }
          list ext-access-list-rule {
            tailf:cli-suppress-mode;
            tailf:cli-delete-when-empty;
            tailf:cli-drop-node-name;
            tailf:cli-compact-syntax;
            ordered-by user;
            key "rule";
            leaf rule {
              tailf:cli-suppress-range;
              tailf:cli-multi-word-key;
              type string;
            }
          }
        }
      }
      list unordered {
        tailf:cli-compact-syntax;
        tailf:cli-sequence-commands;
        key "name";
        leaf name {
          tailf:cli-suppress-range;
          type string;
        }
        leaf type {
          tailf:cli-drop-node-name;
          tailf:cli-prefix-key;
          type enumeration {
            enum "standard";
            enum "extended";
          }
        }
        list rule-list {
          tailf:cli-drop-node-name;
          tailf:cli-suppress-mode;
          tailf:cli-delete-when-empty;
          key "rule";
          leaf rule {
            tailf:cli-suppress-range;
            tailf:cli-multi-word-key;
            type string;
          }
        }
      }
      container resequence {
        tailf:cli-drop-node-name;
        list extended {
          key "name";
          leaf name {
            tailf:cli-suppress-range;
            type string;
          }
          list rule-list {
            tailf:cli-drop-node-name;
            tailf:cli-suppress-mode;
            tailf:cli-delete-when-empty;
            ordered-by user;
            key "rule";
            leaf rule {
              tailf:cli-suppress-range;
              tailf:cli-multi-word-key;
              type string;
            }
          }
        }
      }
      list filter-list {
        tailf:cli-drop-node-name;
        tailf:cli-compact-syntax;
        tailf:cli-sequence-commands;
        key "name";
        leaf name {
          tailf:cli-suppress-range;
          type string;
        }
        leaf type {
          tailf:cli-drop-node-name;
          tailf:cli-prefix-key;
          type enumeration {
            enum "standard";
            enum "extended";
          }
        }
        list entry-list {
          tailf:cli-drop-node-name;
          tailf:cli-suppress-mode;
          tailf:cli-delete-when-empty;
          key "seq";
          leaf seq {
            tailf:cli-suppress-range;
            type uint32;
          }
          leaf entry {
            tailf:cli-drop-node-name;
            tailf:cli-multi-value;
            type string;
          }
        }
      }
    }
    container prefix-list {
      leaf sequence-number {
        type boolean;
      }
      list prefixes {
        tailf:cli-drop-node-name;
        tailf:cli-suppress-mode;
        tailf:cli-delete-when-empty;
        key "name";
        leaf name {
          type string;
        }
        leaf description {
          tailf:cli-multi-value;
          type string;
        }
        list seq {
          tailf:cli-suppress-mode;
          tailf:cli-delete-when-empty;
          key "no";
          leaf no {
            type uint32;
          }
          container deny {
            tailf:cli-compact-syntax;
            tailf:cli-sequence-commands {
              tailf:cli-reset-siblings;
            }
            leaf ip {
              tailf:cli-drop-node-name;
              type ios:ipv4-prefix;
            }
            leaf ge {
              tailf:cli-optional-in-sequence;
              type uint8;
            }
            leaf le {
              type uint8;
            }
          }
          container permit {
            tailf:cli-compact-syntax;
            tailf:cli-sequence-commands {
              tailf:cli-reset-siblings;
            }
            leaf ip {
              tailf:cli-drop-node-name;
              type ios:ipv4-prefix;
            }
            leaf ge {
              tailf:cli-optional-in-sequence;
              type uint8;
            }
            leaf le {
              type uint8;
            }
          }
        }
      }
      list prefixes-no-seq {
        tailf:cli-drop-node-name;
        tailf:cli-suppress-mode;
        tailf:cli-delete-when-empty;
        key "name";
        leaf name {
          type string;
        }
        leaf description {
          tailf:cli-multi-value;
          type string;
        }
        list entry {
          tailf:cli-drop-node-name;
          tailf:cli-suppress-mode;
          tailf:cli-delete-when-empty;
          ordered-by user;
          key "rule";
          leaf rule {
            tailf:cli-multi-word-key;
            type string;
          }
        }
      }
    }
    container radius {
      container source-interface {
        uses interface-name-grouping;
      }
      container source-interface-vrf {
        tailf:cli-drop-node-name;
        list source-interface {
          tailf:cli-suppress-mode;
          tailf:cli-delete-when-empty;
          key "vrf";
          leaf name {
            tailf:cli-drop-node-name;
            tailf:cli-prefix-key;
            type string;
          }
          leaf vrf {
            tailf:cli-expose-key-name;
            type string;
          }
        }
      }
    }
    container sla {
      container auto {
        leaf discovery {
          type empty;
        }
      }
      container responder-twamp {
        tailf:cli-drop-node-name;
        container responder {
          container twamp {
            tailf:cli-add-mode;
            presence "true";
            leaf timeout {
              type uint32;
            }
          }
        }
      }
      container responder-twamp-light {
        tailf:cli-drop-node-name;
        container responder {
          container twamp-light {
            list test-session {
              tailf:cli-suppress-mode;
              tailf:cli-delete-when-empty;
              tailf:cli-compact-syntax;
              tailf:cli-sequence-commands {
                tailf:cli-reset-siblings;
              }
              key "id";
              leaf id {
                type uint16;
              }
              leaf local-ip {
                type union {
                  type inet:host;
                  type enumeration {
                    enum "any";
                  }
                }
              }
              leaf local-ip-af {
                tailf:cli-drop-node-name;
                tailf:cli-optional-in-sequence;
                type enumeration {
                  enum "ipv4";
                  enum "ipv6";
                }
              }
              leaf local-port {
                type uint16;
              }
              leaf remote-ip {
                type union {
                  type inet:host;
                  type enumeration {
                    enum "any";
                  }
                }
              }
              leaf remote-ip-af {
                tailf:cli-drop-node-name;
                tailf:cli-optional-in-sequence;
                type enumeration {
                  enum "ipv4";
                  enum "ipv6";
                }
              }
              leaf remote-port {
                type union {
                  type uint16;
                  type enumeration {
                    enum "any";
                  }
                }
              }
              leaf timeout {
                type uint32;
              }
            }
          }
        }
      }
      container responder-enable {
        tailf:cli-drop-node-name;
        leaf responder {
          type empty;
        }
      }
      container responder-udp-echo {
        tailf:cli-drop-node-name;
        container responder {
          container udp-echo {
            tailf:cli-compact-syntax;
            leaf ipaddress {
              type inet:host;
            }
            leaf port {
              type uint16;
            }
          }
        }
      }
      container responder-tcp-connect {
        tailf:cli-drop-node-name;
        container responder {
          container tcp-connect {
            tailf:cli-compact-syntax;
            leaf ipaddress {
              type inet:host;
            }
            leaf port {
              type uint16;
            }
            leaf vrf {
              type string;
            }
          }
        }
      }
      container server {
        container twamp {
          tailf:cli-add-mode;
          presence "true";
          leaf port {
            type uint16;
          }
          container timer {
            leaf inactivity {
              type uint16;
            }
          }
        }
      }
      container logging {
        leaf traps {
          type empty;
        }
      }
      leaf key-chain {
        type string;
      }
      list ip-sla-list {
        tailf:cli-drop-node-name;
        key "id";
        leaf id {
          type uint32;
        }
        list tcp-connect {
          tailf:cli-suppress-mode;
          tailf:cli-delete-when-empty;
          tailf:cli-compact-syntax;
          key "destination destination-port";
          leaf destination {
            type inet:host;
          }
          leaf destination-port {
            type uint16;
          }
          leaf source-ip {
            type inet:host;
          }
          leaf source-port {
            type uint16;
          }
          leaf control {
            type enumeration {
              enum "disable";
              enum "enable";
            }
          }
        }
        list udp-jitter {
          tailf:cli-suppress-mode;
          tailf:cli-delete-when-empty;
          tailf:cli-compact-syntax;
          key "destination destination-port";
          leaf destination {
            type inet:host;
          }
          leaf destination-port {
            type uint16;
          }
          leaf source-ip {
            type inet:host;
          }
          leaf source-port {
            type uint16;
          }
          leaf num-packets {
            type uint16;
          }
          leaf codec {
            type enumeration {
              enum "g711alaw";
              enum "g711ulaw";
              enum "g729a";
            }
          }
          leaf codec-numpackets {
            type uint32;
          }
          leaf interval {
            type uint32;
          }
          leaf control {
            type enumeration {
              enum "disable";
              enum "enable";
            }
          }
        }
        list icmp-echo {
          tailf:cli-suppress-mode;
          tailf:cli-delete-when-empty;
          tailf:cli-compact-syntax;
          key "host";
          leaf host {
            type inet:host;
          }
          choice source-choice {
            container source-interface {
              tailf:cli-flatten-container;
              uses interface-nodiff-name-grouping;
            }
            leaf source-ip {
              type inet:host;
            }
          }
        }
        list icmp-jitter {
          tailf:cli-suppress-mode;
          tailf:cli-delete-when-empty;
          tailf:cli-compact-syntax;
          key "host";
          leaf host {
            type inet:host;
          }
          leaf source-ip {
            type inet:host;
          }
          leaf num-packets {
            type uint16;
          }
          leaf interval {
            type uint32;
          }
        }
        list udp-echo {
          tailf:cli-suppress-mode;
          tailf:cli-delete-when-empty;
          tailf:cli-compact-syntax;
          key "host port";
          leaf host {
            type inet:host;
          }
          leaf port {
            type uint16;
          }
          leaf control {
            type enumeration {
              enum "disable";
              enum "enable";
            }
          }
          leaf source-ip {
            type inet:host;
          }
          leaf source-port {
            type uint16;
          }
        }
        container ethernet {
          list ethernet-list {
            tailf:cli-drop-node-name;
            tailf:cli-suppress-mode;
            tailf:cli-delete-when-empty;
            tailf:cli-compact-syntax;
            key "type mpid domain";
            leaf type {
              type enumeration {
                enum "jitter";
                enum "echo";
              }
            }
            leaf mpid {
              tailf:cli-expose-key-name;
              type uint16;
            }
            leaf domain {
              tailf:cli-expose-key-name;
              type string;
            }
            choice vlan-or-port {
              leaf port {
                type empty;
              }
              leaf vlan {
                type uint16;
              }
              leaf evc {
                type string;
              }
            }
            leaf num-frames {
              type uint16;
            }
            leaf interval {
              type uint16;
            }
          }
          container y1731 {
            list delay {
              tailf:cli-suppress-mode;
              tailf:cli-delete-when-empty;
              tailf:cli-compact-syntax;
              tailf:cli-sequence-commands;
              key "name";
              leaf name {
                type enumeration {
                  enum "1DM";
                  enum "DMM";
                  enum "DMMv1";
                }
              }
              leaf burst {
                tailf:cli-optional-in-sequence;
                type empty;
              }
              leaf domain {
                type string;
              }
              choice evc-or-vlan {
                leaf evc {
                  type string;
                }
                leaf vlan {
                  type uint16;
                }
              }
              choice mpid-or-mac {
                leaf mac-address {
                  type string;
                }
                leaf mpid {
                  type uint16;
                }
              }
              leaf cos {
                type uint8;
              }
              container source {
                tailf:cli-flatten-container;
                choice mpid-or-mac {
                  leaf mac-address {
                    type string;
                  }
                  leaf mpid {
                    type uint16;
                  }
                }
              }
            }
            container delay-receive {
              tailf:cli-drop-node-name;
              container delay {
                list receive {
                  tailf:cli-suppress-mode;
                  tailf:cli-delete-when-empty;
                  tailf:cli-compact-syntax;
                  tailf:cli-sequence-commands;
                  key "name";
                  leaf name {
                    type enumeration {
                      enum "1DM";
                    }
                  }
                  leaf domain {
                    type string;
                  }
                  choice evc-or-vlan {
                    leaf evc {
                      type string;
                    }
                    leaf vlan {
                      type uint16;
                    }
                  }
                  leaf cos {
                    type uint8;
                  }
                  choice mpid-or-mac {
                    leaf mac-address {
                      type string;
                    }
                    leaf mpid {
                      type uint16;
                    }
                  }
                }
              }
            }
            list loss {
              tailf:cli-suppress-mode;
              tailf:cli-delete-when-empty;
              tailf:cli-compact-syntax;
              tailf:cli-sequence-commands;
              key "name";
              leaf name {
                type enumeration {
                  enum "LMM";
                  enum "SLM";
                }
              }
              leaf burst {
                tailf:cli-optional-in-sequence;
                type empty;
              }
              leaf domain {
                type string;
              }
              choice evc-or-vlan {
                leaf evc {
                  type string;
                }
                leaf vlan {
                  type uint16;
                }
              }
              choice mpid-or-mac {
                leaf mac-address {
                  type string;
                }
                leaf mpid {
                  type uint16;
                }
              }
              leaf cos {
                type uint8;
              }
              container source {
                tailf:cli-flatten-container;
                choice mpid-or-mac {
                  leaf mac-address {
                    type string;
                  }
                  leaf mpid {
                    type uint16;
                  }
                }
              }
            }
          }
        }
        container http {
          leaf get {
            type string;
          }
        }
        list service-performance {
          tailf:cli-suppress-mode;
          tailf:cli-delete-when-empty;
          tailf:cli-compact-syntax;
          tailf:cli-sequence-commands;
          key "type";
          leaf type {
            tailf:cli-expose-key-name;
            type enumeration {
              enum "ethernet";
              enum "ip";
            }
          }
          leaf dest-mac-addr {
            type string;
          }
          leaf dest-ip-addr {
            type inet:host;
          }
          leaf vrf {
            tailf:cli-optional-in-sequence;
            type uint16;
          }
          container interface {
            tailf:cli-flatten-container;
            tailf:cli-compact-syntax;
            uses interface-nodiff-name-grouping;
          }
          container service {
            tailf:cli-flatten-container;
            tailf:cli-compact-syntax;
            leaf instance {
              type uint16;
            }
          }
          leaf ethernet {
            type string;
          }
        }
        container dns {
          tailf:cli-compact-syntax;
          tailf:cli-sequence-commands {
            tailf:cli-reset-siblings;
          }
          leaf name {
            tailf:cli-drop-node-name;
            type string;
          }
          leaf name-server {
            type inet:host;
          }
        }
        uses description-grouping;
        leaf tos {
          type uint8;
        }
        leaf precision {
          type enumeration {
            enum "microseconds";
            enum "milliseconds";
          }
        }
        leaf operation-packet-priority {
          type enumeration {
            enum "normal";
            enum "high";
          }
        }
        container optimize {
          leaf timestamp {
            type empty;
          }
        }
        leaf traffic-class {
          type uint8;
        }
        leaf verify-data {
          type empty;
        }
        leaf data-pattern {
          type string;
        }
        leaf vrf {
          type string;
        }
        container control {
          leaf timeout {
            type uint16;
          }
          leaf retry {
            type uint8;
          }
        }
        container clock {
          leaf sync {
            type empty;
          }
        }
        leaf owner {
          tailf:cli-multi-value;
          type string;
        }
        leaf tag {
          tailf:cli-multi-value;
          type string;
        }
        container frequency {
          leaf seconds {
            tailf:cli-drop-node-name;
            type uint32;
          }
          choice frequency-choice {
            leaf time {
              type uint32;
            }
            container iteration {
              tailf:cli-compact-syntax;
              tailf:cli-sequence-commands {
                tailf:cli-reset-siblings;
              }
              leaf number {
                tailf:cli-drop-node-name;
                type uint8;
              }
              leaf delay {
                type uint8;
              }
            }
          }
        }
        leaf threshold {
          type uint16;
        }
        leaf timeout {
          type uint32;
        }
        container loopback {
          container direction {
            leaf internal {
              type empty;
            }
          }
        }
        container frame {
          leaf size {
            type uint16;
          }
          leaf interval {
            type enumeration {
              enum "10";
              enum "20";
              enum "25";
              enum "50";
              enum "100";
              enum "1000";
            }
          }
        }
        container history {
          leaf hours-of-statistics-kept {
            type uint8;
          }
          leaf distributions-of-statistics-kept {
            type uint8;
          }
          leaf statistics-distribution-interval {
            type uint8;
          }
          leaf statistics-distribution-interval-microseconds {
            tailf:alt-name "statistics-distribution-interval";
            type uint32;
          }
          leaf lives-kept {
            type uint8;
          }
          leaf buckets-kept {
            type uint8;
          }
          leaf filter {
            type enumeration {
              enum "all";
              enum "failures";
              enum "none";
              enum "overThreshold";
            }
          }
          container enhanced {
            tailf:cli-compact-syntax;
            tailf:cli-sequence-commands;
            leaf interval {
              type uint16;
            }
            leaf buckets {
              type uint8;
            }
          }
          leaf interval {
            type uint8;
          }
        }
        container duration {
          leaf time {
            type uint32;
          }
        }
        list measurement-type {
          key "direction";
          leaf direction {
            tailf:cli-expose-key-name;
            type enumeration {
              enum "internal";
              enum "external";
            }
          }
          leaf delay {
            type empty;
          }
          leaf jitter {
            type empty;
          }
          leaf loss {
            type empty;
          }
          leaf receive {
            type empty;
          }
          leaf throughput {
            type empty;
          }
        }
        container profile {
          container packet {
            tailf:cli-add-mode;
            leaf inner-cos {
              type uint8;
            }
            leaf outer-cos {
              type uint8;
            }
            leaf inner-vlan {
              type uint16;
            }
            leaf outer-vlan {
              type uint16;
            }
            leaf source-ip-addr {
              type inet:host;
            }
            leaf packet-size {
              type enumeration {
                enum "1024";
                enum "128";
                enum "1280";
                enum "1518";
                enum "256";
                enum "512";
                enum "64";
                enum "9216";
                enum "imix";
              }
            }
            leaf src-mac-addr {
              type string;
            }
          }
          list traffic {
            key "direction";
            leaf direction {
              tailf:cli-expose-key-name;
              type enumeration {
                enum "internal";
                enum "external";
              }
            }
            container rate-step {
              container kbps {
                tailf:cli-compact-syntax;
                leaf-list step {
                  tailf:cli-drop-node-name;
                  tailf:cli-flat-list-syntax;
                  ordered-by user;
                  type uint32;
                }
              }
            }
          }
        }
        leaf cos {
          type uint8;
        }
        leaf request-data-size {
          type uint16;
        }
        container aggregate {
          leaf interval {
            type uint16;
          }
        }
        container distribution {
          container delay {
            uses ip-sla-distribution-delay-grouping;
          }
          container delay-variation {
            uses ip-sla-distribution-delay-grouping;
          }
        }
        container availability {
          leaf algorithm {
            type enumeration {
              enum "sliding-window";
              enum "static-window";
            }
          }
        }
      }
      list schedule {
        tailf:cli-suppress-mode;
        tailf:cli-delete-when-empty;
        tailf:cli-compact-syntax;
        key "operation-number";
        leaf operation-number {
          type uint32;
        }
        leaf life {
          type union {
            type enumeration {
              enum "forever";
            }
            type uint32;
          }
        }
        container start-time {
          tailf:cli-flatten-container;
          tailf:cli-compact-syntax;
          choice start-time-choice {
            leaf after {
              type string;
            }
            leaf now {
              type empty;
            }
            leaf pending {
              type empty;
            }
            leaf time {
              tailf:cli-drop-node-name;
              type string;
            }
          }
        }
        leaf ageout {
          type uint32;
        }
        leaf recurring {
          type empty;
        }
      }
      container group {
        list schedule {
          tailf:cli-suppress-mode;
          tailf:cli-delete-when-empty;
          tailf:cli-compact-syntax;
          tailf:cli-sequence-commands {
            tailf:cli-reset-all-siblings;
          }
          key "id";
          leaf id {
            type uint32;
          }
          leaf-list operation-ids {
            tailf:cli-drop-node-name;
            tailf:cli-range-list-syntax;
            type uint32;
          }
          choice schedule-choice {
            leaf schedule-together {
              type empty;
            }
            leaf schedule-period {
              type uint32;
            }
          }
          leaf life {
            tailf:cli-break-sequence-commands;
            type union {
              type enumeration {
                enum "forever";
              }
              type uint32;
            }
          }
          container start-time {
            tailf:cli-flatten-container;
            tailf:cli-compact-syntax;
            choice start-time-choice {
              leaf after {
                type string;
              }
              leaf now {
                type empty;
              }
              leaf pending {
                type empty;
              }
              leaf time {
                tailf:cli-drop-node-name;
                type string;
              }
            }
          }
          leaf ageout {
            type uint32;
          }
        }
      }
      container profile {
        list packet {
          tailf:cli-sequence-commands;
          key "name";
          leaf type {
            tailf:cli-prefix-key;
            type enumeration {
              enum "ethernet";
              enum "ip";
            }
          }
          leaf name {
            type string;
          }
          leaf source-ip-addr {
            tailf:cli-break-sequence-commands;
            type inet:host;
          }
          leaf dest-ip-addr {
            type inet:host;
          }
        }
      }
      list endpoint-list {
        tailf:cli-sequence-commands;
        key "name";
        leaf type {
          tailf:cli-prefix-key;
          type enumeration {
            enum "ip";
          }
        }
        leaf name {
          type string;
        }
        leaf description {
          tailf:cli-break-sequence-commands;
          tailf:cli-multi-value;
          type string;
        }
        container ip-address {
          tailf:cli-compact-syntax;
          tailf:cli-sequence-commands {
            tailf:cli-reset-siblings;
          }
          leaf address {
            tailf:cli-drop-node-name;
            type string;
          }
          leaf port {
            type uint16;
          }
        }
      }
      container ethernet-monitor {
        list ip-sla-ethernet-monitor-list {
          tailf:cli-drop-node-name;
          key "id";
          leaf id {
            type uint32;
          }
          list type {
            key "type domain vlan";
            leaf type {
              type enumeration {
                enum "echo";
                enum "jitter";
              }
            }
            leaf domain {
              tailf:cli-expose-key-name;
              type string;
            }
            leaf vlan {
              tailf:cli-expose-key-name;
              type uint16;
            }
            leaf cos {
              type uint8;
            }
            leaf request-data-size {
              type uint16;
            }
          }
        }
        list schedule {
          tailf:cli-delete-when-empty;
          tailf:cli-suppress-mode;
          tailf:cli-compact-syntax;
          key "operation-number";
          leaf operation-number {
            type uint32;
          }
          leaf schedule-period {
            type uint32;
          }
          container start-time {
            tailf:cli-flatten-container;
            tailf:cli-compact-syntax;
            choice start-time-choice {
              leaf after {
                type string;
              }
              leaf now {
                type empty;
              }
              leaf pending {
                type empty;
              }
              leaf time {
                tailf:cli-drop-node-name;
                type string;
              }
            }
          }
        }
        list reaction-configuration {
          tailf:cli-suppress-mode;
          tailf:cli-delete-when-empty;
          tailf:cli-compact-syntax;
          tailf:cli-sequence-commands {
            tailf:cli-reset-all-siblings;
          }
          key "operation-number react";
          leaf operation-number {
            type uint32;
          }
          leaf react {
            tailf:cli-expose-key-name;
            type string;
          }
          uses ip-sla-reaction-grouping;
        }
      }
      list reaction-configuration {
        tailf:cli-suppress-mode;
        tailf:cli-delete-when-empty;
        tailf:cli-compact-syntax;
        tailf:cli-sequence-commands {
          tailf:cli-reset-all-siblings;
        }
        key "operation-number react";
        leaf operation-number {
          type uint32;
        }
        leaf react {
          tailf:cli-expose-key-name;
          type string;
        }
        uses ip-sla-reaction-grouping;
      }
      list reaction-trigger {
        tailf:cli-suppress-mode;
        tailf:cli-delete-when-empty;
        key "operation-number";
        leaf operation-number {
          type uint32;
        }
        leaf target-operation {
          tailf:cli-drop-node-name;
          type uint32;
        }
      }
      container enable {
        leaf timestamp {
          type empty;
        }
        leaf reaction-alerts {
          type empty;
        }
      }
    }
    container wccp {
      uses ip-wccp-grouping;
      list vrf {
        tailf:cli-suppress-mode;
        tailf:cli-delete-when-empty;
        tailf:cli-compact-syntax;
        key "name";
        leaf name {
          type string;
        }
        uses ip-wccp-grouping;
      }
    }
    container nbar {
      list attribute-map {
        key "name";
        leaf name {
          type string;
        }
        container attribute {
          leaf business-relevance {
            type enumeration {
              enum "business-relevant";
              enum "business-irrelevant";
              enum "default";
            }
          }
          leaf traffic-class {
            type enumeration {
              enum "transactional-data";
              enum "voip-telephony";
              enum "signaling";
              enum "real-time-interactive";
              enum "ops-admin-mgmt";
              enum "network-control";
              enum "multimedia-streaming";
              enum "multimedia-conferencing";
              enum "bulk-data";
              enum "broadcast-video";
            }
          }
          leaf application-group {
            type string;
          }
          leaf category {
            type string;
          }
          leaf sub-category {
            type string;
          }
        }
      }
      leaf http-services {
        type empty;
      }
      container classification {
        leaf granularity {
          type enumeration {
            enum "coarse-grain";
            enum "fine-grain";
          }
        }
        container dns {
          container learning {
            leaf guard {
              type empty;
            }
          }
        }
      }
      list custom {
        tailf:cli-suppress-mode;
        tailf:cli-delete-when-empty;
        key "name";
        leaf name {
          type string;
        }
        list ports {
          tailf:cli-drop-node-name;
          tailf:cli-suppress-mode;
          tailf:cli-delete-when-empty;
          tailf:cli-compact-syntax;
          tailf:cli-sequence-commands {
            tailf:cli-reset-siblings;
          }
          key "name";
          leaf name {
            type enumeration {
              enum "udp";
              enum "tcp";
            }
          }
          choice ports-choice {
            container range {
              tailf:cli-flatten-container;
              tailf:cli-compact-syntax;
              tailf:cli-sequence-commands {
                tailf:cli-reset-siblings;
              }
              leaf start {
                tailf:cli-drop-node-name;
                type uint16;
              }
              leaf end {
                tailf:cli-drop-node-name;
                type uint16;
              }
            }
            leaf-list ports {
              tailf:cli-drop-node-name;
              tailf:cli-range-list-syntax;
              type uint16;
            }
          }
          leaf id {
            type uint16;
          }
        }
        container composite {
          tailf:cli-flatten-container;
          tailf:cli-compact-syntax;
          tailf:cli-sequence-commands {
            tailf:cli-reset-siblings;
          }
          leaf server-name {
            type string;
          }
          leaf id {
            tailf:cli-optional-in-sequence;
            type uint16;
          }
          leaf extends {
            type string;
          }
        }
      }
      container custom-transport {
        tailf:cli-drop-node-name;
        list custom {
          key "name";
          leaf name {
            type string;
          }
          leaf transport {
            tailf:cli-hide-in-submode;
            type enumeration {
              enum "tcp";
              enum "udp";
              enum "udp-tcp";
            }
          }
          leaf id {
            tailf:cli-hide-in-submode;
            type uint16;
          }
          container ip {
            leaf-list address {
              tailf:cli-flat-list-syntax;
              ordered-by user;
              type inet:ipv4-address;
            }
            container subnet {
              tailf:cli-compact-syntax;
              tailf:cli-sequence-commands {
                tailf:cli-reset-siblings;
              }
              leaf ip {
                tailf:cli-drop-node-name;
                type inet:ipv4-address;
              }
              leaf mask {
                tailf:cli-drop-node-name;
                type uint8;
              }
            }
          }
          container port {
            leaf-list ports {
              tailf:cli-drop-node-name;
              tailf:cli-flat-list-syntax;
              ordered-by user;
              type uint16;
            }
            container range {
              tailf:cli-compact-syntax;
              tailf:cli-sequence-commands;
              leaf start {
                tailf:cli-drop-node-name;
                type uint16;
              }
              leaf end {
                tailf:cli-drop-node-name;
                type uint16;
              }
            }
          }
          leaf direction {
            type enumeration {
              enum "any";
              enum "destination";
              enum "source";
            }
          }
        }
      }
      list attribute-set {
        tailf:cli-suppress-mode;
        tailf:cli-delete-when-empty;
        key "protocol-name";
        leaf protocol-name {
          type string;
        }
        leaf profile-name {
          tailf:cli-drop-node-name;
          type string;
        }
      }
      list pdlm {
        tailf:cli-suppress-mode;
        tailf:cli-delete-when-empty;
        key "name";
        leaf name {
          type string;
        }
      }
      list port-map {
        tailf:cli-suppress-mode;
        tailf:cli-delete-when-empty;
        key "name";
        leaf name {
          type string;
        }
        leaf-list udp {
          tailf:cli-flat-list-syntax;
          ordered-by user;
          type uint16;
        }
        leaf-list tcp {
          tailf:cli-flat-list-syntax;
          ordered-by user;
          type uint16;
        }
      }
      container protocol-discovery {
        presence "true";
      }
      container protocol-pack {
        tailf:cli-compact-syntax;
        tailf:cli-sequence-commands {
          tailf:cli-reset-siblings;
        }
        leaf path {
          tailf:cli-drop-node-name;
          type string;
        }
        leaf force {
          type empty;
        }
      }
    }
    container inspect {
      list name {
        tailf:cli-suppress-mode;
        tailf:cli-delete-when-empty;
        key "name";
        leaf name {
          type string;
        }
        list rule {
          tailf:cli-drop-node-name;
          tailf:cli-suppress-mode;
          tailf:cli-delete-when-empty;
          ordered-by user;
          key "rule";
          leaf rule {
            tailf:cli-multi-word-key;
            type string;
          }
        }
      }
    }
    container spd {
      leaf enable {
        type boolean;
      }
    }
    container spd-conf {
      tailf:cli-drop-node-name;
      container spd {
        container queue {
          leaf max-threshold {
            type uint16;
          }
          leaf min-threshold {
            type uint16;
          }
        }
      }
    }
    container source {
      list binding {
        tailf:cli-suppress-mode;
        tailf:cli-delete-when-empty;
        tailf:cli-compact-syntax;
        tailf:cli-sequence-commands {
          tailf:cli-reset-siblings;
        }
        key "mac-address vlan";
        leaf mac-address {
          type string;
        }
        leaf vlan {
          tailf:cli-expose-key-name;
          type uint16;
        }
        leaf ip-address {
          tailf:cli-drop-node-name;
          type inet:ipv4-address;
        }
        container interface {
          tailf:cli-flatten-container;
          tailf:cli-compact-syntax;
          uses interface-name-grouping;
        }
      }
    }
    container ips {
      container po {
        leaf max-events {
          type uint16;
        }
      }
    }
  }
  container isdn {
    leaf switch-type {
      type string;
    }
    container leased-line {
      tailf:cli-compact-syntax;
      tailf:cli-sequence-commands {
        tailf:cli-reset-siblings;
      }
      leaf BRI {
        tailf:cli-allow-join-with-value;
        type string;
      }
      leaf hundredtwentyeight {
        tailf:alt-name "128";
        type empty;
      }
    }
  }
  container vmps {
    leaf reconfirm {
      type uint8;
    }
    leaf retry {
      type uint8;
    }
    list server {
      tailf:cli-suppress-mode;
      tailf:cli-delete-when-empty;
      tailf:cli-compact-syntax;
      key "name";
      leaf name {
        type inet:host;
      }
      leaf primary {
        type empty;
      }
    }
  }
  container ipv6 {
    leaf unicast-routing {
      type empty;
    }
    leaf source-route {
      type boolean;
    }
    leaf hop-limit {
      type uint16;
    }
    leaf cef {
      type empty;
    }
    container cef-conf {
      tailf:cli-drop-node-name;
      container cef {
        container accounting {
          tailf:cli-compact-syntax;
          leaf per-prefix {
            type empty;
          }
          leaf prefix-length {
            type empty;
          }
        }
        leaf distributed {
          type empty;
        }
        container load-sharing {
          tailf:cli-compact-syntax;
          tailf:cli-sequence-commands {
            tailf:cli-reset-siblings;
          }
          leaf algorithm {
            type enumeration {
              enum "original";
              enum "universal";
              enum "include-ports";
            }
          }
          leaf source {
            tailf:cli-optional-in-sequence;
            type empty;
          }
          leaf destination {
            tailf:cli-optional-in-sequence;
            type empty;
          }
          leaf id {
            tailf:cli-drop-node-name;
            type string;
          }
        }
      }
    }
    leaf flowset {
      type empty;
    }
    container icmp {
      container error-interval {
        tailf:cli-compact-syntax;
        tailf:cli-sequence-commands {
          tailf:cli-reset-siblings;
        }
        leaf milliseconds {
          tailf:cli-drop-node-name;
          type uint32;
        }
        leaf bucketsize {
          tailf:cli-drop-node-name;
          type uint8;
        }
      }
    }
    container wccp {
      uses ip-wccp-grouping;
      list vrf {
        tailf:cli-suppress-mode;
        tailf:cli-delete-when-empty;
        tailf:cli-compact-syntax;
        key "name";
        leaf name {
          type string;
        }
        uses ip-wccp-grouping;
      }
    }
    container mld {
      container snooping-enable {
        tailf:cli-drop-node-name;
        leaf snooping {
          type boolean;
        }
      }
      leaf state-limit {
        type uint16;
      }
    }
    leaf multicast-routing {
      type empty;
    }
    container multicast-routing-conf {
      tailf:cli-drop-node-name;
      container multicast-routing {
        list vrf {
          tailf:cli-suppress-list-no;
          tailf:cli-suppress-mode;
          tailf:cli-delete-when-empty;
          key "name";
          leaf name {
            type string;
          }
        }
      }
    }
    container multicast {
      uses ipv6-multicast-grouping;
      container hardware-switching {
        leaf replication-mode {
          type enumeration {
            enum "ingress";
          }
        }
      }
      leaf pim-passive-enable {
        type empty;
      }
      list vrf {
        tailf:cli-suppress-list-no;
        tailf:cli-suppress-mode;
        tailf:cli-delete-when-empty;
        key "name";
        leaf name {
          type string;
        }
        uses ipv6-multicast-grouping;
      }
    }
    container mfib-enable {
      tailf:cli-drop-node-name;
      leaf mfib {
        type boolean;
      }
    }
    container mfib {
      container hardware-switching {
        container replication-mode {
          leaf ingress {
            type empty;
          }
        }
      }
    }
    container spd {
      container queue {
        leaf min-threshold {
          type uint16;
        }
        leaf max-threshold {
          type uint16;
        }
      }
    }
    container route {
      container static {
        list bfd {
          tailf:cli-suppress-mode;
          tailf:cli-delete-when-empty;
          tailf:cli-compact-syntax;
          key "interface ipv6-address";
          leaf interface {
            type string;
          }
          leaf ipv6-address {
            type inet:ipv6-address;
          }
          leaf unassociated {
            type empty;
          }
        }
        container bfd-list-vrf {
          tailf:cli-drop-node-name;
          container bfd {
            list vrf {
              tailf:cli-suppress-mode;
              tailf:cli-delete-when-empty;
              tailf:cli-compact-syntax;
              key "name interface ipv6-address";
              leaf name {
                type string;
              }
              leaf interface {
                type string;
              }
              leaf ipv6-address {
                type inet:ipv6-address;
              }
              leaf unassociated {
                type empty;
              }
            }
          }
        }
      }
      list vrf {
        tailf:cli-suppress-mode;
        tailf:cli-delete-when-empty;
        tailf:cli-compact-syntax;
        key "name";
        leaf name {
          type string;
        }
        uses ipv6-route-grouping;
      }
      container no-vrf {
        tailf:cli-drop-node-name;
        uses ipv6-route-grouping;
      }
    }
    list general-prefix {
      tailf:cli-suppress-mode;
      tailf:cli-delete-when-empty;
      tailf:cli-compact-syntax;
      tailf:cli-sequence-commands {
        tailf:cli-reset-siblings;
      }
      key "name";
      leaf name {
        type string;
      }
      choice prefix-choice {
        leaf prefix {
          tailf:cli-drop-node-name;
          type ipv6-prefix;
        }
        case interface {
          leaf type {
            tailf:cli-drop-node-name;
            type enumeration {
              enum "6rd";
              enum "6to4";
            }
          }
          container interface {
            tailf:cli-drop-node-name;
            tailf:cli-flatten-container;
            tailf:cli-compact-syntax;
            uses interface-name-grouping;
          }
        }
      }
    }
    container prefix-list {
      leaf sequence-number {
        type boolean;
      }
      list prefixes {
        tailf:cli-drop-node-name;
        tailf:cli-suppress-mode;
        tailf:cli-delete-when-empty;
        key "name";
        leaf name {
          type string;
        }
        leaf description {
          tailf:cli-multi-value;
          type string;
        }
        list seq {
          tailf:cli-suppress-mode;
          tailf:cli-delete-when-empty;
          tailf:cli-compact-syntax;
          key "no";
          leaf no {
            type uint32;
          }
          container deny {
            tailf:cli-compact-syntax;
            tailf:cli-sequence-commands {
              tailf:cli-reset-all-siblings;
            }
            leaf ip {
              tailf:cli-drop-node-name;
              type ios:ipv6-prefix;
            }
            leaf ge {
              tailf:cli-break-sequence-commands;
              type uint16;
            }
            leaf le {
              type uint16;
            }
          }
          container permit {
            tailf:cli-compact-syntax;
            tailf:cli-sequence-commands {
              tailf:cli-reset-all-siblings;
            }
            leaf ip {
              tailf:cli-drop-node-name;
              type ios:ipv6-prefix;
            }
            leaf ge {
              tailf:cli-break-sequence-commands;
              type uint16;
            }
            leaf le {
              type uint16;
            }
          }
        }
      }
      list prefixes-no-seq {
        tailf:cli-drop-node-name;
        tailf:cli-suppress-mode;
        tailf:cli-delete-when-empty;
        key "name";
        leaf name {
          type string;
        }
        leaf description {
          tailf:cli-multi-value;
          type string;
        }
        list entry {
          tailf:cli-drop-node-name;
          tailf:cli-suppress-mode;
          tailf:cli-delete-when-empty;
          ordered-by user;
          key "rule";
          leaf rule {
            tailf:cli-multi-word-key;
            type string;
          }
        }
      }
    }
    container access-list {
      list named-acl {
        tailf:cli-drop-node-name;
        key "name";
        leaf name {
          tailf:cli-suppress-range;
          type string;
        }
        list access-list-rule {
          tailf:cli-suppress-mode;
          tailf:cli-delete-when-empty;
          tailf:cli-drop-node-name;
          tailf:cli-compact-syntax;
          tailf:cli-case-sensitive;
          ordered-by user;
          key "rule";
          leaf rule {
            tailf:cli-suppress-range;
            tailf:cli-drop-node-name;
            tailf:cli-multi-word-key;
            type string;
          }
        }
      }
      list filter-list {
        tailf:cli-drop-node-name;
        key "name";
        leaf name {
          tailf:cli-suppress-range;
          type string;
        }
        list sequence {
          tailf:cli-suppress-mode;
          tailf:cli-delete-when-empty;
          key "seq";
          leaf seq {
            tailf:cli-suppress-range;
            type uint32;
          }
          leaf entry {
            tailf:cli-drop-node-name;
            tailf:cli-multi-value;
            type string;
          }
        }
      }
    }
    container router {
      list rip {
        key "name";
        leaf name {
          type string;
        }
        container address-family {
          container ipv6 {
            list vrf {
              key "name";
              leaf name {
                type string;
              }
            }
          }
        }
        container distribute-list {
          list prefix-list {
            tailf:cli-suppress-mode;
            tailf:cli-delete-when-empty;
            tailf:cli-compact-syntax;
            tailf:cli-sequence-commands {
              tailf:cli-reset-siblings;
            }
            key "direction";
            leaf direction {
              type enumeration {
                enum "in";
                enum "out";
              }
            }
            leaf prefix-list-name {
              tailf:cli-drop-node-name;
              tailf:cli-prefix-key;
              type string;
            }
            container interface {
              tailf:cli-drop-node-name;
              tailf:cli-flatten-container;
              tailf:cli-compact-syntax;
              uses interface-name-grouping;
            }
          }
        }
      }
      list eigrp {
        key "as-no";
        leaf as-no {
          type uint16;
        }
        container eigrp {
          leaf router-id {
            type inet:ipv4-address;
          }
        }
        leaf shutdown {
          type empty;
        }
        uses passive-interface-grouping;
      }
      list ospf {
        key "id";
        leaf id {
          tailf:cli-suppress-range;
          type uint16;
        }
        uses router-ospfv3-common-grouping;
        uses router-ospf-common-af-grouping;
        uses router-ospf-grouping;
      }
    }
    container ospf {
      leaf name-lookup {
        type empty;
      }
    }
    container pim {
      uses ipv6-pim-grouping;
      list vrf {
        tailf:cli-suppress-mode;
        tailf:cli-delete-when-empty;
        key "name";
        leaf name {
          type string;
        }
        uses ipv6-pim-grouping;
      }
    }
    container nd {
      container raguard {
        list policy {
          key "name";
          leaf name {
            type string;
          }
          leaf trusted-port {
            type empty;
          }
        }
      }
      leaf reachable-time {
        type uint32;
      }
    }
    container neighbor {
      list neighbor-list {
        tailf:cli-drop-node-name;
        tailf:cli-suppress-mode;
        tailf:cli-delete-when-empty;
        key "address interface";
        leaf address {
          type inet:ipv6-address;
        }
        leaf interface {
          type string;
        }
        leaf hardware-address {
          tailf:cli-drop-node-name;
          type string;
        }
      }
    }
    container local {
      container policy {
        leaf route-map {
          type string;
        }
      }
      list pool {
        tailf:cli-suppress-mode;
        tailf:cli-delete-when-empty;
        tailf:cli-compact-syntax;
        tailf:cli-sequence-commands {
          tailf:cli-reset-siblings;
        }
        key "name";
        leaf name {
          tailf:cli-suppress-range;
          type string;
        }
        leaf prefix {
          tailf:cli-drop-node-name;
          type ipv6-prefix;
        }
        leaf assigned-length {
          tailf:cli-drop-node-name;
          type uint8;
        }
        leaf shared {
          tailf:cli-optional-in-sequence;
          type empty;
        }
        leaf cache-size {
          type uint16;
        }
      }
    }
    container dhcp {
      container binding {
        container track {
          leaf ppp {
            type empty;
          }
        }
      }
      list pool {
        key "name";
        leaf name {
          type string;
        }
        leaf vrf {
          type string;
        }
        list address {
          tailf:cli-suppress-mode;
          tailf:cli-delete-when-empty;
          ordered-by user;
          key "prefix";
          leaf prefix {
            tailf:cli-expose-key-name;
            type ios:ipv6-prefix;
          }
        }
        list dns-server {
          tailf:cli-suppress-mode;
          tailf:cli-delete-when-empty;
          ordered-by user;
          key "address";
          leaf address {
            type inet:host;
          }
        }
        list domain-name {
          tailf:cli-suppress-mode;
          tailf:cli-delete-when-empty;
          ordered-by user;
          key "name";
          leaf name {
            type string;
          }
        }
        container prefix-delegation {
          container aaa {
            tailf:cli-compact-syntax;
            tailf:cli-sequence-commands {
              tailf:cli-reset-siblings;
            }
            tailf:cli-delete-when-empty;
            presence "true";
            leaf method-list {
              type string;
            }
            container lifetime {
              tailf:cli-flatten-container;
              tailf:cli-compact-syntax;
              tailf:cli-sequence-commands {
                tailf:cli-reset-siblings;
              }
              leaf valid-lifetime-seconds {
                tailf:cli-drop-node-name;
                type uint32;
              }
              leaf preferred-lifetime-seconds {
                tailf:cli-drop-node-name;
                type uint32;
              }
            }
          }
          container pool {
            tailf:cli-compact-syntax;
            tailf:cli-sequence-commands {
              tailf:cli-reset-siblings;
            }
            leaf poolname {
              tailf:cli-drop-node-name;
              type string;
            }
            container lifetime {
              tailf:cli-flatten-container;
              tailf:cli-compact-syntax;
              tailf:cli-sequence-commands {
                tailf:cli-reset-siblings;
              }
              leaf valid-lifetime-seconds {
                tailf:cli-drop-node-name;
                type uint32;
              }
              leaf preferred-lifetime-seconds {
                tailf:cli-drop-node-name;
                type uint32;
              }
            }
          }
        }
      }
      container guard {
        list policy {
          key "name";
          leaf name {
            type string;
          }
          choice port-choice {
            case a {
              leaf device-role {
                type enumeration {
                  enum "client";
                  enum "server";
                }
              }
              container match {
                container server {
                  leaf access-list {
                    type string;
                  }
                }
                container reply {
                  leaf prefix-list {
                    type string;
                  }
                }
              }
            }
            case b {
              leaf trusted-port {
                type empty;
              }
            }
          }
        }
      }
      container server {
        container vrf {
          leaf enable {
            type empty;
          }
        }
      }
    }
    container dhcp-relay {
      container bulk-lease {
        leaf disable {
          type empty;
        }
      }
    }
    container rip {
      container vrf-mode {
        leaf enable {
          type empty;
        }
      }
    }
    container mobile {
      list pmipv6-domain {
        key "name";
        leaf name {
          type string;
        }
        container replay-protection {
          container timestamp {
            leaf window {
              type uint8;
            }
          }
        }
        leaf encap {
          type enumeration {
            enum "gre-ipv4";
            enum "gre-ipv6";
            enum "ipv6-in-ipv6";
            enum "udptunnel";
          }
        }
        list lma {
          key "name";
          leaf name {
            type string;
          }
          leaf ipv6-address {
            type inet:ipv6-address;
          }
          leaf ipv4-address {
            type inet:ipv4-address;
          }
        }
        list mobile-map {
          key "name sequence";
          leaf name {
            type string;
          }
          leaf sequence {
            tailf:cli-suppress-range;
            type uint8;
          }
          container match {
            leaf access-list {
              type string;
            }
          }
          container set {
            tailf:cli-compact-syntax;
            tailf:cli-sequence-commands {
              tailf:cli-reset-siblings;
            }
            leaf link-type {
              type string;
            }
            leaf link-name1 {
              tailf:cli-drop-node-name;
              type string;
            }
            leaf link-name2 {
              tailf:cli-drop-node-name;
              type string;
            }
            leaf link-name3 {
              tailf:cli-drop-node-name;
              type string;
            }
          }
        }
        list nai {
          key "name";
          leaf name {
            type string;
          }
          leaf network {
            type string;
          }
          leaf lma {
            type string;
          }
        }
      }
      list pmipv6-lma {
        key "name domain";
        leaf name {
          type string;
        }
        leaf domain {
          tailf:cli-expose-key-name;
          type string;
        }
        container address {
          list ipv4 {
            tailf:cli-suppress-mode;
            tailf:cli-delete-when-empty;
            key "address";
            leaf address {
              type inet:ipv4-address;
            }
          }
        }
        uses ipv6-mobile-pmipv6-mag-lma-grouping;
        container bce {
          leaf maximum {
            type uint32;
          }
        }
        container dynamic {
          container mag {
            leaf learning {
              type empty;
            }
          }
        }
        list network {
          key "name";
          leaf name {
            type string;
          }
          container pool {
            list ipv4 {
              tailf:cli-suppress-mode;
              tailf:cli-delete-when-empty;
              key "name";
              leaf name {
                type string;
              }
              leaf pfxlen {
                type uint8;
              }
            }
          }
          container mobile-network {
            list pool {
              tailf:cli-suppress-mode;
              tailf:cli-delete-when-empty;
              tailf:cli-compact-syntax;
              tailf:cli-sequence-commands {
                tailf:cli-reset-siblings;
              }
              key "address";
              leaf address {
                type inet:ipv4-address;
              }
              leaf pool-prefix {
                type uint8;
              }
              leaf network-prefix {
                type uint8;
              }
            }
          }
        }
      }
      list pmipv6-mag {
        key "name domain";
        leaf name {
          type string;
        }
        leaf domain {
          tailf:cli-expose-key-name;
          type string;
        }
        container tunnel-template {
          leaf Tunnel {
            tailf:cli-allow-join-with-value;
            type uint32;
          }
        }
        uses ipv6-mobile-pmipv6-mag-lma-grouping;
        container address {
          choice address-choice {
            leaf ipv4 {
              type inet:ipv4-address;
            }
            container dynamic {
              tailf:cli-add-mode;
              presence "true";
              container roaming {
                list interface {
                  tailf:cli-suppress-mode;
                  tailf:cli-delete-when-empty;
                  tailf:cli-compact-syntax;
                  tailf:cli-sequence-commands {
                    tailf:cli-reset-siblings;
                  }
                  key "name";
                  leaf name {
                    type string;
                  }
                  leaf egress-interface {
                    type string;
                  }
                  leaf priority {
                    type uint8;
                  }
                  leaf egress-att {
                    type enumeration {
                      enum "3G";
                      enum "ETHERNET";
                      enum "LTE";
                      enum "WLAN";
                    }
                  }
                  leaf label {
                    type string;
                  }
                }
              }
            }
          }
        }
        list interface {
          key "name";
          leaf name {
            type string;
          }
        }
        list lma {
          key "name domain";
          leaf name {
            type string;
          }
          leaf domain {
            type string;
          }
          list ipv4-address {
            tailf:cli-suppress-mode;
            tailf:cli-delete-when-empty;
            key "address";
            leaf address {
              type inet:ipv4-address;
            }
          }
          leaf encap {
            type enumeration {
              enum "gre-ipv4";
              enum "gre-ipv6";
              enum "ipv6-in-ipv6";
              enum "udptunnel";
            }
          }
        }
        list logical-mn {
          key "name";
          leaf name {
            type string;
          }
          container mobile {
            list network {
              tailf:cli-suppress-mode;
              tailf:cli-delete-when-empty;
              tailf:cli-compact-syntax;
              key "name";
              leaf name {
                type string;
              }
              leaf label {
                type string;
              }
            }
          }
          container reverse-tunnel {
            container route {
              list ipv4 {
                tailf:cli-suppress-mode;
                tailf:cli-delete-when-empty;
                key "prefix length";
                leaf prefix {
                  type inet:ipv4-address;
                }
                leaf length {
                  type uint8;
                }
                leaf metric {
                  tailf:cli-drop-node-name;
                  type uint8;
                }
              }
            }
          }
        }
      }
    }
  }

  grouping ipv6-pim-grouping {
    leaf rp-address {
      type inet:host;
    }
    list anycast-rp {
      tailf:cli-suppress-mode;
      tailf:cli-delete-when-empty;
      key "address peer";
      leaf address {
        type inet:host;
      }
      leaf peer {
        type inet:host;
      }
    }
    container rp {
      leaf no-embedded {
        type empty;
      }
    }
  }

  grouping ipv6-multicast-grouping {
    container rpf {
      container backoff {
        tailf:cli-compact-syntax;
        tailf:cli-sequence-commands {
          tailf:cli-reset-siblings;
        }
        leaf initial-delay {
          tailf:cli-drop-node-name;
          type uint16;
        }
        leaf max-delay {
          tailf:cli-drop-node-name;
          type uint16;
        }
      }
      leaf use-bgp {
        type empty;
      }
    }
    leaf group-range {
      type string;
    }
    container mpls {
      container source {
        uses interface-name-grouping;
      }
      leaf mldp {
        type empty;
      }
    }
  }

  grouping ipv6-mobile-pmipv6-mag-lma-grouping {
    container heartbeat {
      container interval {
        container default {
          tailf:cli-drop-node-name;
          tailf:cli-compact-syntax;
          tailf:cli-sequence-commands {
            tailf:cli-reset-siblings;
          }
          leaf periodicity {
            tailf:cli-drop-node-name;
            type uint16;
          }
          leaf retries {
            type uint16;
          }
          leaf natreboot {
            tailf:cli-optional-in-sequence;
            type empty;
          }
          leaf timeout {
            type uint16;
          }
        }
        list label-list {
          tailf:cli-drop-node-name;
          tailf:cli-suppress-mode;
          tailf:cli-delete-when-empty;
          tailf:cli-compact-syntax;
          tailf:cli-sequence-commands {
            tailf:cli-reset-siblings;
          }
          key "label";
          leaf periodicity {
            tailf:cli-drop-node-name;
            tailf:cli-prefix-key;
            type uint16;
          }
          leaf retries {
            tailf:cli-prefix-key;
            type uint16;
          }
          leaf label {
            tailf:cli-expose-key-name;
            type string;
          }
          leaf natreboot {
            tailf:cli-optional-in-sequence;
            type empty;
          }
          leaf timeout {
            type uint16;
          }
        }
      }
    }
    container replay-protection {
      container timestamp {
        leaf window {
          type union {
            type uint8;
            type enumeration {
              enum "ignore";
            }
          }
        }
      }
    }
  }

  container subscriber {
    leaf templating {
      type boolean;
    }
    list profile {
      key "name";
      leaf name {
        type string;
      }
      container pppoe {
        list service {
          tailf:cli-suppress-mode;
          tailf:cli-delete-when-empty;
          key "name";
          leaf name {
            type string;
          }
          leaf delay {
            type uint16;
          }
        }
      }
    }
  }
  container avc {
    container sd-service {
      tailf:cli-add-mode;
      presence "true";
      leaf segment {
        type string;
      }
      container controller {
        tailf:cli-add-mode;
        leaf address {
          tailf:cli-multi-value;
          type string;
        }
        container source-interface {
          uses interface-name-grouping;
        }
        leaf vrf {
          type string;
        }
      }
    }
  }
  container multilink {
    leaf virtual-template {
      type uint16;
    }
    leaf bundle-name {
      type enumeration {
        enum "authenticated";
        enum "both";
        enum "endpoint";
        enum "rfc";
      }
    }
  }
  container site-manager {
    tailf:cli-add-mode;
    presence "true";
    list vrf {
      key "name";
      leaf name {
        type string;
      }
      container border {
        tailf:cli-add-mode;
        presence "true";
        container source-interface {
          tailf:cli-compact-syntax;
          tailf:cli-sequence-commands {
            tailf:cli-reset-siblings;
          }
          leaf Loopback {
            tailf:cli-allow-join-with-value;
            type string;
          }
          leaf virtual-template {
            type uint16;
          }
        }
        leaf master {
          type union {
            type inet:ipv4-address;
            type enumeration {
              enum "local";
            }
          }
        }
      }
      container master {
        tailf:cli-add-mode;
        tailf:cli-sequence-commands;
        presence "true";
        leaf type {
          tailf:cli-drop-node-name;
          tailf:cli-hide-in-submode;
          type enumeration {
            enum "branch";
            enum "hub";
          }
        }
        container source-interface {
          tailf:cli-break-sequence-commands;
          leaf Loopback {
            tailf:cli-allow-join-with-value;
            type string;
          }
        }
        leaf hub {
          type inet:ipv4-address;
        }
        container policy {
          container group {
            container default {
              uses site-manager-policy-list-grouping;
            }
          }
          container local {
            uses site-manager-policy-list-grouping;
          }
        }
      }
    }
  }

  grouping site-manager-policy-list-grouping {
    list type {
      key "name";
      leaf name {
        type enumeration {
          enum "dca";
          enum "dia";
        }
      }
      list class {
        key "sequence";
        leaf name {
          tailf:cli-drop-node-name;
          tailf:cli-prefix-key;
          type string;
        }
        leaf sequence {
          tailf:cli-expose-key-name;
          type uint16;
        }
        container match {
          list app-group {
            tailf:cli-suppress-mode;
            tailf:cli-delete-when-empty;
            key "name";
            leaf name {
              type string;
            }
            leaf policy {
              type enumeration {
                enum "best-effort";
                enum "custom";
                enum "saas-dca";
              }
            }
          }
          list application {
            tailf:cli-suppress-mode;
            tailf:cli-delete-when-empty;
            key "name";
            leaf name {
              type string;
            }
            leaf policy {
              type enumeration {
                enum "best-effort";
                enum "custom";
                enum "saas-dca";
              }
            }
          }
        }
        uses domain-path-preference-grouping;
      }
    }
  }

  list dapr {
    key "name";
    leaf name {
      type string;
    }
    container route-manager {
      tailf:cli-add-mode;
      presence "true";
      container source-interface {
        leaf Loopback {
          tailf:cli-allow-join-with-value;
          type string;
        }
      }
      container authentication {
        container password {
          tailf:cli-compact-syntax;
          tailf:cli-sequence-commands;
          leaf type {
            tailf:cli-drop-node-name;
            tailf:cli-optional-in-sequence;
            type enumeration {
              enum "0";
              enum "4";
            }
          }
          leaf secret {
            tailf:cli-drop-node-name;
            type string;
          }
        }
      }
      container link-thresholds {
        tailf:cli-add-mode;
        leaf max-utilization {
          type uint8;
        }
        leaf min-bandwidth {
          type uint32;
        }
      }
      container border-routers {
        tailf:cli-add-mode;
        list address-list {
          tailf:cli-drop-node-name;
          tailf:cli-suppress-mode;
          tailf:cli-delete-when-empty;
          ordered-by user;
          key "address";
          leaf address {
            type inet:ipv4-address;
          }
        }
      }
      container class {
        container bypass-class {
          tailf:cli-drop-node-name;
          tailf:cli-sequence-commands;
          tailf:cli-add-mode;
          presence "true";
          leaf name {
            tailf:cli-drop-node-name;
            tailf:cli-hide-in-submode;
            type string;
          }
          leaf type {
            tailf:cli-hide-in-submode;
            type enumeration {
              enum "bypass";
            }
          }
          container match {
            tailf:cli-break-sequence-commands;
            leaf access-list {
              type string;
            }
          }
        }
      }
      leaf shutdown {
        type empty;
      }
    }
    container border-router {
      tailf:cli-add-mode;
      presence "true";
      container source-interface {
        leaf Loopback {
          tailf:cli-allow-join-with-value;
          type string;
        }
      }
      leaf route-manager {
        type inet:ipv4-address;
      }
      container authentication {
        container password {
          tailf:cli-compact-syntax;
          tailf:cli-sequence-commands;
          leaf type {
            tailf:cli-drop-node-name;
            tailf:cli-optional-in-sequence;
            type enumeration {
              enum "0";
              enum "4";
            }
          }
          leaf secret {
            tailf:cli-drop-node-name;
            type string;
          }
        }
      }
      leaf shutdown {
        type empty;
      }
    }
  }
  container flow {
    list exporter {
      key "name";
      leaf name {
        type string;
      }
      leaf description {
        tailf:cli-multi-value;
        type string;
      }
      container destination {
        tailf:cli-compact-syntax;
        tailf:cli-sequence-commands {
          tailf:cli-reset-siblings;
        }
        tailf:cli-case-insensitive;
        leaf address {
          tailf:cli-drop-node-name;
          type inet:host;
        }
        leaf vrf {
          type string;
        }
      }
      container source {
        uses interface-name-grouping;
      }
      leaf mtu {
        type uint16;
      }
      leaf ttl {
        type uint8;
      }
      leaf dscp {
        type uint8;
      }
      container transport {
        leaf udp {
          type uint16;
        }
      }
      leaf export-protocol {
        type enumeration {
          enum "ipfix";
          enum "netflow-v5";
          enum "netflow-v9";
        }
      }
      container template {
        container data {
          leaf timeout {
            type uint32;
          }
        }
      }
      container option {
        container interface-table {
          presence "true";
          leaf timeout {
            type uint32;
          }
        }
        container exporter-stats {
          presence "true";
          leaf timeout {
            type uint32;
          }
        }
        container vrf-table {
          presence "true";
          leaf timeout {
            type uint32;
          }
        }
        container vrf-attributes {
          presence "true";
          leaf timeout {
            type uint32;
          }
        }
        container sampler-table {
          presence "true";
          leaf timeout {
            type uint32;
          }
        }
        container c3pl-class-table {
          presence "true";
          leaf timeout {
            type uint32;
          }
        }
        container c3pl-policy-table {
          presence "true";
          leaf timeout {
            type uint32;
          }
        }
        container application-attributes {
          presence "true";
          leaf timeout {
            type uint32;
          }
        }
        container application-table {
          presence "true";
          leaf timeout {
            type uint32;
          }
        }
        container sub-application-table {
          presence "true";
          leaf timeout {
            type uint32;
          }
        }
      }
    }
    list record {
      key "name";
      leaf name {
        type string;
      }
      leaf type {
        tailf:cli-prefix-key;
        type enumeration {
          enum "mace";
          enum "performance-monitor";
        }
      }
      leaf description {
        tailf:cli-multi-value;
        type string;
      }
      container match {
        container routing {
          container source {
            container as-peer {
              tailf:cli-drop-node-name;
              container as {
                leaf peer {
                  type empty;
                }
              }
            }
            container as {
              tailf:cli-delete-when-empty;
              presence "true";
              leaf four-octet {
                tailf:alt-name "4-octet";
                type empty;
              }
            }
            leaf traffic-index {
              type empty;
            }
          }
          container destination {
            container as-peer {
              tailf:cli-drop-node-name;
              container as {
                leaf peer {
                  type empty;
                }
              }
            }
            container as {
              tailf:cli-delete-when-empty;
              presence "true";
              leaf four-octet {
                tailf:alt-name "4-octet";
                type empty;
              }
            }
            leaf traffic-index {
              type empty;
            }
          }
          container forwarding-status {
            tailf:cli-delete-when-empty;
            presence "true";
            leaf reason {
              type empty;
            }
          }
          container vrf {
            leaf service {
              type empty;
            }
            leaf input {
              type empty;
            }
            leaf output {
              type empty;
            }
          }
          container pw {
            container destination {
              leaf address {
                type empty;
              }
            }
          }
          container next-hop {
            container address {
              container ipv4-bgp {
                tailf:cli-drop-node-name;
                container ipv4 {
                  leaf bgp {
                    type empty;
                  }
                }
              }
              leaf ipv4 {
                type empty;
              }
              leaf ipv6 {
                type empty;
              }
            }
          }
        }
        container ipv4 {
          leaf tos {
            type empty;
          }
          leaf id {
            type empty;
          }
          leaf ttl {
            type empty;
          }
          leaf version {
            type empty;
          }
          leaf protocol {
            type empty;
          }
          container source {
            leaf address {
              type empty;
            }
            container prefix {
              presence "true";
              leaf minimum-mask {
                type uint8;
              }
            }
            container mask {
              presence "true";
              leaf minimum-mask {
                type uint8;
              }
            }
          }
          container destination {
            leaf address {
              type empty;
            }
            leaf mask {
              type empty;
            }
          }
          leaf precedence {
            type empty;
          }
          leaf dscp {
            type empty;
          }
        }
        container ipv6 {
          leaf version {
            type empty;
          }
          leaf traffic-class {
            type empty;
          }
          leaf precedence {
            type empty;
          }
          leaf dscp {
            type empty;
          }
          leaf protocol {
            type empty;
          }
          container source {
            leaf address {
              type empty;
            }
            container prefix {
              presence "true";
            }
          }
          container destination {
            leaf address {
              type empty;
            }
            container prefix {
              presence "true";
            }
          }
        }
        container mpls {
          list label {
            tailf:cli-suppress-mode;
            tailf:cli-delete-when-empty;
            key "id";
            leaf id {
              type uint8;
            }
            leaf exp {
              type empty;
            }
            leaf details {
              type empty;
            }
            leaf ttl {
              type empty;
            }
            leaf type {
              type empty;
            }
          }
        }
        container connection {
          leaf id {
            type empty;
          }
          leaf transaction-id {
            type empty;
          }
          container client {
            container ipv4 {
              leaf address {
                type empty;
              }
            }
            container ipv6 {
              leaf address {
                type empty;
              }
            }
            container transport {
              leaf port {
                type empty;
              }
            }
          }
          container server {
            container ipv4 {
              leaf address {
                type empty;
              }
            }
            container ipv6 {
              leaf address {
                type empty;
              }
            }
            container transport {
              leaf port {
                type empty;
              }
            }
          }
        }
        container timestamp {
          container absolute {
            container monitoring-interval {
              leaf start {
                type empty;
              }
            }
          }
        }
        container policy {
          container qos {
            container classification {
              leaf hierarchy {
                type empty;
              }
            }
            container queue {
              leaf drops {
                type empty;
              }
              leaf index {
                type empty;
              }
            }
          }
        }
        container datalink {
          container mac {
            container source {
              container address {
                leaf input {
                  type empty;
                }
                leaf output {
                  type empty;
                }
              }
            }
            container destination {
              container address {
                leaf input {
                  type empty;
                }
                leaf output {
                  type empty;
                }
              }
            }
          }
          container vlan {
            leaf input {
              type empty;
            }
            leaf output {
              type empty;
            }
          }
        }
        container transport {
          leaf source-port {
            type empty;
          }
          leaf destination-port {
            type empty;
          }
          container rtp {
            leaf ssrc {
              type empty;
            }
          }
          container tcp {
            leaf destination-port {
              type empty;
            }
            leaf source-port {
              type empty;
            }
            choice flags-choice {
              container flags-cont {
                tailf:cli-drop-node-name;
                container flags {
                  leaf-list flag {
                    tailf:cli-drop-node-name;
                    tailf:cli-flat-list-syntax;
                    type enumeration {
                      enum "ack";
                      enum "cwr";
                      enum "ece";
                      enum "fin";
                      enum "psh";
                      enum "rst";
                      enum "syn";
                      enum "urg";
                    }
                  }
                }
              }
              leaf flags {
                type empty;
              }
            }
          }
          container udp {
            leaf destination-port {
              type empty;
            }
            leaf source-port {
              type empty;
            }
          }
          container icmp {
            container ipv4 {
              leaf type {
                type empty;
              }
              leaf code {
                type empty;
              }
            }
          }
        }
        container interface {
          container input {
            presence "true";
            leaf snmp {
              type empty;
            }
          }
          container output {
            presence "true";
            leaf snmp {
              type empty;
            }
          }
        }
        container flow {
          leaf direction {
            type empty;
          }
          container sampler {
            presence "true";
            container hash {
              leaf digest-value {
                type empty;
              }
            }
          }
          container observation {
            leaf point {
              type empty;
            }
          }
        }
        container application {
          container name {
            tailf:cli-delete-when-empty;
            presence "true";
            leaf account-on-resolution {
              type empty;
            }
          }
        }
        container services {
          container waas {
            container segment {
              leaf account-on-resolution {
                type empty;
              }
            }
          }
        }
      }
      container collect {
        container routing {
          container source {
            container as {
              tailf:cli-compact-syntax;
              tailf:cli-delete-when-empty;
              presence "true";
              leaf peer {
                type empty;
              }
              leaf four-octet {
                tailf:alt-name "4-octet";
                type empty;
              }
            }
          }
          container destination {
            container as {
              tailf:cli-compact-syntax;
              tailf:cli-delete-when-empty;
              presence "true";
              leaf peer {
                type empty;
              }
              leaf four-octet {
                tailf:alt-name "4-octet";
                type empty;
              }
            }
          }
          container vrf {
            leaf input {
              type empty;
            }
            leaf output {
              type empty;
            }
          }
          container next-hop {
            container address {
              container ipv4 {
                presence "true";
              }
              container ipv4-bgp {
                tailf:cli-drop-node-name;
                container ipv4 {
                  leaf bgp {
                    type empty;
                  }
                }
              }
              container ipv6 {
                presence "true";
              }
              container ipv6-bgp {
                tailf:cli-drop-node-name;
                container ipv6 {
                  leaf bgp {
                    type empty;
                  }
                }
              }
            }
          }
          container forwarding-status {
            presence "true";
          }
          leaf is-multicast {
            type empty;
          }
        }
        container mpls {
          container label {
            container one {
              tailf:alt-name "1";
              leaf exp {
                type empty;
              }
              leaf type {
                type empty;
              }
              leaf ttl {
                type empty;
              }
              leaf details {
                type empty;
              }
            }
          }
        }
        container ipv4 {
          leaf dscp {
            type empty;
          }
          container dscp-cont {
            tailf:cli-drop-node-name;
            container dscp {
              leaf output {
                type empty;
              }
            }
          }
          leaf protocol {
            type empty;
          }
          leaf tos {
            type empty;
          }
          leaf id {
            type empty;
          }
          leaf total-length {
            type empty;
          }
          container total-length-min-max {
            tailf:cli-drop-node-name;
            container total-length {
              leaf minimum {
                type empty;
              }
              leaf maximum {
                type empty;
              }
            }
          }
          container ttl {
            presence "true";
          }
          container ttl-min-max {
            tailf:cli-drop-node-name;
            container ttl {
              leaf minimum {
                type empty;
              }
              leaf maximum {
                type empty;
              }
            }
          }
          container section {
            container header {
              leaf size {
                type uint16;
              }
            }
            container payload {
              leaf size {
                type uint16;
              }
            }
          }
          container source {
            container mask {
              presence "true";
            }
            container prefix {
              presence "true";
            }
          }
          container destination {
            container mask {
              presence "true";
            }
          }
          container fragmentation {
            leaf flags {
              type empty;
            }
            leaf offset {
              type empty;
            }
          }
        }
        container ipv6 {
          leaf traffic-class {
            type empty;
          }
          leaf dscp {
            type empty;
          }
          container source {
            leaf address {
              type empty;
            }
            container mask {
              presence "true";
            }
            container prefix {
              presence "true";
            }
          }
          leaf flow-label {
            type empty;
          }
          container destination {
            leaf address {
              type empty;
            }
            container mask {
              presence "true";
            }
            container prefix {
              presence "true";
            }
          }
          container fragmentation {
            leaf flags {
              type empty;
            }
            leaf id {
              type empty;
            }
            leaf offset {
              type empty;
            }
          }
          leaf next-header {
            type empty;
          }
        }
        container transport {
          container packets {
            container expected {
              leaf counter {
                type empty;
              }
            }
            container lost {
              container counter {
                presence "true";
              }
              container rate {
                presence "true";
              }
            }
          }
          leaf destination-port {
            type empty;
          }
          leaf source-port {
            type empty;
          }
          container round-trip-time {
            presence "true";
          }
          container event {
            container packet-loss {
              container counter {
                presence "true";
              }
            }
          }
          container icmp {
            container ipv4 {
              leaf type {
                type empty;
              }
              leaf code {
                type empty;
              }
            }
          }
          container tcp {
            container flags {
              presence "true";
            }
          }
          container rtp {
            leaf payload-type {
              type empty;
            }
            container jitter {
              container mean {
                presence "true";
              }
              container mean-sum {
                tailf:cli-drop-node-name;
                container mean {
                  leaf sum {
                    type empty;
                  }
                }
              }
              container minimum {
                presence "true";
              }
              container maximum {
                presence "true";
              }
            }
            container flow {
              leaf count {
                type empty;
              }
            }
          }
        }
        container interface {
          leaf input {
            type empty;
          }
          leaf output {
            type empty;
          }
          container output-snmp {
            tailf:cli-drop-node-name;
            container output {
              leaf snmp {
                type empty;
              }
            }
          }
          container output-physical-snmp {
            tailf:cli-drop-node-name;
            container output {
              container physical {
                leaf snmp {
                  type empty;
                }
              }
            }
          }
        }
        container flow {
          leaf sampler {
            type empty;
          }
          leaf direction {
            type empty;
          }
        }
        container counter {
          container bytes {
            tailf:cli-delete-when-empty;
            presence "true";
            container layer2 {
              leaf long {
                type empty;
              }
            }
            leaf long {
              type empty;
            }
            container rate {
              presence "true";
            }
          }
          container packets {
            tailf:cli-delete-when-empty;
            presence "true";
            leaf long {
              type empty;
            }
            container dropped {
              presence "true";
            }
          }
          leaf flows {
            type empty;
          }
        }
        container timestamp {
          container interval {
            presence "true";
          }
          container sys-uptime {
            leaf first {
              type empty;
            }
            leaf last {
              type empty;
            }
          }
          container absolute {
            leaf first {
              type empty;
            }
            leaf last {
              type empty;
            }
          }
        }
        container datalink {
          container mac {
            container source {
              container address {
                leaf input {
                  type empty;
                }
                leaf output {
                  type empty;
                }
              }
            }
            container destination {
              container address {
                leaf input {
                  type empty;
                }
                leaf output {
                  type empty;
                }
              }
            }
          }
          leaf source-vlan-id {
            type empty;
          }
        }
        container application {
          container media {
            container bytes {
              container counter {
                presence "true";
              }
              container rate {
                presence "true";
              }
            }
            container packets {
              container counter {
                presence "true";
              }
              container rate {
                presence "true";
              }
            }
            container event {
              presence "true";
            }
          }
          container name {
            presence "true";
          }
          container http {
            leaf host {
              type empty;
            }
            container uri {
              leaf statistics {
                type empty;
              }
            }
          }
          container ssl {
            leaf common-name {
              type empty;
            }
          }
          container sip {
            leaf server {
              type empty;
            }
          }
        }
        container monitor {
          container event {
            presence "true";
          }
        }
        container connection {
          leaf initiator {
            type empty;
          }
          leaf new-connections {
            type empty;
          }
          leaf sum-duration {
            type empty;
          }
          container server {
            container counter {
              leaf responses {
                type empty;
              }
              container packets {
                leaf long {
                  type empty;
                }
              }
              container bytes {
                leaf long {
                  type empty;
                }
                container network {
                  leaf long {
                    type empty;
                  }
                }
              }
            }
            container ipv4 {
              leaf address {
                type empty;
              }
            }
            container transport {
              leaf port {
                type empty;
              }
            }
          }
          container delay {
            container response {
              container to-server {
                container histogram {
                  leaf bucket1 {
                    type empty;
                  }
                  leaf bucket2 {
                    type empty;
                  }
                  leaf bucket3 {
                    type empty;
                  }
                  leaf bucket4 {
                    type empty;
                  }
                  leaf bucket5 {
                    type empty;
                  }
                  leaf bucket6 {
                    type empty;
                  }
                  leaf bucket7 {
                    type empty;
                  }
                  leaf late {
                    type empty;
                  }
                }
                leaf sum {
                  type empty;
                }
              }
              container client-to-server {
                leaf sum {
                  type empty;
                }
              }
            }
            container network {
              container to-server {
                leaf sum {
                  type empty;
                }
              }
              container to-client {
                leaf sum {
                  type empty;
                }
              }
              container client-to-server {
                leaf sum {
                  type empty;
                }
              }
            }
            container application {
              leaf sum {
                type empty;
              }
              leaf max {
                type empty;
              }
            }
          }
          container transaction {
            container counter {
              leaf complete {
                type empty;
              }
            }
            container duration {
              leaf sum {
                type empty;
              }
            }
          }
          container client {
            container counter {
              container packets {
                leaf retransmitted {
                  type empty;
                }
                leaf long {
                  type empty;
                }
              }
              container bytes {
                leaf long {
                  type empty;
                }
                container network {
                  leaf long {
                    type empty;
                  }
                }
              }
            }
            container ipv4 {
              leaf address {
                type empty;
              }
            }
            container transport {
              leaf port {
                type empty;
              }
            }
          }
        }
        container policy {
          container qos {
            container queue {
              leaf drops {
                type empty;
              }
              leaf index {
                type empty;
              }
            }
            container classification {
              leaf hierarchy {
                type empty;
              }
            }
          }
        }
        container services {
          container waas {
            leaf segment {
              type empty;
            }
            leaf passthrough-reason {
              type empty;
            }
          }
        }
      }
    }
    list monitor {
      key "name";
      leaf name {
        type string;
      }
      leaf type {
        tailf:cli-prefix-key;
        type enumeration {
          enum "mace";
          enum "performance-monitor";
        }
      }
      leaf description {
        tailf:cli-multi-value;
        type string;
      }
      container statistics {
        container packet {
          leaf protocol {
            type empty;
          }
          leaf size {
            type empty;
          }
        }
      }
      leaf record {
        type string;
      }
      container record-netflow {
        tailf:cli-drop-node-name;
        container record {
          container netflow {
            tailf:cli-compact-syntax;
            tailf:cli-sequence-commands {
              tailf:cli-reset-siblings;
            }
            leaf protocol {
              tailf:cli-drop-node-name;
              type enumeration {
                enum "ipv4";
                enum "ipv6";
              }
            }
            choice original-choice {
              leaf original-input {
                type empty;
              }
              leaf original-output {
                type empty;
              }
              leaf prefix {
                type empty;
              }
            }
            leaf peer {
              type empty;
            }
          }
        }
      }
      list exporter {
        tailf:cli-suppress-mode;
        tailf:cli-delete-when-empty;
        key "name";
        leaf name {
          type string;
        }
      }
      container cache {
        container timeout {
          leaf inactive {
            type uint32;
          }
          leaf active {
            type uint32;
          }
          leaf update {
            type uint32;
          }
          container synchronized {
            tailf:cli-compact-syntax;
            tailf:cli-sequence-commands {
              tailf:cli-reset-siblings;
            }
            leaf value {
              tailf:cli-drop-node-name;
              type uint32;
            }
            leaf export-spread {
              type uint8;
            }
          }
          container event {
            leaf transaction-end {
              type empty;
            }
          }
        }
        leaf type {
          type enumeration {
            enum "immediate";
            enum "normal";
            enum "permanent";
            enum "synchronized";
          }
        }
        leaf entries {
          type uint32;
        }
      }
      container history {
        leaf size {
          type uint8;
        }
      }
    }
  }
  list sampler {
    key "name";
    leaf name {
      type string;
    }
    container mode {
      tailf:cli-compact-syntax;
      tailf:cli-sequence-commands;
      leaf value {
        tailf:cli-drop-node-name;
        type enumeration {
          enum "deterministic";
          enum "random";
        }
      }
      leaf packets {
        tailf:cli-drop-node-name;
        type uint8;
      }
      leaf out-of {
        type uint16;
      }
    }
    leaf granularity {
      type enumeration {
        enum "connection";
        enum "packet";
      }
    }
  }
  list domain {
    key "name";
    leaf name {
      type string;
    }
    list vrf {
      key "name";
      leaf name {
        type string;
      }
      uses domain-master-grouping;
      uses domain-border-grouping {
        augment "border" {
          container advanced {
            tailf:cli-add-mode;
            leaf monitor-cache-percent {
              type uint8;
            }
          }
        }
      }
    }
    uses domain-master-grouping {
      refine "master";
    }
    uses domain-border-grouping {
      refine "border";
      refine "border/password/secret";
      augment "border" {
        container advanced {
          tailf:cli-add-mode;
          presence "true";
          uses domain-advanced-smart-probes-grouping;
        }
      }
    }
  }
  container archive {
    tailf:cli-add-mode;
    container log {
      container config {
        tailf:cli-add-mode;
        container logging {
          leaf enable {
            type empty;
          }
          leaf size {
            type uint16;
          }
        }
        leaf hidekeys {
          type empty;
        }
        container notify {
          container syslog {
            tailf:cli-delete-when-empty;
            presence "true";
            leaf contenttype {
              type enumeration {
                enum "plaintext";
                enum "xml";
              }
            }
          }
        }
        container record {
          leaf rc {
            type empty;
          }
        }
      }
    }
    leaf path {
      type string;
    }
    leaf maximum {
      type uint8;
    }
    leaf write-memory {
      type empty;
    }
    leaf time-period {
      type uint32;
    }
  }
  container file {
    leaf privilege {
      type uint8;
    }
    leaf prompt {
      type enumeration {
        enum "alert";
        enum "noisy";
        enum "quiet";
      }
    }
    leaf verify {
      type enumeration {
        enum "auto";
      }
    }
  }
  container object-group {
    list network {
      key "name";
      leaf name {
        type string;
      }
      leaf description {
        tailf:cli-multi-value;
        type string;
      }
      list host {
        tailf:cli-suppress-mode;
        tailf:cli-delete-when-empty;
        key "name";
        leaf name {
          type inet:host;
        }
      }
      list subnet {
        tailf:cli-drop-node-name;
        tailf:cli-suppress-mode;
        tailf:cli-delete-when-empty;
        key "network-address network-mask";
        leaf network-address {
          type inet:ipv4-address;
        }
        leaf network-mask {
          type inet:ipv4-address;
        }
      }
    }
    list service {
      key "name";
      leaf name {
        type string;
      }
      leaf description {
        tailf:cli-multi-value;
        type string;
      }
      leaf-list protocol {
        tailf:cli-drop-node-name;
        type union {
          type uint8;
          type enumeration {
            enum "icmp" {
              value 1;
            }
            enum "tcp" {
              value 6;
            }
            enum "udp" {
              value 17;
            }
            enum "esp" {
              value 50;
            }
          }
        }
      }
      container icmp-options {
        tailf:cli-drop-node-name;
        container icmp {
          list match {
            tailf:cli-drop-node-name;
            tailf:cli-suppress-mode;
            tailf:cli-delete-when-empty;
            key "port";
            leaf port {
              type object-group-service-icmp-type;
            }
            uses object-group-service-protocol-match;
          }
          list range {
            tailf:cli-suppress-mode;
            tailf:cli-delete-when-empty;
            key "begin end";
            leaf begin {
              type object-group-service-icmp-type;
            }
            leaf end {
              type object-group-service-icmp-type;
            }
          }
        }
      }
      container udp-options {
        tailf:cli-drop-node-name;
        container udp {
          list match {
            tailf:cli-drop-node-name;
            tailf:cli-suppress-mode;
            tailf:cli-delete-when-empty;
            key "port";
            leaf port {
              type object-group-service-udp-type;
            }
            uses object-group-service-protocol-match;
          }
          list range {
            tailf:cli-suppress-mode;
            tailf:cli-delete-when-empty;
            key "begin end";
            leaf begin {
              type object-group-service-udp-type;
            }
            leaf end {
              type object-group-service-udp-type;
            }
          }
        }
      }
      container tcp-options {
        tailf:cli-drop-node-name;
        container tcp {
          list match {
            tailf:cli-drop-node-name;
            tailf:cli-suppress-mode;
            tailf:cli-delete-when-empty;
            key "port";
            leaf port {
              type object-group-service-tcp-type;
            }
            uses object-group-service-protocol-match;
          }
          list range {
            tailf:cli-suppress-mode;
            tailf:cli-delete-when-empty;
            key "begin end";
            leaf begin {
              type object-group-service-tcp-type;
            }
            leaf end {
              type object-group-service-tcp-type;
            }
          }
        }
      }
      container tcp-udp {
        list match {
          tailf:cli-drop-node-name;
          tailf:cli-suppress-mode;
          tailf:cli-delete-when-empty;
          key "port";
          leaf port {
            type object-group-service-tcp-udp-type;
          }
          uses object-group-service-protocol-match;
        }
        list range {
          tailf:cli-suppress-mode;
          tailf:cli-delete-when-empty;
          key "begin end";
          leaf begin {
            type object-group-service-tcp-udp-type;
          }
          leaf end {
            type object-group-service-tcp-udp-type;
          }
        }
      }
    }
    list security {
      key "name";
      leaf name {
        type string;
      }
      leaf description {
        tailf:cli-multi-value;
        type string;
      }
    }
    container ip {
      list address {
        key "name";
        leaf name {
          type string;
        }
        list host-info {
          tailf:cli-suppress-mode;
          tailf:cli-delete-when-empty;
          key "name";
          leaf name {
            type inet:host;
          }
        }
        list subnet {
          tailf:cli-drop-node-name;
          tailf:cli-suppress-mode;
          tailf:cli-delete-when-empty;
          key "network-address network-mask";
          leaf network-address {
            type inet:ipv4-address;
          }
          leaf network-mask {
            type inet:ipv4-address;
          }
        }
      }
      list port {
        key "name";
        leaf name {
          type string;
        }
        list entry {
          tailf:cli-drop-node-name;
          tailf:cli-suppress-mode;
          tailf:cli-delete-when-empty;
          key "match";
          leaf match {
            tailf:cli-multi-word-key;
            tailf:cli-suppress-range;
            type string;
          }
        }
      }
    }
  }
  container key {
    container config-key {
      leaf password-encrypt {
        type tailf:aes-cfb-128-encrypted-string;
      }
    }
    list chain {
      key "name";
      leaf name {
        type string;
      }
      uses description-grouping;
      list key {
        key "id";
        leaf id {
          type uint32;
        }
        container key-string {
          tailf:cli-compact-syntax;
          tailf:cli-sequence-commands {
            tailf:cli-reset-siblings;
          }
          uses password-grouping {
            refine "secret";
          }
        }
        leaf cryptographic-algorithm {
          type enumeration {
            enum "hmac-sha-1";
            enum "hmac-sha-256";
            enum "hmac-sha-384";
            enum "hmac-sha-512";
            enum "md5";
          }
        }
        container accept-lifetime {
          tailf:cli-compact-syntax;
          tailf:cli-sequence-commands {
            tailf:cli-reset-siblings;
          }
          choice accept-lifetime-choice {
            case global {
              uses lifetime-grouping;
            }
            container local {
              tailf:cli-compact-syntax;
              tailf:cli-sequence-commands {
                tailf:cli-reset-siblings;
              }
              uses lifetime-grouping;
            }
          }
        }
        container send-lifetime {
          tailf:cli-compact-syntax;
          tailf:cli-sequence-commands {
            tailf:cli-reset-siblings;
          }
          choice send-lifetime-choice {
            case global {
              uses lifetime-grouping;
            }
            container local {
              tailf:cli-compact-syntax;
              tailf:cli-sequence-commands {
                tailf:cli-reset-siblings;
              }
              uses lifetime-grouping;
            }
          }
        }
      }
    }
    container tcp {
      tailf:cli-drop-node-name;
      list chain {
        key "name";
        leaf name {
          type string;
        }
        leaf tcp {
          tailf:cli-hide-in-submode;
          type empty;
        }
        uses description-grouping;
        list key {
          key "id";
          leaf id {
            type uint32;
          }
          container key-string {
            tailf:cli-compact-syntax;
            tailf:cli-sequence-commands {
              tailf:cli-reset-siblings;
            }
            uses password-grouping {
              refine "secret";
            }
          }
          leaf send-id {
            type uint8;
          }
          leaf recv-id {
            type uint8;
          }
          leaf include-tcp-options {
            type empty;
          }
          leaf cryptographic-algorithm {
            type enumeration {
              enum "hmac-sha-1";
              enum "hmac-sha-256";
              enum "aes-128-cmac";
            }
          }
          container accept-lifetime {
            tailf:cli-compact-syntax;
            tailf:cli-sequence-commands {
              tailf:cli-reset-siblings;
            }
            choice accept-lifetime-choice {
              case global {
                uses lifetime-grouping;
              }
              container local {
                tailf:cli-compact-syntax;
                tailf:cli-sequence-commands {
                  tailf:cli-reset-siblings;
                }
                uses lifetime-grouping;
              }
            }
          }
          container send-lifetime {
            tailf:cli-compact-syntax;
            tailf:cli-sequence-commands {
              tailf:cli-reset-siblings;
            }
            choice send-lifetime-choice {
              case global {
                uses lifetime-grouping;
              }
              container local {
                tailf:cli-compact-syntax;
                tailf:cli-sequence-commands {
                  tailf:cli-reset-siblings;
                }
                uses lifetime-grouping;
              }
            }
          }
        }
      }
    }
    container macsec {
      tailf:cli-drop-node-name;
      list chain {
        key "name";
        leaf name {
          type string;
        }
        leaf macsec {
          tailf:cli-hide-in-submode;
          type empty;
        }
        uses description-grouping;
        list key {
          key "id";
          leaf id {
            type string;
          }
          leaf cryptographic-algorithm {
            type enumeration {
              enum "aes-128-cmac";
              enum "aes-256-cmac";
            }
          }
          container key-string {
            tailf:cli-compact-syntax;
            tailf:cli-sequence-commands {
              tailf:cli-reset-siblings;
            }
            uses password-grouping {
              refine "secret";
            }
          }
          container lifetime {
            tailf:cli-compact-syntax;
            tailf:cli-sequence-commands {
              tailf:cli-reset-siblings;
            }
            choice accept-lifetime-choice {
              case global {
                uses lifetime-grouping;
              }
              container local {
                tailf:cli-compact-syntax;
                tailf:cli-sequence-commands {
                  tailf:cli-reset-siblings;
                }
                uses lifetime-grouping;
              }
            }
          }
        }
      }
    }
  }
  container fips {
    leaf authorization-key {
      type string;
    }
  }
  container modemcap {
    list entry {
      tailf:cli-suppress-mode;
      tailf:cli-delete-when-empty;
      key "line";
      leaf line {
        tailf:cli-multi-word-key;
        type string;
      }
    }
  }
  container flowspec {
    tailf:cli-add-mode;
    presence "true";
    container local-install {
      leaf interface-all {
        type empty;
      }
    }
    container address-family {
      container ipv4 {
        tailf:cli-add-mode;
        container local-install {
          leaf interface-all {
            type empty;
          }
        }
      }
      container ipv6 {
        tailf:cli-add-mode;
        container local-install {
          leaf interface-all {
            type empty;
          }
        }
      }
    }
    list vrf {
      key "name";
      leaf name {
        type string;
      }
      container address-family {
        container ipv4 {
          tailf:cli-add-mode;
          container local-install {
            leaf interface-all {
              type empty;
            }
          }
        }
        container ipv6 {
          tailf:cli-add-mode;
          container local-install {
            leaf interface-all {
              type empty;
            }
          }
        }
      }
    }
  }
  list acr {
    tailf:cli-suppress-mode;
    tailf:cli-delete-when-empty;
    tailf:cli-compact-syntax;
    key "id";
    leaf id {
      type uint8;
    }
    leaf type {
      type enumeration {
        enum "ATM";
        enum "CH-OC3";
        enum "CHOCX-OC3";
        enum "CHOCX-OC12";
        enum "CHOCX-OC48";
        enum "CHOCX-OC192";
        enum "STM1";
        enum "STM4";
        enum "STM16";
        enum "STM64";
      }
    }
  }
  list service-template {
    key "name";
    leaf name {
      type string;
    }
    list access-group {
      tailf:cli-suppress-mode;
      tailf:cli-delete-when-empty;
      key "name";
      leaf name {
        type string;
      }
    }
    leaf inactivity-timer {
      type uint16;
    }
    container linksec {
      leaf policy {
        type enumeration {
          enum "must-not-secure";
          enum "should-secure";
          enum "must-secure";
        }
      }
    }
    container voice {
      leaf vlan {
        type empty;
      }
    }
    leaf vlan {
      type uint16;
    }
  }
  container issu {
    container set {
      leaf rollback-timer {
        type union {
          type uint16;
          type string;
        }
      }
    }
  }
  list username {
    tailf:cli-suppress-mode;
    tailf:cli-delete-when-empty;
    tailf:cli-compact-syntax;
    key "name";
    leaf name {
      tailf:cli-suppress-range;
      type string;
    }
    leaf privilege {
      type uint8;
    }
    leaf common-criteria-policy {
      type string;
    }
    leaf view {
      type string;
    }
    leaf algorithm-type {
      type enumeration {
        enum "md5";
        enum "scrypt";
        enum "sha256";
      }
    }
    container password {
      tailf:cli-flatten-container;
      tailf:cli-compact-syntax;
      tailf:cli-sequence-commands {
        tailf:cli-reset-siblings;
      }
      leaf type {
        tailf:cli-drop-node-name;
        tailf:cli-optional-in-sequence;
        type enumeration {
          enum "0";
          enum "5";
          enum "6";
          enum "7";
        }
      }
      leaf secret {
        tailf:cli-drop-node-name;
        type string;
      }
    }
    container secret {
      tailf:cli-flatten-container;
      tailf:cli-compact-syntax;
      tailf:cli-sequence-commands {
        tailf:cli-reset-siblings;
      }
      leaf type {
        tailf:cli-optional-in-sequence;
        tailf:cli-drop-node-name;
        type enumeration {
          enum "0";
          enum "4";
          enum "5";
          enum "8";
          enum "9";
        }
      }
      leaf secret {
        tailf:cli-drop-node-name;
        type string;
      }
    }
    container autocommand {
      leaf command {
        tailf:cli-drop-node-name;
        tailf:cli-multi-value;
        type string;
      }
    }
  }
  list table-map {
    key "name";
    leaf name {
      type string;
    }
    container map {
      list from {
        tailf:cli-suppress-mode;
        tailf:cli-delete-when-empty;
        key "id";
        leaf id {
          type uint8;
        }
        leaf to {
          type uint8;
        }
      }
    }
    leaf default {
      type union {
        type uint8;
        type enumeration {
          enum "copy";
          enum "ignore";
        }
      }
    }
  }
  container sdm {
    container prefer {
      tailf:cli-delete-when-empty;
      presence "true";
      leaf disable_qos_scale {
        type empty;
      }
      leaf disable_8k_efp {
        type empty;
      }
      leaf disable_acl_copp {
        type empty;
      }
      leaf disable_color_blind_policer {
        type empty;
      }
      leaf disable_tdm_to_ip_iw {
        type empty;
      }
      leaf disable_l2pt_fwd_all {
        type empty;
      }
      leaf disable_multicast_stats {
        type empty;
      }
      leaf disable_bdi_mtu {
        type empty;
      }
      leaf disable_portchannel_qos_multiple_active {
        type empty;
      }
      leaf no_efp_feat_ext {
        type empty;
      }
      choice egr_l3vpn_cm-choice {
        leaf disable_egr_l3vpn_cm {
          type empty;
        }
        leaf enable_egr_l3vpn_cm {
          type empty;
        }
      }
      leaf disable_l3vpn_cm {
        type empty;
      }
      choice copp-choice {
        leaf disable_copp {
          type empty;
        }
        leaf enable_copp {
          type empty;
        }
      }
      leaf disable_match_inner_dscp {
        type empty;
      }
      leaf sr_pfp_disable {
        type empty;
      }
      leaf sr_5_label_push_disable {
        type empty;
      }
      leaf access {
        type empty;
      }
      leaf default {
        type empty;
      }
      leaf dual-ipv4-and-ipv6 {
        type enumeration {
          enum "default";
          enum "routing";
          enum "vlan";
        }
      }
      leaf routing {
        type empty;
      }
      leaf qos {
        type empty;
      }
      leaf ip {
        type empty;
      }
      leaf advanced {
        type empty;
      }
      leaf vlan {
        type empty;
      }
      leaf video {
        type empty;
      }
      choice vpls_stats-choice {
        leaf vpls_stats_disable {
          type empty;
        }
        leaf vpls_stats_enable {
          type empty;
        }
      }
      leaf disable_vlan_translation {
        type empty;
      }
    }
  }
  container mls {
    container acl {
      container tcam {
        leaf default-result {
          type enumeration {
            enum "bridge";
            enum "deny";
            enum "permit";
          }
        }
        container log-update {
          presence "true";
          leaf rate-limit-msg {
            type enumeration {
              enum "disable";
              enum "enable";
            }
          }
        }
        leaf share-global {
          type boolean;
        }
      }
    }
    container cef {
      container adjacency-mcast {
        list region {
          tailf:cli-suppress-mode;
          tailf:cli-delete-when-empty;
          key "id";
          leaf id {
            type uint8;
          }
          leaf value {
            tailf:cli-drop-node-name;
            type uint8;
          }
        }
        leaf value {
          tailf:cli-drop-node-name;
          type uint8;
        }
      }
      container error {
        leaf action {
          type enumeration {
            enum "reset";
            enum "freeze";
          }
        }
      }
      container maximum-routes {
        leaf ip {
          type uint16;
        }
        leaf ipv6 {
          type uint16;
        }
        leaf mpls {
          type uint16;
        }
        leaf ip-multicast {
          type uint16;
        }
      }
    }
    container rp {
      container ip {
        leaf input-acl {
          type empty;
        }
        leaf route-map {
          type empty;
        }
      }
      container ip-enable {
        tailf:cli-drop-node-name;
        leaf ip {
          type empty;
        }
      }
    }
    container nde {
      container sender {
        tailf:cli-delete-when-empty;
        presence "true";
        leaf version {
          type enumeration {
            enum "5";
            enum "7";
          }
        }
      }
    }
    container ip {
      container slb {
        container purge {
          leaf global {
            type boolean;
          }
        }
      }
      container cef {
        container load-sharing {
          tailf:cli-compact-syntax;
          tailf:cli-sequence-commands {
            tailf:cli-reset-siblings;
          }
          leaf full {
            tailf:cli-optional-in-sequence;
            type empty;
          }
          leaf exclude-port {
            tailf:cli-optional-in-sequence;
            type enumeration {
              enum "destination";
              enum "source";
            }
          }
          leaf simple {
            type empty;
          }
        }
      }
      container multicast {
        container consistency-check {
          tailf:cli-delete-when-empty;
          presence "true";
          container type {
            container rp-sp {
              presence "true";
            }
            container met {
              presence "true";
            }
          }
          leaf settle-time {
            type uint16;
          }
        }
        leaf flow-stat-timer {
          type uint8;
        }
        leaf replication-mode {
          type enumeration {
            enum "ingress";
            enum "egress";
          }
        }
        container egress {
          leaf local {
            type empty;
          }
        }
        container met-optimization {
          leaf enable {
            type empty;
          }
        }
        container bidir {
          leaf gm-scan-interval {
            type uint16;
          }
        }
        leaf threshold {
          type uint16;
        }
      }
      container multicast-enable {
        tailf:cli-drop-node-name;
        leaf multicast {
          type boolean;
        }
      }
    }
    container ipv6 {
      leaf vrf {
        type empty;
      }
    }
    container aging {
      container fast {
        tailf:cli-compact-syntax;
        tailf:cli-delete-when-empty;
        presence "true";
        leaf time {
          type uint8;
        }
        leaf threshold {
          type uint8;
        }
      }
      container normal {
        leaf seconds {
          tailf:cli-drop-node-name;
          type uint16;
        }
      }
      container long {
        leaf timeout {
          tailf:cli-drop-node-name;
          type uint16;
        }
      }
    }
    container netflow {
      tailf:cli-delete-when-empty;
      presence "true";
      leaf interface {
        type empty;
      }
      container usage {
        container notify {
          tailf:cli-compact-syntax;
          tailf:cli-sequence-commands {
            tailf:cli-reset-siblings;
          }
          leaf percentage {
            tailf:cli-drop-node-name;
            type uint8;
          }
          leaf seconds {
            tailf:cli-drop-node-name;
            type uint32;
          }
        }
      }
    }
    container flow {
      leaf ip {
        type enumeration {
          enum "interface-destination";
          enum "interface-destination-source";
          enum "interface-full";
          enum "interface-source";
          enum "full";
        }
      }
      choice ipv6-choice {
        container no-ipv6 {
          tailf:cli-drop-node-name;
          leaf ipv6 {
            type boolean;
          }
        }
        container ipv6 {
          choice ipv6-choice2 {
            leaf interface-destination {
              type empty;
            }
            leaf interface-destination-source {
              type empty;
            }
            leaf interface-full {
              type empty;
            }
            leaf interface-source {
              type empty;
            }
          }
        }
      }
    }
    container sampling {
      choice sampling-choice {
        leaf time-based {
          type uint16;
        }
        container packet-based {
          tailf:cli-compact-syntax;
          tailf:cli-sequence-commands {
            tailf:cli-reset-siblings;
          }
          leaf rate {
            tailf:cli-drop-node-name;
            type uint16;
          }
          leaf interval {
            tailf:cli-drop-node-name;
            type uint16;
          }
        }
      }
    }
    container mls-qos-conf {
      tailf:cli-drop-node-name;
      leaf qos {
        type empty;
      }
    }
    container qos {
      list protocol {
        tailf:cli-suppress-mode;
        tailf:cli-delete-when-empty;
        tailf:cli-compact-syntax;
        tailf:cli-sequence-commands {
          tailf:cli-reset-siblings;
        }
        key "name";
        leaf name {
          type string;
        }
        leaf precedence {
          tailf:cli-optional-in-sequence;
          type uint8;
        }
        container police {
          tailf:cli-flatten-container;
          tailf:cli-compact-syntax;
          tailf:cli-sequence-commands {
            tailf:cli-reset-siblings;
          }
          leaf target-bit-rate {
            tailf:cli-drop-node-name;
            type uint64;
          }
          leaf burst {
            tailf:cli-drop-node-name;
            type uint32;
          }
        }
      }
      list aggregate-policer {
        tailf:cli-suppress-mode;
        tailf:cli-delete-when-empty;
        tailf:cli-compact-syntax;
        tailf:cli-sequence-commands {
          tailf:cli-reset-all-siblings;
        }
        key "name";
        leaf name {
          type string;
        }
        leaf target-bit-rate {
          tailf:cli-drop-node-name;
          type uint64;
        }
        leaf burst-normal {
          tailf:cli-drop-node-name;
          tailf:cli-optional-in-sequence;
          type uint32;
        }
        leaf burst-max {
          tailf:cli-drop-node-name;
          tailf:cli-optional-in-sequence;
          type uint32;
        }
        leaf pir {
          tailf:cli-optional-in-sequence;
          type uint64;
        }
        container conform-action {
          tailf:cli-optional-in-sequence;
          tailf:cli-flatten-container;
          tailf:cli-compact-syntax;
          choice action-choice {
            leaf drop {
              type empty;
            }
            leaf set-dscp-transmit {
              type dscp-type;
            }
            leaf set-mpls-exp-imposition-transmit {
              type uint8;
            }
            leaf set-prec-transmit {
              type uint8;
            }
            leaf transmit {
              type empty;
            }
          }
        }
        leaf exceed-action {
          tailf:cli-optional-in-sequence;
          type enumeration {
            enum "drop";
            enum "policed-dscp-transmit";
            enum "transmit";
          }
        }
        leaf violate-action {
          type enumeration {
            enum "drop";
            enum "policed-dscp-transmit";
            enum "transmit";
          }
        }
      }
      container cos {
        leaf policy-map {
          type empty;
        }
      }
      container rewrite {
        container ip {
          container dscp {
            presence "true";
            leaf slot {
              type string;
            }
          }
        }
      }
      container map {
        list dscp-mutation {
          tailf:cli-suppress-mode;
          tailf:cli-delete-when-empty;
          tailf:cli-compact-syntax;
          tailf:cli-sequence-commands {
            tailf:cli-reset-siblings;
          }
          key "name";
          leaf name {
            type string;
          }
          leaf mutated-dscp1 {
            tailf:cli-drop-node-name;
            type uint8;
          }
          leaf mutated-dscp2 {
            tailf:cli-drop-node-name;
            tailf:cli-optional-in-sequence;
            type uint8;
          }
          leaf mutated-dscp3 {
            tailf:cli-drop-node-name;
            tailf:cli-optional-in-sequence;
            type uint8;
          }
          leaf mutated-dscp4 {
            tailf:cli-drop-node-name;
            tailf:cli-optional-in-sequence;
            type uint8;
          }
          leaf mutated-dscp5 {
            tailf:cli-drop-node-name;
            tailf:cli-optional-in-sequence;
            type uint8;
          }
          leaf mutated-dscp6 {
            tailf:cli-drop-node-name;
            tailf:cli-optional-in-sequence;
            type uint8;
          }
          leaf mutated-dscp7 {
            tailf:cli-drop-node-name;
            tailf:cli-optional-in-sequence;
            type uint8;
          }
          leaf mutated-dscp8 {
            tailf:cli-drop-node-name;
            tailf:cli-optional-in-sequence;
            type uint8;
          }
          leaf to {
            type uint16;
          }
        }
        leaf-list cos-dscp {
          tailf:cli-flat-list-syntax;
          type uint8;
        }
        container cos-dscp-new {
          tailf:cli-drop-node-name;
          container cos-dscp {
            tailf:cli-compact-syntax;
            tailf:cli-sequence-commands;
            uses cos-value-0-7-grouping;
          }
        }
        leaf-list ip-prec-dscp {
          tailf:cli-flat-list-syntax;
          type uint8;
        }
        list policed-dscp {
          tailf:cli-suppress-mode;
          tailf:cli-delete-when-empty;
          tailf:cli-compact-syntax;
          tailf:cli-sequence-commands;
          key "dscp";
          leaf dscp {
            type uint8;
          }
          leaf to {
            type uint8;
          }
        }
        list exp-mutation {
          tailf:cli-suppress-mode;
          tailf:cli-delete-when-empty;
          tailf:cli-compact-syntax;
          tailf:cli-sequence-commands {
            tailf:cli-reset-siblings;
          }
          key "name";
          leaf name {
            type string;
          }
          leaf mutated-exp1 {
            tailf:cli-drop-node-name;
            type uint8;
          }
          leaf mutated-exp2 {
            tailf:cli-drop-node-name;
            type uint8;
          }
          leaf mutated-exp3 {
            tailf:cli-drop-node-name;
            type uint8;
          }
          leaf mutated-exp4 {
            tailf:cli-drop-node-name;
            type uint8;
          }
          leaf mutated-exp5 {
            tailf:cli-drop-node-name;
            type uint8;
          }
          leaf mutated-exp6 {
            tailf:cli-drop-node-name;
            type uint8;
          }
          leaf mutated-exp7 {
            tailf:cli-drop-node-name;
            type uint8;
          }
          leaf mutated-exp8 {
            tailf:cli-drop-node-name;
            type uint8;
          }
        }
        container exp-dscp {
          tailf:cli-compact-syntax;
          tailf:cli-sequence-commands {
            tailf:cli-reset-siblings;
          }
          leaf dscp1 {
            tailf:cli-drop-node-name;
            type uint8;
          }
          leaf dscp2 {
            tailf:cli-drop-node-name;
            tailf:cli-optional-in-sequence;
            type uint8;
          }
          leaf dscp3 {
            tailf:cli-drop-node-name;
            tailf:cli-optional-in-sequence;
            type uint8;
          }
          leaf dscp4 {
            tailf:cli-drop-node-name;
            tailf:cli-optional-in-sequence;
            type uint8;
          }
          leaf dscp5 {
            tailf:cli-drop-node-name;
            tailf:cli-optional-in-sequence;
            type uint8;
          }
          leaf dscp6 {
            tailf:cli-drop-node-name;
            tailf:cli-optional-in-sequence;
            type uint8;
          }
          leaf dscp7 {
            tailf:cli-drop-node-name;
            tailf:cli-optional-in-sequence;
            type uint8;
          }
          leaf dscp8 {
            tailf:cli-drop-node-name;
            type uint8;
          }
        }
      }
      container srr-queue {
        list cos-dscp-list {
          tailf:cli-drop-node-name;
          tailf:cli-suppress-mode;
          tailf:cli-delete-when-empty;
          tailf:cli-compact-syntax;
          key "direction maptype";
          leaf direction {
            type enumeration {
              enum "input";
              enum "output";
            }
          }
          leaf maptype {
            type enumeration {
              enum "cos-map";
              enum "dscp-map";
              enum "cpu";
            }
          }
          list queue-threshold-list {
            tailf:cli-drop-node-name;
            tailf:cli-suppress-mode;
            tailf:cli-delete-when-empty;
            tailf:cli-compact-syntax;
            key "queue threshold";
            leaf queue {
              tailf:cli-expose-key-name;
              type uint8;
            }
            leaf threshold {
              tailf:cli-expose-key-name;
              type uint8;
            }
            leaf-list values {
              tailf:cli-drop-node-name;
              tailf:cli-flat-list-syntax;
              type uint8;
            }
          }
        }
        container input {
          list priority-queue {
            tailf:cli-suppress-mode;
            tailf:cli-delete-when-empty;
            tailf:cli-compact-syntax;
            key "queue";
            leaf queue {
              type uint8;
            }
            leaf bandwidth {
              type uint8;
            }
          }
          container bandwidth {
            tailf:cli-compact-syntax;
            tailf:cli-sequence-commands {
              tailf:cli-reset-siblings;
            }
            leaf weight1 {
              tailf:cli-drop-node-name;
              type uint8;
            }
            leaf weight2 {
              tailf:cli-drop-node-name;
              type uint8;
            }
          }
          list threshold {
            tailf:cli-suppress-mode;
            tailf:cli-delete-when-empty;
            tailf:cli-compact-syntax;
            key "queue";
            leaf queue {
              type uint8;
            }
            leaf threshold-percentage1 {
              tailf:cli-drop-node-name;
              type uint8;
            }
            leaf threshold-percentage2 {
              tailf:cli-drop-node-name;
              type uint8;
            }
          }
          container buffers {
            tailf:cli-compact-syntax;
            tailf:cli-sequence-commands {
              tailf:cli-reset-siblings;
            }
            leaf percentage1 {
              tailf:cli-drop-node-name;
              type uint8;
            }
            leaf percentage2 {
              tailf:cli-drop-node-name;
              type uint8;
            }
          }
        }
      }
      container queue-set {
        container output {
          list threshold-list {
            tailf:cli-drop-node-name;
            tailf:cli-suppress-mode;
            tailf:cli-delete-when-empty;
            tailf:cli-compact-syntax;
            key "queue threshold";
            leaf queue {
              type uint8;
            }
            leaf threshold {
              tailf:cli-expose-key-name;
              type uint8;
            }
            leaf drop-threshold1 {
              tailf:cli-drop-node-name;
              type uint16;
            }
            leaf drop-threshold2 {
              tailf:cli-drop-node-name;
              type uint16;
            }
            leaf reserved-threshold {
              tailf:cli-drop-node-name;
              type uint16;
            }
            leaf maximum-threshold {
              tailf:cli-drop-node-name;
              type uint16;
            }
          }
          list buffers-list {
            tailf:cli-drop-node-name;
            tailf:cli-suppress-mode;
            tailf:cli-delete-when-empty;
            tailf:cli-compact-syntax;
            key "queue";
            leaf queue {
              type uint8;
            }
            container buffers {
              tailf:cli-compact-syntax;
              tailf:cli-sequence-commands {
                tailf:cli-reset-siblings;
              }
              leaf allocation1 {
                tailf:cli-drop-node-name;
                type uint8;
              }
              leaf allocation2 {
                tailf:cli-drop-node-name;
                type uint8;
              }
              leaf allocation3 {
                tailf:cli-drop-node-name;
                type uint8;
              }
              leaf allocation4 {
                tailf:cli-drop-node-name;
                type uint8;
              }
            }
          }
        }
      }
      list min-reserve {
        tailf:cli-suppress-mode;
        tailf:cli-delete-when-empty;
        key "level";
        leaf level {
          type uint8;
        }
        leaf buffersize {
          tailf:cli-drop-node-name;
          type uint8;
        }
      }
    }
    container rate-limit {
      container multicast {
        list ipv4 {
          tailf:cli-suppress-mode;
          tailf:cli-delete-when-empty;
          tailf:cli-compact-syntax;
          tailf:cli-sequence-commands {
            tailf:cli-reset-siblings;
          }
          key "name";
          leaf name {
            type enumeration {
              enum "fib-miss";
              enum "connected";
              enum "ip-options";
              enum "igmp";
              enum "partial";
              enum "pim";
              enum "tiny-fragment";
              enum "non-rpf";
            }
          }
          uses mls-rate-limit-grouping;
        }
      }
      container unicast {
        container cef {
          container glean {
            tailf:cli-compact-syntax;
            tailf:cli-sequence-commands {
              tailf:cli-reset-siblings;
            }
            uses mls-rate-limit-grouping;
          }
          container receive {
            tailf:cli-compact-syntax;
            tailf:cli-sequence-commands {
              tailf:cli-reset-siblings;
            }
            uses mls-rate-limit-grouping;
          }
        }
        container acl {
          container input {
            tailf:cli-compact-syntax;
            tailf:cli-sequence-commands {
              tailf:cli-reset-siblings;
            }
            uses mls-rate-limit-grouping;
          }
          container output {
            tailf:cli-compact-syntax;
            tailf:cli-sequence-commands {
              tailf:cli-reset-siblings;
            }
            uses mls-rate-limit-grouping;
          }
          leaf vacl-log {
            tailf:code-name "mls-rate-limit-vacl-log";
            type uint32;
          }
        }
        container ip {
          container rpf-failure {
            tailf:cli-compact-syntax;
            tailf:cli-sequence-commands {
              tailf:cli-reset-siblings;
            }
            uses mls-rate-limit-grouping;
          }
          container icmp {
            container redirect {
              tailf:cli-compact-syntax;
              tailf:cli-sequence-commands {
                tailf:cli-reset-siblings;
              }
              uses mls-rate-limit-grouping;
            }
            container unreachable {
              container no-route {
                tailf:cli-compact-syntax;
                tailf:cli-sequence-commands {
                  tailf:cli-reset-siblings;
                }
                uses mls-rate-limit-grouping;
              }
              container acl-drop {
                tailf:cli-compact-syntax;
                tailf:cli-sequence-commands {
                  tailf:cli-reset-siblings;
                }
                uses mls-rate-limit-grouping;
              }
            }
          }
          container options {
            tailf:cli-compact-syntax;
            tailf:cli-sequence-commands {
              tailf:cli-reset-siblings;
            }
            uses mls-rate-limit-grouping;
          }
          container errors {
            tailf:cli-compact-syntax;
            tailf:cli-sequence-commands {
              tailf:cli-reset-siblings;
            }
            uses mls-rate-limit-grouping;
          }
        }
      }
      container all {
        container mtu-failure {
          tailf:cli-compact-syntax;
          tailf:cli-sequence-commands {
            tailf:cli-reset-siblings;
          }
          uses mls-rate-limit-grouping;
        }
        container ttl-failure {
          tailf:cli-compact-syntax;
          tailf:cli-sequence-commands {
            tailf:cli-reset-siblings;
          }
          uses mls-rate-limit-grouping;
        }
      }
      container layer2 {
        container l2pt {
          tailf:cli-compact-syntax;
          tailf:cli-sequence-commands {
            tailf:cli-reset-siblings;
          }
          uses mls-rate-limit-grouping;
        }
        container pdu {
          tailf:cli-compact-syntax;
          tailf:cli-sequence-commands {
            tailf:cli-reset-siblings;
          }
          uses mls-rate-limit-grouping;
        }
        container mac-security {
          tailf:cli-compact-syntax;
          tailf:cli-sequence-commands {
            tailf:cli-reset-siblings;
          }
          uses mls-rate-limit-grouping;
        }
      }
    }
    container verify {
      container ip {
        leaf checksum {
          type boolean;
        }
        container length {
          leaf consistent {
            type boolean;
          }
          leaf minimum {
            type boolean;
          }
        }
        leaf same-address {
          type empty;
        }
        leaf syslog {
          type empty;
        }
      }
    }
    container mpls {
      leaf recir-agg {
        type empty;
      }
      leaf tunnel-recir {
        type empty;
      }
    }
  }
  container policer {
    list aggregate {
      tailf:cli-suppress-mode;
      tailf:cli-delete-when-empty;
      tailf:cli-compact-syntax;
      tailf:cli-sequence-commands {
        tailf:cli-reset-siblings;
      }
      key "name";
      leaf name {
        type string;
      }
      leaf cir {
        type uint32;
      }
      leaf bc {
        tailf:cli-optional-in-sequence;
        type uint32;
      }
      leaf conform-action {
        tailf:cli-optional-in-sequence;
        type empty;
      }
      leaf set-qos-transmit {
        tailf:cli-optional-in-sequence;
        type uint8;
      }
      leaf set-dot1ad-dei-transmit {
        tailf:cli-optional-in-sequence;
        type uint8;
      }
      leaf set-prec-transmit {
        tailf:cli-optional-in-sequence;
        type prec_value-type;
      }
      container set-prec-transmit-table {
        tailf:cli-no-keyword;
        tailf:cli-drop-node-name;
        tailf:cli-optional-in-sequence;
        tailf:cli-flatten-container;
        leaf table {
          tailf:cli-optional-in-sequence;
          type string;
        }
      }
      leaf set-dscp-transmit {
        tailf:cli-optional-in-sequence;
        type dscp-type;
      }
      container set-dscp-transmit-table {
        tailf:cli-no-keyword;
        tailf:cli-drop-node-name;
        tailf:cli-optional-in-sequence;
        tailf:cli-flatten-container;
        leaf table {
          tailf:cli-optional-in-sequence;
          type string;
        }
      }
      leaf set-cos-transmit {
        tailf:cli-optional-in-sequence;
        type cos_value-type;
      }
      container set-cos-transmit-table {
        tailf:cli-no-keyword;
        tailf:cli-drop-node-name;
        tailf:cli-optional-in-sequence;
        tailf:cli-flatten-container;
        leaf table {
          tailf:cli-optional-in-sequence;
          type string;
        }
      }
      leaf transmit {
        tailf:cli-optional-in-sequence;
        type empty;
      }
      leaf exceed-action {
        type empty;
      }
      leaf drop {
        tailf:cli-optional-in-sequence;
        type empty;
      }
      container exceed-transmit {
        tailf:cli-no-keyword;
        tailf:cli-drop-node-name;
        tailf:cli-optional-in-sequence;
        tailf:cli-flatten-container;
        leaf transmit {
          tailf:cli-optional-in-sequence;
          type empty;
        }
      }
    }
  }
  container hw-switch {
    list switch {
      tailf:cli-suppress-mode;
      tailf:cli-delete-when-empty;
      tailf:cli-compact-syntax;
      tailf:cli-sequence-commands {
        tailf:cli-reset-siblings;
      }
      key "id";
      leaf id {
        type uint8;
      }
      container logging {
        list onboard {
          tailf:cli-suppress-mode;
          tailf:cli-delete-when-empty;
          key "name";
          leaf name {
            type enumeration {
              enum "counter";
              enum "environment";
              enum "message";
              enum "poe";
              enum "temperature";
              enum "voltage";
            }
          }
          leaf level {
            type uint8;
          }
        }
      }
    }
  }
  container redundancy {
    tailf:cli-add-mode;
    presence "true";
    leaf maintenance-mode {
      type empty;
    }
    leaf mode {
      type enumeration {
        enum "rpr";
        enum "rpr-plus";
        enum "sso";
        enum "none";
      }
    }
    leaf notification-timer {
      type uint32;
    }
    container application {
      container redundancy {
        tailf:cli-add-mode;
        list group {
          key "id";
          leaf id {
            type uint8;
          }
          leaf name {
            type string;
          }
          leaf preempt {
            type empty;
          }
          container priority {
            tailf:cli-compact-syntax;
            tailf:cli-sequence-commands {
              tailf:cli-reset-siblings;
            }
            leaf value {
              tailf:cli-drop-node-name;
              type uint8;
            }
            container failover {
              tailf:cli-flatten-container;
              leaf threshold {
                type uint8;
              }
            }
          }
          container timers {
            tailf:cli-compact-syntax;
            tailf:cli-sequence-commands {
              tailf:cli-reset-siblings;
            }
            leaf delay {
              type uint16;
            }
            leaf reload {
              type uint16;
            }
          }
          container control {
            tailf:cli-compact-syntax;
            tailf:cli-sequence-commands {
              tailf:cli-reset-siblings;
            }
            uses interface-name-grouping;
            leaf protocol {
              type uint8;
            }
          }
          container data {
            uses interface-name-grouping;
          }
          container asymmetric-routing {
            container interface {
              uses interface-name-grouping;
            }
            container always-divert {
              leaf enable {
                type empty;
              }
            }
          }
          container track {
            tailf:cli-compact-syntax;
            tailf:cli-sequence-commands {
              tailf:cli-reset-siblings;
            }
            leaf id {
              tailf:cli-drop-node-name;
              type uint16;
            }
            choice action-choice {
              leaf decrement {
                type uint8;
              }
              leaf shutdown {
                type empty;
              }
            }
          }
        }
        list protocol {
          key "id";
          leaf id {
            type uint8;
          }
          container timers {
            tailf:cli-compact-syntax;
            tailf:cli-sequence-commands {
              tailf:cli-reset-siblings;
            }
            leaf hellotime {
              type empty;
            }
            choice hellotime-choice {
              leaf seconds {
                tailf:cli-drop-node-name;
                type uint8;
              }
              leaf msec {
                type uint16;
              }
            }
            leaf holdtime {
              type uint8;
            }
          }
          container authentication {
            container md5 {
              container key-string {
                tailf:cli-flatten-container;
                tailf:cli-compact-syntax;
                tailf:cli-sequence-commands;
                uses password-grouping {
                  refine "secret";
                }
                leaf timeout {
                  type uint16;
                }
              }
            }
          }
        }
      }
    }
    list linecard-group {
      key "id";
      leaf id {
        type uint32;
      }
      leaf cable {
        tailf:cli-hide-in-submode;
        type empty;
      }
      leaf internal-switch {
        tailf:cli-hide-in-submode;
        type empty;
      }
      leaf description {
        tailf:cli-multi-value;
        type string;
      }
      leaf class {
        type enumeration {
          enum "1:1";
          enum "1:N";
        }
      }
      container reserve {
        leaf cardtype {
          type string;
        }
      }
      container rf-switch {
        leaf snmp-community {
          type string;
        }
      }
      container member {
        list slot {
          tailf:cli-suppress-mode;
          tailf:cli-delete-when-empty;
          tailf:cli-compact-syntax;
          key "id";
          leaf id {
            type uint8;
          }
          choice primary-secondary-choice {
            leaf primary {
              type empty;
            }
            leaf secondary {
              type empty;
            }
          }
        }
        list subslot {
          tailf:cli-suppress-mode;
          tailf:cli-delete-when-empty;
          tailf:cli-compact-syntax;
          tailf:cli-suppress-list-no;
          key "id";
          leaf id {
            type string;
          }
          leaf working {
            type empty;
          }
          container protect {
            presence "true";
            choice config-choice {
              leaf config {
                type string;
              }
              container no-config {
                tailf:cli-drop-node-name;
                leaf config {
                  type boolean;
                }
              }
            }
          }
        }
      }
      leaf revertive {
        type uint32;
      }
      container main-cpu {
        tailf:cli-add-mode;
        presence "true";
      }
      container standby {
        container console {
          leaf enable {
            type empty;
          }
          leaf lock {
            type empty;
          }
        }
        container initialization {
          leaf delay {
            type uint16;
          }
        }
      }
    }
    container main-cpu {
      tailf:cli-add-mode;
      presence "true";
      container auto-sync {
        leaf running-config {
          type empty;
        }
        leaf config-register {
          type empty;
        }
        leaf bootvar {
          type empty;
        }
        leaf startup-config {
          type empty;
        }
        leaf standard {
          type empty;
        }
      }
      container switchover {
        container pxf {
          container restart {
            tailf:cli-compact-syntax;
            tailf:cli-sequence-commands;
            leaf number-of-crashes {
              tailf:cli-drop-node-name;
              type uint8;
            }
            leaf time-period {
              tailf:cli-drop-node-name;
              type uint8;
            }
          }
        }
      }
      container standby {
        container initialization {
          tailf:cli-compact-syntax;
          tailf:cli-sequence-commands {
            tailf:cli-reset-siblings;
          }
          leaf delay {
            type uint16;
          }
          leaf boot-only {
            type empty;
          }
        }
        container console {
          leaf enable {
            type empty;
          }
          leaf lock {
            type empty;
          }
        }
      }
    }
    container interchassis {
      list group {
        key "id";
        leaf id {
          type uint32;
        }
        container member {
          leaf ip {
            type inet:ipv4-address;
          }
        }
        container backbone {
          list interface {
            tailf:cli-suppress-mode;
            tailf:cli-delete-when-empty;
            key "name";
            leaf name {
              type string;
            }
          }
        }
        container mlacp {
          leaf system-mac {
            type string;
          }
          leaf system-priority {
            type uint16;
          }
          leaf node-id {
            type uint8;
          }
        }
      }
    }
    container cloud {
      container provider {
        list aws {
          key "id";
          leaf id {
            type uint16;
          }
          container bfd {
            leaf peer {
              type string;
            }
          }
          leaf route-table {
            type string;
          }
          container cidr {
            leaf ip {
              type ios:ipv4-prefix;
            }
          }
          leaf eni {
            type string;
          }
          leaf region {
            type string;
          }
        }
      }
    }
  }
  container mdns-sd {
    list service-list {
      key "name";
      leaf name {
        type string;
      }
      leaf direction {
        tailf:cli-drop-node-name;
        tailf:cli-hide-in-submode;
        type enumeration {
          enum "IN";
          enum "OUT";
        }
      }
      list match {
        tailf:cli-suppress-mode;
        tailf:cli-delete-when-empty;
        key "name";
        leaf name {
          type string;
        }
      }
    }
    list service-policy {
      key "name";
      leaf name {
        type string;
      }
      list service-list {
        tailf:cli-suppress-mode;
        tailf:cli-delete-when-empty;
        tailf:cli-compact-syntax;
        tailf:cli-sequence-commands {
          tailf:cli-reset-siblings;
        }
        key "direction";
        leaf direction {
          type enumeration {
            enum "IN";
            enum "OUT";
          }
        }
        leaf name {
          tailf:cli-drop-node-name;
          tailf:cli-prefix-key;
          type string;
        }
      }
    }
    list service-definition {
      key "name";
      leaf name {
        type string;
      }
      uses description-grouping;
      leaf service-type {
        type string;
      }
    }
  }
  container bfd {
    container map {
      container ipv4 {
        list list {
          tailf:cli-drop-node-name;
          tailf:cli-suppress-mode;
          tailf:cli-delete-when-empty;
          key "destination source";
          leaf destination {
            type ios:ipv4-prefix;
          }
          leaf source {
            type ios:ipv4-prefix;
          }
          leaf bfd-template {
            tailf:cli-drop-node-name;
            type string;
          }
        }
        list vrf {
          tailf:cli-suppress-mode;
          tailf:cli-delete-when-empty;
          key "name destination source";
          leaf name {
            type string;
          }
          leaf destination {
            type ios:ipv4-prefix;
          }
          leaf source {
            type ios:ipv4-prefix;
          }
          leaf bfd-template {
            tailf:cli-drop-node-name;
            type string;
          }
        }
        container src-vrf {
          tailf:cli-drop-node-name;
          list vrf {
            tailf:cli-suppress-mode;
            tailf:cli-delete-when-empty;
            key "name destination vrf source";
            leaf name {
              type string;
            }
            leaf destination {
              type ios:ipv4-prefix;
            }
            leaf vrf {
              tailf:cli-expose-key-name;
              type string;
            }
            leaf source {
              type ios:ipv4-prefix;
            }
            leaf bfd-template {
              tailf:cli-drop-node-name;
              type string;
            }
          }
        }
      }
      container ipv6 {
        list list {
          tailf:cli-drop-node-name;
          tailf:cli-suppress-mode;
          tailf:cli-delete-when-empty;
          key "destination source";
          leaf destination {
            type ipv6-prefix;
          }
          leaf source {
            type ipv6-prefix;
          }
          leaf bfd-template {
            tailf:cli-drop-node-name;
            type string;
          }
        }
      }
    }
    container snmp {
      container traps {
        leaf more {
          type empty;
        }
      }
    }
    leaf fast-timers-on-slow-interface {
      type empty;
    }
    leaf slow-timers {
      type uint16;
    }
  }
  container bfd-template {
    list single-hop {
      key "name";
      leaf name {
        type string;
      }
      uses bfd-template-grouping;
    }
    list multi-hop {
      key "name";
      leaf name {
        type string;
      }
      uses bfd-template-grouping;
    }
  }
  leaf process-max-time {
    type uint8;
  }
  container map-class {
    list frame-relay {
      key "name";
      leaf name {
        type string;
      }
      container frame-relay {
        leaf cir {
          type uint32;
        }
        leaf mincir {
          type uint32;
        }
        leaf fragment {
          type uint16;
        }
        container bc {
          leaf value {
            tailf:cli-drop-node-name;
            type uint32;
          }
        }
        container be {
          leaf value {
            tailf:cli-drop-node-name;
            type uint32;
          }
        }
        container fair-queue {
          presence "true";
        }
      }
      container service-policy {
        uses service-policy-grouping;
      }
    }
  }
  container class {
    list cem {
      key "name";
      leaf name {
        type string;
      }
      leaf payload-size {
        type uint16;
      }
      leaf dejitter-buffer {
        type uint16;
      }
      leaf idle-pattern {
        type string;
      }
    }
  }
  container redirect {
    list server-group {
      key "name";
      leaf name {
        type string;
      }
      list server {
        tailf:cli-suppress-mode;
        tailf:cli-delete-when-empty;
        key "ip port";
        leaf ip {
          tailf:cli-expose-key-name;
          type union {
            type inet:ipv4-address;
            type inet:ipv6-address;
          }
        }
        leaf port {
          tailf:cli-expose-key-name;
          type uint16;
        }
      }
    }
  }
  list class-map {
    tailf:cli-compact-syntax;
    tailf:cli-sequence-commands;
    key "name";
    leaf name {
      type string;
    }
    leaf type {
      tailf:cli-optional-in-sequence;
      tailf:cli-prefix-key;
      type enumeration {
        enum "access-control";
        enum "inspect";
        enum "logging";
        enum "port-filter";
        enum "queue-threshold";
        enum "stack";
        enum "appnav";
        enum "multicast-flows";
        enum "site-manager";
      }
    }
    leaf protocol {
      tailf:cli-drop-node-name;
      tailf:cli-prefix-key;
      tailf:cli-optional-in-sequence;
      type enumeration {
        enum "aol";
        enum "edonkey";
        enum "fasttrack";
        enum "gnutella";
        enum "http";
        enum "imap";
        enum "kazaa2";
        enum "msnmsgr";
        enum "pop3";
        enum "smtp";
        enum "sunrpc";
        enum "ymsgr";
      }
    }
    leaf prematch {
      tailf:cli-drop-node-name;
      tailf:cli-no-keyword;
      tailf:cli-prefix-key;
      type enumeration {
        enum "match-all";
        enum "match-any";
      }
    }
    leaf description {
      tailf:cli-break-sequence-commands;
      tailf:cli-multi-value;
      type string;
    }
    container match {
      uses class-map-match-grouping;
      container not {
        uses class-map-match-grouping;
      }
    }
  }
  container class-map-multicast-flows {
    tailf:cli-drop-node-name;
    list class-map {
      tailf:cli-suppress-list-no;
      tailf:cli-compact-syntax;
      tailf:cli-sequence-commands;
      key "name";
      leaf name {
        type string;
      }
      leaf type {
        tailf:cli-prefix-key;
        type enumeration {
          enum "multicast-flows";
        }
      }
      container group {
        list list {
          tailf:cli-drop-node-name;
          tailf:cli-suppress-mode;
          tailf:cli-delete-when-empty;
          key "address source";
          leaf address {
            type inet:ipv4-address;
          }
          leaf source {
            tailf:cli-expose-key-name;
            type inet:ipv4-address;
          }
        }
        list list-range {
          tailf:cli-drop-node-name;
          tailf:cli-suppress-mode;
          tailf:cli-delete-when-empty;
          key "address to source";
          leaf address {
            type inet:ipv4-address;
          }
          leaf to {
            tailf:cli-expose-key-name;
            type inet:ipv4-address;
          }
          leaf source {
            tailf:cli-expose-key-name;
            type inet:ipv4-address;
          }
        }
      }
    }
  }
  container class-map-control {
    tailf:cli-drop-node-name;
    list class-map {
      tailf:cli-suppress-list-no;
      tailf:cli-compact-syntax;
      tailf:cli-sequence-commands;
      key "name";
      leaf name {
        type string;
      }
      leaf type {
        tailf:cli-prefix-key;
        type enumeration {
          enum "control";
        }
      }
      leaf prematch {
        tailf:cli-drop-node-name;
        tailf:cli-prefix-key;
        type enumeration {
          enum "match-all";
          enum "match-any";
          enum "match-none";
        }
      }
      container match {
        leaf authen-status {
          type enumeration {
            enum "authenticated";
            enum "unauthenticated";
          }
        }
        leaf timer {
          type string;
        }
        leaf service-name {
          type string;
        }
      }
    }
  }
  container class-map-filter-control {
    tailf:cli-drop-node-name;
    list class-map {
      tailf:cli-suppress-list-no;
      tailf:cli-compact-syntax;
      tailf:cli-sequence-commands;
      key "name";
      leaf name {
        type string;
      }
      leaf type {
        tailf:cli-prefix-key;
        type enumeration {
          enum "control";
        }
      }
      leaf domain {
        tailf:cli-drop-node-name;
        tailf:cli-prefix-key;
        type enumeration {
          enum "subscriber";
        }
      }
      leaf prematch {
        tailf:cli-drop-node-name;
        tailf:cli-prefix-key;
        type enumeration {
          enum "match-all";
          enum "match-any";
          enum "match-none";
        }
      }
      container match {
        tailf:cli-break-sequence-commands;
        uses class-map-type-ctrl-sub-match;
      }
      container no-match {
        uses class-map-type-ctrl-sub-match;
      }
    }
  }

  grouping class-map-type-ctrl-sub-match {
    container method {
      leaf webauth {
        type empty;
      }
      leaf mab {
        type empty;
      }
      leaf dot1x {
        type empty;
      }
    }
    container result-type {
      container method {
        container dot1x {
          uses result-type-method-grouping;
        }
        container mab {
          uses result-type-method-grouping;
        }
        container webauth {
          uses result-type-method-grouping;
        }
      }
      uses result-type-method-grouping;
    }
    leaf authorization-status {
      type enumeration {
        enum "authorized";
        enum "unauthorized";
      }
    }
    list activated-service-template {
      tailf:cli-suppress-mode;
      tailf:cli-delete-when-empty;
      key "name";
      leaf name {
        type string;
      }
    }
    list authorizing-method-priority {
      tailf:cli-suppress-mode;
      tailf:cli-delete-when-empty;
      key "op priority";
      leaf op {
        type enumeration {
          enum "eq";
          enum "gt";
          enum "lt";
        }
      }
      leaf priority {
        type uint8;
      }
    }
  }

  container class-map-traffic {
    tailf:cli-drop-node-name;
    list class-map {
      tailf:cli-suppress-list-no;
      tailf:cli-compact-syntax;
      tailf:cli-sequence-commands;
      key "name";
      leaf name {
        type string;
      }
      leaf type {
        tailf:cli-prefix-key;
        type enumeration {
          enum "traffic";
        }
      }
      leaf prematch {
        tailf:cli-drop-node-name;
        tailf:cli-prefix-key;
        type enumeration {
          enum "match-any";
        }
      }
      container match {
        container access-group {
          container input {
            choice access-list-choice {
              leaf name {
                type string;
              }
              leaf index {
                tailf:cli-drop-node-name;
                type uint32;
              }
            }
          }
          container output {
            choice access-list-choice {
              leaf name {
                type string;
              }
              leaf index {
                tailf:cli-drop-node-name;
                type uint32;
              }
            }
          }
        }
      }
    }
  }
  list policy-map {
    key "name";
    leaf name {
      type string;
    }
    leaf type {
      tailf:cli-prefix-key;
      type enumeration {
        enum "inspect";
        enum "performance-monitor";
        enum "mace";
        enum "packet-service";
        enum "appnav";
        enum "umbrella";
        enum "epbr";
      }
    }
    leaf protocol {
      tailf:cli-drop-node-name;
      tailf:cli-prefix-key;
      type enumeration {
        enum "http";
        enum "im";
        enum "imap";
        enum "p2p";
        enum "pop3";
        enum "smtp";
        enum "sunrpc";
        enum "avc";
      }
    }
    leaf description {
      tailf:cli-multi-value;
      type string;
    }
    container parameter {
      container default {
        leaf account-on-resolution {
          type empty;
        }
      }
    }
    list class {
      ordered-by user;
      key "name";
      leaf type {
        tailf:cli-prefix-key;
        type enumeration {
          enum "inspect";
        }
      }
      leaf name {
        type string;
      }
      uses policy-map-class-grouping {
        refine "bandwidth/bits";
      }
    }
    container class-default {
      tailf:cli-drop-node-name;
      list class {
        key "name";
        leaf type {
          tailf:cli-prefix-key;
          type enumeration {
            enum "inspect";
          }
        }
        leaf name {
          type enumeration {
            enum "class-default";
          }
        }
        uses policy-map-class-grouping;
      }
    }
  }
  container policy-map-service {
    tailf:cli-drop-node-name;
    list policy-map {
      tailf:cli-sequence-commands;
      key "name";
      leaf name {
        type string;
      }
      leaf type {
        tailf:cli-prefix-key;
        type enumeration {
          enum "service";
        }
      }
      container keepalive {
        tailf:cli-break-sequence-commands;
        tailf:cli-compact-syntax;
        leaf idle {
          type uint32;
        }
        leaf attempts {
          type uint8;
        }
        leaf interval {
          type uint8;
        }
        leaf protocol {
          type enumeration {
            enum "ARP";
            enum "ICMP";
          }
        }
      }
      container pppoe {
        leaf service {
          type string;
        }
      }
      list class-list {
        tailf:cli-drop-node-name;
        tailf:cli-sequence-commands;
        key "id";
        leaf id {
          type uint16;
        }
        leaf class {
          tailf:cli-hide-in-submode;
          type empty;
        }
        leaf type {
          tailf:cli-hide-in-submode;
          type enumeration {
            enum "traffic";
          }
        }
        leaf name {
          tailf:cli-drop-node-name;
          tailf:cli-hide-in-submode;
          type string;
        }
        container redirect {
          tailf:cli-break-sequence-commands;
          container to {
            leaf group {
              type string;
            }
          }
        }
      }
      container class-name {
        tailf:cli-drop-node-name;
        list class {
          ordered-by user;
          key "name";
          leaf type {
            tailf:cli-prefix-key;
            type enumeration {
              enum "traffic";
            }
          }
          leaf name {
            type string;
          }
          container timeout {
            leaf idle {
              type uint32;
            }
            leaf absolute {
              type uint32;
            }
          }
          container accounting {
            container aaa {
              leaf list {
                type string;
              }
            }
          }
        }
      }
      container class-default {
        tailf:cli-drop-node-name;
        list class {
          key "name";
          leaf type {
            tailf:cli-prefix-key;
            type enumeration {
              enum "traffic";
            }
          }
          leaf name {
            type enumeration {
              enum "default";
            }
          }
          leaf direction {
            tailf:cli-drop-node-name;
            tailf:cli-hide-in-submode;
            type enumeration {
              enum "in-out";
              enum "input";
              enum "output";
            }
          }
          leaf drop {
            type empty;
          }
        }
      }
    }
  }
  container policy-map-control {
    tailf:cli-drop-node-name;
    list policy-map {
      tailf:cli-sequence-commands;
      key "name";
      leaf name {
        type string;
      }
      leaf type {
        tailf:cli-prefix-key;
        type enumeration {
          enum "control";
        }
      }
      container class-name {
        tailf:cli-break-sequence-commands;
        tailf:cli-drop-node-name;
        list class {
          tailf:cli-sequence-commands;
          key "name";
          leaf type {
            tailf:cli-prefix-key;
            type enumeration {
              enum "control";
            }
          }
          leaf name {
            type string;
          }
          leaf event {
            tailf:cli-hide-in-submode;
            type pm-class-type-control-event-type;
          }
          uses policy-map-type-control-class-grouping;
        }
      }
      container class-always {
        tailf:cli-drop-node-name;
        list class {
          tailf:cli-sequence-commands;
          key "name event";
          leaf type {
            tailf:cli-prefix-key;
            type enumeration {
              enum "control";
            }
          }
          leaf name {
            type enumeration {
              enum "always";
            }
          }
          leaf event {
            tailf:cli-expose-key-name;
            type pm-class-type-control-event-type;
          }
          uses policy-map-type-control-class-grouping;
        }
      }
    }
  }
  container policy-map-event-control {
    tailf:cli-drop-node-name;
    list policy-map {
      tailf:cli-sequence-commands;
      key "name";
      leaf name {
        type string;
      }
      leaf type {
        tailf:cli-prefix-key;
        type enumeration {
          enum "control";
        }
      }
      leaf domain {
        tailf:cli-drop-node-name;
        tailf:cli-prefix-key;
        type enumeration {
          enum "subscriber";
        }
      }
      list event {
        ordered-by user;
        key "name match";
        leaf name {
          tailf:cli-suppress-range;
          type enumeration {
            enum "aaa-available";
            enum "absolute-timeout";
            enum "agent-found";
            enum "authentication-failure";
            enum "authentication-success";
            enum "authorization-failure";
            enum "authorization-success";
            enum "identity-update";
            enum "inactivity-timeout";
            enum "remote-authentication-failure";
            enum "remote-authentication-success";
            enum "session-disconnected";
            enum "session-started";
            enum "tag-added";
            enum "tag-removed";
            enum "template-activated";
            enum "template-activation-failed";
            enum "template-deactivated";
            enum "template-deactivation-failed";
            enum "timer-expiry";
            enum "violation";
          }
        }
        leaf match {
          type enumeration {
            enum "match-all";
            enum "match-first";
          }
        }
        list class-list {
          tailf:cli-drop-node-name;
          key "id";
          leaf id {
            type uint8;
          }
          leaf class {
            tailf:cli-hide-in-submode;
            type union {
              type string;
              type enumeration {
                enum "always";
              }
            }
          }
          leaf execute {
            tailf:cli-drop-node-name;
            tailf:cli-hide-in-submode;
            type enumeration {
              enum "do-all";
              enum "do-until-failure";
              enum "do-until-success";
            }
          }
          list action-list {
            tailf:cli-drop-node-name;
            tailf:cli-suppress-mode;
            tailf:cli-delete-when-empty;
            tailf:cli-compact-syntax;
            tailf:cli-sequence-commands {
              tailf:cli-reset-siblings;
            }
            key "id";
            leaf id {
              type uint8;
            }
            leaf action {
              tailf:cli-drop-node-name;
              type enumeration {
                enum "activate";
                enum "authenticate";
                enum "authentication-restart";
                enum "authorize";
                enum "notify";
                enum "set-domain";
                enum "set-timer";
                enum "unauthorize";
                enum "terminate";
                enum "restrict";
                enum "pause";
                enum "clear-session";
                enum "resume";
              }
            }
            leaf action-string {
              tailf:cli-drop-node-name;
              tailf:cli-multi-value;
              type string;
            }
          }
        }
      }
    }
  }
  container dot11 {
    leaf syslog {
      type empty;
    }
    list ssid {
      key "id";
      leaf id {
        type string;
      }
      leaf vlan {
        type string;
      }
      container authentication {
        container open {
          tailf:cli-delete-when-empty;
          tailf:cli-compact-syntax;
          presence "true";
          choice open-choice {
            leaf mac-address {
              type string;
            }
            leaf eap {
              type string;
            }
          }
        }
        leaf network-eap {
          type string;
        }
        container key-management {
          container wpa {
            tailf:cli-delete-when-empty;
            tailf:cli-compact-syntax;
            presence "true";
            leaf version {
              type enumeration {
                enum "1";
                enum "2";
              }
            }
            leaf optional {
              type empty;
            }
          }
        }
      }
      leaf guest-mode {
        type empty;
      }
      container mbssid {
        leaf guest-mode {
          type empty;
        }
      }
      container wpa-psk {
        choice wpa-psk-choice {
          container ascii {
            tailf:cli-compact-syntax;
            tailf:cli-sequence-commands;
            uses password-grouping {
              refine "secret";
            }
          }
          container hex {
            tailf:cli-compact-syntax;
            tailf:cli-sequence-commands;
            uses password-grouping {
              refine "secret";
            }
          }
        }
      }
    }
    container arp-cache {
      tailf:cli-delete-when-empty;
      presence "true";
      leaf optional {
        type empty;
      }
    }
  }
  container bridge {
    leaf irb {
      type empty;
    }
    list bridge-list {
      tailf:cli-drop-node-name;
      tailf:cli-suppress-mode;
      tailf:cli-delete-when-empty;
      key "id";
      leaf id {
        type uint8;
      }
      leaf protocol {
        type enumeration {
          enum "dec";
          enum "ibm";
          enum "ieee";
          enum "vlan-bridge";
        }
      }
      container bridge {
        leaf clns {
          type boolean;
        }
        leaf ip {
          type boolean;
        }
      }
      container route {
        leaf ip {
          type empty;
        }
      }
    }
  }
  container bridge-domain {
    list bridge-domain-list {
      tailf:cli-drop-node-name;
      key "id";
      leaf id {
        type uint16;
      }
      container ip {
        container igmp {
          container snooping {
            leaf immediate-leave {
              type empty;
            }
          }
          container snooping-enable {
            tailf:cli-drop-node-name;
            leaf snooping {
              type boolean;
            }
          }
        }
      }
      container member {
        leaf vni {
          type uint32;
        }
        leaf vfi {
          type string;
        }
        list interface-list {
          tailf:cli-drop-node-name;
          tailf:cli-suppress-mode;
          tailf:cli-delete-when-empty;
          key "name service-instance";
          leaf name {
            type string;
          }
          leaf service-instance {
            tailf:cli-expose-key-name;
            type uint16;
          }
          container split-horizon {
            leaf group {
              type uint8;
            }
          }
        }
        list ip-list {
          tailf:cli-drop-node-name;
          tailf:cli-suppress-mode;
          tailf:cli-delete-when-empty;
          tailf:cli-compact-syntax;
          key "address vcid";
          leaf address {
            type inet:ipv4-address;
          }
          leaf vcid {
            type uint32;
          }
          choice encapsulation-template-choice {
            container encapsulation {
              tailf:cli-flatten-container;
              tailf:cli-compact-syntax;
              leaf mpls {
                type empty;
              }
            }
            leaf template {
              type string;
            }
          }
        }
        container evpn-instance {
          tailf:cli-compact-syntax;
          tailf:cli-sequence-commands {
            tailf:cli-reset-siblings;
          }
          leaf id {
            tailf:cli-drop-node-name;
            type uint16;
          }
          leaf vni {
            type uint32;
          }
        }
        list pseudowire {
          tailf:cli-suppress-mode;
          tailf:cli-delete-when-empty;
          tailf:cli-compact-syntax;
          tailf:cli-sequence-commands;
          tailf:cli-allow-join-with-key;
          key "name";
          leaf name {
            type uint32;
          }
          leaf ip-address {
            tailf:cli-drop-node-name;
            type inet:ipv4-address;
          }
          leaf vc-id {
            tailf:cli-drop-node-name;
            tailf:cli-optional-in-sequence;
            type uint32;
          }
          choice encapsulation-template-choice {
            leaf encapsulation {
              type enumeration {
                enum "mpls";
              }
            }
            leaf template {
              type string;
            }
          }
        }
      }
      container mac {
        leaf learning {
          type boolean;
        }
        leaf aging-time {
          type uint16;
        }
        container limit {
          container maximum {
            leaf addresses {
              type uint32;
            }
          }
          container action {
            container flooding {
              leaf disable {
                type empty;
              }
            }
          }
        }
      }
      uses snmp-context-grouping;
      leaf shutdown {
        type empty;
      }
    }
  }
  list service-group {
    key "id";
    leaf id {
      type uint32;
    }
    leaf description {
      tailf:cli-multi-value;
      type string;
    }
    container service-policy {
      uses service-policy-grouping {
        refine "output";
        refine "input";
      }
    }
  }
  container service-instance {
    container mdns-sd {
      list service {
        key "name regtype domain";
        leaf name {
          type string;
        }
        leaf regtype {
          tailf:cli-expose-key-name;
          type string;
        }
        leaf domain {
          tailf:cli-expose-key-name;
          type string;
        }
        leaf target-hostname {
          type string;
        }
        leaf priority {
          type uint16;
        }
        leaf weight {
          type uint16;
        }
        leaf port {
          type uint32;
        }
        leaf txt {
          type string;
        }
        leaf ipv4addr {
          type inet:ipv4-address;
        }
        leaf ipv6addr {
          type inet:ipv6-address;
        }
      }
    }
  }
  container service-insertion {
    list service-node-group {
      key "name";
      leaf name {
        type string;
      }
      leaf description {
        type string;
      }
      list service-node {
        tailf:cli-suppress-mode;
        tailf:cli-delete-when-empty;
        key "ip-address";
        leaf ip-address {
          type inet:ipv4-address;
        }
      }
      leaf node-discovery {
        type enumeration {
          enum "enable";
        }
      }
    }
    list appnav-controller-group {
      key "name";
      leaf name {
        type string;
      }
      leaf description {
        type string;
      }
      list appnav-controller {
        tailf:cli-suppress-mode;
        tailf:cli-delete-when-empty;
        key "ip-address";
        leaf ip-address {
          type inet:ipv4-address;
        }
      }
    }
    list service-context {
      key "name";
      leaf name {
        type string;
      }
      leaf appnav-controller-group {
        type string;
      }
      leaf service-node-group {
        type string;
      }
      leaf service-policy {
        type string;
      }
      container vrf {
        choice c-type {
          leaf name {
            type string;
          }
          leaf default {
            type empty;
          }
          leaf global {
            type empty;
          }
        }
      }
      leaf enable {
        type empty;
      }
    }
  }
  container vtp {
    leaf file {
      type string;
    }
    leaf interface {
      type string;
    }
    leaf password {
      type string;
    }
    leaf pruning {
      type empty;
    }
    leaf version {
      type uint8;
    }
    leaf domain {
      type string;
    }
    leaf mode {
      type enumeration {
        enum "client";
        enum "off";
        enum "server";
        enum "transparent";
      }
    }
  }
  container cluster {
    leaf run {
      type empty;
    }
    container commander-address {
      tailf:cli-compact-syntax;
      tailf:cli-sequence-commands {
        tailf:cli-reset-siblings;
      }
      leaf address {
        tailf:cli-drop-node-name;
        type string;
      }
      leaf member {
        tailf:cli-optional-in-sequence;
        type uint16;
      }
      leaf name {
        type string;
      }
      leaf vlan {
        type uint16;
      }
    }
  }
  container link {
    container state {
      leaf-list track {
        type uint8;
      }
    }
  }
  container vlan {
    choice vlan-accounting-choice {
      leaf accounting {
        type boolean;
      }
      container accounting-input {
        tailf:cli-drop-node-name;
        container accounting {
          leaf input {
            type boolean;
          }
        }
      }
      container accounting-output {
        tailf:cli-drop-node-name;
        container accounting {
          leaf output {
            type boolean;
          }
        }
      }
    }
    list group {
      tailf:cli-suppress-mode;
      tailf:cli-delete-when-empty;
      key "name";
      leaf name {
        tailf:cli-suppress-range;
        type string;
      }
      leaf-list vlan-list {
        tailf:cli-range-list-syntax;
        type uint16;
      }
    }
    container internal {
      container reserved {
        container met {
          leaf vlan {
            type uint16;
          }
        }
      }
      container allocation {
        leaf policy {
          type enumeration {
            enum "ascending";
            enum "descending";
          }
        }
      }
    }
    container ifdescr {
      leaf detail {
        type empty;
      }
    }
    container dot1q {
      container tag {
        leaf native {
          type empty;
        }
      }
    }
    container access-log {
      leaf maxflow {
        type uint16;
      }
      leaf ratelimit {
        type uint16;
      }
      leaf threshold {
        type uint32;
      }
    }
    list filter {
      tailf:cli-suppress-mode;
      tailf:cli-delete-when-empty;
      tailf:cli-compact-syntax;
      key "name";
      leaf name {
        type string;
      }
      leaf-list vlan-list {
        tailf:cli-range-list-syntax;
        type uint16;
      }
    }
    list vlan-list {
      tailf:cli-drop-node-name;
      tailf:cli-range-list-syntax;
      key "id";
      leaf id {
        type uint16;
      }
      leaf name {
        tailf:cli-multi-value;
        type string;
      }
      leaf state {
        type enumeration {
          enum "active";
          enum "suspend";
        }
      }
      leaf shutdown {
        type empty;
      }
      leaf media {
        type enumeration {
          enum "ethernet";
          enum "fd-net";
          enum "fddi";
          enum "tokenring";
          enum "tr-net";
        }
      }
      leaf mtu {
        type uint16;
      }
      leaf remote-span {
        type empty;
      }
      leaf uni-vlan {
        type enumeration {
          enum "community";
          enum "isolated";
        }
      }
      container private-vlan {
        choice type-choice {
          leaf primary {
            type empty;
          }
          leaf community {
            type empty;
          }
          leaf isolated {
            type empty;
          }
        }
        container association {
          leaf-list vlans {
            tailf:cli-drop-node-name;
            tailf:cli-range-list-syntax;
            type uint16;
          }
        }
      }
      leaf said {
        type uint32;
      }
      container bridge {
        leaf value {
          tailf:cli-drop-node-name;
          type uint8;
        }
      }
      container stp {
        container type {
          tailf:cli-delete-when-empty;
          presence "true";
          leaf value {
            tailf:cli-drop-node-name;
            type enumeration {
              enum "auto";
              enum "ibm";
              enum "ieee";
            }
          }
        }
      }
      leaf tb-vlan1 {
        type uint16;
      }
      leaf tb-vlan2 {
        type uint16;
      }
      leaf parent {
        type uint16;
      }
      leaf backupcrf {
        type enumeration {
          enum "disable";
          enum "enable";
        }
      }
    }
    list configuration {
      tailf:cli-range-list-syntax;
      key "id";
      leaf id {
        type uint16;
      }
      container ip {
        container igmp {
          leaf snooping {
            type boolean;
          }
        }
        container flow {
          uses ip-flow-monitor-grouping;
        }
      }
      container ipv6 {
        container mld {
          leaf snooping {
            type boolean;
          }
        }
      }
      container service-policy {
        tailf:cli-compact-syntax;
        uses service-policy-grouping;
      }
      container device-tracking {
        tailf:cli-delete-when-empty;
        presence "true";
        leaf attach-policy {
          type string;
        }
      }
      container member {
        container evpn-instance {
          tailf:cli-compact-syntax;
          tailf:cli-sequence-commands;
          leaf id {
            tailf:cli-drop-node-name;
            type uint16;
          }
          leaf vni {
            type uint32;
          }
        }
        leaf vni {
          type uint32;
        }
      }
    }
    list access-map {
      key "name number";
      leaf name {
        type string;
      }
      leaf number {
        type uint16;
      }
      container action {
        choice action-choice {
          container drop {
            presence "true";
          }
          container forward {
            tailf:cli-delete-when-empty;
            presence "true";
            leaf capture {
              type empty;
            }
          }
        }
      }
      container match {
        container mac {
          leaf-list address {
            tailf:cli-flat-list-syntax;
            type string;
          }
        }
        container ip {
          leaf-list address {
            tailf:cli-flat-list-syntax;
            type exp-ip-acl-type;
          }
        }
      }
    }
  }
  container lldp {
    leaf run {
      type empty;
    }
    leaf timer {
      type uint16;
    }
    leaf holdtime {
      type uint16;
    }
    leaf reinit {
      type uint8;
    }
  }
  container EXEC {
    tailf:cli-drop-node-name;
  }
  container pm-agent {
    tailf:cli-add-mode;
    presence "true";
    container tenant {
      tailf:cli-compact-syntax;
      tailf:cli-sequence-commands {
        tailf:cli-reset-siblings;
      }
      leaf id {
        type uint32;
      }
      leaf name {
        type string;
      }
    }
    container region {
      tailf:cli-compact-syntax;
      tailf:cli-sequence-commands {
        tailf:cli-reset-siblings;
      }
      leaf id {
        type uint32;
      }
      leaf name {
        type string;
      }
    }
    container site {
      tailf:cli-compact-syntax;
      tailf:cli-sequence-commands {
        tailf:cli-reset-siblings;
      }
      leaf id {
        type uint32;
      }
      leaf name {
        type string;
      }
    }
    container device {
      container id {
        tailf:cli-compact-syntax;
        tailf:cli-sequence-commands {
          tailf:cli-reset-siblings;
        }
        leaf id {
          tailf:cli-drop-node-name;
          type uint32;
        }
        leaf name {
          type string;
        }
      }
      leaf type {
        type enumeration {
          enum "ntr";
          enum "pxtr";
          enum "rtr";
          enum "xtr";
        }
      }
    }
    container pmcs {
      list ipv4 {
        tailf:cli-suppress-mode;
        tailf:cli-delete-when-empty;
        key "address";
        leaf address {
          type inet:ipv4-address;
        }
      }
      list ipv6 {
        tailf:cli-suppress-mode;
        tailf:cli-delete-when-empty;
        key "address";
        leaf address {
          type inet:ipv6-address;
        }
      }
    }
    list instance-id {
      key "id";
      leaf id {
        type uint32;
      }
      container enterprise-prefix {
        leaf prefix-list {
          type string;
        }
        container ipv4 {
          leaf prefix-list {
            type string;
          }
        }
        container ipv6 {
          leaf prefix-list {
            type string;
          }
        }
      }
    }
    leaf shutdown {
      type empty;
    }
  }
  container mka {
    list policy {
      key "name";
      leaf name {
        type string;
      }
      container key-server {
        leaf priority {
          type uint8;
        }
      }
      leaf-list macsec-cipher-suite {
        tailf:cli-flat-list-syntax;
        ordered-by user;
        type enumeration {
          enum "gcm-aes-128";
          enum "gcm-aes-256";
          enum "gcm-aes-xpn-256";
        }
      }
      leaf confidentiality-offset {
        type enumeration {
          enum "0";
          enum "30";
          enum "50";
        }
      }
      container sak-rekey {
        leaf interval {
          type uint16;
        }
        leaf on-live-peer-loss {
          type empty;
        }
      }
      leaf send-secure-announcements {
        type empty;
      }
      leaf ssci-based-on-sci {
        type empty;
      }
      leaf include-icv-indicator {
        type boolean;
      }
      leaf use-updated-eth-header {
        type empty;
      }
    }
  }
  container crypto {
    list keyring {
      key "name";
      leaf name {
        type string;
      }
      leaf vrf {
        tailf:cli-hide-in-submode;
        type string;
      }
      uses description-grouping;
      container local-address {
        uses interface-name-grouping;
      }
      container pre-shared-key {
        list address {
          tailf:cli-suppress-mode;
          tailf:cli-delete-when-empty;
          tailf:cli-compact-syntax;
          key "address";
          leaf ipv6 {
            tailf:cli-prefix-key;
            type empty;
          }
          leaf address {
            tailf:cli-suppress-range;
            type union {
              type inet:ipv4-address;
              type inet:ipv6-address;
              type ipv6-prefix;
            }
          }
          leaf mask {
            tailf:cli-drop-node-name;
            type inet:ipv4-address;
          }
          container key {
            tailf:cli-flatten-container;
            tailf:cli-compact-syntax;
            tailf:cli-sequence-commands;
            uses crypto-key-grouping {
              refine "secret";
            }
          }
        }
        list hostname {
          tailf:cli-suppress-mode;
          tailf:cli-delete-when-empty;
          tailf:cli-compact-syntax;
          key "name";
          leaf name {
            tailf:cli-suppress-range;
            type string;
          }
          container key {
            tailf:cli-flatten-container;
            tailf:cli-compact-syntax;
            tailf:cli-sequence-commands;
            uses crypto-key-grouping {
              refine "secret";
            }
          }
        }
      }
      container rsa-pubkey {
        list address {
          key "ip-address type";
          leaf ip-address {
            type inet:ipv4-address;
          }
          leaf type {
            type enumeration {
              enum "signature";
              enum "encryption";
            }
          }
          leaf address {
            type inet:ipv4-address;
          }
          container key-string {
            tailf:cli-add-mode;
            leaf hex-data {
              tailf:cli-drop-node-name;
              type string;
            }
          }
        }
      }
    }
    container key {
      container pubkey-chain {
        container rsa {
          tailf:cli-add-mode;
          list addressed-key {
            key "address";
            leaf address {
              type inet:ipv4-address;
            }
            container key-string {
              tailf:cli-add-mode;
              leaf hex-data {
                tailf:cli-drop-node-name;
                type string;
              }
            }
          }
        }
      }
    }
    container logging {
      leaf session {
        type empty;
      }
      leaf ikev2 {
        type empty;
      }
    }
    container ikev2 {
      list name-mangler {
        key "name";
        leaf name {
          type string;
        }
        container eap {
          choice eap-choice {
            leaf all {
              type empty;
            }
            container suffix {
              leaf delimiter {
                type enumeration {
                  enum ".";
                  enum "@";
                }
              }
            }
          }
        }
        leaf fqdn {
          type enumeration {
            enum "all";
            enum "domain";
            enum "hostname";
          }
        }
        leaf dn {
          type enumeration {
            enum "common-name";
            enum "country";
            enum "domain";
            enum "locality";
            enum "organization";
            enum "organization-unit";
            enum "state";
          }
        }
        leaf email {
          type enumeration {
            enum "all";
            enum "domain";
            enum "username";
          }
        }
      }
      container authorization {
        list policy {
          key "name";
          leaf name {
            type string;
          }
          leaf pool {
            type string;
          }
          leaf netmask {
            type inet:ipv4-address;
          }
          container aaa {
            container attribute {
              leaf list {
                type string;
              }
            }
          }
          container ipv6 {
            leaf prefix {
              type uint8;
            }
            leaf pool {
              type string;
            }
            leaf dns {
              type inet:ipv6-address;
            }
          }
          container route {
            container set {
              container remote {
                list ipv4 {
                  tailf:cli-suppress-mode;
                  tailf:cli-delete-when-empty;
                  key "prefix mask";
                  leaf prefix {
                    type inet:ipv4-address;
                  }
                  leaf mask {
                    type inet:ipv4-address;
                  }
                }
                list ipv6 {
                  tailf:cli-suppress-mode;
                  tailf:cli-delete-when-empty;
                  key "address";
                  leaf address {
                    type ipv6-prefix;
                  }
                }
              }
              container access-list {
                leaf ipv4 {
                  tailf:cli-drop-node-name;
                  type std-ip-acl-type;
                }
                leaf ipv6 {
                  type string;
                }
              }
              container interface {
                presence "true";
              }
              container interface-list {
                tailf:cli-drop-node-name;
                list interface {
                  tailf:cli-suppress-mode;
                  tailf:cli-delete-when-empty;
                  key "name";
                  leaf name {
                    type string;
                  }
                }
              }
            }
            container accept {
              choice any-choice {
                container any-enable {
                  tailf:cli-drop-node-name;
                  leaf any {
                    type boolean;
                  }
                }
                container any {
                  choice any-choice {
                    leaf distance {
                      type uint8;
                    }
                    leaf tag {
                      type uint32;
                    }
                  }
                }
              }
            }
          }
          leaf session-lifetime {
            type uint32;
          }
          container dns {
            tailf:cli-compact-syntax;
            tailf:cli-sequence-commands {
              tailf:cli-reset-siblings;
            }
            leaf primary {
              tailf:cli-drop-node-name;
              type inet:ipv4-address;
            }
            leaf secondary {
              tailf:cli-drop-node-name;
              type inet:ipv4-address;
            }
          }
        }
      }
      container redirect {
        container client {
          tailf:cli-delete-when-empty;
          presence "true";
          leaf max-redirects {
            type uint8;
          }
        }
      }
      list keyring {
        key "name";
        leaf name {
          type string;
        }
        list peer {
          key "name";
          leaf name {
            type string;
          }
          leaf description {
            tailf:cli-multi-value;
            type string;
          }
          container address {
            tailf:cli-compact-syntax;
            tailf:cli-sequence-commands {
              tailf:cli-reset-siblings;
            }
            choice address-choice {
              case ipv4 {
                leaf ipv4-address {
                  tailf:cli-drop-node-name;
                  type inet:ipv4-address;
                }
                leaf ipv4-mask {
                  tailf:cli-drop-node-name;
                  type inet:ipv4-address;
                }
              }
              case ipv6 {
                leaf ipv6-address {
                  tailf:cli-drop-node-name;
                  type ipv6-prefix;
                }
              }
            }
          }
          container identity {
            choice identity-choice {
              leaf key-id {
                type string;
              }
              container fqdn {
                tailf:cli-compact-syntax;
                tailf:cli-sequence-commands;
                leaf domain {
                  tailf:cli-optional-in-sequence;
                  type empty;
                }
                leaf name {
                  tailf:cli-drop-node-name;
                  type string;
                }
              }
              container email {
                tailf:cli-compact-syntax;
                tailf:cli-sequence-commands;
                leaf domain {
                  tailf:cli-optional-in-sequence;
                  type empty;
                }
                leaf name {
                  tailf:cli-drop-node-name;
                  type string;
                }
              }
              leaf address {
                type union {
                  type inet:ipv4-address;
                  type inet:ipv6-address;
                }
              }
            }
          }
          container pre-shared-key {
            tailf:cli-flatten-container;
            tailf:cli-compact-syntax;
            tailf:cli-sequence-commands;
            choice pre-shared-key-choice {
              case one-case {
                uses crypto-key-grouping {
                  refine "secret";
                }
              }
              case local-remote-case {
                container local {
                  tailf:cli-optional-in-sequence;
                  tailf:cli-compact-syntax;
                  tailf:cli-sequence-commands;
                  uses crypto-key-grouping {
                    refine "secret";
                  }
                }
                container remote {
                  tailf:cli-compact-syntax;
                  tailf:cli-sequence-commands;
                  uses crypto-key-grouping {
                    refine "secret";
                  }
                }
              }
            }
          }
          container ppk {
            container manual {
              tailf:cli-compact-syntax;
              tailf:cli-sequence-commands {
                tailf:cli-reset-siblings;
              }
              leaf id {
                type string;
              }
              container key {
                tailf:cli-flatten-container;
                tailf:cli-compact-syntax;
                tailf:cli-sequence-commands;
                uses crypto-key-grouping {
                  refine "secret";
                }
              }
              leaf Required {
                tailf:cli-case-sensitive;
                type empty;
              }
            }
          }
        }
      }
      leaf proposal-default-disabled {
        type empty;
      }
      list proposal {
        key "name";
        leaf name {
          type string;
        }
        leaf-list encryption {
          tailf:cli-flat-list-syntax;
          ordered-by user;
          type enumeration {
            enum "aes-cbc-128";
            enum "3des";
            enum "aes-cbc-192";
            enum "aes-cbc-256";
            enum "des";
            enum "aes-gcm-128";
            enum "aes-gcm-256";
          }
        }
        leaf-list prf {
          tailf:cli-flat-list-syntax;
          ordered-by user;
          type enumeration {
            enum "md5";
            enum "sha1";
            enum "sha256";
            enum "sha384";
            enum "sha512";
          }
        }
        leaf-list integrity {
          tailf:cli-flat-list-syntax;
          ordered-by user;
          type enumeration {
            enum "md5";
            enum "sha1";
            enum "sha256";
            enum "sha384";
            enum "sha512";
          }
        }
        leaf-list group {
          tailf:cli-flat-list-syntax;
          ordered-by user;
          type enumeration {
            enum "1";
            enum "14";
            enum "15";
            enum "16";
            enum "19";
            enum "2";
            enum "20";
            enum "21";
            enum "24";
            enum "5";
          }
        }
      }
      leaf policy-default-disabled {
        type empty;
      }
      list policy {
        key "name";
        leaf name {
          type string;
        }
        leaf-list proposal {
          ordered-by user;
          type string;
        }
        container match {
          leaf fvrf {
            type union {
              type string;
              type enumeration {
                enum "any";
              }
            }
          }
          container address {
            list local {
              tailf:cli-suppress-mode;
              tailf:cli-delete-when-empty;
              key "address";
              leaf address {
                type union {
                  type inet:ipv4-address;
                  type inet:ipv6-address;
                }
              }
            }
          }
        }
      }
      list profile {
        key "name";
        leaf name {
          type string;
        }
        leaf description {
          tailf:cli-multi-value;
          type string;
        }
        leaf ivrf {
          type string;
        }
        container match {
          list certificate {
            tailf:cli-suppress-mode;
            tailf:cli-delete-when-empty;
            key "name";
            leaf name {
              type string;
            }
          }
          container address {
            container local-interface {
              tailf:cli-drop-node-name;
              container local {
                list interface {
                  tailf:cli-suppress-mode;
                  tailf:cli-delete-when-empty;
                  key "name";
                  leaf name {
                    type string;
                  }
                }
              }
            }
            list local {
              tailf:cli-suppress-mode;
              tailf:cli-delete-when-empty;
              key "address";
              leaf address {
                type inet:host;
              }
            }
          }
          leaf fvrf {
            type union {
              type string;
              type enumeration {
                enum "any";
              }
            }
          }
          container identity {
            container remote {
              leaf any {
                type empty;
              }
              list key-id {
                tailf:cli-suppress-mode;
                tailf:cli-delete-when-empty;
                key "name";
                leaf name {
                  type string;
                }
              }
              container fqdn {
                list fqdn-list {
                  tailf:cli-drop-node-name;
                  tailf:cli-suppress-mode;
                  tailf:cli-delete-when-empty;
                  key "name";
                  leaf name {
                    type string;
                  }
                }
                list domain {
                  tailf:cli-suppress-mode;
                  tailf:cli-delete-when-empty;
                  key "name";
                  leaf name {
                    type string;
                  }
                }
              }
              list address {
                tailf:cli-suppress-mode;
                tailf:cli-delete-when-empty;
                tailf:cli-compact-syntax;
                key "name";
                leaf name {
                  type union {
                    type inet:ipv4-address;
                    type ipv6-prefix;
                  }
                }
                leaf mask {
                  tailf:cli-drop-node-name;
                  type inet:ipv4-address;
                }
              }
              container email {
                list exact {
                  tailf:cli-drop-node-name;
                  tailf:cli-suppress-mode;
                  tailf:cli-delete-when-empty;
                  key "name";
                  leaf name {
                    type string;
                  }
                }
                list domain {
                  tailf:cli-suppress-mode;
                  tailf:cli-delete-when-empty;
                  key "name";
                  leaf name {
                    type string;
                  }
                }
              }
            }
          }
        }
        container identity {
          container local {
            choice local-choice {
              leaf dn {
                type empty;
              }
              leaf email {
                type string;
              }
              leaf fqdn {
                type string;
              }
              leaf address {
                type union {
                  type inet:ipv4-address;
                  type inet:ipv6-address;
                }
              }
            }
          }
        }
        container authentication {
          container local {
            choice method-choice {
              container eap {
                presence "true";
              }
              leaf ecdsa-sig {
                type empty;
              }
              container pre-share {
                tailf:cli-flatten-container;
                tailf:cli-compact-syntax;
                tailf:cli-delete-when-empty;
                presence "true";
                container key {
                  tailf:cli-flatten-container;
                  tailf:cli-compact-syntax;
                  tailf:cli-sequence-commands;
                  uses crypto-key-grouping {
                    refine "secret";
                  }
                }
              }
              leaf rsa-sig {
                type empty;
              }
            }
          }
          container remote {
            tailf:cli-delete-when-empty;
            presence "true";
            container eap {
              tailf:cli-delete-when-empty;
              presence "true";
              leaf query-identity {
                type empty;
              }
            }
            leaf ecdsa-sig {
              type empty;
            }
            container pre-share {
              tailf:cli-flatten-container;
              tailf:cli-compact-syntax;
              tailf:cli-delete-when-empty;
              presence "true";
              container key {
                tailf:cli-flatten-container;
                tailf:cli-compact-syntax;
                tailf:cli-sequence-commands;
                uses crypto-key-grouping {
                  refine "secret";
                }
              }
            }
            leaf rsa-sig {
              type empty;
            }
            container anyconnect-eap {
              container aggregate {
                presence "true";
              }
            }
          }
        }
        container pki {
          leaf-list trustpoint {
            type string;
          }
        }
        container keyring {
          leaf ppk {
            type string;
          }
          choice keyring-choice {
            container aaa {
              tailf:cli-compact-syntax;
              tailf:cli-sequence-commands {
                tailf:cli-reset-siblings;
              }
              leaf name {
                tailf:cli-drop-node-name;
                type string;
              }
              leaf name-mangler {
                type string;
              }
            }
            leaf local {
              type string;
            }
          }
        }
        container nat {
          leaf keepalive {
            type uint16;
          }
        }
        container aaa {
          container authentication {
            leaf eap {
              type string;
            }
            leaf anyconnect-eap {
              type string;
            }
          }
          container authorization {
            container group {
              container psk {
                uses crypto-ikev2-profile-aaa-authorization-group-list;
              }
              container eap {
                uses crypto-ikev2-profile-aaa-authorization-group-list;
              }
              container cert {
                uses crypto-ikev2-profile-aaa-authorization-group-list;
              }
              container anyconnect-eap {
                uses crypto-ikev2-profile-aaa-authorization-group-list;
              }
            }
            container user {
              container psk {
                leaf cached {
                  type empty;
                }
                leaf list {
                  type string;
                }
              }
              container anyconnect-eap {
                leaf cached {
                  type empty;
                }
                leaf list {
                  type string;
                }
              }
            }
          }
          container accounting {
            leaf cert {
              type string;
            }
            leaf anyconnect-eap {
              type string;
            }
          }
        }
        container virtual-template {
          tailf:cli-compact-syntax;
          tailf:cli-sequence-commands;
          leaf number {
            tailf:cli-drop-node-name;
            type uint16;
          }
          leaf mode {
            type enumeration {
              enum "auto";
            }
          }
        }
        leaf lifetime {
          type uint32;
        }
        container lifetime-certificate {
          tailf:cli-drop-node-name;
          container lifetime {
            leaf certificate {
              type boolean;
            }
          }
        }
        container dpd {
          tailf:cli-compact-syntax;
          tailf:cli-sequence-commands;
          leaf interval {
            tailf:cli-drop-node-name;
            type uint16;
          }
          leaf retry-interval {
            tailf:cli-drop-node-name;
            type uint8;
          }
          leaf queries {
            tailf:cli-drop-node-name;
            type enumeration {
              enum "on-demand";
              enum "periodic";
            }
          }
        }
        container config-exchange {
          container set {
            leaf send {
              type boolean;
            }
            leaf accept {
              type boolean;
            }
          }
          leaf request {
            type boolean;
          }
        }
      }
      container fragmentation {
        tailf:cli-delete-when-empty;
        presence "true";
        leaf mtu {
          type uint16;
        }
      }
      container http-url {
        leaf cert {
          type boolean;
        }
      }
      container client {
        list flexvpn {
          key "name";
          leaf name {
            type string;
          }
          container peer {
            list peer-list {
              tailf:cli-drop-node-name;
              tailf:cli-suppress-mode;
              tailf:cli-delete-when-empty;
              tailf:cli-compact-syntax;
              tailf:cli-sequence-commands {
                tailf:cli-reset-siblings;
              }
              key "sequence";
              leaf sequence {
                type uint8;
              }
              choice address-choice {
                leaf ipv4-address {
                  tailf:cli-drop-node-name;
                  type inet:ipv4-address;
                }
                leaf ipv6-address {
                  tailf:cli-drop-node-name;
                  type inet:ipv6-address;
                }
                case fqdn {
                  leaf fqdn {
                    type string;
                  }
                  leaf dynamic {
                    tailf:cli-optional-in-sequence;
                    type empty;
                  }
                  leaf ipv6 {
                    tailf:cli-optional-in-sequence;
                    type empty;
                  }
                }
              }
              leaf track {
                type uint16;
              }
            }
            leaf reactivate {
              type empty;
            }
          }
          list source {
            tailf:cli-suppress-mode;
            tailf:cli-delete-when-empty;
            tailf:cli-compact-syntax;
            tailf:cli-sequence-commands {
              tailf:cli-reset-siblings;
            }
            key "seq";
            leaf seq {
              type uint8;
            }
            container interface {
              tailf:cli-drop-node-name;
              tailf:cli-flatten-container;
              tailf:cli-compact-syntax;
              uses interface-name-grouping;
            }
            leaf track {
              type uint16;
            }
          }
          container client {
            container connect {
              leaf Tunnel {
                tailf:cli-allow-join-with-value;
                type uint32;
              }
            }
          }
        }
      }
      container dpd {
        tailf:cli-compact-syntax;
        tailf:cli-sequence-commands {
          tailf:cli-reset-siblings;
        }
        leaf interval {
          tailf:cli-drop-node-name;
          type uint32;
        }
        leaf retry-interval {
          tailf:cli-drop-node-name;
          type uint32;
        }
        leaf mode {
          tailf:cli-drop-node-name;
          type enumeration {
            enum "on-demand";
            enum "periodic";
          }
        }
      }
      container diagnose {
        leaf error {
          type uint16;
        }
      }
      container limit {
        container max-in-negotation-sa {
          container incoming {
            tailf:cli-drop-node-name;
            leaf value {
              tailf:cli-drop-node-name;
              type uint16;
            }
          }
          container outgoing {
            tailf:cli-drop-node-name;
            tailf:cli-compact-syntax;
            tailf:cli-sequence-commands {
              tailf:cli-reset-siblings;
            }
            leaf value {
              tailf:cli-drop-node-name;
              type uint16;
            }
            leaf outgoing {
              type empty;
            }
          }
        }
        container queue {
          leaf sa-init {
            type uint32;
          }
        }
      }
      leaf window {
        type uint8;
      }
      leaf cookie-challenge {
        type uint16;
      }
      leaf certificate-cache {
        type uint16;
      }
    }
    container ca {
      container certificate {
        list chain {
          key "name";
          leaf name {
            type string;
          }
          list certificate {
            tailf:cli-delete-when-empty;
            tailf:cli-compact-syntax;
            tailf:cli-sequence-commands;
            key "serial";
            leaf serial {
              type string;
            }
            leaf cert-type {
              tailf:cli-optional-in-sequence;
              tailf:cli-drop-node-name;
              tailf:cli-prefix-key;
              type enumeration {
                enum "ca";
                enum "ra-encrypt";
                enum "ra-general";
                enum "ra-sign";
                enum "rollover";
                enum "self-signed";
              }
            }
            leaf rollover {
              tailf:cli-optional-in-sequence;
              tailf:cli-prefix-key;
              type empty;
            }
            leaf cert {
              tailf:cli-drop-node-name;
              type string;
            }
          }
        }
      }
    }
    container pki {
      list server {
        key "cs-label";
        leaf cs-label {
          type string;
        }
        container database {
          leaf level {
            type enumeration {
              enum "minimum";
              enum "names";
              enum "complete";
            }
          }
          choice archive-choice {
            container no-archice {
              tailf:cli-drop-node-name;
              leaf archive {
                type boolean;
              }
            }
            container archive {
              tailf:cli-compact-syntax;
              tailf:cli-sequence-commands;
              leaf format {
                tailf:cli-drop-node-name;
                type enumeration {
                  enum "pem";
                  enum "pkcs12";
                }
              }
              container password {
                tailf:cli-flatten-container;
                tailf:cli-compact-syntax;
                tailf:cli-sequence-commands {
                  tailf:cli-reset-siblings;
                }
                leaf type {
                  tailf:cli-drop-node-name;
                  tailf:cli-optional-in-sequence;
                  type uint8;
                }
                leaf secret {
                  tailf:cli-drop-node-name;
                  type string;
                }
              }
            }
          }
          container url {
            tailf:cli-compact-syntax;
            tailf:cli-sequence-commands {
              tailf:cli-reset-siblings;
            }
            leaf file-type {
              tailf:cli-drop-node-name;
              tailf:cli-optional-in-sequence;
              type enumeration {
                enum "cnm";
                enum "crl";
                enum "crt";
                enum "p12";
                enum "pem";
                enum "ser";
              }
            }
            leaf root-url {
              tailf:cli-drop-node-name;
              type string;
            }
          }
        }
        leaf issuer-name {
          type string;
        }
        leaf grant {
          type enumeration {
            enum "auto";
            enum "none";
            enum "ra-auto";
          }
        }
        container lifetime {
          container certificate {
            tailf:cli-compact-syntax;
            tailf:cli-sequence-commands {
              tailf:cli-reset-siblings;
            }
            uses crypto-pki-server-lifetime-grouping {
              refine "days";
            }
          }
          container ca-certificate {
            tailf:cli-compact-syntax;
            tailf:cli-sequence-commands {
              tailf:cli-reset-siblings;
            }
            uses crypto-pki-server-lifetime-grouping {
              refine "days";
            }
          }
        }
        leaf hash {
          type enumeration {
            enum "md5";
            enum "sha1";
            enum "sha256";
            enum "sha384";
            enum "sha512";
          }
        }
        leaf cdp-url {
          type string;
        }
        leaf shutdown {
          type empty;
        }
      }
      list trustpoint {
        key "id";
        leaf id {
          type string;
        }
        container serial-number {
          presence "true";
          leaf none {
            type empty;
          }
        }
        leaf ip-address {
          type union {
            type string;
            type enumeration {
              enum "none";
            }
          }
        }
        container enrollment {
          leaf http-proxy {
            type string;
          }
          container retry {
            leaf count {
              type uint8;
            }
            leaf period {
              type uint8;
            }
          }
          container mode {
            leaf ra {
              type empty;
            }
          }
          leaf pkcs12 {
            type empty;
          }
          leaf profile {
            type string;
          }
          choice enrollment-choice {
            leaf selfsigned {
              type empty;
            }
            container terminal {
              tailf:cli-delete-when-empty;
              presence "true";
              leaf pem {
                type empty;
              }
            }
            leaf url {
              type string;
            }
            container url-pem {
              tailf:cli-drop-node-name;
              tailf:cli-compact-syntax;
              tailf:cli-sequence-commands;
              leaf url {
                type string;
              }
              leaf pem {
                type empty;
              }
            }
          }
        }
        container query {
          leaf certificate {
            type empty;
          }
        }
        container crl {
          container cache {
            choice cache-choice {
              leaf delete-after {
                type uint16;
              }
              leaf extend {
                type uint16;
              }
              leaf none {
                type empty;
              }
            }
          }
        }
        container password {
          tailf:cli-compact-syntax;
          tailf:cli-sequence-commands;
          uses password-grouping {
            refine "secret";
          }
        }
        leaf subject-name {
          type string;
        }
        leaf subject-alt-name {
          type string;
        }
        container chain-validation {
          choice validation-choice {
            leaf continue {
              type string;
            }
            leaf validation {
              tailf:cli-drop-node-name;
              type enumeration {
                enum "stop";
              }
            }
          }
        }
        leaf fqdn {
          type union {
            type enumeration {
              enum "none";
            }
            type string;
          }
        }
        container usage {
          leaf ike {
            type empty;
          }
          leaf ssl-server {
            type empty;
          }
          leaf ssl-client {
            type empty;
          }
        }
        leaf fingerprint {
          type string;
        }
        leaf vrf {
          type string;
        }
        leaf-list revocation-check {
          tailf:cli-flat-list-syntax;
          ordered-by user;
          type enumeration {
            enum "crl";
            enum "none";
            enum "ocsp";
          }
        }
        leaf hash {
          type enumeration {
            enum "md5";
            enum "sha1";
            enum "sha256";
            enum "sha384";
            enum "sha512";
          }
        }
        container source {
          container interface {
            uses interface-name-grouping;
          }
        }
        container rsakeypair {
          tailf:cli-compact-syntax;
          tailf:cli-sequence-commands {
            tailf:cli-reset-siblings;
          }
          leaf key-label {
            tailf:cli-drop-node-name;
            type string;
          }
          leaf key-size {
            tailf:cli-drop-node-name;
            type uint16;
          }
          leaf encryption-key-size {
            tailf:cli-drop-node-name;
            type uint16;
          }
        }
        container authorization {
          leaf list {
            type string;
          }
          container username {
            tailf:cli-flatten-container;
            tailf:cli-compact-syntax;
            choice username-choice {
              leaf alt-subjectname {
                type enumeration {
                  enum "userprinciplename";
                }
              }
              leaf subjectname {
                type subjectname-type;
              }
            }
          }
          container username-secondary {
            tailf:cli-drop-node-name;
            tailf:cli-compact-syntax;
            tailf:cli-sequence-commands {
              tailf:cli-reset-siblings;
            }
            container username {
              tailf:cli-flatten-container;
              tailf:cli-compact-syntax;
              choice username-choice {
                leaf alt-subjectname {
                  type enumeration {
                    enum "userprinciplename";
                  }
                }
                leaf subjectname {
                  type subjectname-type;
                }
              }
            }
            leaf secondary {
              type empty;
            }
          }
        }
        container auto-enroll {
          tailf:cli-compact-syntax;
          tailf:cli-delete-when-empty;
          presence "true";
          leaf percent {
            tailf:cli-drop-node-name;
            type uint8;
          }
          leaf regenerate {
            type empty;
          }
        }
        container match {
          leaf certificate {
            type string;
          }
        }
        container eku {
          leaf-list request {
            tailf:cli-flat-list-syntax;
            type enumeration {
              enum "client-auth";
              enum "code-signing";
              enum "email-protection";
              enum "ipsec-end-system";
              enum "ipsec-tunnel";
              enum "ipsec-user";
              enum "ocsp-signing";
              enum "server-auth";
              enum "ssh-client";
              enum "ssh-server";
              enum "time-stamping";
            }
          }
        }
      }
      container profile {
        list enrollment {
          key "name";
          leaf name {
            type string;
          }
          container authentication {
            choice url-choice {
              leaf url {
                type string;
              }
              container url-vrf {
                tailf:cli-drop-node-name;
                tailf:cli-compact-syntax;
                tailf:cli-sequence-commands;
                leaf url {
                  type string;
                }
                leaf vrf {
                  type string;
                }
              }
            }
            leaf command {
              type string;
            }
          }
          container enrollment {
            container url {
              tailf:cli-compact-syntax;
              tailf:cli-sequence-commands;
              leaf path {
                tailf:cli-drop-node-name;
                type string;
              }
              leaf vrf {
                type string;
              }
            }
          }
        }
      }
      container certificate {
        list map {
          key "name seq";
          leaf name {
            type string;
          }
          leaf seq {
            type uint16;
          }
          list alt-subject-name {
            tailf:cli-suppress-mode;
            tailf:cli-delete-when-empty;
            ordered-by user;
            key "criteria value";
            leaf criteria {
              type enumeration {
                enum "co";
                enum "eq";
                enum "nc";
                enum "ne";
              }
            }
            leaf value {
              tailf:cli-multi-word-key;
              type string;
            }
          }
          list subject-name {
            tailf:cli-suppress-mode;
            tailf:cli-delete-when-empty;
            ordered-by user;
            key "criteria value";
            leaf criteria {
              type enumeration {
                enum "co";
                enum "eq";
                enum "nc";
                enum "ne";
              }
            }
            leaf value {
              tailf:cli-multi-word-key;
              type string;
            }
          }
        }
        list chain {
          key "name";
          leaf name {
            type string;
          }
          uses crypto-pki-certificate-grouping;
        }
        container pool {
          tailf:cli-add-mode;
          leaf cabundle {
            type string;
          }
          uses crypto-pki-certificate-grouping;
        }
      }
      container token {
        list token-name {
          tailf:cli-drop-node-name;
          tailf:cli-suppress-mode;
          tailf:cli-delete-when-empty;
          key "name";
          leaf name {
            type string;
          }
          uses crypto-pki-token-grouping;
        }
      }
      container default {
        uses crypto-pki-token-grouping;
      }
    }
    container isakmp {
      container default {
        leaf policy {
          type boolean;
        }
      }
      leaf enable {
        type boolean;
      }
      container aggressive-mode {
        leaf disable {
          type empty;
        }
      }
      leaf identity {
        type enumeration {
          enum "address";
          enum "dn";
          enum "hostname";
        }
      }
      leaf fragmentation {
        type empty;
      }
      leaf invalid-spi-recovery {
        type empty;
      }
      container client {
        container configuration {
          list group {
            key "name";
            leaf name {
              type string;
            }
            container key {
              tailf:cli-flatten-container;
              tailf:cli-compact-syntax;
              tailf:cli-sequence-commands;
              uses crypto-key-grouping {
                refine "secret";
              }
            }
            container dns {
              tailf:cli-compact-syntax;
              tailf:cli-sequence-commands {
                tailf:cli-reset-siblings;
              }
              leaf primary {
                tailf:cli-drop-node-name;
                type inet:ipv4-address;
              }
              leaf secondary {
                tailf:cli-drop-node-name;
                type inet:ipv4-address;
              }
            }
            leaf pool {
              type string;
            }
            leaf save-password {
              type empty;
            }
            leaf max-users {
              type uint16;
            }
            leaf netmask {
              type inet:ipv4-address;
            }
          }
        }
      }
      list profile {
        key "name";
        leaf name {
          type string;
        }
        leaf description {
          tailf:cli-multi-value;
          type string;
        }
        leaf vrf {
          type string;
        }
        container ca {
          leaf-list trust-point {
            ordered-by user;
            type string;
          }
        }
        list keyring {
          tailf:cli-suppress-mode;
          tailf:cli-delete-when-empty;
          key "name";
          leaf name {
            type union {
              type enumeration {
                enum "default";
              }
              type string;
            }
          }
        }
        container self-identity {
          choice self-identity-choice {
            container address {
              presence "true";
            }
            container address-ipv6 {
              tailf:cli-drop-node-name;
              leaf address {
                type enumeration {
                  enum "ipv6";
                }
              }
            }
            container fqdn {
              tailf:cli-delete-when-empty;
              presence "true";
              leaf id {
                tailf:cli-drop-node-name;
                type string;
              }
            }
            leaf user-fqdn {
              type string;
            }
          }
        }
        container match {
          leaf fvrf {
            type union {
              type string;
              type enumeration {
                enum "any";
              }
            }
          }
          container identity {
            list group {
              tailf:cli-suppress-mode;
              tailf:cli-delete-when-empty;
              key "name";
              leaf name {
                type string;
              }
            }
            container address {
              list ipv4 {
                tailf:cli-drop-node-name;
                tailf:cli-suppress-mode;
                tailf:cli-delete-when-empty;
                key "address mask";
                leaf address {
                  type inet:ipv4-address;
                }
                leaf mask {
                  type inet:ipv4-address;
                }
                leaf vrf {
                  tailf:cli-drop-node-name;
                  type string;
                }
              }
              container ipv4-host {
                tailf:cli-drop-node-name;
                list ipv4 {
                  tailf:cli-drop-node-name;
                  tailf:cli-suppress-mode;
                  tailf:cli-delete-when-empty;
                  key "address";
                  leaf address {
                    type inet:ipv4-address;
                  }
                  leaf vrf {
                    tailf:cli-drop-node-name;
                    type string;
                  }
                }
              }
              list ipv6 {
                tailf:cli-suppress-mode;
                tailf:cli-delete-when-empty;
                key "address";
                leaf address {
                  type ipv6-prefix;
                }
                leaf vrf {
                  tailf:cli-drop-node-name;
                  type string;
                }
              }
            }
            container host {
              list domain-name-vrf {
                tailf:cli-drop-node-name;
                tailf:cli-suppress-mode;
                tailf:cli-delete-when-empty;
                key "domain vrf";
                leaf domain {
                  type string;
                }
                leaf vrf {
                  type string;
                }
              }
              leaf-list domain-name {
                tailf:cli-drop-node-name;
                type string;
              }
              container domain {
                list domain-name-vrf {
                  tailf:cli-drop-node-name;
                  tailf:cli-suppress-mode;
                  tailf:cli-delete-when-empty;
                  key "domain vrf";
                  leaf domain {
                    type string;
                  }
                  leaf vrf {
                    type string;
                  }
                }
                leaf-list domain-name {
                  tailf:cli-drop-node-name;
                  type string;
                }
              }
            }
            container user-fqdn {
              list domain-name-vrf {
                tailf:cli-drop-node-name;
                tailf:cli-suppress-mode;
                tailf:cli-delete-when-empty;
                key "domain vrf";
                leaf domain {
                  type string;
                }
                leaf vrf {
                  type string;
                }
              }
              leaf-list domain-name {
                tailf:cli-drop-node-name;
                type string;
              }
            }
          }
          leaf certificate {
            type string;
          }
        }
        container client {
          container authentication {
            leaf list {
              type string;
            }
          }
          container configuration {
            container address {
              leaf initiate {
                type empty;
              }
              leaf respond {
                type empty;
              }
            }
          }
        }
        container isakmp {
          container authorization {
            tailf:cli-compact-syntax;
            tailf:cli-sequence-commands {
              tailf:cli-reset-siblings;
            }
            leaf list {
              type string;
            }
            container password {
              tailf:cli-flatten-container;
              tailf:cli-compact-syntax;
              tailf:cli-sequence-commands;
              uses crypto-key-grouping {
                refine "secret";
              }
            }
          }
        }
        choice keepalive-choice {
          container keepalive {
            tailf:cli-compact-syntax;
            tailf:cli-sequence-commands {
              tailf:cli-reset-siblings;
            }
            leaf seconds {
              tailf:cli-drop-node-name;
              type uint16;
            }
            leaf retry {
              type uint8;
            }
          }
          container keepalive-enable {
            tailf:cli-drop-node-name;
            leaf keepalive {
              type boolean;
            }
          }
        }
        container local-address {
          choice local-address-choice {
            leaf ipv4-address {
              tailf:cli-drop-node-name;
              type inet:ipv4-address;
            }
            leaf ipv6-address {
              tailf:cli-drop-node-name;
              type inet:ipv6-address;
            }
            container interface {
              tailf:cli-drop-node-name;
              uses interface-name-grouping;
            }
          }
        }
        leaf accounting {
          type string;
        }
        leaf virtual-template {
          type uint16;
        }
        leaf qos-group {
          type uint16;
        }
      }
      list policy {
        key "priority";
        leaf priority {
          type uint16;
        }
        container encr {
          tailf:cli-compact-syntax;
          tailf:cli-sequence-commands {
            tailf:cli-reset-siblings;
          }
          leaf algorithm {
            tailf:cli-drop-node-name;
            type enumeration {
              enum "des";
              enum "3des";
              enum "aes";
            }
          }
          leaf bits {
            tailf:cli-drop-node-name;
            type enumeration {
              enum "128";
              enum "192";
              enum "256";
            }
          }
        }
        leaf hash {
          type enumeration {
            enum "md5";
            enum "sha";
            enum "sha256";
            enum "sha384";
            enum "sha512";
          }
        }
        leaf authentication {
          type enumeration {
            enum "pre-share";
            enum "rsa-encr";
            enum "rsa-sig";
          }
        }
        leaf group {
          type enumeration {
            enum "1";
            enum "2";
            enum "5";
            enum "14";
            enum "15";
            enum "16";
            enum "19";
            enum "20";
            enum "21";
            enum "24";
          }
        }
        leaf lifetime {
          type uint32;
        }
      }
      container keepalive {
        tailf:cli-compact-syntax;
        tailf:cli-sequence-commands {
          tailf:cli-reset-siblings;
        }
        leaf seconds {
          tailf:cli-drop-node-name;
          type uint16;
        }
        leaf retry-seconds {
          tailf:cli-drop-node-name;
          tailf:cli-optional-in-sequence;
          type uint8;
        }
        leaf option {
          tailf:cli-drop-node-name;
          type enumeration {
            enum "periodic";
            enum "on-demand";
          }
        }
      }
      container nat {
        container keepalive {
          leaf seconds {
            tailf:cli-drop-node-name;
            type uint16;
          }
        }
      }
      list key {
        tailf:cli-suppress-mode;
        tailf:cli-delete-when-empty;
        tailf:cli-compact-syntax;
        tailf:cli-sequence-commands {
          tailf:cli-reset-siblings;
        }
        key "address";
        leaf address {
          tailf:cli-expose-key-name;
          type inet:ipv4-address;
        }
        leaf encrypted {
          tailf:cli-drop-node-name;
          tailf:cli-prefix-key;
          tailf:cli-optional-in-sequence;
          type enumeration {
            enum "6";
          }
        }
        leaf keystring {
          tailf:cli-drop-node-name;
          tailf:cli-prefix-key;
          type string;
        }
        leaf mask {
          tailf:cli-drop-node-name;
          tailf:cli-optional-in-sequence;
          type inet:ipv4-address;
        }
        leaf no-xauth {
          type empty;
        }
      }
      container key-ipv6-list {
        tailf:cli-drop-node-name;
        list key {
          tailf:cli-suppress-mode;
          tailf:cli-delete-when-empty;
          tailf:cli-compact-syntax;
          tailf:cli-sequence-commands {
            tailf:cli-reset-siblings;
          }
          key "ipv6";
          leaf ipv6 {
            tailf:cli-expose-key-name;
            type ipv6-prefix;
          }
          leaf encrypted {
            tailf:cli-drop-node-name;
            tailf:cli-prefix-key;
            tailf:cli-optional-in-sequence;
            type enumeration {
              enum "6";
            }
          }
          leaf keystring {
            tailf:cli-drop-node-name;
            tailf:cli-prefix-key;
            type string;
          }
          leaf address {
            tailf:cli-prefix-key;
            type empty;
          }
          leaf no-xauth {
            type empty;
          }
        }
      }
      container key-hostname-list {
        tailf:cli-drop-node-name;
        list key {
          tailf:cli-suppress-mode;
          tailf:cli-delete-when-empty;
          tailf:cli-compact-syntax;
          tailf:cli-sequence-commands {
            tailf:cli-reset-siblings;
          }
          key "hostname";
          leaf hostname {
            tailf:cli-expose-key-name;
            type string;
          }
          leaf encrypted {
            tailf:cli-drop-node-name;
            tailf:cli-prefix-key;
            tailf:cli-optional-in-sequence;
            type enumeration {
              enum "6";
            }
          }
          leaf keystring {
            tailf:cli-drop-node-name;
            tailf:cli-prefix-key;
            type string;
          }
          leaf no-xauth {
            type empty;
          }
        }
      }
    }
    container ipsec {
      container optional {
        tailf:cli-delete-when-empty;
        presence "true";
        leaf retry {
          type uint32;
        }
      }
      container security-association {
        leaf idle-time {
          type uint32;
        }
        container lifetime {
          leaf kilobytes {
            type union {
              type uint32;
              type enumeration {
                enum "disable";
              }
            }
          }
          leaf seconds {
            type uint32;
          }
        }
        container replay {
          leaf disable {
            type empty;
          }
          leaf window-size {
            type ipsec-window-size-type;
          }
        }
      }
      list transform-set {
        tailf:cli-compact-syntax;
        key "name";
        leaf name {
          type string;
        }
        leaf transform1 {
          tailf:cli-drop-node-name;
          tailf:cli-hide-in-submode;
          type enumeration {
            enum "ah-md5-hmac";
            enum "ah-sha-hmac";
            enum "ah-sha256-hmac";
            enum "ah-sha384-hmac";
            enum "ah-sha512-hmac";
          }
        }
        leaf transform2 {
          tailf:cli-drop-node-name;
          tailf:cli-hide-in-submode;
          type enumeration {
            enum "esp-3des";
            enum "esp-aes";
            enum "esp-des";
            enum "esp-gcm";
            enum "esp-gmac";
            enum "esp-null";
            enum "esp-seal";
          }
        }
        leaf transform2-bits {
          tailf:cli-drop-node-name;
          tailf:cli-hide-in-submode;
          type enumeration {
            enum "128";
            enum "192";
            enum "256";
          }
        }
        leaf transform3 {
          tailf:cli-drop-node-name;
          tailf:cli-hide-in-submode;
          type enumeration {
            enum "esp-md5-hmac";
            enum "esp-sha-hmac";
            enum "esp-sha256-hmac";
            enum "esp-sha384-hmac";
            enum "esp-sha512-hmac";
          }
        }
        leaf transform4 {
          tailf:cli-drop-node-name;
          tailf:cli-hide-in-submode;
          type enumeration {
            enum "comp-lzs";
          }
        }
        container mode {
          choice mode-choice {
            container transport {
              presence "true";
              leaf require {
                type empty;
              }
            }
            leaf tunnel {
              type empty;
            }
          }
        }
      }
      container default {
        leaf transform-set {
          type boolean;
        }
      }
      leaf fragmentation {
        type enumeration {
          enum "after-encryption";
          enum "before-encryption";
        }
      }
      leaf df-bit {
        type enumeration {
          enum "clear";
          enum "copy";
          enum "set";
        }
      }
      leaf nat-transparency {
        type enumeration {
          enum "spi-matching";
          enum "udp-encapsulation";
        }
      }
      list profile {
        key "name";
        leaf name {
          type string;
        }
        leaf description {
          tailf:cli-multi-value;
          type string;
        }
        container set {
          container security-association {
            leaf dfbit {
              type enumeration {
                enum "clear";
                enum "copy";
                enum "set";
              }
            }
            container lifetime {
              leaf kilobytes {
                type union {
                  type uint32;
                  type enumeration {
                    enum "disable";
                  }
                }
              }
              choice time-based-choice {
                leaf seconds {
                  type uint32;
                }
                leaf days {
                  type uint8;
                }
              }
            }
            container idle-time {
              tailf:cli-compact-syntax;
              tailf:cli-sequence-commands {
                tailf:cli-reset-siblings;
              }
              leaf seconds {
                tailf:cli-drop-node-name;
                type uint32;
              }
              leaf default {
                type empty;
              }
            }
            container replay {
              leaf disable {
                type empty;
              }
              leaf window-size {
                type ipsec-window-size-type;
              }
            }
            container dummy {
              choice dummy-choice {
                leaf pps {
                  type uint8;
                }
                leaf seconds {
                  type uint16;
                }
              }
            }
            leaf ecn {
              type enumeration {
                enum "discard";
                enum "propagate";
              }
            }
          }
          container security-policy {
            leaf limit {
              type uint16;
            }
          }
          leaf-list transform-set {
            tailf:cli-flat-list-syntax;
            type string;
          }
          leaf pfs {
            type isakmp-pfs-type;
          }
          leaf identity {
            type string;
          }
          leaf mixed-mode {
            type empty;
          }
          choice ike-profile {
            leaf isakmp-profile {
              type string;
            }
            leaf ikev2-profile {
              type string;
            }
          }
        }
        container redundancy {
          tailf:cli-compact-syntax;
          tailf:cli-sequence-commands;
          leaf name {
            tailf:cli-drop-node-name;
            type string;
          }
          leaf stateful {
            type empty;
          }
        }
        leaf responder-only {
          type empty;
        }
        container reverse-route {
          tailf:cli-compact-syntax;
          tailf:cli-sequence-commands;
          tailf:cli-delete-when-empty;
          presence "true";
          leaf remote-peer {
            tailf:cli-optional-in-sequence;
            type inet:ipv4-address;
          }
          leaf gateway {
            tailf:cli-optional-in-sequence;
            type empty;
          }
          leaf static {
            type empty;
          }
        }
      }
    }
    container call {
      container admission {
        container limit {
          container ike {
            leaf in-negotiation-sa {
              type uint32;
            }
          }
        }
      }
    }
    list identity {
      key "name";
      leaf name {
        type string;
      }
      uses description-grouping;
      list dn {
        tailf:cli-suppress-mode;
        tailf:cli-delete-when-empty;
        ordered-by user;
        key "name";
        leaf name {
          type string;
        }
      }
    }
    container gdoi {
      list group {
        key "name";
        leaf name {
          type string;
        }
        leaf ipv6 {
          tailf:cli-prefix-key;
          type empty;
        }
        container identity {
          choice identify-choice {
            leaf number {
              type uint32;
            }
            container address {
              leaf ipv4 {
                type inet:ipv4-address;
              }
            }
          }
        }
        container server {
          container address {
            list ipv4 {
              tailf:cli-suppress-mode;
              tailf:cli-delete-when-empty;
              key "name";
              leaf name {
                type inet:ipv4-address;
              }
            }
          }
          container local {
            tailf:cli-add-mode;
            presence "true";
            uses crypto-gdoi-local-server-grouping;
          }
        }
        container client {
          container status {
            container active-sa {
              leaf track {
                type uint16;
              }
            }
          }
          container recovery-check {
            leaf interval {
              type uint16;
            }
          }
          container registration {
            container interface {
              uses interface-name-grouping;
            }
          }
          container fail-close {
            leaf revert {
              type empty;
            }
          }
          container protocol {
            leaf gikev2 {
              type string;
            }
          }
        }
      }
    }
    list dynamic-map {
      key "name map-entry";
      leaf name {
        type string;
      }
      leaf map-entry {
        type uint32;
      }
      container set {
        container security-association {
          container level {
            leaf per-host {
              type empty;
            }
          }
          leaf dfbit {
            type enumeration {
              enum "clear";
              enum "copy";
              enum "set";
            }
          }
          container lifetime {
            leaf kilobytes {
              type union {
                type uint32;
                type enumeration {
                  enum "disable";
                }
              }
            }
            choice days-seconds-choice {
              leaf days {
                type uint8;
              }
              leaf seconds {
                type uint32;
              }
            }
          }
          container idle-time {
            tailf:cli-compact-syntax;
            tailf:cli-sequence-commands {
              tailf:cli-reset-siblings;
            }
            leaf seconds {
              tailf:cli-drop-node-name;
              type uint32;
            }
            leaf default {
              type empty;
            }
          }
          container replay {
            leaf disable {
              type empty;
            }
            leaf window-size {
              type enumeration {
                enum "1024";
                enum "512";
                enum "256";
                enum "128";
                enum "64";
              }
            }
          }
          container dummy {
            choice dummy-choice {
              leaf pps {
                type uint8;
              }
              leaf seconds {
                type uint16;
              }
            }
          }
          leaf ecn {
            type enumeration {
              enum "discard";
              enum "propagate";
            }
          }
        }
        leaf isakmp-profile {
          type string;
        }
        leaf-list transform-set {
          tailf:cli-flat-list-syntax;
          type string;
        }
        leaf pfs {
          type isakmp-pfs-type;
        }
      }
      container match {
        leaf address {
          type ext-acl-type;
        }
      }
      container reverse-route {
        tailf:cli-compact-syntax;
        tailf:cli-sequence-commands;
        tailf:cli-delete-when-empty;
        presence "true";
        leaf remote-peer {
          tailf:cli-optional-in-sequence;
          type inet:ipv4-address;
        }
        leaf gateway {
          tailf:cli-optional-in-sequence;
          type empty;
        }
        leaf static {
          type empty;
        }
      }
    }
    container gkm {
      list group {
        key "name";
        leaf name {
          type string;
        }
        leaf ipv6 {
          tailf:cli-prefix-key;
          type empty;
        }
        container identity {
          choice identity-choice {
            leaf number {
              type uint32;
            }
            container address {
              leaf ipv4 {
                type inet:ipv4-address;
              }
            }
          }
        }
        container server {
          list address {
            tailf:cli-suppress-mode;
            tailf:cli-delete-when-empty;
            ordered-by user;
            key "protocol address";
            leaf protocol {
              type enumeration {
                enum "ipv4";
                enum "ipv6";
              }
            }
            leaf address {
              type union {
                type inet:ipv4-address;
                type inet:ipv6-address;
              }
            }
          }
          container local {
            tailf:cli-add-mode;
            presence "true";
            uses crypto-gdoi-local-server-grouping;
          }
        }
        container client {
          container status {
            container active-sa {
              leaf track {
                type uint16;
              }
            }
          }
          container recovery-check {
            leaf interval {
              type uint16;
            }
          }
          container protocol {
            leaf gikev2 {
              type string;
            }
          }
          container registration {
            container interface {
              uses interface-name-grouping;
            }
          }
        }
      }
    }
    list map {
      tailf:cli-suppress-mode;
      tailf:cli-delete-when-empty;
      tailf:cli-compact-syntax;
      tailf:cli-sequence-commands;
      key "name";
      leaf name {
        type string;
      }
      leaf ipv6 {
        tailf:cli-prefix-key;
        tailf:cli-optional-in-sequence;
        type empty;
      }
      container local-address {
        tailf:cli-optional-in-sequence;
        uses interface-name-grouping;
      }
      container gdoi {
        tailf:cli-optional-in-sequence;
        container fail-close {
          tailf:cli-add-mode;
          presence "true";
          container match {
            leaf address {
              type ext-acl-type;
            }
          }
          leaf activate {
            type empty;
          }
        }
      }
      list seq-list {
        tailf:cli-drop-node-name;
        tailf:cli-compact-syntax;
        tailf:cli-sequence-commands;
        key "id";
        leaf id {
          tailf:cli-suppress-range;
          type uint16;
        }
        leaf policy {
          tailf:cli-drop-node-name;
          tailf:cli-hide-in-submode;
          type enumeration {
            enum "ipsec-isakmp";
            enum "ipsec-manual";
            enum "gdoi";
            enum "ckm";
          }
        }
        leaf dynamic {
          tailf:cli-hide-in-submode;
          tailf:cli-optional-in-sequence;
          type string;
        }
        leaf profile {
          tailf:cli-hide-in-submode;
          tailf:cli-optional-in-sequence;
          type string;
        }
        leaf description {
          tailf:cli-break-sequence-commands;
          tailf:cli-multi-value;
          type string;
        }
        container set {
          container session-key {
            container inbound {
              container esp {
                tailf:cli-compact-syntax;
                tailf:cli-sequence-commands {
                  tailf:cli-reset-siblings;
                }
                leaf spi {
                  tailf:cli-drop-node-name;
                  type uint32;
                }
                leaf cipher {
                  tailf:cli-optional-in-sequence;
                  type string;
                }
                leaf authenticator {
                  type string;
                }
              }
              container ah {
                tailf:cli-compact-syntax;
                tailf:cli-sequence-commands {
                  tailf:cli-reset-siblings;
                }
                leaf spi {
                  tailf:cli-drop-node-name;
                  type uint32;
                }
                leaf key {
                  tailf:cli-drop-node-name;
                  type string;
                }
              }
            }
            container outbound {
              container esp {
                tailf:cli-compact-syntax;
                tailf:cli-sequence-commands {
                  tailf:cli-reset-siblings;
                }
                leaf spi {
                  tailf:cli-drop-node-name;
                  type uint32;
                }
                leaf cipher {
                  tailf:cli-optional-in-sequence;
                  type string;
                }
                leaf authenticator {
                  type string;
                }
              }
              container ah {
                tailf:cli-compact-syntax;
                tailf:cli-sequence-commands {
                  tailf:cli-reset-siblings;
                }
                leaf spi {
                  tailf:cli-drop-node-name;
                  type uint32;
                }
                leaf key {
                  tailf:cli-drop-node-name;
                  type string;
                }
              }
            }
          }
          leaf-list transform-set {
            tailf:cli-flat-list-syntax;
            type string;
          }
          leaf isakmp-profile {
            type string;
          }
          leaf ikev2-profile {
            type string;
          }
          leaf peer-default {
            type inet:host;
          }
          leaf-list peer {
            type inet:host;
          }
          container security-association {
            container level {
              leaf per-host {
                type empty;
              }
            }
            leaf dfbit {
              type enumeration {
                enum "clear";
                enum "copy";
                enum "set";
              }
            }
            container lifetime {
              leaf kilobytes {
                type union {
                  type uint32;
                  type enumeration {
                    enum "disable";
                  }
                }
              }
              choice days-seconds-choice {
                leaf days {
                  type uint8;
                }
                leaf seconds {
                  type uint32;
                }
              }
            }
            container idle-time {
              tailf:cli-compact-syntax;
              tailf:cli-sequence-commands {
                tailf:cli-reset-siblings;
              }
              leaf seconds {
                tailf:cli-drop-node-name;
                type uint32;
              }
              leaf default {
                type empty;
              }
            }
            container replay {
              leaf disable {
                type empty;
              }
              leaf window-size {
                type enumeration {
                  enum "1024";
                  enum "512";
                  enum "256";
                  enum "128";
                  enum "64";
                }
              }
            }
            container dummy {
              choice dummy-choice {
                leaf pps {
                  type uint8;
                }
                leaf seconds {
                  type uint16;
                }
              }
            }
            leaf ecn {
              type enumeration {
                enum "discard";
                enum "propagate";
              }
            }
          }
          leaf pfs {
            type isakmp-pfs-type;
          }
          container reverse-route {
            leaf distance {
              type uint8;
            }
            leaf tag {
              type uint32;
            }
          }
          leaf group {
            type string;
          }
        }
        container gdoi-set {
          tailf:cli-break-sequence-commands;
          tailf:cli-drop-node-name;
          container set {
            leaf group {
              type string;
            }
          }
        }
        container match {
          leaf address {
            type ext-ip-acl-type;
          }
        }
        container reverse-route {
          tailf:cli-compact-syntax;
          tailf:cli-sequence-commands;
          tailf:cli-delete-when-empty;
          presence "true";
          leaf remote-peer {
            tailf:cli-optional-in-sequence;
            type inet:ipv4-address;
          }
          leaf gateway {
            tailf:cli-optional-in-sequence;
            type empty;
          }
          leaf static {
            type empty;
          }
        }
        container qos {
          leaf pre-classify {
            type empty;
          }
        }
      }
    }
    container ssl {
      list proposal {
        key "name";
        leaf name {
          type string;
        }
        leaf-list protection {
          tailf:cli-flat-list-syntax;
          type enumeration {
            enum "rsa-3des-ede-sha1";
            enum "rsa-rc4128-md5";
            enum "rsa-aes128-sha1";
            enum "rsa-aes256-sha1";
          }
        }
      }
      container authorization {
        list policy {
          key "name";
          leaf name {
            type string;
          }
          leaf pool {
            type string;
          }
          container dns {
            tailf:cli-compact-syntax;
            tailf:cli-sequence-commands {
              tailf:cli-reset-siblings;
            }
            leaf primary-server {
              tailf:cli-drop-node-name;
              type inet:ipv4-address;
            }
            leaf secondary-server {
              tailf:cli-drop-node-name;
              type inet:ipv4-address;
            }
          }
          leaf banner {
            tailf:cli-multi-value;
            type string;
          }
          leaf def-domain {
            type string;
          }
        }
      }
      list policy {
        key "name";
        leaf name {
          type string;
        }
        container ssl {
          leaf proposal {
            type string;
          }
        }
        container pki {
          tailf:cli-compact-syntax;
          tailf:cli-sequence-commands {
            tailf:cli-reset-siblings;
          }
          leaf trustpoint {
            type string;
          }
          leaf sign {
            type empty;
          }
        }
        container ip {
          container address {
            tailf:cli-compact-syntax;
            tailf:cli-sequence-commands {
              tailf:cli-reset-siblings;
            }
            leaf local {
              type inet:ipv4-address;
            }
            leaf port {
              type union {
                type uint16;
                type uint16;
              }
            }
          }
        }
        leaf shutdown {
          type empty;
        }
      }
      list profile {
        key "name";
        leaf name {
          type string;
        }
        container match {
          leaf policy {
            type string;
          }
          leaf url {
            type string;
          }
        }
        container aaa {
          container authentication {
            leaf list {
              type string;
            }
          }
          container authorization {
            container user {
              tailf:cli-compact-syntax;
              tailf:cli-sequence-commands {
                tailf:cli-reset-siblings;
              }
              leaf list {
                type string;
              }
              leaf aaa-username {
                tailf:cli-drop-node-name;
                type string;
              }
            }
          }
        }
        container authentication {
          container remote {
            leaf user-credentials {
              type empty;
            }
          }
        }
        leaf shutdown {
          type empty;
        }
      }
    }
    list tls-tunnel {
      key "name";
      leaf name {
        type string;
      }
      list server {
        tailf:cli-suppress-mode;
        tailf:cli-delete-when-empty;
        tailf:cli-compact-syntax;
        key "protocol address";
        leaf protocol {
          type enumeration {
            enum "ipv4";
            enum "ipv6";
          }
        }
        leaf address {
          type union {
            type inet:ipv4-address;
            type inet:ipv6-address;
          }
        }
        leaf port {
          type union {
            type uint16;
            type uint16;
          }
        }
      }
      leaf protection {
        type enumeration {
          enum "dhe-psk-aes128-cbc-sha1";
          enum "dhe-psk-aes256-cbc-sha1";
          enum "psk-aes128-cbc-sha1";
          enum "psk-aes256-cbc-sha1";
        }
      }
      list local-interface {
        tailf:cli-suppress-mode;
        tailf:cli-delete-when-empty;
        key "name";
        leaf name {
          type string;
        }
        leaf priority {
          type uint8;
        }
      }
      container psk {
        tailf:cli-compact-syntax;
        tailf:cli-sequence-commands;
        leaf id {
          type string;
        }
        container key {
          tailf:cli-flatten-container;
          tailf:cli-compact-syntax;
          tailf:cli-sequence-commands;
          uses crypto-key-grouping {
            refine "secret";
          }
        }
      }
      container overlay {
        container address {
          tailf:cli-compact-syntax;
          tailf:cli-sequence-commands {
            tailf:cli-reset-siblings;
          }
          leaf address {
            tailf:cli-drop-node-name;
            type union {
              type inet:ipv4-address;
              type inet:ipv6-address;
            }
          }
          leaf vrf {
            type string;
          }
        }
      }
      container overlay-address {
        tailf:cli-compact-syntax;
        tailf:cli-sequence-commands {
          tailf:cli-reset-siblings;
        }
        leaf address {
          tailf:cli-drop-node-name;
          type union {
            type inet:ipv4-address;
            type inet:ipv6-address;
          }
        }
        leaf vrf {
          type string;
        }
      }
      leaf shutdown {
        type empty;
      }
    }
    container engine {
      container compliance {
        container shield {
          leaf disable {
            type empty;
          }
        }
      }
    }
  }
  container transport-map {
    container type {
      tailf:cli-compact-syntax;
      tailf:cli-sequence-commands;
      list persistent {
        key "name";
        leaf name {
          type string;
        }
        leaf type {
          tailf:cli-drop-node-name;
          tailf:cli-prefix-key;
          type enumeration {
            enum "ssh";
            enum "telnet";
            enum "webui";
          }
        }
        leaf authentication-retries {
          type uint8;
        }
        container rsa {
          leaf keypair-name {
            type string;
          }
        }
        container transport {
          container interface {
            tailf:cli-compact-syntax;
            uses interface-name-grouping;
          }
        }
      }
    }
  }
  container macro {
    container auto {
      list execute {
        tailf:cli-suppress-mode;
        tailf:cli-delete-when-empty;
        key "name";
        leaf name {
          tailf:cli-multi-word-key;
          type string;
        }
      }
      container global {
        leaf processing {
          type empty;
        }
      }
      leaf monitor {
        type boolean;
      }
    }
    container global {
      uses description-grouping;
    }
    list name {
      tailf:cli-suppress-mode;
      tailf:cli-delete-when-empty;
      tailf:cli-compact-syntax;
      key "name";
      leaf name {
        type string;
      }
      leaf commands {
        tailf:cli-drop-node-name;
        type string;
      }
    }
  }
  container buffers {
    container tune {
      leaf automatic {
        type empty;
      }
    }
    list pool-list {
      tailf:cli-drop-node-name;
      tailf:cli-suppress-mode;
      tailf:cli-delete-when-empty;
      key "name";
      leaf name {
        type enumeration {
          enum "small";
          enum "middle";
          enum "big";
          enum "verybig";
          enum "large";
          enum "huge";
          enum "fastswitching";
        }
      }
      leaf permanent {
        type uint16;
      }
      leaf min-free {
        type uint16;
      }
      leaf max-free {
        type uint16;
      }
      leaf size {
        type uint32;
      }
    }
  }
  container track {
    container timer {
      container interface {
        uses track-timer-grouping;
      }
      container ip {
        container route {
          uses track-timer-grouping;
        }
        container sla {
          uses track-timer-grouping;
        }
      }
      container ipv6 {
        container route {
          uses track-timer-grouping;
        }
      }
      container list {
        uses track-timer-grouping;
      }
      container stub-object {
        uses track-timer-grouping;
      }
    }
    container resolution {
      container ip {
        container route {
          leaf static {
            type uint32;
          }
          leaf EIGRP {
            tailf:cli-case-insensitive;
            type uint32;
          }
          leaf OSPF {
            tailf:cli-case-insensitive;
            type uint16;
          }
          leaf ISIS {
            tailf:cli-case-insensitive;
            type uint16;
          }
          leaf BGP {
            tailf:cli-case-insensitive;
            type uint32;
          }
        }
      }
    }
    list track-object {
      tailf:cli-drop-node-name;
      tailf:cli-compact-syntax;
      key "object-number";
      leaf object-number {
        type uint16;
      }
      choice track-type {
        container rtr {
          tailf:cli-hide-in-submode;
          tailf:cli-flatten-container;
          tailf:cli-compact-syntax;
          tailf:cli-sequence-commands;
          leaf operation-number {
            tailf:cli-drop-node-name;
            type uint32;
          }
          leaf option {
            tailf:cli-drop-node-name;
            type enumeration {
              enum "reachability";
              enum "state";
            }
          }
        }
        container list {
          tailf:cli-hide-in-submode;
          tailf:cli-flatten-container;
          tailf:cli-compact-syntax;
          leaf boolean {
            type enumeration {
              enum "and";
              enum "or";
            }
          }
        }
        container list-threshold {
          tailf:cli-drop-node-name;
          tailf:cli-flatten-container;
          tailf:cli-hide-in-submode;
          container list {
            leaf threshold {
              type enumeration {
                enum "percentage";
                enum "weight";
              }
            }
          }
        }
        container interface {
          tailf:cli-hide-in-submode;
          tailf:cli-flatten-container;
          tailf:cli-compact-syntax;
          tailf:cli-sequence-commands;
          uses interface-name-grouping;
          container ip {
            tailf:cli-flatten-container;
            tailf:cli-optional-in-sequence;
            leaf routing {
              type empty;
            }
          }
          container ipv6 {
            tailf:cli-flatten-container;
            tailf:cli-optional-in-sequence;
            leaf routing {
              type empty;
            }
          }
          leaf line-protocol {
            type empty;
          }
        }
        container ip {
          tailf:cli-hide-in-submode;
          tailf:cli-flatten-container;
          tailf:cli-compact-syntax;
          container route {
            tailf:cli-flatten-container;
            tailf:cli-compact-syntax;
            tailf:cli-sequence-commands;
            leaf prefix {
              tailf:cli-drop-node-name;
              type inet:ipv4-address;
            }
            leaf mask {
              tailf:cli-drop-node-name;
              type inet:ipv4-address;
            }
            choice option-choice {
              leaf reachability {
                type empty;
              }
              container metric {
                tailf:cli-flatten-container;
                leaf threshold {
                  type empty;
                }
              }
            }
          }
          container sla {
            tailf:cli-flatten-container;
            tailf:cli-compact-syntax;
            tailf:cli-sequence-commands;
            leaf operation-number {
              tailf:cli-drop-node-name;
              type uint32;
            }
            choice option-choice {
              leaf reachability {
                type empty;
              }
              leaf state {
                type empty;
              }
            }
          }
        }
        container ipv6 {
          tailf:cli-hide-in-submode;
          tailf:cli-flatten-container;
          tailf:cli-compact-syntax;
          container route {
            tailf:cli-flatten-container;
            tailf:cli-compact-syntax;
            tailf:cli-sequence-commands;
            leaf prefix {
              tailf:cli-drop-node-name;
              type ipv6-prefix;
            }
            choice option-choice {
              leaf reachability {
                type empty;
              }
              container metric {
                tailf:cli-flatten-container;
                leaf threshold {
                  type empty;
                }
              }
            }
          }
        }
        leaf stub-object {
          tailf:cli-hide-in-submode;
          type empty;
        }
      }
      list object {
        tailf:cli-suppress-mode;
        tailf:cli-delete-when-empty;
        key "id";
        leaf id {
          type uint16;
        }
        choice object-choice {
          leaf not {
            type empty;
          }
          leaf weight {
            type uint8;
          }
        }
      }
      container ip-vrf {
        tailf:cli-drop-node-name;
        container ip {
          leaf vrf {
            type string;
          }
        }
      }
      container ipv6-vrf {
        tailf:cli-drop-node-name;
        container ipv6 {
          leaf vrf {
            type string;
          }
        }
      }
      container threshold {
        container percentage {
          leaf down {
            type uint8;
          }
          leaf up {
            type uint8;
          }
        }
        container metric {
          tailf:cli-compact-syntax;
          leaf up {
            type uint8;
          }
          leaf down {
            type uint8;
          }
        }
        container weight {
          tailf:cli-compact-syntax;
          tailf:cli-sequence-commands {
            tailf:cli-reset-siblings;
          }
          leaf down {
            tailf:cli-optional-in-sequence;
            type uint8;
          }
          leaf up {
            type uint8;
          }
        }
      }
      leaf carrier-delay {
        type empty;
      }
      container delay {
        tailf:cli-compact-syntax;
        leaf down {
          type uint8;
        }
        leaf up {
          type uint8;
        }
      }
      leaf default-state {
        type enumeration {
          enum "down";
          enum "up";
        }
      }
    }
  }
  container csdb {
    container tcp {
      leaf finwait-time {
        type uint8;
      }
      leaf idle-time {
        type uint16;
      }
      container reassembly {
        leaf max-memory {
          type uint32;
        }
        leaf max-queue-length {
          type uint8;
        }
      }
      leaf synwait-time {
        type uint16;
      }
    }
    container udp {
      leaf idle-time {
        type uint16;
      }
    }
    container icmp {
      leaf idle-time {
        type uint16;
      }
    }
    container session {
      leaf max-session {
        type uint32;
      }
    }
  }
  container performance {
    container monitor {
      list context {
        tailf:cli-sequence-commands;
        key "name";
        leaf name {
          type string;
        }
        leaf profile {
          tailf:cli-hide-in-submode;
          type enumeration {
            enum "application-experience";
            enum "application-performance";
            enum "application-statistics";
          }
        }
        container exporter {
          tailf:cli-break-sequence-commands;
          list destination {
            tailf:cli-suppress-mode;
            tailf:cli-delete-when-empty;
            tailf:cli-compact-syntax;
            key "address source";
            leaf address {
              type inet:host;
            }
            leaf source {
              tailf:cli-expose-key-name;
              type string;
            }
            leaf vrf {
              type string;
            }
            leaf transport {
              type enumeration {
                enum "udp";
              }
            }
            leaf port {
              type uint16;
            }
          }
        }
        container traffic-monitor {
          container all {
            presence "true";
            leaf ipv4 {
              type empty;
            }
            leaf ipv6 {
              type empty;
            }
          }
          container url {
            tailf:cli-compact-syntax;
            presence "true";
            leaf ipv4 {
              type empty;
            }
            leaf class-replace {
              type string;
            }
            leaf cache-size {
              type uint32;
            }
          }
          container application-client-server-stats {
            presence "true";
          }
          container application-stats {
            presence "true";
          }
          container application-response-time {
            presence "true";
          }
          container media {
            presence "true";
          }
        }
      }
    }
  }
  container performance-measurement {
    tailf:cli-add-mode;
    presence "true";
    container protocol {
      container twamp-light {
        tailf:cli-add-mode;
        container measurement {
          container delay {
            tailf:cli-add-mode;
            container unauthenticated {
              tailf:cli-add-mode;
              leaf querier-dst-port {
                type uint16;
              }
              leaf querier-src-port {
                type uint16;
              }
            }
          }
        }
      }
    }
    container delay-profile {
      container interfaces {
        tailf:cli-add-mode;
        uses pm-dm-x-grouping;
      }
      container interface-name {
        tailf:cli-drop-node-name;
        container interfaces {
          list name {
            key "name";
            leaf name {
              type string;
            }
            uses pm-dm-x-grouping;
          }
        }
      }
      container sr-policy {
        tailf:cli-add-mode;
        uses pm-dm-x-grouping;
      }
      container sr-policy-name {
        tailf:cli-drop-node-name;
        container sr-policy {
          list name {
            key "name";
            leaf name {
              type string;
            }
            uses pm-dm-x-grouping;
          }
        }
      }
      container endpoint {
        tailf:cli-add-mode;
        uses pm-dm-x-grouping;
      }
      container endpoint-name {
        tailf:cli-drop-node-name;
        container endpoint {
          list name {
            key "name";
            leaf name {
              type string;
            }
            uses pm-dm-x-grouping;
          }
        }
      }
    }
    list interface {
      key "name";
      leaf name {
        type string;
      }
      container delay-measurement {
        tailf:cli-add-mode;
        presence "true";
        leaf advertise-delay {
          type uint32;
        }
        leaf profile {
          type string;
        }
      }
      container next-hop {
        choice address-choice {
          leaf ipv4 {
            type inet:ipv4-address;
          }
          leaf ipv6 {
            type inet:ipv6-address;
          }
        }
      }
    }
    list endpoint {
      key "name";
      leaf name {
        type string;
      }
      container source-address {
        choice address-choice {
          leaf ipv4 {
            type inet:ipv4-address;
          }
          leaf ipv6 {
            type inet:ipv6-address;
          }
        }
      }
      container destination-address {
        choice address-choice {
          leaf ipv4 {
            type inet:ipv4-address;
          }
          leaf ipv6 {
            type inet:ipv6-address;
          }
        }
      }
      container delay-measurement {
        tailf:cli-add-mode;
        presence "true";
        leaf profile {
          type string;
        }
      }
      leaf vrf {
        type string;
      }
    }
  }

  grouping pm-dm-x-grouping {
    container advertisement {
      tailf:cli-add-mode;
      container threshold-check {
        tailf:cli-add-mode;
        leaf delay {
          tailf:cli-drop-node-name;
          type enumeration {
            enum "average-delay";
            enum "minimum-delay";
            enum "maximum-delay";
          }
        }
      }
      container accelerated {
        tailf:cli-add-mode;
        presence "true";
        leaf threshold {
          type uint8;
        }
        leaf minimum-change {
          type uint32;
        }
      }
      container periodic {
        tailf:cli-add-mode;
        leaf interval {
          type uint16;
        }
        leaf threshold {
          type uint8;
        }
        leaf minimum-change {
          type uint32;
        }
        leaf disabled {
          type empty;
        }
      }
    }
    container probe {
      tailf:cli-add-mode;
      container sweep {
        tailf:cli-add-mode;
        container destination {
          tailf:cli-compact-syntax;
          tailf:cli-sequence-commands {
            tailf:cli-reset-siblings;
          }
          leaf ipv4 {
            type inet:ipv4-address;
          }
          leaf range {
            type uint8;
          }
        }
      }
      leaf computation-interval {
        type uint16;
      }
      leaf measurement-mode {
        type enumeration {
          enum "one-way";
          enum "two-way";
          enum "loopback";
        }
      }
      leaf burst-interval {
        type uint16;
      }
      leaf tos-dscp {
        type uint8;
      }
      container protocol {
        tailf:cli-add-mode;
        leaf pm-mpls {
          type empty;
        }
      }
    }
    container liveness-detection {
      tailf:cli-add-mode;
      leaf multiplier {
        type uint8;
      }
    }
  }

  container l2 {
    leaf router-id {
      type inet:ipv4-address;
    }
    list vfi {
      key "name";
      leaf name {
        type string;
      }
      leaf point-to-point {
        tailf:cli-hide-in-submode;
        type empty;
      }
      leaf manual {
        tailf:cli-hide-in-submode;
        type empty;
      }
      leaf autodiscovery {
        tailf:cli-hide-in-submode;
        type empty;
      }
      leaf evc {
        tailf:cli-drop-node-name;
        tailf:cli-hide-in-submode;
        type string;
      }
      container vpn {
        leaf id {
          type uint32;
        }
      }
      leaf vpls-id {
        type string;
      }
      leaf bridge-domain {
        type uint16;
      }
      container bridge-domain-vlan {
        tailf:cli-drop-node-name;
        tailf:cli-compact-syntax;
        tailf:cli-sequence-commands {
          tailf:cli-reset-siblings;
        }
        leaf bridge-domain {
          type uint16;
        }
        leaf vlan {
          type empty;
        }
      }
      leaf mtu {
        type uint16;
      }
      leaf rd {
        type rd-type;
      }
      container route-target {
        uses route-target-grouping;
      }
      container neighbor-vfi {
        tailf:cli-drop-node-name;
        list neighbor {
          key "id vcid";
          leaf id {
            type inet:ipv4-address;
          }
          leaf vcid {
            type uint32;
          }
          uses l2-vfi-grouping;
        }
      }
      list neighbor {
        key "id";
        leaf id {
          type inet:ipv4-address;
        }
        uses l2-vfi-grouping;
      }
    }
  }
  list pseudowire-class {
    key "name";
    leaf name {
      type string;
    }
    leaf encapsulation {
      type enumeration {
        enum "l2tpv2";
        enum "l2tpv3";
        enum "mpls";
        enum "udp";
      }
    }
    leaf interworking {
      type enumeration {
        enum "ethernet";
        enum "ip";
        enum "vlan";
      }
    }
    leaf control-word {
      type empty;
    }
    container sequencing {
      choice sequencing-choice {
        leaf both {
          type empty;
        }
        leaf receive {
          type empty;
        }
        container resync {
          presence "true";
        }
        leaf transmit {
          type empty;
        }
      }
    }
    container protocol {
      choice protocol-choice {
        leaf none {
          type empty;
        }
        leaf l2tpv2 {
          type string;
        }
        leaf l2tpv3 {
          type string;
        }
      }
    }
    container status {
      container peer {
        container topology {
          leaf dual-homed {
            type empty;
          }
        }
      }
      container protocol {
        container notification {
          leaf static {
            type string;
          }
        }
      }
    }
    container ip {
      leaf protocol {
        type enumeration {
          enum "l2tp";
          enum "uti";
        }
      }
      container local {
        container interface {
          tailf:cli-compact-syntax;
          uses interface-name-grouping;
        }
      }
      container pmtu {
        tailf:cli-delete-when-empty;
        presence "true";
        leaf max {
          type uint16;
        }
      }
      container tos {
        leaf value {
          type uint8;
        }
      }
      leaf ttl {
        type uint8;
      }
    }
    uses pseudowire-preferred-path-grouping;
  }
  container device-tracking {
    container tracking {
      presence "true";
      container auto-source {
        tailf:cli-compact-syntax;
        tailf:cli-delete-when-empty;
        presence "true";
        container fallback {
          tailf:cli-flatten-container;
          tailf:cli-compact-syntax;
          tailf:cli-sequence-commands;
          leaf address {
            tailf:cli-drop-node-name;
            type inet:ipv4-address;
          }
          leaf mask {
            tailf:cli-drop-node-name;
            type inet:ipv4-address;
          }
        }
        leaf override {
          type empty;
        }
      }
      leaf retry-interval {
        type uint16;
      }
    }
    container logging {
      container packet {
        leaf drop {
          type boolean;
        }
      }
      leaf theft {
        type boolean;
      }
      leaf resolution-veto {
        type boolean;
      }
    }
    list policy {
      key "name";
      leaf name {
        type string;
      }
      leaf trusted-port {
        type empty;
      }
      leaf security-level {
        type enumeration {
          enum "glean";
          enum "guard";
          enum "inspect";
        }
      }
      container limit {
        leaf address-count {
          type uint16;
        }
      }
      leaf device-role {
        type enumeration {
          enum "node";
          enum "switch";
        }
      }
      container protocol {
        leaf ndp {
          type boolean;
        }
        leaf arp {
          type boolean;
        }
        leaf dhcp6 {
          type boolean;
        }
        leaf udp {
          type boolean;
        }
      }
      container tracking {
        choice tracking-choice {
          leaf disable {
            type empty;
          }
          container enable {
            tailf:cli-delete-when-empty;
            presence "true";
            leaf reachable-lifetime {
              type union {
                type uint32;
                type enumeration {
                  enum "infinite";
                }
              }
            }
          }
        }
      }
    }
  }
  container global-address-family {
    container ipv4 {
      container multicast {
        tailf:cli-add-mode;
        container topology {
          container base {
            tailf:cli-add-mode;
            uses config-af-topology-grouping;
          }
          list instance {
            tailf:cli-drop-node-name;
            key "name";
            leaf name {
              type string;
            }
            uses config-af-topology-grouping;
          }
        }
      }
    }
  }

  grouping config-af-topology-grouping {
    container route-replicate {
      list from {
        tailf:cli-suppress-mode;
        tailf:cli-delete-when-empty;
        tailf:cli-compact-syntax;
        tailf:cli-sequence-commands {
          tailf:cli-reset-siblings;
        }
        key "name";
        leaf name {
          type enumeration {
            enum "unicast";
            enum "multicast";
          }
        }
        uses config-af-topology-rr-grouping;
      }
    }
  }

  grouping config-af-topology-rr-grouping {
    leaf all {
      type empty;
    }
  }

  container interface {
    list Null {
      tailf:cli-allow-join-with-key;
      tailf:cli-suppress-key-abbreviation;
      key "name";
      leaf name {
        type uint8;
      }
      container ip {
        leaf unreachables {
          type boolean;
        }
      }
      container ipv6 {
        leaf unreachables {
          type boolean;
        }
      }
      container ntp {
        leaf enable {
          type empty;
        }
      }
    }
    list Loopback {
      tailf:cli-allow-join-with-key;
      tailf:cli-suppress-key-abbreviation;
      key "name";
      leaf name {
        type string;
      }
      uses interface-common-pre-grouping;
      uses interface-common-grouping;
    }
    list VirtualPortGroup {
      tailf:cli-allow-join-with-key;
      tailf:cli-suppress-key-abbreviation;
      key "name";
      leaf name {
        type uint8;
      }
      uses interface-common-pre-grouping;
      uses interface-common-grouping;
      uses interface-pointtopoint-grouping;
    }
    list Dot11Radio {
      tailf:cli-allow-join-with-key;
      tailf:cli-suppress-key-abbreviation;
      key "name";
      leaf name {
        type string;
      }
      uses interface-common-pre-grouping;
      uses interface-ethernet-pre-grouping;
      uses interface-common-grouping;
      uses interface-ethernet-post-grouping;
      container encryption {
        uses interface-encryption-mode-grouping;
        list vlan {
          tailf:cli-suppress-mode;
          tailf:cli-delete-when-empty;
          tailf:cli-compact-syntax;
          key "id";
          leaf id {
            type string;
          }
          uses interface-encryption-mode-grouping;
        }
      }
      container broadcast-key {
        list vlan {
          tailf:cli-suppress-mode;
          tailf:cli-delete-when-empty;
          tailf:cli-compact-syntax;
          key "name";
          leaf name {
            type string;
          }
          leaf change {
            type uint32;
          }
        }
      }
      list ssid {
        tailf:cli-suppress-mode;
        tailf:cli-delete-when-empty;
        key "name";
        leaf name {
          type string;
        }
      }
      container antenna {
        leaf gain {
          type int16;
        }
      }
      leaf peakdetect {
        type empty;
      }
      leaf mbssid {
        type empty;
      }
      leaf speed {
        tailf:cli-multi-value;
        type string;
      }
      container dfs {
        container band {
          choice band-choice {
            leaf block {
              type boolean;
            }
            container block-conf {
              tailf:cli-drop-node-name;
              tailf:cli-compact-syntax;
              tailf:cli-sequence-commands {
                tailf:cli-reset-siblings;
              }
              leaf one {
                tailf:alt-name "1";
                tailf:cli-optional-in-sequence;
                type empty;
              }
              leaf two {
                tailf:alt-name "2";
                tailf:cli-optional-in-sequence;
                type empty;
              }
              leaf three {
                tailf:alt-name "3";
                tailf:cli-optional-in-sequence;
                type empty;
              }
              leaf four {
                tailf:alt-name "4";
                tailf:cli-optional-in-sequence;
                type empty;
              }
              leaf block {
                type empty;
              }
            }
          }
        }
      }
      container packet {
        leaf retries {
          type uint8;
        }
      }
      container channel {
        leaf dfs {
          type empty;
        }
      }
      container channel-conf {
        tailf:cli-drop-node-name;
        container channel {
          tailf:cli-compact-syntax;
          leaf least-congested {
            type empty;
          }
          leaf-list frequency {
            tailf:cli-drop-node-name;
            tailf:cli-flat-list-syntax;
            ordered-by user;
            type uint16;
          }
        }
      }
      container station-role {
        container root {
          presence "true";
        }
      }
      container rts {
        leaf threshold {
          type uint16;
        }
        leaf retries {
          type uint8;
        }
      }
      container world-mode {
        container dot11d {
          tailf:cli-compact-syntax;
          tailf:cli-sequence-commands {
            tailf:cli-reset-siblings;
          }
          leaf country-code {
            type string;
          }
          leaf location {
            tailf:cli-drop-node-name;
            type enumeration {
              enum "both";
              enum "indoor";
              enum "outdoor";
            }
          }
        }
      }
      leaf infrastructure-client {
        type empty;
      }
    }
    list Embedded-Service-Engine {
      tailf:cli-allow-join-with-key;
      tailf:cli-suppress-key-abbreviation;
      key "name";
      leaf name {
        type string;
      }
      uses interface-common-pre-grouping;
      uses interface-common-grouping;
    }
    list Service-Engine {
      tailf:cli-allow-join-with-key;
      tailf:cli-suppress-key-abbreviation;
      key "name";
      leaf name {
        type string;
      }
      uses interface-common-pre-grouping;
      uses interface-common-grouping;
    }
    list Tunnel {
      tailf:cli-allow-join-with-key;
      tailf:cli-suppress-key-abbreviation;
      key "name";
      leaf name {
        type uint32;
      }
      uses interface-common-pre-grouping {
        refine "description";
      }
      uses interface-common-grouping;
      uses interface-tunnel-grouping;
    }
    list Port-channel {
      tailf:cli-allow-join-with-key;
      tailf:cli-suppress-key-abbreviation;
      key "name";
      leaf name {
        type uint32;
      }
      uses interface-common-pre-grouping;
      uses interface-ethernet-pre-grouping;
      uses interface-switch-grouping;
      uses interface-ethernet-switch-grouping;
      uses interface-common-macsec-grouping;
      uses interface-ethernet-post-grouping;
      leaf load-balancing {
        type enumeration {
          enum "flow";
          enum "vlan";
        }
      }
      container mlacp {
        leaf lag-priority {
          type uint16;
        }
        container interchassis {
          leaf group {
            type uint32;
          }
        }
      }
      container counter {
        presence "true";
      }
      container port-channel {
        leaf standalone-disable {
          type boolean;
        }
        container load-balance {
          leaf flow-based {
            type empty;
          }
          leaf link {
            type uint8;
          }
          container weighted {
            container default {
              leaf weight {
                type uint16;
              }
            }
            leaf rebalance {
              type union {
                type uint16;
                type enumeration {
                  enum "disable";
                }
              }
            }
          }
        }
        leaf min-links {
          type uint8;
        }
        container bfd {
          container destination {
            container ipv4 {
              tailf:cli-compact-syntax;
              tailf:cli-sequence-commands {
                tailf:cli-reset-siblings;
              }
              leaf address {
                tailf:cli-drop-node-name;
                type inet:ipv4-address;
              }
              leaf name {
                tailf:cli-drop-node-name;
                type string;
              }
            }
          }
        }
      }
    }
    container Port-channel-subinterface {
      tailf:cli-drop-node-name;
      list Port-channel {
        tailf:cli-allow-join-with-key;
        tailf:cli-suppress-key-abbreviation;
        key "name";
        leaf name {
          type string;
        }
        uses interface-common-pre-grouping;
        uses interface-ethernet-pre-grouping;
        uses interface-switch-grouping;
        uses interface-ethernet-grouping;
        uses interface-common-macsec-grouping;
        uses interface-ethernet-post-grouping;
      }
    }
    list nve {
      tailf:cli-allow-join-with-key;
      tailf:cli-suppress-key-abbreviation;
      key "name";
      leaf name {
        type uint16;
      }
      uses interface-common-pre-grouping;
      uses interface-common-grouping;
      container vxlan {
        container udp {
          leaf port {
            type uint16;
          }
        }
      }
      container source-interface {
        uses interface-name-grouping;
      }
      container host-reachability {
        container protocol {
          leaf bgp {
            type empty;
          }
        }
      }
      container member {
        list vni {
          key "id";
          leaf id {
            type string;
          }
          container ingress-replication {
            tailf:cli-delete-when-empty;
            presence "true";
            choice address-choice {
              leaf address {
                tailf:cli-drop-node-name;
                type inet:ipv4-address;
              }
              leaf local-routing {
                type empty;
              }
            }
          }
          leaf mcast-group {
            type inet:ip-address;
          }
        }
      }
      container member-vrf {
        tailf:cli-drop-node-name;
        container member {
          list vni {
            tailf:cli-suppress-mode;
            tailf:cli-delete-when-empty;
            key "id";
            leaf id {
              type string;
            }
            leaf vrf {
              tailf:cli-hide-in-submode;
              type string;
            }
          }
        }
      }
    }
    list vmi {
      tailf:cli-allow-join-with-key;
      tailf:cli-suppress-key-abbreviation;
      key "name";
      leaf name {
        type uint32;
      }
      uses interface-common-pre-grouping;
      uses interface-common-grouping;
      container physical-interface {
        leaf GigabitEthernet {
          tailf:cli-allow-join-with-value;
          type string;
        }
      }
      leaf mode {
        type enumeration {
          enum "aggregate";
          enum "bypass";
        }
      }
    }
    list Multilink {
      tailf:cli-allow-join-with-key;
      tailf:cli-suppress-key-abbreviation;
      key "name";
      leaf name {
        type uint32;
      }
      uses interface-common-pre-grouping;
      uses interface-common-ptp-grouping {
        refine "service-policy/input";
        refine "service-policy/output";
      }
      uses interface-pointtopoint-grouping;
    }
    list MFR {
      tailf:cli-allow-join-with-key;
      tailf:cli-suppress-key-abbreviation;
      key "name";
      leaf name {
        type uint32;
      }
      uses interface-common-pre-grouping;
      uses interface-common-grouping;
      uses interface-pointtopoint-grouping;
    }
    container MFR-subinterface {
      tailf:cli-drop-node-name;
      list MFR {
        tailf:cli-allow-join-with-key;
        tailf:cli-suppress-key-abbreviation;
        key "name";
        leaf name {
          type string;
        }
        leaf type {
          tailf:cli-drop-node-name;
          tailf:cli-hide-in-submode;
          type enumeration {
            enum "multipoint";
            enum "point-to-point";
          }
        }
        uses interface-common-pre-grouping;
        uses interface-common-grouping;
        uses interface-pointtopoint-grouping;
      }
    }
    list BRI {
      tailf:cli-allow-join-with-key;
      tailf:cli-suppress-key-abbreviation;
      key "name";
      leaf name {
        type string;
      }
      uses interface-common-pre-grouping;
      uses interface-common-grouping;
      uses interface-pointtopoint-grouping;
    }
    list Ethernet-Internal {
      tailf:cli-allow-join-with-key;
      tailf:cli-suppress-key-abbreviation;
      key "name";
      leaf name {
        type string;
      }
      uses interface-common-pre-grouping;
      uses interface-ethernet-pre-grouping;
      uses interface-switch-grouping;
      uses interface-ethernet-switch-grouping;
      uses interface-common-macsec-grouping;
      uses interface-ethernet-post-grouping;
    }
    list Ethernet {
      tailf:cli-allow-join-with-key;
      tailf:cli-suppress-key-abbreviation;
      key "name";
      leaf name {
        type string;
      }
      uses interface-common-pre-grouping;
      uses interface-ethernet-pre-grouping;
      uses interface-switch-grouping;
      uses interface-ethernet-switch-grouping;
      uses interface-common-macsec-grouping;
      uses interface-ethernet-post-grouping;
    }
    list FastEthernet {
      tailf:cli-allow-join-with-key;
      tailf:cli-suppress-key-abbreviation;
      key "name";
      leaf name {
        type string;
      }
      uses interface-common-pre-grouping;
      uses interface-ethernet-pre-grouping;
      uses interface-switch-grouping;
      uses interface-ethernet-switch-grouping;
      uses interface-common-macsec-grouping;
      uses interface-ethernet-post-grouping;
    }
    list GigabitEthernet {
      tailf:cli-allow-join-with-key;
      tailf:cli-suppress-key-abbreviation;
      key "name";
      leaf name {
        type string;
      }
      uses interface-common-pre-grouping;
      uses interface-ethernet-pre-grouping;
      uses interface-switch-grouping {
        refine "switchport";
      }
      uses interface-ethernet-switch-grouping;
      uses interface-common-macsec-grouping;
      uses interface-ethernet-post-grouping;
    }
    list TwoGigabitEthernet {
      tailf:cli-allow-join-with-key;
      tailf:cli-suppress-key-abbreviation;
      key "name";
      leaf name {
        type string;
      }
      uses interface-common-pre-grouping;
      uses interface-ethernet-pre-grouping;
      uses interface-switch-grouping {
        refine "switchport";
      }
      uses interface-ethernet-switch-grouping;
      uses interface-common-macsec-grouping;
      uses interface-ethernet-post-grouping;
    }
    list FiveGigabitEthernet {
      tailf:cli-allow-join-with-key;
      tailf:cli-suppress-key-abbreviation;
      key "name";
      leaf name {
        type string;
      }
      uses interface-common-pre-grouping;
      uses interface-ethernet-pre-grouping;
      uses interface-switch-grouping {
        refine "switchport";
      }
      uses interface-ethernet-switch-grouping;
      uses interface-common-macsec-grouping;
      uses interface-ethernet-post-grouping;
    }
    list TenGigabitEthernet {
      tailf:cli-allow-join-with-key;
      tailf:cli-suppress-key-abbreviation;
      key "name";
      leaf name {
        type string;
      }
      uses interface-common-pre-grouping;
      uses interface-ethernet-pre-grouping;
      uses interface-switch-grouping {
        refine "switchport";
      }
      uses interface-ethernet-switch-grouping;
      uses interface-common-macsec-grouping;
      uses interface-ethernet-post-grouping;
    }
    list TwentyFiveGigE {
      tailf:cli-allow-join-with-key;
      tailf:cli-suppress-key-abbreviation;
      key "name";
      leaf name {
        type string;
      }
      uses interface-common-pre-grouping;
      uses interface-ethernet-pre-grouping;
      uses interface-switch-grouping {
        refine "switchport";
      }
      uses interface-ethernet-switch-grouping;
      uses interface-common-macsec-grouping;
      uses interface-ethernet-post-grouping;
    }
    list FortyGigabitEthernet {
      tailf:cli-allow-join-with-key;
      tailf:cli-suppress-key-abbreviation;
      key "name";
      leaf name {
        type string;
      }
      uses interface-common-pre-grouping;
      uses interface-ethernet-pre-grouping;
      uses interface-switch-grouping {
        refine "switchport";
      }
      uses interface-ethernet-switch-grouping;
      uses interface-common-macsec-grouping;
      uses interface-ethernet-post-grouping;
    }
    list FiftyGigE {
      tailf:cli-allow-join-with-key;
      tailf:cli-suppress-key-abbreviation;
      key "name";
      leaf name {
        type string;
      }
      uses interface-common-pre-grouping;
      uses interface-ethernet-pre-grouping;
      uses interface-switch-grouping {
        refine "switchport";
      }
      uses interface-ethernet-switch-grouping;
      uses interface-common-macsec-grouping;
      uses interface-ethernet-post-grouping;
    }
    list HundredGigE {
      tailf:cli-allow-join-with-key;
      tailf:cli-suppress-key-abbreviation;
      key "name";
      leaf name {
        type string;
      }
      uses interface-common-pre-grouping;
      uses interface-ethernet-pre-grouping;
      uses interface-switch-grouping {
        refine "switchport";
      }
      uses interface-ethernet-switch-grouping;
      uses interface-common-macsec-grouping;
      uses interface-ethernet-post-grouping;
    }
    list TwoHundredGigE {
      tailf:cli-allow-join-with-key;
      tailf:cli-suppress-key-abbreviation;
      key "name";
      leaf name {
        type string;
      }
      uses interface-common-pre-grouping;
      uses interface-ethernet-pre-grouping;
      uses interface-switch-grouping {
        refine "switchport";
      }
      uses interface-ethernet-switch-grouping;
      uses interface-common-macsec-grouping;
      uses interface-ethernet-post-grouping;
    }
    list FourHundredGigE {
      tailf:cli-allow-join-with-key;
      tailf:cli-suppress-key-abbreviation;
      key "name";
      leaf name {
        type string;
      }
      uses interface-common-pre-grouping;
      uses interface-ethernet-pre-grouping;
      uses interface-switch-grouping {
        refine "switchport";
      }
      uses interface-ethernet-switch-grouping;
      uses interface-common-macsec-grouping;
      uses interface-ethernet-post-grouping;
    }
    list AppGigabitEthernet {
      tailf:cli-allow-join-with-key;
      tailf:cli-suppress-key-abbreviation;
      key "name";
      leaf name {
        type string;
      }
      uses interface-common-pre-grouping;
      uses interface-ethernet-pre-grouping;
      uses interface-switch-grouping {
        refine "switchport";
      }
      uses interface-ethernet-switch-grouping;
      uses interface-common-macsec-grouping;
      uses interface-ethernet-post-grouping;
    }
    list mgmt {
      tailf:cli-allow-join-with-key;
      tailf:cli-suppress-key-abbreviation;
      key "name";
      leaf name {
        type uint8;
      }
      uses interface-common-pre-grouping;
      uses interface-common-grouping;
    }
    list Wlan-GigabitEthernet {
      tailf:cli-allow-join-with-key;
      tailf:cli-suppress-key-abbreviation;
      key "name";
      leaf name {
        type string;
      }
      uses interface-common-pre-grouping;
      uses interface-ethernet-pre-grouping;
      uses interface-switch-grouping;
      uses interface-ethernet-switch-grouping;
      uses interface-common-macsec-grouping;
      uses interface-ethernet-post-grouping;
    }
    list wlan-ap {
      tailf:cli-allow-join-with-key;
      tailf:cli-suppress-key-abbreviation;
      key "name";
      leaf name {
        type string;
      }
      uses interface-common-pre-grouping;
      uses interface-ethernet-pre-grouping;
      uses interface-ethernet-grouping;
      uses interface-common-macsec-grouping;
      uses interface-ethernet-post-grouping;
    }
    list Dialer {
      tailf:cli-allow-join-with-key;
      tailf:cli-suppress-key-abbreviation;
      key "name";
      leaf name {
        type string;
      }
      uses interface-common-pre-grouping;
      uses interface-common-grouping {
        refine "mtu";
      }
      uses interface-pointtopoint-grouping;
    }
    list ISM {
      tailf:cli-allow-join-with-key;
      tailf:cli-suppress-key-abbreviation;
      key "name";
      leaf name {
        type string;
      }
      uses interface-common-pre-grouping;
      uses interface-common-grouping;
      uses interface-pointtopoint-grouping;
    }
    list Analysis-Module {
      tailf:cli-allow-join-with-key;
      tailf:cli-suppress-key-abbreviation;
      key "name";
      leaf name {
        type string;
      }
      uses interface-common-pre-grouping;
      uses interface-common-grouping;
      uses interface-pointtopoint-grouping;
    }
    list Integrated-Service-Engine {
      tailf:cli-allow-join-with-key;
      tailf:cli-suppress-key-abbreviation;
      key "name";
      leaf name {
        type string;
      }
      uses interface-common-pre-grouping;
      uses interface-common-grouping;
      uses interface-pointtopoint-grouping;
    }
    list ATM {
      tailf:cli-allow-join-with-key;
      tailf:cli-suppress-key-abbreviation;
      key "name";
      leaf name {
        type string;
      }
      leaf point-to-point {
        tailf:cli-hide-in-submode;
        type empty;
      }
      uses interface-common-pre-grouping;
      uses interface-common-grouping;
      container bundle {
        list vc {
          tailf:cli-drop-node-name;
          key "name";
          leaf name {
            type string;
          }
          container oam {
            container retry {
              tailf:cli-compact-syntax;
              tailf:cli-sequence-commands;
              leaf up-count {
                tailf:cli-drop-node-name;
                type uint16;
              }
              leaf down-count {
                tailf:cli-drop-node-name;
                type uint16;
              }
              leaf retry-frequency {
                tailf:cli-drop-node-name;
                type uint16;
              }
            }
          }
          container encapsulation {
            choice encap-choice {
              container aal5mux {
                leaf ip {
                  type empty;
                }
              }
              leaf aal5snap {
                type empty;
              }
            }
          }
          container oam-bundle {
            tailf:cli-compact-syntax;
            tailf:cli-sequence-commands {
              tailf:cli-reset-siblings;
            }
            leaf manage {
              tailf:cli-optional-in-sequence;
              type empty;
            }
            leaf frequency {
              tailf:cli-drop-node-name;
              type uint16;
            }
          }
        }
      }
      container ima {
        leaf version {
          type enumeration {
            enum "1.0";
            enum "1.1";
          }
        }
        leaf group-id {
          type uint8;
        }
      }
      container atm {
        container bandwidth {
          leaf dynamic {
            type empty;
          }
        }
        container mcpt-timers {
          tailf:cli-compact-syntax;
          tailf:cli-sequence-commands {
            tailf:cli-reset-siblings;
          }
          leaf timer-1 {
            tailf:cli-drop-node-name;
            type uint16;
          }
          leaf timer-2 {
            tailf:cli-drop-node-name;
            type uint16;
          }
          leaf timer-3 {
            tailf:cli-drop-node-name;
            type uint16;
          }
        }
        container oversubscribe {
          tailf:cli-delete-when-empty;
          presence "true";
          leaf factor {
            type uint8;
          }
        }
        leaf enable-ilmi-trap {
          type boolean;
        }
        container ilmi-keepalive {
          presence "true";
        }
        container route-bridged {
          leaf ip {
            type empty;
          }
          leaf ipv6 {
            type empty;
          }
        }
        container clock {
          leaf INTERNAL {
            type empty;
          }
        }
      }
      list pvc {
        tailf:cli-sequence-commands;
        key "name";
        leaf handle {
          tailf:cli-prefix-key;
          tailf:cli-drop-node-name;
          tailf:cli-optional-in-sequence;
          type uint32;
        }
        leaf name {
          tailf:cli-suppress-range;
          type string;
        }
        leaf l2transport {
          tailf:cli-hide-in-submode;
          type empty;
        }
        leaf class-vc {
          tailf:cli-break-sequence-commands;
          type string;
        }
        container vbr-nrt {
          tailf:cli-compact-syntax;
          tailf:cli-sequence-commands {
            tailf:cli-reset-siblings;
          }
          leaf pcr {
            tailf:cli-drop-node-name;
            type uint16;
          }
          leaf scr {
            tailf:cli-drop-node-name;
            type uint16;
          }
          leaf mbs {
            tailf:cli-drop-node-name;
            type uint16;
          }
        }
        leaf tx-limit {
          type uint32;
        }
        leaf tx-ring-limit {
          type uint8;
        }
        leaf vc-hold-queue {
          type uint16;
        }
        container cell-packing {
          tailf:cli-compact-syntax;
          tailf:cli-sequence-commands {
            tailf:cli-reset-siblings;
          }
          leaf maxcells {
            tailf:cli-drop-node-name;
            type uint8;
          }
          leaf mcpt-timer {
            type uint8;
          }
        }
        choice encap-choice {
          leaf encapsulation {
            type enumeration {
              enum "aal0";
              enum "aal5";
              enum "aal5snap";
              enum "aal5nlpid";
            }
          }
          container encapsulation-aal5mux {
            tailf:cli-drop-node-name;
            container encapsulation {
              tailf:cli-compact-syntax;
              tailf:cli-sequence-commands {
                tailf:cli-reset-siblings;
              }
              leaf aal5mux {
                type empty;
              }
              container ppp {
                tailf:cli-flatten-container;
                tailf:cli-compact-syntax;
                leaf dialer {
                  type empty;
                }
              }
            }
          }
        }
        container dialer {
          tailf:cli-compact-syntax;
          tailf:cli-sequence-commands {
            tailf:cli-reset-siblings;
          }
          presence "true";
          leaf pool-member {
            type uint8;
          }
        }
        container service-policy {
          uses service-policy-grouping;
        }
        uses pppoe-client-grouping;
        uses xconnect-grouping;
      }
    }
    list CEM {
      tailf:cli-allow-join-with-key;
      tailf:cli-suppress-key-abbreviation;
      key "name";
      leaf name {
        type string;
      }
      uses interface-common-pre-grouping;
      uses interface-common-grouping;
      uses interface-cem-grouping;
    }
    list CEM-ACR {
      tailf:cli-allow-join-with-key;
      tailf:cli-suppress-key-abbreviation;
      key "name";
      leaf name {
        type string;
      }
      uses interface-common-pre-grouping;
      uses interface-common-grouping;
      uses interface-cem-grouping;
    }
    list Vif {
      tailf:cli-allow-join-with-key;
      tailf:cli-suppress-key-abbreviation;
      key "name";
      leaf name {
        type uint32;
      }
      uses interface-common-pre-grouping;
      uses interface-ethernet-pre-grouping;
      uses interface-ethernet-grouping;
      uses interface-common-macsec-grouping;
      uses interface-ethernet-post-grouping;
    }
    list BDI {
      tailf:cli-allow-join-with-key;
      tailf:cli-suppress-key-abbreviation;
      key "name";
      leaf name {
        type uint16;
      }
      uses interface-common-pre-grouping;
      uses interface-ethernet-pre-grouping;
      uses interface-ethernet-grouping;
      uses interface-common-macsec-grouping;
      uses interface-ethernet-post-grouping;
    }
    list BVI {
      tailf:cli-allow-join-with-key;
      tailf:cli-suppress-key-abbreviation;
      key "name";
      leaf name {
        type string;
      }
      uses interface-common-pre-grouping;
      uses interface-common-grouping;
    }
    list CMON-Tunnel {
      tailf:cli-allow-join-with-key;
      tailf:cli-suppress-key-abbreviation;
      key "name";
      leaf name {
        type string;
      }
      uses description-grouping;
      container ip {
        container subscriber {
          tailf:cli-add-mode;
          presence "true";
        }
      }
      container mode {
        choice mode-choice {
          leaf buffer {
            type empty;
          }
          leaf tunnel {
            type enumeration {
              enum "gre";
              enum "erspan";
            }
          }
        }
      }
      uses interface-tunnel-grouping;
    }
    list Cable {
      tailf:cli-allow-join-with-key;
      tailf:cli-suppress-key-abbreviation;
      key "name";
      leaf name {
        type string;
      }
      uses interface-common-pre-grouping;
      uses interface-common-grouping;
      container downstream {
        list Cable {
          tailf:cli-suppress-mode;
          tailf:cli-delete-when-empty;
          key "name rf-channel";
          leaf name {
            type string;
          }
          leaf rf-channel {
            tailf:cli-expose-key-name;
            type uint8;
          }
          leaf-list upstream {
            tailf:cli-range-list-syntax;
            type uint8;
          }
        }
        list Modular-Cable {
          tailf:cli-suppress-mode;
          tailf:cli-delete-when-empty;
          key "name rf-channel";
          leaf name {
            type string;
          }
          leaf rf-channel {
            tailf:cli-expose-key-name;
            type uint8;
          }
          leaf-list upstream {
            tailf:cli-range-list-syntax;
            type uint8;
          }
        }
        list Integrated-Cable {
          tailf:cli-suppress-mode;
          tailf:cli-delete-when-empty;
          key "name rf-channel";
          leaf name {
            type string;
          }
          leaf rf-channel {
            tailf:cli-expose-key-name;
            type uint8;
          }
          leaf-list upstream {
            tailf:cli-range-list-syntax;
            type uint8;
          }
        }
        list Downstream-Cable {
          tailf:cli-suppress-mode;
          tailf:cli-delete-when-empty;
          key "name rf-channel";
          leaf name {
            type string;
          }
          leaf rf-channel {
            tailf:cli-expose-key-name;
            type uint8;
          }
          leaf-list upstream {
            tailf:cli-range-list-syntax;
            type uint8;
          }
        }
      }
      list upstream {
        tailf:cli-suppress-mode;
        tailf:cli-delete-when-empty;
        tailf:cli-compact-syntax;
        key "id";
        leaf id {
          type uint8;
        }
        leaf Upstream-Cable {
          type string;
        }
        leaf us-channel {
          type uint8;
        }
      }
      container cable {
        container tftp-enforce {
          tailf:cli-delete-when-empty;
          presence "true";
          leaf mark-only {
            type empty;
          }
        }
        leaf ip-init {
          type enumeration {
            enum "apm";
            enum "dual-stack";
            enum "ipv4";
            enum "ipv6";
          }
        }
        container managed {
          leaf fiber-node {
            type uint16;
          }
        }
        container mtc-mode {
          presence "true";
        }
        leaf mrc-mode {
          type boolean;
        }
        list rcc-template {
          tailf:cli-suppress-mode;
          tailf:cli-delete-when-empty;
          key "index";
          leaf index {
            type uint8;
          }
        }
        container rcp-control {
          leaf verbose {
            type empty;
          }
        }
        container shared-secret {
          tailf:cli-compact-syntax;
          tailf:cli-sequence-commands;
          uses password-grouping {
            refine "secret";
          }
        }
        container dynamic-secret {
          tailf:cli-compact-syntax;
          tailf:cli-sequence-commands {
            tailf:cli-reset-siblings;
          }
          choice dynamic-secret-choice {
            case reject {
              leaf reject {
                type empty;
              }
            }
            case mark {
              leaf mark {
                type empty;
              }
            }
            case lock {
              leaf lock {
                type empty;
              }
              leaf lock-qos {
                tailf:cli-drop-node-name;
                tailf:cli-optional-in-sequence;
                type uint16;
              }
            }
          }
          leaf nocrypt {
            type empty;
          }
        }
        leaf d31-mode {
          type boolean;
        }
        leaf udc-capability {
          type empty;
        }
        container enable-trap {
          leaf cmonoff-notification {
            type empty;
          }
          leaf cmonoff-interval {
            type uint32;
          }
        }
        leaf packet-cache {
          type boolean;
        }
        leaf default-phy-burst {
          type uint16;
        }
        container insertion-interval {
          choice interval-choice {
            leaf fixed-intrvl {
              tailf:cli-drop-node-name;
              type uint16;
            }
            container automatic {
              tailf:cli-compact-syntax;
              tailf:cli-sequence-commands {
                tailf:cli-reset-siblings;
              }
              leaf min-intrvl {
                tailf:cli-drop-node-name;
                type uint8;
              }
              leaf max-intrvl {
                tailf:cli-drop-node-name;
                type uint16;
              }
            }
          }
        }
        uses cable-map-advance-grouping;
        leaf sync-interval {
          type uint16;
        }
        leaf bundle {
          type uint8;
        }
        container downstream {
          leaf description {
            tailf:cli-multi-value;
            type string;
          }
          container dsg {
            leaf timer {
              type uint16;
            }
            list tg {
              tailf:cli-suppress-mode;
              tailf:cli-delete-when-empty;
              key "tgid";
              leaf tgid {
                type uint16;
              }
              list channel {
                tailf:cli-suppress-mode;
                tailf:cli-delete-when-empty;
                key "channel-id";
                leaf channel-id {
                  type uint16;
                }
              }
            }
          }
        }
        container upstream {
          leaf balance-scheduling {
            type empty;
          }
          leaf max-ports {
            type uint8;
          }
          list bonding-group {
            key "id";
            leaf id {
              type uint16;
            }
            uses description-grouping;
            list upstream {
              tailf:cli-suppress-mode;
              tailf:cli-delete-when-empty;
              key "number";
              leaf number {
                type uint8;
              }
            }
            leaf attributes {
              type string;
            }
          }
          list cable-upstream-list {
            tailf:cli-drop-node-name;
            tailf:cli-suppress-mode;
            tailf:cli-delete-when-empty;
            key "port";
            leaf port {
              type uint8;
            }
            leaf connector {
              type uint8;
            }
            leaf frequency {
              type uint32;
            }
            container channel-width {
              tailf:cli-compact-syntax;
              tailf:cli-sequence-commands {
                tailf:cli-reset-siblings;
              }
              leaf first-choice-width {
                tailf:cli-drop-node-name;
                type uint32;
              }
              leaf last-choice-width {
                tailf:cli-drop-node-name;
                type uint32;
              }
            }
            leaf description {
              tailf:cli-multi-value;
              type string;
            }
            leaf docsis-mode {
              type enumeration {
                enum "atdma";
                enum "scdma";
                enum "tdma";
                enum "tdma-atdma";
              }
            }
            leaf minislot-size {
              type uint8;
            }
            container power-adjust {
              leaf continue {
                type uint8;
              }
            }
            container range-backoff {
              tailf:cli-compact-syntax;
              tailf:cli-sequence-commands;
              choice range-backoff-choice {
                case automatic {
                  leaf automatic {
                    type empty;
                  }
                }
                case numeric {
                  leaf start {
                    tailf:cli-drop-node-name;
                    type uint8;
                  }
                  leaf end {
                    tailf:cli-drop-node-name;
                    type uint8;
                  }
                }
              }
            }
            container modulation-profile {
              tailf:cli-compact-syntax;
              tailf:cli-sequence-commands {
                tailf:cli-reset-siblings;
              }
              leaf primary-profile-number {
                tailf:cli-drop-node-name;
                type uint8;
              }
              leaf secondary-profile-number {
                tailf:cli-drop-node-name;
                type uint8;
              }
              leaf tertiary-profile-number {
                tailf:cli-drop-node-name;
                type uint8;
              }
            }
            leaf rate-limit {
              type boolean;
            }
            leaf equalization-coefficient {
              type empty;
            }
            leaf equalization-error-recovery {
              type boolean;
            }
            container rate-adapt {
              presence "true";
            }
            leaf attribute-mask {
              type string;
            }
            leaf chan-class-id {
              type string;
            }
            leaf shutdown {
              type boolean;
            }
          }
          container ranging-poll {
            tailf:cli-compact-syntax;
            leaf interval {
              type uint16;
            }
            leaf t4-multiplier {
              type uint8;
            }
          }
          container resiliency {
            leaf on-failure {
              type enumeration {
                enum "disable-channel";
                enum "extended-ranging";
                enum "reset-modem";
              }
            }
            list sf-move {
              tailf:cli-suppress-mode;
              tailf:cli-delete-when-empty;
              key "name";
              leaf name {
                type enumeration {
                  enum "RTPS";
                  enum "NRTPS";
                  enum "UGS";
                  enum "UGS-AD";
                }
              }
            }
          }
          leaf ext-power {
            type boolean;
          }
          leaf max-channel-power-offset {
            type uint8;
          }
        }
        container sid-cluster-group {
          leaf dynamic {
            type empty;
          }
          leaf num-of-cluster {
            type uint8;
          }
          leaf req-multiplier {
            type uint8;
          }
        }
        container sid-cluster-switching {
          leaf max-request {
            type uint8;
          }
          leaf max-time {
            type uint16;
          }
        }
        container divert-rate-limit {
          tailf:cli-compact-syntax;
          tailf:cli-sequence-commands {
            tailf:cli-reset-siblings;
          }
          leaf rate {
            type uint16;
          }
          leaf limit {
            type uint16;
          }
        }
        leaf mac-domain-profile {
          type string;
        }
        container privacy {
          leaf mandatory {
            type empty;
          }
          leaf bpi-plus-policy {
            type enumeration {
              enum "capable-enforcement";
              enum "d11-enabled-enforcement";
              enum "d11-enforcement";
              enum "total-enforcement";
            }
          }
          leaf accept-self-signed-certificate {
            type empty;
          }
          leaf eae-policy {
            type enumeration {
              enum "capability-enforcement" {
                value 3;
              }
              enum "disable-enforcement" {
                value 1;
              }
              enum "ranging-enforcement" {
                value 2;
              }
              enum "total-enforcement" {
                value 4;
              }
            }
          }
          leaf skip-validity-period {
            type empty;
          }
        }
        leaf diplexer-band-edge {
          type boolean;
        }
        container cm-status {
          leaf-list enable {
            tailf:cli-range-list-syntax;
            type uint8;
          }
        }
      }
    }
    list Video {
      tailf:cli-allow-join-with-key;
      tailf:cli-suppress-key-abbreviation;
      key "name";
      leaf name {
        type string;
      }
      uses interface-common-pre-grouping;
      uses interface-common-grouping;
    }
    list Integrated-Cable {
      tailf:cli-allow-join-with-key;
      tailf:cli-suppress-key-abbreviation;
      key "name";
      leaf name {
        type string;
      }
      uses interface-common-pre-grouping;
      uses interface-common-grouping;
      container cable {
        container downstream {
          container qos {
            container wfq {
              container weights {
                tailf:cli-compact-syntax;
                tailf:cli-sequence-commands {
                  tailf:cli-reset-siblings;
                }
                leaf pri0 {
                  tailf:cli-drop-node-name;
                  type uint8;
                }
                leaf pri1 {
                  tailf:cli-drop-node-name;
                  type uint8;
                }
                leaf pri2 {
                  tailf:cli-drop-node-name;
                  type uint8;
                }
                leaf pri3 {
                  tailf:cli-drop-node-name;
                  type uint8;
                }
                leaf pri4 {
                  tailf:cli-drop-node-name;
                  type uint8;
                }
                leaf pri5 {
                  tailf:cli-drop-node-name;
                  type uint8;
                }
                leaf pri6 {
                  tailf:cli-drop-node-name;
                  type uint8;
                }
                leaf pri7 {
                  tailf:cli-drop-node-name;
                  type uint8;
                }
              }
            }
          }
        }
        leaf bundle {
          type uint8;
        }
        container managed {
          leaf fiber-node {
            type uint16;
          }
        }
        container rf-bandwidth-percent {
          leaf percent-value {
            tailf:cli-drop-node-name;
            type uint8;
          }
        }
      }
    }
    list Modular-Cable {
      tailf:cli-allow-join-with-key;
      tailf:cli-suppress-key-abbreviation;
      key "name";
      leaf name {
        type string;
      }
      uses interface-common-pre-grouping;
      uses interface-common-grouping;
      container cable {
        leaf bundle {
          type uint8;
        }
        container rf-bandwidth-percent {
          tailf:cli-compact-syntax;
          tailf:cli-sequence-commands {
            tailf:cli-reset-siblings;
          }
          leaf percent-value {
            tailf:cli-drop-node-name;
            type uint8;
          }
          container remaining {
            tailf:cli-flatten-container;
            tailf:cli-compact-syntax;
            leaf ratio {
              type uint8;
            }
          }
        }
        container cm-status {
          container enable {
            leaf no-list {
              tailf:cli-multi-value;
              type string;
            }
          }
        }
      }
    }
    list Downstream-Cable {
      tailf:cli-allow-join-with-key;
      tailf:cli-suppress-key-abbreviation;
      key "name";
      leaf name {
        type string;
      }
      uses interface-common-pre-grouping;
      uses interface-common-grouping;
      container cable {
        leaf bundle {
          type uint8;
        }
        container managed {
          leaf fiber-node {
            type uint16;
          }
        }
        container rf-bandwidth-percent {
          leaf percent-value {
            tailf:cli-drop-node-name;
            type uint8;
          }
        }
      }
    }
    list Wideband-Cable {
      tailf:cli-allow-join-with-key;
      tailf:cli-suppress-key-abbreviation;
      key "name";
      leaf name {
        type string;
      }
      uses interface-common-pre-grouping;
      uses interface-common-grouping;
      container cable {
        leaf bundle {
          type uint8;
        }
        container managed {
          leaf fiber-node {
            type uint16;
          }
        }
        leaf wideband-profile {
          type string;
        }
        container privacy {
          leaf accept-self-signed-certificate {
            type empty;
          }
        }
        leaf ds-resiliency {
          type empty;
        }
        container rf-channel {
          list rf-channel-list {
            tailf:cli-drop-node-name;
            tailf:cli-suppress-mode;
            tailf:cli-delete-when-empty;
            tailf:cli-compact-syntax;
            tailf:cli-sequence-commands {
              tailf:cli-reset-siblings;
            }
            key "rf-port";
            leaf rf-port {
              type uint8;
            }
            leaf bandwidth-percent {
              type uint8;
            }
            container remaining {
              tailf:cli-flatten-container;
              tailf:cli-compact-syntax;
              leaf ratio {
                type uint8;
              }
            }
          }
        }
        container rf-channels {
          list channel-list {
            tailf:cli-suppress-mode;
            tailf:cli-delete-when-empty;
            key "id";
            leaf id {
              type uint8;
            }
            leaf bandwidth-percent {
              type uint8;
            }
          }
          list controller {
            tailf:cli-suppress-mode;
            tailf:cli-delete-when-empty;
            tailf:cli-compact-syntax;
            tailf:cli-sequence-commands;
            key "id";
            leaf id {
              type uint8;
            }
            leaf-list channel-list {
              tailf:cli-range-list-syntax;
              type uint8;
            }
            leaf bandwidth-percent {
              type uint8;
            }
          }
        }
        container downstream {
          leaf attribute-mask {
            type string;
          }
        }
      }
    }
    list Bundle {
      tailf:cli-allow-join-with-key;
      tailf:cli-suppress-key-abbreviation;
      key "name";
      leaf name {
        type uint8;
      }
      uses interface-common-pre-grouping;
      uses interface-common-grouping;
      container cable {
        uses bundle-interface-cable-common;
        container arp {
          container filter {
            container request-send {
              tailf:cli-compact-syntax;
              tailf:cli-sequence-commands;
              tailf:cli-delete-when-empty;
              presence "true";
              leaf number {
                tailf:cli-drop-node-name;
                type uint8;
              }
              leaf window-size {
                tailf:cli-drop-node-name;
                type uint8;
              }
            }
            container reply-accept {
              tailf:cli-compact-syntax;
              tailf:cli-sequence-commands;
              tailf:cli-delete-when-empty;
              presence "true";
              leaf number {
                tailf:cli-drop-node-name;
                type uint8;
              }
              leaf window-size {
                tailf:cli-drop-node-name;
                type uint8;
              }
            }
          }
        }
        container dhcp-parse {
          leaf option-43 {
            type empty;
          }
          leaf option-60 {
            type empty;
          }
        }
      }
    }
    container Bundle-subinterface {
      tailf:cli-drop-node-name;
      list Bundle {
        tailf:cli-allow-join-with-key;
        tailf:cli-suppress-key-abbreviation;
        key "name";
        leaf name {
          type string;
        }
        uses interface-common-pre-grouping;
        uses interface-common-grouping;
        container cable {
          uses bundle-interface-cable-common;
        }
      }
    }
    list Cellular {
      tailf:cli-allow-join-with-key;
      tailf:cli-suppress-key-abbreviation;
      key "name";
      leaf name {
        type string;
      }
      uses interface-common-pre-grouping;
      uses interface-common-grouping;
      uses interface-pointtopoint-grouping;
    }
    list Qam-red {
      tailf:cli-allow-join-with-key;
      tailf:cli-suppress-key-abbreviation;
      key "name";
      leaf name {
        type string;
      }
      uses interface-common-pre-grouping;
      uses interface-common-grouping;
      container cable {
        leaf carrier-id {
          type uint16;
        }
        container mode {
          container depi {
            choice depi-choice {
              container local;
              container remote {
                tailf:cli-delete-when-empty;
                presence "true";
                leaf learn {
                  type empty;
                }
              }
            }
          }
        }
        container downstream {
          leaf max-carriers {
            type uint8;
          }
          leaf lqam-group {
            type uint8;
          }
          leaf tsid {
            type uint16;
          }
        }
      }
      container depi {
        leaf depi-tunnel {
          type string;
        }
      }
    }
    list Asi {
      tailf:cli-allow-join-with-key;
      tailf:cli-suppress-key-abbreviation;
      key "name";
      leaf name {
        type string;
      }
      uses interface-common-pre-grouping;
      uses interface-common-grouping;
    }
    list Vlan {
      tailf:cli-allow-join-with-key;
      key "name";
      leaf name {
        type uint16;
      }
      uses interface-common-pre-grouping;
      uses interface-ethernet-pre-grouping;
      uses interface-ethernet-grouping;
      uses interface-common-macsec-grouping;
      uses interface-ethernet-post-grouping;
      leaf autostate {
        type boolean;
      }
    }
    list Async {
      tailf:cli-allow-join-with-key;
      tailf:cli-suppress-key-abbreviation;
      key "name";
      leaf name {
        type string;
      }
      uses interface-common-pre-grouping;
      uses interface-common-grouping;
      uses interface-pointtopoint-grouping;
      container ignore {
        leaf dcd {
          type empty;
        }
        leaf cts {
          type empty;
        }
        leaf dsr {
          type empty;
        }
      }
    }
    list Group-Async {
      tailf:cli-allow-join-with-key;
      tailf:cli-suppress-key-abbreviation;
      key "name";
      leaf name {
        type uint16;
      }
      uses interface-common-pre-grouping;
      uses interface-common-grouping;
      uses interface-pointtopoint-grouping;
    }
    list POS {
      tailf:cli-allow-join-with-key;
      tailf:cli-suppress-key-abbreviation;
      key "name";
      leaf name {
        type string;
      }
      leaf type {
        tailf:cli-drop-node-name;
        tailf:cli-hide-in-submode;
        type enumeration {
          enum "point-to-point";
        }
      }
      uses interface-common-pre-grouping;
      uses interface-common-grouping;
      uses interface-pointtopoint-grouping;
      container aps {
        leaf group {
          type uint8;
        }
        list protect {
          tailf:cli-suppress-mode;
          tailf:cli-delete-when-empty;
          key "circuit-number ip-address";
          leaf circuit-number {
            type uint32;
          }
          leaf ip-address {
            type inet:ip-address;
          }
        }
        leaf working {
          type uint32;
        }
      }
      container pos {
        leaf ais-shut {
          type empty;
        }
        leaf framing {
          type enumeration {
            enum "sdh";
            enum "sonet";
          }
        }
        container report {
          leaf rdool {
            type empty;
          }
          leaf lais {
            type empty;
          }
          leaf lrdi {
            type empty;
          }
          leaf pais {
            type empty;
          }
          leaf prdi {
            type empty;
          }
          leaf sd-ber {
            type empty;
          }
        }
        leaf scramble-atm {
          type empty;
        }
        container threshold {
          leaf sf-ber {
            type uint8;
          }
        }
        container flag {
          leaf c2 {
            type uint8;
          }
          leaf j0 {
            type uint8;
          }
          leaf s1s0 {
            type uint8;
          }
        }
        container delay {
          container triggers {
            leaf line {
              type uint16;
            }
            leaf path {
              type uint16;
            }
          }
        }
      }
    }
    list SM {
      tailf:cli-allow-join-with-key;
      tailf:cli-suppress-key-abbreviation;
      key "name";
      leaf name {
        type string;
      }
      uses interface-common-pre-grouping;
      uses interface-common-grouping;
    }
    list Serial {
      tailf:cli-allow-join-with-key;
      tailf:cli-suppress-key-abbreviation;
      key "name";
      leaf name {
        type string;
      }
      uses interface-common-pre-grouping;
      uses interface-common-ptp-grouping;
      uses interface-pointtopoint-grouping;
      uses interface-Serial-grouping;
      uses xconnect-grouping;
    }
    container Serial-subinterface {
      tailf:cli-drop-node-name;
      list Serial {
        tailf:cli-allow-join-with-key;
        tailf:cli-suppress-key-abbreviation;
        key "name";
        leaf name {
          type string;
        }
        leaf type {
          tailf:cli-drop-node-name;
          tailf:cli-hide-in-submode;
          type enumeration {
            enum "multipoint";
            enum "point-to-point";
          }
        }
        uses interface-common-pre-grouping;
        uses interface-common-ptp-grouping;
        uses interface-pointtopoint-grouping;
        uses interface-Serial-grouping;
        uses xconnect-grouping;
      }
    }

    grouping interface-Serial-grouping {
      container pos {
        container report {
          leaf b3-tca {
            type empty;
          }
          leaf pais {
            type empty;
          }
          leaf plop {
            type empty;
          }
          leaf pplm {
            type empty;
          }
          leaf prdi {
            type empty;
          }
          leaf ptim {
            type empty;
          }
          leaf ptiu {
            type empty;
          }
          leaf puneq {
            type empty;
          }
        }
      }
    }
    list Virtual-Template {
      tailf:cli-allow-join-with-key;
      tailf:cli-suppress-key-abbreviation;
      key "name";
      leaf name {
        type uint16;
      }
      leaf type {
        tailf:cli-hide-in-submode;
        type enumeration {
          enum "ethernet";
          enum "serial";
          enum "tunnel";
        }
      }
      uses interface-common-pre-grouping;
      uses interface-ethernet-pre-grouping;
      uses interface-ethernet-grouping;
      uses interface-common-macsec-grouping;
      uses interface-ethernet-post-grouping;
      uses interface-pointtopoint-grouping;
      uses interface-tunnel-grouping;
    }
    list Virtual-PPP {
      tailf:cli-allow-join-with-key;
      tailf:cli-suppress-key-abbreviation;
      key "name";
      leaf name {
        type uint32;
      }
      uses interface-common-pre-grouping;
      uses interface-ethernet-pre-grouping;
      uses interface-ethernet-grouping;
      uses interface-common-macsec-grouping;
      uses interface-ethernet-post-grouping;
      uses interface-pointtopoint-grouping;
      uses interface-tunnel-grouping;
    }
    list pseudowire {
      tailf:cli-allow-join-with-key;
      tailf:cli-suppress-key-abbreviation;
      key "name";
      leaf name {
        type uint32;
      }
      leaf description {
        tailf:cli-multi-value;
        type string;
      }
      leaf shutdown {
        type empty;
      }
      container source {
        container template {
          tailf:cli-compact-syntax;
          tailf:cli-sequence-commands {
            tailf:cli-reset-siblings;
          }
          leaf type {
            type enumeration {
              enum "pseudowire";
            }
          }
          leaf name {
            tailf:cli-drop-node-name;
            type string;
          }
        }
      }
      leaf encapsulation {
        type enumeration {
          enum "l2tpv3";
          enum "mpls";
        }
      }
      container signaling {
        leaf protocol {
          type enumeration {
            enum "ldp";
            enum "none";
          }
        }
      }
      container neighbor {
        tailf:cli-compact-syntax;
        tailf:cli-sequence-commands;
        leaf address {
          tailf:cli-drop-node-name;
          type inet:ipv4-address;
        }
        leaf vcid {
          tailf:cli-drop-node-name;
          type uint32;
        }
      }
      container vc {
        leaf type {
          type enumeration {
            enum "vlan";
            enum "ethernet";
          }
        }
      }
      leaf mtu {
        type uint16;
      }
      leaf control-word {
        type enumeration {
          enum "exclude";
          enum "include";
        }
      }
      container label {
        tailf:cli-compact-syntax;
        tailf:cli-sequence-commands;
        leaf local-pseudowire-label {
          tailf:cli-drop-node-name;
          type uint32;
        }
        leaf remote-pseudowire-label {
          tailf:cli-drop-node-name;
          type uint32;
        }
      }
      container pseudowire {
        leaf type {
          type string;
        }
      }
      container service-policy {
        uses service-policy-grouping;
      }
      uses pseudowire-preferred-path-grouping;
      container bandwidth {
        tailf:cli-compact-syntax;
        tailf:cli-sequence-commands {
          tailf:cli-reset-siblings;
        }
        leaf kilobits {
          tailf:cli-drop-node-name;
          type uint32;
        }
        leaf persistent {
          type empty;
        }
      }
      container load-balance {
        leaf flow-label {
          type enumeration {
            enum "both";
            enum "receive";
            enum "transmit";
          }
        }
      }
    }
    list LISP {
      tailf:cli-allow-join-with-key;
      tailf:cli-suppress-key-abbreviation;
      key "name";
      leaf name {
        type uint16;
      }
      uses interface-common-pre-grouping;
      uses interface-common-grouping;
    }
    container LISP-subinterface {
      tailf:cli-drop-node-name;
      list LISP {
        tailf:cli-allow-join-with-key;
        tailf:cli-suppress-key-abbreviation;
        key "name";
        leaf name {
          type string;
        }
        uses interface-common-pre-grouping;
        uses interface-common-grouping;
      }
    }
    list vasileft {
      tailf:cli-allow-join-with-key;
      tailf:cli-suppress-key-abbreviation;
      key "name";
      leaf name {
        type uint16;
      }
      uses interface-common-pre-grouping;
      uses interface-common-grouping;
    }
    list vasiright {
      tailf:cli-allow-join-with-key;
      tailf:cli-suppress-key-abbreviation;
      key "name";
      leaf name {
        type uint16;
      }
      uses interface-common-pre-grouping;
      uses interface-common-grouping;
    }
    list AppNav-Compress {
      tailf:cli-allow-join-with-key;
      tailf:cli-suppress-key-abbreviation;
      key "name";
      leaf name {
        type uint16;
      }
      uses interface-common-pre-grouping;
      uses interface-common-grouping;
    }
    list AppNav-UnCompress {
      tailf:cli-allow-join-with-key;
      tailf:cli-suppress-key-abbreviation;
      key "name";
      leaf name {
        type uint16;
      }
      uses interface-common-pre-grouping;
      uses interface-common-grouping;
    }
    list ucse {
      tailf:cli-allow-join-with-key;
      tailf:cli-suppress-key-abbreviation;
      key "name";
      leaf name {
        tailf:cli-suppress-range;
        type string;
      }
      uses interface-common-pre-grouping;
      uses interface-ethernet-pre-grouping;
      uses interface-switch-grouping;
      uses interface-ethernet-switch-grouping;
      uses interface-common-macsec-grouping;
      uses interface-ethernet-post-grouping;
    }
    list GMPLS {
      tailf:cli-allow-join-with-key;
      tailf:cli-suppress-key-abbreviation;
      key "name";
      leaf name {
        type uint16;
      }
      uses interface-common-pre-grouping;
      uses interface-common-grouping;
    }
    container GMPLS-subinterface {
      tailf:cli-drop-node-name;
      list GMPLS {
        tailf:cli-allow-join-with-key;
        tailf:cli-suppress-key-abbreviation;
        key "name";
        leaf name {
          type string;
        }
        uses interface-common-pre-grouping;
        uses interface-common-grouping;
      }
    }
  }
  container ethernet {
    container oam {
      container mib {
        container log {
          leaf size {
            type uint8;
          }
        }
      }
    }
    container lmi {
      leaf global {
        type empty;
      }
      leaf ce {
        type empty;
      }
    }
    list evc {
      tailf:cli-compact-syntax;
      key "name";
      leaf name {
        type string;
      }
      container uni {
        leaf count {
          type uint16;
        }
      }
      container oam {
        container protocol {
          choice protocol-choice {
            leaf ldp {
              type empty;
            }
            container cfm {
              tailf:cli-compact-syntax;
              tailf:cli-sequence-commands {
                tailf:cli-reset-siblings;
              }
              leaf svlan {
                tailf:cli-optional-in-sequence;
                type uint16;
              }
              leaf domain {
                type string;
              }
            }
          }
        }
      }
    }
    container cfm {
      leaf enable {
        type empty;
      }
      leaf ieee {
        type empty;
      }
      container alarm {
        leaf notification {
          type enumeration {
            enum "none";
            enum "xcon";
            enum "error-xcon";
            enum "remote-error-xcon";
            enum "mac-remote-error-xcon";
            enum "all";
          }
        }
      }
      leaf global {
        type empty;
      }
      container logging {
        tailf:cli-delete-when-empty;
        presence "true";
        container alarm {
          leaf ieee {
            type empty;
          }
          leaf cisco {
            type empty;
          }
        }
      }
      container traceroute {
        container cache {
          presence "true";
          leaf size {
            type uint16;
          }
          leaf hold-time {
            type uint16;
          }
        }
      }
      container mip {
        list auto-create {
          tailf:cli-suppress-mode;
          tailf:cli-delete-when-empty;
          tailf:cli-compact-syntax;
          tailf:cli-sequence-commands;
          key "evc";
          leaf evc {
            tailf:cli-expose-key-name;
            type string;
          }
          leaf level {
            tailf:cli-prefix-key;
            type uint8;
          }
        }
      }
      list domain {
        tailf:cli-compact-syntax;
        key "name";
        leaf name {
          type string;
        }
        leaf level {
          tailf:cli-hide-in-submode;
          type uint8;
        }
        container mip {
          container auto-create {
            tailf:cli-delete-when-empty;
            presence "true";
            leaf lower-mep-only {
              type empty;
            }
          }
        }
        container mep {
          leaf archive-hold-time {
            type uint16;
          }
        }
        container id {
          choice id-choice {
            leaf mac {
              tailf:cli-drop-node-name;
              type string;
            }
            leaf dns {
              type string;
            }
            leaf null {
              type empty;
            }
          }
        }
        leaf sender-id {
          type enumeration {
            enum "chassis";
            enum "none";
          }
        }
        list service {
          tailf:cli-sequence-commands;
          key "csi-id";
          leaf csi-id {
            type string;
          }
          leaf icc {
            tailf:cli-prefix-key;
            tailf:cli-optional-in-sequence;
            type string;
          }
          leaf vlan-id {
            tailf:cli-prefix-key;
            tailf:cli-optional-in-sequence;
            type empty;
          }
          leaf port {
            tailf:cli-hide-in-submode;
            tailf:cli-optional-in-sequence;
            type empty;
          }
          leaf evc {
            tailf:cli-hide-in-submode;
            tailf:cli-optional-in-sequence;
            type string;
          }
          leaf vlan {
            tailf:cli-hide-in-submode;
            tailf:cli-optional-in-sequence;
            type uint16;
          }
          leaf inner-vlan {
            tailf:cli-hide-in-submode;
            tailf:cli-optional-in-sequence;
            type uint16;
          }
          leaf direction {
            tailf:cli-hide-in-submode;
            type enumeration {
              enum "down";
            }
          }
          container mep {
            tailf:cli-break-sequence-commands;
            list mpid {
              tailf:cli-suppress-mode;
              tailf:cli-delete-when-empty;
              ordered-by user;
              key "id";
              leaf id {
                tailf:cli-suppress-range;
                type uint16;
              }
            }
          }
          container continuity-check {
            presence "true";
            leaf interval {
              type string;
            }
            leaf loss-threshold {
              type uint8;
            }
            container static {
              leaf rmep {
                type empty;
              }
            }
          }
          leaf sender-id {
            type enumeration {
              enum "chassis";
              enum "none";
            }
          }
          container mip {
            container auto-create {
              tailf:cli-delete-when-empty;
              presence "true";
              leaf lower-mep-only {
                type empty;
              }
            }
          }
          container ais {
            leaf period {
              type enumeration {
                enum "1";
                enum "60";
              }
            }
            leaf level {
              type uint8;
            }
          }
          container efd {
            container notify {
              leaf g8032 {
                type empty;
              }
            }
          }
        }
      }
      container ais {
        container link-status {
          container global {
            tailf:cli-add-mode;
            presence "true";
            leaf disable {
              type empty;
            }
          }
        }
      }
      container mep {
        container crosscheck {
          leaf start-delay {
            type uint16;
          }
        }
      }
    }
    container ring {
      container g8032 {
        list profile {
          key "profile-name";
          leaf profile-name {
            type string;
          }
          container timer {
            leaf wtr {
              type uint8;
            }
            leaf guard {
              type uint16;
            }
          }
        }
        list g8032-list {
          tailf:cli-drop-node-name;
          key "ring-name";
          leaf ring-name {
            type string;
          }
          leaf open-ring {
            type empty;
          }
          container exclusion-list {
            leaf-list vlan-ids {
              tailf:cli-range-list-syntax;
              type uint16;
            }
          }
          container port0 {
            tailf:cli-add-mode;
            tailf:cli-compact-syntax;
            tailf:cli-sequence-commands;
            tailf:cli-delete-when-empty;
            presence "true";
            container interface {
              tailf:cli-flatten-container;
              tailf:cli-compact-syntax;
              tailf:cli-hide-in-submode;
              uses interface-name-grouping;
            }
            container monitor {
              container service {
                leaf instance {
                  type uint16;
                }
              }
            }
          }
          choice port1-choice {
            container port1 {
              tailf:cli-add-mode;
              tailf:cli-compact-syntax;
              tailf:cli-sequence-commands;
              tailf:cli-delete-when-empty;
              presence "true";
              container interface {
                tailf:cli-flatten-container;
                tailf:cli-compact-syntax;
                tailf:cli-hide-in-submode;
                uses interface-name-grouping;
              }
              container monitor {
                container service {
                  leaf instance {
                    type uint16;
                  }
                }
              }
            }
            container port1-none {
              tailf:cli-drop-node-name;
              container port1 {
                leaf none {
                  type empty;
                }
              }
            }
          }
          list instance {
            key "instance-id";
            leaf instance-id {
              type uint8;
            }
            uses description-grouping;
            leaf profile {
              type string;
            }
            container rpl {
              tailf:cli-compact-syntax;
              tailf:cli-sequence-commands;
              leaf port {
                tailf:cli-drop-node-name;
                type enumeration {
                  enum "port0";
                  enum "port1";
                }
              }
              leaf type {
                tailf:cli-drop-node-name;
                type enumeration {
                  enum "neighbor";
                  enum "next-neighbor";
                  enum "owner";
                }
              }
            }
            container inclusion-list {
              leaf-list vlan-ids {
                tailf:cli-range-list-syntax;
                type uint16;
              }
            }
            container aps-channel {
              tailf:cli-add-mode;
              container port0 {
                container service {
                  leaf instance {
                    type uint16;
                  }
                }
              }
              container port1 {
                choice port1-choice {
                  container service {
                    leaf instance {
                      type uint16;
                    }
                  }
                  leaf none {
                    type empty;
                  }
                }
              }
            }
          }
        }
      }
    }
    list tcn-propagation {
      tailf:cli-suppress-mode;
      tailf:cli-delete-when-empty;
      key "source to";
      leaf source {
        type enumeration {
          enum "g8032";
          enum "rep";
        }
      }
      leaf to {
        tailf:cli-expose-key-name;
        type enumeration {
          enum "g8032";
          enum "rep";
        }
      }
    }
  }
  container access-list {
    list access-list {
      tailf:cli-drop-node-name;
      tailf:cli-suppress-mode;
      tailf:cli-delete-when-empty;
      tailf:cli-compact-syntax;
      key "id";
      leaf id {
        tailf:cli-suppress-range;
        type union {
          type uint16;
          type uint16;
          type uint16;
          type uint16;
          type uint16;
          type uint16;
          type uint16;
          type uint16;
          type uint16;
          type uint16;
          type uint16;
          type uint16;
          type uint16;
        }
      }
      list rule {
        tailf:cli-drop-node-name;
        tailf:cli-suppress-mode;
        tailf:cli-delete-when-empty;
        tailf:cli-compact-syntax;
        ordered-by user;
        key "rule";
        leaf seq {
          tailf:cli-drop-node-name;
          tailf:cli-prefix-key;
          type uint32;
        }
        leaf rule {
          tailf:cli-multi-word-key;
          type string;
        }
      }
    }
    leaf dynamic-extended {
      type empty;
    }
    list rate-limit {
      tailf:cli-suppress-mode;
      tailf:cli-delete-when-empty;
      key "id";
      leaf id {
        type union {
          type uint8;
          type uint8;
        }
      }
      choice rate-choice {
        leaf mac-address {
          tailf:cli-drop-node-name;
          type mac-address-type;
        }
        leaf precedence {
          tailf:cli-drop-node-name;
          type uint8;
        }
        leaf mask {
          type string;
        }
      }
    }
  }
  container access-session {
    container attributes {
      container filter-list {
        list list {
          key "name";
          leaf name {
            type string;
          }
          list include {
            tailf:cli-drop-node-name;
            tailf:cli-suppress-mode;
            tailf:cli-delete-when-empty;
            key "name";
            leaf name {
              type enumeration {
                enum "vlan-id";
                enum "cdp";
                enum "lldp";
                enum "dhcp";
                enum "dhcpv6";
                enum "http";
              }
            }
          }
        }
      }
    }
    container authentication {
      container attributes {
        container filter-spec {
          container include {
            leaf list {
              type string;
            }
          }
        }
      }
    }
    container accounting {
      container attributes {
        container filter-spec {
          container include {
            leaf list {
              type string;
            }
          }
        }
      }
    }
    leaf monitor {
      type empty;
    }
    container acl {
      container default {
        leaf passthrough {
          type empty;
        }
      }
    }
    container mac-move {
      leaf deny {
        type empty;
      }
    }
    container interface-template {
      container sticky {
        tailf:cli-delete-when-empty;
        presence "true";
        leaf timer {
          type uint16;
        }
      }
    }
  }
  container arp {
    uses arp-grouping;
    list vrf {
      tailf:cli-suppress-mode;
      tailf:cli-delete-when-empty;
      tailf:cli-compact-syntax;
      key "name";
      leaf name {
        type string;
      }
      uses arp-grouping;
    }
    list access-list {
      key "name";
      leaf name {
        type string;
      }
      list access-list-rule {
        tailf:cli-suppress-mode;
        tailf:cli-delete-when-empty;
        tailf:cli-drop-node-name;
        tailf:cli-compact-syntax;
        tailf:cli-case-sensitive;
        ordered-by user;
        key "rule";
        leaf rule {
          tailf:cli-drop-node-name;
          tailf:cli-multi-word-key;
          type string;
        }
      }
    }
  }
  container threat-visibility {
    tailf:cli-add-mode;
    presence "true";
  }
  container utd-st {
    tailf:cli-drop-node-name;
    container utd {
      uses utd-web-filter-grouping {
        augment "web-filter/domain" {
          list profile {
            key "id";
            leaf id {
              tailf:cli-suppress-range;
              type string;
            }
            leaf alert {
              type enumeration {
                enum "all";
                enum "blacklist";
                enum "whitelist";
              }
            }
            container blacklist {
              tailf:cli-add-mode;
              presence "true";
              container parameter-map {
                leaf regex {
                  type string;
                }
              }
            }
            container redirect-server {
              choice id-choice {
                leaf external {
                  type inet:ipv4-address;
                }
                leaf local-block-server {
                  type string;
                }
              }
            }
            container whitelist {
              tailf:cli-add-mode;
              presence "true";
              container parameter-map {
                leaf regex {
                  type string;
                }
              }
            }
          }
        }
      }
      container engine {
        container standard {
          tailf:cli-add-mode;
          presence "true";
          uses utd-engine-standard-grouping {
            augment "threat-inspection" {
              uses utd-engine-threat-inspection-grouping;
              leaf whitelist {
                type empty;
              }
            }
          }
          container web-filter {
            tailf:cli-add-mode;
            presence "true";
            leaf domain-profile {
              type string;
            }
            leaf sourcedb {
              type string;
            }
            leaf url-profile {
              type string;
            }
          }
        }
        container advanced {
          tailf:cli-add-mode;
          presence "true";
          container threat {
            leaf detection {
              type empty;
            }
          }
        }
      }
      container threat-inspection {
        container whitelist {
          tailf:cli-add-mode;
          presence "true";
          container generator {
            list id {
              tailf:cli-suppress-mode;
              tailf:cli-delete-when-empty;
              tailf:cli-compact-syntax;
              tailf:cli-sequence-commands {
                tailf:cli-reset-siblings;
              }
              key "generator-id id";
              leaf generator-id {
                tailf:cli-suppress-range;
                type uint32;
              }
              leaf signature {
                tailf:cli-prefix-key {
                  tailf:cli-before-key "2";
                }
                type empty;
              }
              leaf id {
                tailf:cli-expose-key-name;
                tailf:cli-suppress-range;
                type uint32;
              }
              leaf comment {
                type string;
              }
            }
          }
          list signature {
            tailf:cli-suppress-mode;
            tailf:cli-delete-when-empty;
            key "id";
            leaf id {
              tailf:cli-expose-key-name;
              tailf:cli-suppress-range;
              type uint32;
            }
            leaf comment {
              type string;
            }
          }
        }
      }
    }
  }
  container utd-mt {
    tailf:cli-drop-node-name;
    container utd {
      leaf multi-tenancy {
        type empty;
      }
      container engine {
        container standard {
          container multi-tenancy {
            tailf:cli-add-mode;
            presence "true";
            uses utd-web-filter-grouping;
            container threat-inspection {
              container whitelist {
                list profile {
                  key "name";
                  leaf name {
                    tailf:cli-suppress-range;
                    type string;
                  }
                  list signature {
                    tailf:cli-suppress-mode;
                    tailf:cli-delete-when-empty;
                    key "id";
                    leaf id {
                      tailf:cli-expose-key-name;
                      tailf:cli-suppress-range;
                      type uint32;
                    }
                    leaf comment {
                      type string;
                    }
                  }
                }
              }
              list profile {
                key "name";
                leaf name {
                  tailf:cli-suppress-range;
                  type string;
                }
                uses utd-engine-threat-inspection-grouping;
                container whitelist {
                  leaf profile {
                    type string;
                  }
                }
              }
            }
            container utd {
              container global {
                tailf:cli-add-mode;
                presence "true";
                uses utd-engine-standard-grouping;
                container web-filter {
                  tailf:cli-add-mode;
                  presence "true";
                  leaf sourcedb {
                    type string;
                  }
                }
              }
            }
            list policy {
              key "name";
              leaf name {
                tailf:cli-suppress-range;
                type string;
              }
              list vrf {
                tailf:cli-suppress-mode;
                tailf:cli-delete-when-empty;
                key "name";
                leaf name {
                  type string;
                }
              }
              leaf all-interfaces {
                type empty;
              }
              container threat-inspection {
                leaf profile {
                  type string;
                }
              }
              container web-filter {
                container url {
                  leaf profile {
                    type string;
                  }
                }
              }
            }
          }
        }
      }
    }
  }
  container utd {
    tailf:cli-add-mode;
    presence "true";
    leaf all-interfaces {
      type empty;
    }
    container redirect {
      container interface {
        choice interface-choice {
          leaf BDI {
            tailf:cli-allow-join-with-value;
            type uint16;
          }
          leaf VirtualPortGroup {
            tailf:cli-allow-join-with-value;
            type uint8;
          }
        }
      }
    }
    container engine {
      tailf:cli-add-mode;
      presence "true";
      leaf mode {
        tailf:cli-drop-node-name;
        tailf:cli-hide-in-submode;
        type enumeration {
          enum "standard";
          enum "advanced";
        }
      }
      container fail {
        leaf close {
          type empty;
        }
      }
    }
  }
  container virtual-template {
    leaf subinterface {
      type boolean;
    }
  }
  list virtual-service {
    key "name";
    leaf name {
      type string;
    }
    leaf description {
      tailf:cli-multi-value;
      type string;
    }
    container ip {
      container shared {
        container host-interface {
          leaf GigabitEthernet {
            tailf:cli-allow-join-with-value;
            type string;
          }
        }
      }
    }
    leaf profile {
      type enumeration {
        enum "ISR-WAAS-1300";
        enum "ISR-WAAS-750";
        enum "ISR-WAAS-2500";
        enum "high";
        enum "low";
        enum "medium";
        enum "urlf-low";
        enum "multi-tenancy";
      }
    }
    container vnic {
      container gateway {
        list VirtualPortGroup {
          tailf:cli-allow-join-with-key;
          tailf:cli-suppress-key-abbreviation;
          key "name";
          leaf name {
            type uint8;
          }
          container guest {
            container ip {
              leaf address {
                type inet:ipv4-address;
              }
            }
            container ipv6 {
              leaf address {
                type inet:ipv6-address;
              }
            }
          }
        }
      }
      container management {
        list GigabitEthernet {
          tailf:cli-allow-join-with-key;
          tailf:cli-suppress-key-abbreviation;
          key "name";
          leaf name {
            type string;
          }
          container guest {
            container ip {
              leaf address {
                type inet:host;
              }
            }
            container ipv6 {
              leaf address {
                type inet:ipv6-address;
              }
            }
          }
        }
      }
    }
    leaf activate {
      type empty;
    }
  }
  list route-map {
    tailf:cli-compact-syntax;
    key "name sequence";
    leaf name {
      type string;
    }
    leaf sequence {
      tailf:cli-drop-node-name;
      type uint16;
    }
    leaf operation {
      tailf:cli-drop-node-name;
      tailf:cli-prefix-key {
        tailf:cli-before-key "2";
      }
      type enumeration {
        enum "deny" {
          tailf:code-name "op_deny";
        }
        enum "permit" {
          tailf:code-name "op_internet";
        }
      }
    }
    leaf description {
      tailf:cli-multi-value;
      type string;
    }
    container match {
      leaf-list as-path {
        tailf:cli-flat-list-syntax;
        type string;
      }
      container ip {
        container address {
          leaf-list access-list {
            tailf:cli-drop-node-name;
            tailf:cli-flat-list-syntax;
            type exp-ip-acl-type;
          }
          leaf-list prefix-list {
            tailf:cli-flat-list-syntax;
            type string;
          }
        }
        container next-hop {
          leaf-list access-list {
            tailf:cli-drop-node-name;
            tailf:cli-flat-list-syntax;
            type std-ip-acl-type;
          }
          leaf-list prefix-list {
            tailf:cli-flat-list-syntax;
            type string;
          }
        }
        container route-source {
          leaf-list access-list {
            tailf:cli-drop-node-name;
            tailf:cli-flat-list-syntax;
            type std-ip-acl-type;
          }
          leaf-list prefix-list {
            tailf:cli-flat-list-syntax;
            type string;
          }
        }
      }
      container ipv6 {
        container address {
          leaf access-list {
            tailf:cli-drop-node-name;
            type string;
          }
          leaf prefix-list {
            type string;
          }
        }
        container next-hop {
          leaf access-list {
            tailf:cli-drop-node-name;
            type string;
          }
          leaf prefix-list {
            type string;
          }
        }
        container route-source {
          leaf access-list {
            tailf:cli-drop-node-name;
            type string;
          }
          leaf prefix-list {
            type string;
          }
        }
      }
      leaf-list community {
        tailf:cli-flat-list-syntax;
        type string;
      }
      leaf-list extcommunity {
        tailf:cli-flat-list-syntax;
        type string;
      }
      leaf-list tag {
        tailf:cli-flat-list-syntax;
        type uint32;
      }
      container clns {
        leaf-list address {
          tailf:cli-flat-list-syntax;
          type string;
        }
      }
      leaf-list interface {
        tailf:cli-flat-list-syntax;
        type string;
      }
      leaf-list source-protocol {
        tailf:cli-flat-list-syntax;
        type union {
          type enumeration {
            enum "bgp";
            enum "connected";
            enum "eigrp";
            enum "isis";
            enum "lisp";
            enum "mobile";
            enum "ospf";
            enum "ospfv3";
            enum "rip";
            enum "static";
          }
          type string;
        }
      }
      list route-type {
        tailf:cli-suppress-mode;
        tailf:cli-delete-when-empty;
        ordered-by user;
        key "tag";
        leaf tag {
          tailf:cli-multi-word-key;
          type string;
        }
      }
      leaf-list local-preference {
        tailf:cli-flat-list-syntax;
        type uint32;
      }
      list policy-list {
        tailf:cli-suppress-mode;
        tailf:cli-delete-when-empty;
        key "name";
        leaf name {
          tailf:cli-multi-word-key;
          type string;
        }
      }
      leaf track {
        type uint16;
      }
      container length {
        tailf:cli-compact-syntax;
        tailf:cli-sequence-commands {
          tailf:cli-reset-siblings;
        }
        leaf min {
          tailf:cli-drop-node-name;
          type uint32;
        }
        leaf max {
          tailf:cli-drop-node-name;
          type uint32;
        }
      }
    }
    container set {
      leaf global {
        type empty;
      }
      container as-path {
        container replace {
          leaf any {
            type empty;
          }
        }
        container prepend {
          leaf as-list {
            tailf:cli-drop-node-name;
            tailf:cli-multi-value;
            type string;
          }
          leaf last-as {
            type uint8;
          }
        }
        container tag {
          presence "true";
        }
      }
      leaf attribute-set {
        type string;
      }
      container comm-list {
        tailf:cli-compact-syntax;
        tailf:cli-sequence-commands {
          tailf:cli-reset-siblings;
        }
        leaf name {
          tailf:cli-drop-node-name;
          type union {
            type uint16;
            type uint16;
            type string;
          }
        }
        leaf delete {
          type empty;
        }
      }
      container community {
        choice set-community-choice {
          leaf none {
            type empty;
          }
          leaf-list community-number {
            tailf:cli-drop-node-name;
            tailf:cli-flat-list-syntax;
            type union {
              type uint32;
              type enumeration {
                enum "additive";
                enum "internet";
                enum "local-AS";
                enum "no-advertise";
                enum "no-export";
                enum "gshut";
              }
              type string;
            }
          }
        }
      }
      container extcomm-list {
        tailf:cli-compact-syntax;
        tailf:cli-sequence-commands {
          tailf:cli-reset-siblings;
        }
        leaf name {
          tailf:cli-drop-node-name;
          type union {
            type uint16;
            type uint16;
            type string;
          }
        }
        leaf delete {
          type empty;
        }
      }
      container extcommunity {
        leaf soo {
          type string;
        }
        leaf color {
          type uint32;
        }
        leaf-list rt {
          tailf:cli-flat-list-syntax;
          ordered-by user;
          type union {
            type enumeration {
              enum "range";
              enum "additive";
            }
            type asn-ip-type;
          }
        }
      }
      container ip {
        container address {
          leaf prefix-list {
            type string;
          }
        }
        container vrf-conf {
          tailf:cli-drop-node-name;
          list vrf {
            tailf:cli-suppress-mode;
            tailf:cli-delete-when-empty;
            tailf:cli-compact-syntax;
            tailf:cli-sequence-commands;
            key "sequence";
            leaf name {
              tailf:cli-drop-node-name;
              tailf:cli-prefix-key;
              type string;
            }
            leaf next-hop {
              tailf:cli-prefix-key;
              type enumeration {
                enum "verify-availability";
              }
            }
            leaf address {
              tailf:cli-drop-node-name;
              tailf:cli-prefix-key;
              type inet:ipv4-address;
            }
            leaf sequence {
              type uint16;
            }
            leaf track {
              type uint16;
            }
          }
        }
        list vrf {
          tailf:cli-suppress-mode;
          tailf:cli-delete-when-empty;
          key "name";
          leaf name {
            type string;
          }
          leaf-list next-hop {
            tailf:cli-flat-list-syntax;
            ordered-by user;
            type inet:ipv4-address;
          }
        }
        container next-hop {
          leaf self {
            type empty;
          }
          container verify-availability-conf {
            tailf:cli-drop-node-name;
            list verify-availability {
              tailf:cli-suppress-mode;
              tailf:cli-delete-when-empty;
              tailf:cli-compact-syntax;
              tailf:cli-sequence-commands;
              key "sequence";
              leaf address {
                tailf:cli-drop-node-name;
                tailf:cli-prefix-key;
                type inet:ipv4-address;
              }
              leaf sequence {
                type uint16;
              }
              leaf track {
                type uint16;
              }
            }
          }
          leaf peer-address {
            type empty;
          }
          leaf-list address {
            tailf:cli-drop-node-name;
            tailf:cli-flat-list-syntax;
            ordered-by user;
            type inet:ipv4-address;
          }
          leaf verify-availability {
            type empty;
          }
          container dynamic {
            leaf dhcp {
              type empty;
            }
          }
          container recursive {
            tailf:cli-compact-syntax;
            tailf:cli-sequence-commands {
              tailf:cli-reset-siblings;
            }
            choice global-or-vrf-choice {
              leaf global {
                tailf:cli-optional-in-sequence;
                type empty;
              }
              leaf vrf {
                tailf:cli-optional-in-sequence;
                type string;
              }
            }
            leaf address {
              tailf:cli-drop-node-name;
              type inet:ipv4-address;
            }
          }
          container encapsulate {
            leaf l3vpn {
              type string;
            }
          }
        }
        container df {
          tailf:cli-delete-when-empty;
          presence "true";
          leaf bit {
            tailf:cli-drop-node-name;
            type uint8;
          }
        }
        leaf precedence {
          type precedence-type;
        }
        leaf qos-group {
          type uint8;
        }
        leaf tos {
          type union {
            type uint8;
            type enumeration {
              enum "normal" {
                value 0;
              }
              enum "min-monetary-cost" {
                value 1;
              }
              enum "max-reliability" {
                value 2;
              }
              enum "max-throughput" {
                value 4;
              }
              enum "min-delay" {
                value 8;
              }
            }
          }
        }
        container default {
          container next-hop {
            leaf-list address {
              tailf:cli-drop-node-name;
              tailf:cli-flat-list-syntax;
              ordered-by user;
              type inet:ipv4-address;
            }
          }
          list vrf {
            tailf:cli-suppress-mode;
            tailf:cli-delete-when-empty;
            key "name";
            leaf name {
              type string;
            }
            leaf-list next-hop {
              tailf:cli-flat-list-syntax;
              ordered-by user;
              type inet:ipv4-address;
            }
          }
        }
      }
      container ipv6 {
        container next-hop {
          choice next-hop-choice {
            leaf-list address {
              tailf:cli-drop-node-name;
              tailf:cli-flat-list-syntax;
              ordered-by user;
              type inet:ipv6-address;
            }
            leaf peer-address {
              type empty;
            }
          }
          leaf recursive {
            type inet:ipv6-address;
          }
          list verify-availability {
            tailf:cli-suppress-mode;
            tailf:cli-delete-when-empty;
            tailf:cli-compact-syntax;
            tailf:cli-sequence-commands {
              tailf:cli-reset-siblings;
            }
            key "sequence";
            leaf address {
              tailf:cli-drop-node-name;
              tailf:cli-prefix-key;
              type inet:ipv6-address;
            }
            leaf sequence {
              type uint16;
            }
            leaf track {
              type uint16;
            }
          }
        }
        leaf precedence {
          type uint8;
        }
      }
      leaf level {
        type enumeration {
          enum "level-1";
          enum "level-1-2";
          enum "level-2";
          enum "nssa-only";
        }
      }
      container local-preference {
        tailf:cli-delete-when-empty;
        presence "true";
        leaf value {
          tailf:cli-drop-node-name;
          type uint32;
        }
      }
      leaf-list metric {
        tailf:cli-flat-list-syntax;
        ordered-by user;
        type string;
      }
      leaf aigp-metric {
        type union {
          type uint32;
          type enumeration {
            enum "igp-metric";
          }
        }
      }
      leaf metric-type {
        type enumeration {
          enum "external";
          enum "internal";
          enum "type-1";
          enum "type-2";
        }
      }
      leaf weight {
        type uint32;
      }
      container origin {
        choice origin-choice {
          leaf origin-value {
            tailf:cli-drop-node-name;
            type enumeration {
              enum "igp";
              enum "incomplete";
            }
          }
          leaf egp {
            type uint32;
          }
        }
      }
      leaf vrf {
        type string;
      }
      leaf tag {
        type uint32;
      }
      leaf mpls-label {
        type empty;
      }
      leaf-list interface {
        tailf:cli-flat-list-syntax;
        ordered-by user;
        type string;
      }
      container default {
        container interface {
          tailf:cli-compact-syntax;
          uses interface-name-grouping;
        }
      }
    }
    container continue {
      tailf:cli-delete-when-empty;
      presence "true";
      leaf sequence-number {
        tailf:cli-drop-node-name;
        type uint16;
      }
    }
  }
  container dialer {
    list watch-list {
      tailf:cli-suppress-mode;
      tailf:cli-delete-when-empty;
      key "id";
      leaf id {
        type uint16;
      }
      list ip {
        tailf:cli-suppress-mode;
        tailf:cli-delete-when-empty;
        key "address";
        leaf address {
          type inet:ipv4-address;
        }
        leaf mask {
          tailf:cli-drop-node-name;
          type inet:ipv4-address;
        }
      }
      container delay {
        container route-check {
          leaf initial {
            type uint32;
          }
        }
        leaf connect {
          type uint32;
        }
        leaf disconnect {
          type uint32;
        }
      }
    }
  }
  list dialer-list {
    tailf:cli-suppress-mode;
    tailf:cli-delete-when-empty;
    tailf:cli-compact-syntax;
    key "id";
    leaf id {
      type uint16;
    }
    container protocol {
      tailf:cli-flatten-container;
      tailf:cli-compact-syntax;
      tailf:cli-sequence-commands {
        tailf:cli-reset-siblings;
      }
      leaf ip {
        type enumeration {
          enum "deny";
          enum "list";
          enum "permit";
        }
      }
      leaf acl {
        tailf:cli-drop-node-name;
        type union {
          type uint16;
          type uint16;
        }
      }
    }
  }
  container authentication {
    container critical {
      container recovery {
        leaf delay {
          type uint16;
        }
      }
    }
    container mac-move {
      leaf permit {
        type empty;
      }
    }
    container logging {
      leaf verbose {
        type empty;
      }
    }
  }
  list num-exp {
    tailf:cli-suppress-mode;
    tailf:cli-delete-when-empty;
    tailf:cli-compact-syntax;
    key "dd-pattern";
    leaf dd-pattern {
      type string;
    }
    leaf subst-pattern {
      tailf:cli-drop-node-name;
      type string;
    }
  }
  container banner {
    leaf exec {
      type string;
    }
    leaf incoming {
      type string;
    }
    leaf login {
      type string;
    }
    leaf lcd {
      type string;
    }
    leaf prompt-timeout {
      type string;
    }
    leaf motd {
      type string;
    }
    leaf config-save {
      type string;
    }
  }
  container pseudowire-static-oam {
    list class {
      key "name";
      leaf name {
        type string;
      }
      container timeout {
        container refresh {
          leaf send {
            type uint16;
          }
        }
      }
      leaf ttl {
        type uint8;
      }
    }
  }
  container control-plane-host {
    tailf:cli-drop-node-name;
    container control-plane {
      container host {
        tailf:cli-add-mode;
        presence "true";
        list management-interface {
          tailf:cli-suppress-mode;
          tailf:cli-delete-when-empty;
          key "interface";
          leaf interface {
            type string;
          }
          leaf-list allow {
            tailf:cli-flat-list-syntax;
            type enumeration {
              enum "beep";
              enum "ftp";
              enum "http";
              enum "https";
              enum "snmp";
              enum "ssh";
              enum "telnet";
              enum "tftp";
              enum "tl1";
            }
          }
        }
      }
    }
  }
  container control-plane {
    tailf:cli-add-mode;
    presence "true";
    container service-policy {
      uses service-policy-grouping;
    }
  }
  container credentials {
    tailf:cli-add-mode;
    presence "true";
  }
  container cops {
    container listener {
      leaf access-list {
        type exp-ip-acl-type;
      }
    }
    container ip {
      leaf dscp {
        type dscp-type;
      }
    }
  }
  list connect {
    tailf:cli-compact-syntax;
    tailf:cli-sequence-commands {
      tailf:cli-reset-siblings;
    }
    key "name";
    leaf name {
      type string;
    }
    leaf interface1 {
      tailf:cli-drop-node-name;
      tailf:cli-hide-in-submode;
      type string;
    }
    leaf number1 {
      tailf:cli-drop-node-name;
      tailf:cli-optional-in-sequence;
      tailf:cli-hide-in-submode;
      type uint16;
    }
    leaf interface2 {
      tailf:cli-drop-node-name;
      tailf:cli-hide-in-submode;
      type string;
    }
    leaf number2 {
      tailf:cli-drop-node-name;
      tailf:cli-optional-in-sequence;
      tailf:cli-hide-in-submode;
      type uint16;
    }
    container backup {
      tailf:cli-break-sequence-commands;
      container peer {
        tailf:cli-compact-syntax;
        tailf:cli-sequence-commands {
          tailf:cli-reset-siblings;
        }
        leaf peer-router-ip-addr {
          tailf:cli-drop-node-name;
          type inet:ipv4-address;
        }
        leaf vcid {
          tailf:cli-drop-node-name;
          type uint32;
        }
        leaf pw-class {
          tailf:cli-optional-in-sequence;
          type string;
        }
      }
    }
    uses xconnect-grouping;
  }
  container vxlan {
    container udp {
      leaf port {
        type uint16;
      }
    }
  }
  list voice-port {
    key "name";
    leaf name {
      type string;
    }
    leaf trunk-group {
      type string;
    }
    container translation-profile {
      leaf incoming {
        type string;
      }
      leaf outgoing {
        type string;
      }
    }
    container signal {
      leaf groundStart {
        type empty;
      }
    }
    container echo-cancel {
      leaf coverage {
        type enumeration {
          enum "24";
          enum "32";
          enum "48";
          enum "64";
          enum "80";
          enum "96";
          enum "112";
          enum "128";
        }
      }
    }
    leaf vad {
      type boolean;
    }
    container timeouts {
      leaf ringing {
        type union {
          type uint16;
          type enumeration {
            enum "infinity";
          }
        }
      }
      leaf interdigit {
        type uint8;
      }
    }
    leaf shutdown {
      type empty;
    }
    container connection {
      container plar {
        tailf:cli-compact-syntax;
        tailf:cli-sequence-commands {
          tailf:cli-reset-siblings;
        }
        leaf opx {
          tailf:cli-optional-in-sequence;
          type empty;
        }
        leaf digits {
          tailf:cli-drop-node-name;
          type string;
        }
      }
    }
    uses description-grouping;
    leaf bearer-cap {
      type enumeration {
        enum "3100hz";
        enum "Speech";
      }
    }
    container station-id {
      leaf-list name {
        tailf:cli-flat-list-syntax;
        type string;
      }
      leaf number {
        type string;
      }
    }
    container caller-id {
      container enable {
        presence "true";
      }
    }
    container busyout {
      container action {
        leaf shutdown {
          type empty;
        }
      }
      container monitor {
        container action {
          choice action-choice {
            leaf graceful {
              type empty;
            }
            leaf shutdown {
              type empty;
            }
            container alarm {
              leaf blue {
                type empty;
              }
            }
          }
        }
        list state {
          tailf:cli-drop-node-name;
          tailf:cli-suppress-mode;
          tailf:cli-delete-when-empty;
          tailf:cli-compact-syntax;
          key "name";
          leaf name {
            type string;
          }
          leaf in-service {
            type empty;
          }
        }
      }
    }
  }
  container dspfarm {
    list profile {
      key "id";
      leaf id {
        type uint16;
      }
      leaf type {
        tailf:cli-drop-node-name;
        tailf:cli-hide-in-submode;
        type enumeration {
          enum "conference";
          enum "mtp";
          enum "transcode";
        }
      }
      leaf universal {
        tailf:cli-hide-in-submode;
        type empty;
      }
      leaf acoustic-shock-protection {
        type empty;
      }
      uses description-grouping;
      list codec {
        tailf:cli-suppress-mode;
        tailf:cli-delete-when-empty;
        key "name";
        leaf name {
          type enumeration {
            enum "pass-through";
            enum "ilbc";
            enum "isac";
            enum "g729br8";
            enum "g729r8";
            enum "g729abr8";
            enum "g729ar8";
            enum "g711alaw";
            enum "g711ulaw";
            enum "g722-64";
          }
        }
      }
      container maximum {
        leaf conference-participants {
          type uint32;
        }
        container sessions {
          leaf value {
            tailf:cli-drop-node-name;
            type uint32;
          }
          leaf hardware {
            type uint32;
          }
          leaf software {
            type uint32;
          }
        }
      }
      container conference-join {
        leaf custom-cptone {
          type string;
        }
      }
      container conference-leave {
        leaf custom-cptone {
          type string;
        }
      }
      container associate {
        leaf application {
          type enumeration {
            enum "CUBE";
            enum "SCCP";
          }
        }
      }
      leaf shutdown {
        type empty;
      }
    }
  }
  container presence {
    tailf:cli-add-mode;
    presence "true";
    container presence {
      leaf call-list {
        type empty;
      }
    }
    leaf max-subscription {
      type uint16;
    }
    container watcher {
      leaf all {
        type empty;
      }
    }
    container allow {
      leaf subscribe {
        type empty;
      }
    }
  }
  container call-manager-fallback {
    tailf:cli-add-mode;
    presence "true";
    container max-conferences {
      tailf:cli-compact-syntax;
      tailf:cli-sequence-commands {
        tailf:cli-reset-siblings;
      }
      leaf max {
        tailf:cli-drop-node-name;
        type uint8;
      }
      leaf gain {
        type int8;
      }
    }
    leaf transfer-system {
      type enumeration {
        enum "blind";
        enum "full-blind";
        enum "full-consult";
        enum "local-consult";
      }
    }
    list limit-dn {
      tailf:cli-suppress-mode;
      tailf:cli-delete-when-empty;
      key "name";
      leaf name {
        type string;
      }
      leaf max-lines {
        tailf:cli-drop-node-name;
        type uint8;
      }
    }
    container ip {
      container source-address {
        tailf:cli-compact-syntax;
        tailf:cli-sequence-commands {
          tailf:cli-reset-siblings;
        }
        leaf address {
          tailf:cli-drop-node-name;
          type inet:ipv4-address;
        }
        leaf port {
          type uint16;
        }
      }
    }
    container timeouts {
      leaf interdigit {
        type uint8;
      }
      leaf ringing {
        type uint16;
      }
    }
    container max-ephones {
      leaf max {
        tailf:cli-drop-node-name;
        type uint16;
      }
    }
    container max-dn {
      tailf:cli-compact-syntax;
      tailf:cli-sequence-commands {
        tailf:cli-reset-siblings;
      }
      leaf max {
        tailf:cli-drop-node-name;
        type uint16;
      }
      leaf line {
        tailf:cli-drop-node-name;
        tailf:cli-optional-in-sequence;
        type enumeration {
          enum "dual-line";
          enum "octo-line";
        }
      }
      leaf preference {
        type uint8;
      }
    }
    list transfer-pattern {
      tailf:cli-suppress-mode;
      tailf:cli-delete-when-empty;
      key "pattern";
      leaf pattern {
        type string;
      }
    }
    list dialplan-pattern {
      tailf:cli-suppress-mode;
      tailf:cli-delete-when-empty;
      tailf:cli-compact-syntax;
      tailf:cli-sequence-commands {
        tailf:cli-reset-siblings;
      }
      key "tag";
      leaf tag {
        type uint8;
      }
      leaf pattern {
        tailf:cli-drop-node-name;
        type string;
      }
      leaf extension-length {
        type uint8;
      }
    }
    container keepalive {
      tailf:cli-compact-syntax;
      tailf:cli-sequence-commands {
        tailf:cli-reset-siblings;
      }
      leaf seconds {
        tailf:cli-drop-node-name;
        type uint16;
      }
      leaf auxiliary {
        type uint16;
      }
    }
    leaf default-destination {
      type string;
    }
    leaf time-format {
      type enumeration {
        enum "12";
        enum "24";
      }
    }
    container translate {
      leaf calling {
        type uint32;
      }
      leaf called {
        type uint32;
      }
    }
    container call-forward {
      list pattern {
        tailf:cli-suppress-mode;
        tailf:cli-delete-when-empty;
        key "pattern";
        leaf pattern {
          type string;
        }
      }
      container system {
        leaf redirecting-expanded {
          type empty;
        }
      }
      leaf busy {
        type string;
      }
      container noan {
        tailf:cli-compact-syntax;
        tailf:cli-sequence-commands {
          tailf:cli-reset-siblings;
        }
        leaf target-number {
          tailf:cli-drop-node-name;
          type string;
        }
        leaf timeout {
          type uint16;
        }
      }
    }
    container multicast {
      tailf:cli-compact-syntax;
      tailf:cli-sequence-commands {
        tailf:cli-reset-siblings;
      }
      leaf moh {
        type inet:ipv4-address;
      }
      leaf port {
        type uint16;
      }
      leaf route {
        type inet:ipv4-address;
      }
    }
    leaf time-zone {
      type uint16;
    }
  }
  container dial-peer {
    container cor {
      container custom {
        tailf:cli-add-mode;
        presence "true";
        list name {
          tailf:cli-suppress-mode;
          tailf:cli-delete-when-empty;
          key "name";
          leaf name {
            type string;
          }
        }
      }
      list list {
        key "name";
        leaf name {
          type string;
        }
        list member {
          tailf:cli-suppress-mode;
          tailf:cli-delete-when-empty;
          key "name";
          leaf name {
            type string;
          }
        }
      }
    }
    list voice {
      tailf:cli-sequence-commands;
      key "id";
      leaf id {
        type uint32;
      }
      leaf peer {
        tailf:cli-drop-node-name;
        tailf:cli-hide-in-submode;
        type enumeration {
          enum "mmoip";
          enum "pots";
          enum "voatm";
          enum "vofr";
          enum "voip";
        }
      }
      leaf answer-address {
        tailf:cli-break-sequence-commands;
        type string;
      }
      leaf trunkgroup {
        type string;
      }
      container corlist {
        leaf incoming {
          type string;
        }
        leaf outgoing {
          type string;
        }
      }
      leaf description {
        tailf:cli-multi-value;
        type string;
      }
      leaf preference {
        type uint8;
      }
      container translation-profile {
        leaf incoming {
          type string;
        }
        leaf outgoing {
          type string;
        }
      }
      container call-block {
        container translation-profile {
          leaf incoming {
            type string;
          }
        }
        container disconnect-cause {
          leaf incoming {
            type enumeration {
              enum "call-reject";
              enum "invalid-number";
              enum "unassigned-number";
              enum "user-busy";
            }
          }
        }
      }
      leaf huntstop {
        type empty;
      }
      leaf max-conn {
        type uint32;
      }
      container destination {
        leaf e164-pattern-map {
          type uint32;
        }
      }
      leaf destination-pattern {
        type string;
      }
      leaf prefix {
        type string;
      }
      container modem {
        container passthrough {
          choice passthrough-choice {
            leaf system {
              type boolean;
            }
            container nse {
              tailf:cli-compact-syntax;
              leaf payload-type {
                type uint32;
              }
              leaf codec {
                type enumeration {
                  enum "g711ulaw";
                  enum "g711alaw";
                }
              }
              leaf redundancy {
                type empty;
              }
            }
          }
        }
      }
      container session {
        leaf protocol {
          type enumeration {
            enum "aal2-trunk";
            enum "cisco";
            enum "sipv2";
            enum "smtp";
            enum "multicast";
          }
        }
        leaf server-group {
          type uint16;
        }
        leaf target {
          tailf:cli-multi-value;
          type string;
        }
        container transport {
          tailf:cli-compact-syntax;
          tailf:cli-sequence-commands {
            tailf:cli-reset-siblings;
          }
          leaf protocol {
            tailf:cli-drop-node-name;
            type enumeration {
              enum "system";
              enum "tcp";
              enum "udp";
            }
          }
          leaf tls {
            type empty;
          }
        }
      }
      leaf numbering-type {
        type enumeration {
          enum "abbreviated";
          enum "international";
          enum "national";
          enum "network";
          enum "reserved";
          enum "subscriber";
          enum "unknown";
        }
      }
      container incoming {
        leaf called-number {
          type string;
        }
        container uri {
          leaf via {
            type string;
          }
          leaf from {
            type string;
          }
        }
      }
      container voice-class {
        container codec {
          tailf:cli-compact-syntax;
          tailf:cli-sequence-commands {
            tailf:cli-reset-siblings;
          }
          leaf id {
            tailf:cli-drop-node-name;
            type uint16;
          }
          leaf offer-all {
            type empty;
          }
        }
        container sip {
          choice proxy-address-choice {
            leaf outbound-proxy {
              type boolean;
            }
            container outbound-proxy-conf {
              tailf:cli-drop-node-name;
              container outbound-proxy {
                leaf proxy-address {
                  tailf:cli-drop-node-name;
                  type string;
                }
              }
            }
          }
          container options-keepalive {
            presence "true";
            leaf profile {
              type uint16;
            }
          }
          container bind {
            container control {
              container source-interface {
                uses interface-name-grouping;
              }
            }
            container media {
              container source-interface {
                uses interface-name-grouping;
              }
            }
          }
        }
      }
      leaf-list dtmf-relay {
        tailf:cli-flat-list-syntax;
        ordered-by user;
        type enumeration {
          enum "cisco-rtp";
          enum "h245-alphanumeric";
          enum "h245-signal";
          enum "rtp-nte";
          enum "sip-kpml";
          enum "digit-drop";
        }
      }
      leaf direct-inward-dial {
        type empty;
      }
      leaf forward-digits {
        type union {
          type uint8;
          type enumeration {
            enum "all";
            enum "extra";
          }
        }
      }
      leaf port {
        type string;
      }
      leaf sip-register {
        type boolean;
      }
      container codec {
        tailf:cli-compact-syntax;
        tailf:cli-sequence-commands {
          tailf:cli-reset-siblings;
        }
        leaf name {
          tailf:cli-drop-node-name;
          type string;
        }
        leaf bytes {
          tailf:cli-break-sequence-commands;
          type uint32;
        }
        leaf mode {
          type uint32;
        }
      }
      container fax {
        container protocol {
          choice protocol-option {
            leaf none {
              type empty;
            }
            leaf cisco {
              type empty;
            }
            leaf pass-through {
              type enumeration {
                enum "g711ulaw";
                enum "g711alaw";
              }
            }
          }
        }
      }
      container ip {
        container qos {
          list dscp {
            tailf:cli-compact-syntax;
            tailf:cli-suppress-mode;
            tailf:cli-delete-when-empty;
            key "name";
            leaf name {
              type string;
            }
            choice dscp-choice {
              leaf media {
                type empty;
              }
              leaf signaling {
                type empty;
              }
              leaf video {
                type enumeration {
                  enum "rsvp-none";
                  enum "rsvp-pass";
                  enum "rsvp-fail";
                }
              }
            }
          }
        }
      }
      leaf vad {
        type boolean;
      }
      leaf dtmf-interworking {
        type enumeration {
          enum "rtp-nte";
          enum "standard";
          enum "system";
        }
      }
    }
    container outbound {
      container status-check {
        leaf pots {
          type boolean;
        }
      }
    }
  }
  container gateway {
    tailf:cli-add-mode;
    presence "true";
    container timer {
      leaf receive-rtp {
        type uint32;
      }
    }
  }
  leaf config-register {
    type string;
  }
  container network-clock-participate {
    container slot {
      list slot-disabled {
        tailf:cli-suppress-mode;
        tailf:cli-delete-when-empty;
        key "slot";
        leaf slot {
          tailf:cli-suppress-range;
          type uint8;
        }
      }
    }
    container wic {
      list wic-enabled {
        tailf:cli-drop-node-name;
        tailf:cli-suppress-mode;
        tailf:cli-delete-when-empty;
        key "slot";
        leaf slot {
          tailf:cli-suppress-range;
          type uint8;
        }
      }
      list wic-disabled {
        tailf:cli-suppress-mode;
        tailf:cli-delete-when-empty;
        key "slot";
        leaf slot {
          tailf:cli-suppress-range;
          type uint8;
        }
      }
    }
    list T1 {
      tailf:cli-suppress-mode;
      tailf:cli-delete-when-empty;
      key "name";
      leaf name {
        tailf:cli-suppress-range;
        type string;
      }
    }
  }
  container service-routing {
    leaf capabilities-manager {
      type boolean;
    }
    container xmcp {
      container listen {
        tailf:cli-add-mode;
        presence "true";
        leaf af {
          tailf:cli-drop-node-name;
          tailf:cli-hide-in-submode;
          type enumeration {
            enum "ipv4";
            enum "ipv6";
          }
        }
        leaf port {
          tailf:cli-hide-in-submode;
          type uint16;
        }
        leaf vrf {
          tailf:cli-hide-in-submode;
          type string;
        }
        list client {
          key "username";
          leaf username {
            tailf:cli-expose-key-name;
            type string;
          }
          container password {
            tailf:cli-hide-in-submode;
            tailf:cli-flatten-container;
            tailf:cli-compact-syntax;
            tailf:cli-sequence-commands;
            uses password-grouping {
              refine "secret";
            }
          }
          container domain {
            tailf:cli-compact-syntax;
            tailf:cli-sequence-commands {
              tailf:cli-reset-siblings;
            }
            leaf value {
              tailf:cli-drop-node-name;
              type uint16;
            }
            leaf mode {
              tailf:cli-drop-node-name;
              type enumeration {
                enum "default";
                enum "only";
              }
            }
          }
        }
      }
    }
  }
  container mgcp {
    container call-agent {
      tailf:cli-compact-syntax;
      tailf:cli-sequence-commands {
        tailf:cli-reset-siblings;
      }
      leaf address {
        tailf:cli-drop-node-name;
        type inet:host;
      }
      leaf port {
        tailf:cli-drop-node-name;
        tailf:cli-optional-in-sequence;
        type uint16;
      }
      leaf service-type {
        type enumeration {
          enum "mgcp";
          enum "ncs";
          enum "sgcp";
          enum "tgcp";
        }
      }
      leaf version {
        type enumeration {
          enum "0.1";
          enum "1.0";
          enum "rfc3435-1.0";
        }
      }
    }
    container dtmf-relay {
      container voip {
        tailf:cli-compact-syntax;
        tailf:cli-sequence-commands {
          tailf:cli-reset-siblings;
        }
        leaf codec {
          type enumeration {
            enum "all";
            enum "low-bit-rate";
          }
        }
        leaf mode {
          type enumeration {
            enum "cisco";
            enum "disabled";
            enum "nse";
            enum "nte-ca";
            enum "nte-gw";
            enum "out-of-band";
          }
        }
      }
      container voaal2 {
        tailf:cli-compact-syntax;
        tailf:cli-sequence-commands {
          tailf:cli-reset-siblings;
        }
        leaf codec {
          type enumeration {
            enum "all";
            enum "low-bit-rate";
          }
        }
      }
    }
    container rtp {
      container unreachable {
        tailf:cli-compact-syntax;
        tailf:cli-sequence-commands {
          tailf:cli-reset-siblings;
        }
        leaf timeout {
          type uint16;
        }
        leaf action {
          type enumeration {
            enum "disconnect";
            enum "notify";
          }
        }
      }
    }
    container modem {
      container passthrough {
        container voaal2 {
          container mode {
            leaf nse {
              type empty;
            }
          }
          leaf codec {
            type enumeration {
              enum "g711alaw";
              enum "g711ulaw";
              enum "g726r32";
            }
          }
        }
        container voip {
          leaf mode {
            type enumeration {
              enum "ca";
              enum "cisco";
              enum "nse";
            }
          }
          leaf codec {
            type enumeration {
              enum "g711alaw";
              enum "g711ulaw";
              enum "g726r32";
            }
          }
          leaf redundancy {
            type empty;
          }
        }
      }
    }
    container package-capability {
      leaf rtp-package {
        type boolean;
      }
      leaf sst-package {
        type boolean;
      }
      leaf pre-package {
        type boolean;
      }
      leaf res-package {
        type boolean;
      }
    }
    container timer {
      choice receive-rtcp-choice {
        leaf receive-rtcp {
          type boolean;
        }
        container receive-rtcp-conf {
          tailf:cli-drop-node-name;
          leaf receive-rtcp {
            type uint8;
          }
        }
      }
    }
    container sdp {
      leaf simple {
        type empty;
      }
    }
    container validate {
      leaf domain-name {
        type empty;
      }
    }
    container fax {
      container t38 {
        leaf ecm {
          type empty;
        }
        leaf inhibit {
          type empty;
        }
      }
    }
    list behavior {
      tailf:cli-suppress-mode;
      tailf:cli-delete-when-empty;
      key "category";
      leaf category {
        type string;
      }
      leaf version {
        tailf:cli-drop-node-name;
        type string;
      }
    }
    list profile {
      tailf:cli-delete-when-empty;
      key "name";
      leaf name {
        type union {
          type enumeration {
            enum "default";
          }
          type string;
        }
      }
    }
  }
  container mgcp-conf {
    tailf:cli-drop-node-name;
    leaf mgcp {
      type empty;
    }
  }
  container sccp {
    container local {
      uses interface-name-grouping;
    }
    container ccm {
      list list {
        tailf:cli-drop-node-name;
        tailf:cli-suppress-mode;
        tailf:cli-delete-when-empty;
        tailf:cli-compact-syntax;
        tailf:cli-sequence-commands {
          tailf:cli-reset-siblings;
        }
        key "address";
        leaf address {
          type inet:host;
        }
        leaf identifier {
          type uint16;
        }
        leaf version {
          type string;
        }
      }
      list group {
        key "id";
        leaf id {
          type uint16;
        }
        uses description-grouping;
        container associate {
          list ccm {
            tailf:cli-suppress-mode;
            tailf:cli-delete-when-empty;
            key "id";
            leaf id {
              type uint16;
            }
            leaf priority {
              type uint8;
            }
          }
          list profile {
            tailf:cli-suppress-mode;
            tailf:cli-delete-when-empty;
            key "id";
            leaf id {
              type uint16;
            }
            leaf register {
              type string;
            }
          }
        }
      }
    }
  }
  container sccp-enable {
    tailf:cli-drop-node-name;
    leaf sccp {
      type empty;
    }
  }
  container sip-ua {
    tailf:cli-add-mode;
    presence "true";
    leaf remote-party-id {
      type boolean;
    }
    container retry {
      leaf invite {
        type uint8;
      }
    }
    container timers {
      leaf connect {
        type uint16;
      }
    }
    container mwi-server {
      tailf:cli-compact-syntax;
      tailf:cli-sequence-commands {
        tailf:cli-reset-all-siblings;
      }
      leaf address {
        tailf:cli-drop-node-name;
        type string;
      }
      leaf expires {
        tailf:cli-break-sequence-commands;
        type uint32;
      }
      leaf port {
        type uint16;
      }
      leaf transport {
        type enumeration {
          enum "tcp";
          enum "udp";
        }
      }
      leaf unsolicited {
        type empty;
      }
    }
    leaf sip-server {
      type string;
    }
    container presence {
      leaf enable {
        type empty;
      }
    }
    container transport {
      leaf udp {
        type boolean;
      }
      leaf tcp {
        type boolean;
      }
      container tcp-tls {
        tailf:cli-drop-node-name;
        choice tcp-tls-choice {
          container tcp {
            leaf tls {
              type boolean;
            }
          }
          container tcp-conf {
            tailf:cli-drop-node-name;
            container tcp {
              leaf tls {
                type enumeration {
                  enum "v1.0";
                  enum "v1.1";
                  enum "v1.2";
                }
              }
            }
          }
        }
      }
    }
    container reason-header {
      leaf override {
        type empty;
      }
    }
    container connection-reuse {
      presence "true";
    }
    container crypto {
      container signaling {
        list remote-addr {
          tailf:cli-suppress-mode;
          tailf:cli-delete-when-empty;
          tailf:cli-compact-syntax;
          tailf:cli-sequence-commands {
            tailf:cli-reset-siblings;
          }
          key "address mask";
          leaf address {
            type inet:ipv4-address;
          }
          leaf mask {
            type inet:ipv4-address;
          }
          leaf trustpoint {
            type string;
          }
          leaf cipher {
            tailf:cli-drop-node-name;
            type enumeration {
              enum "ecdsa-cipher";
              enum "strict-cipher";
            }
          }
        }
        container default {
          tailf:cli-compact-syntax;
          tailf:cli-sequence-commands {
            tailf:cli-reset-siblings;
          }
          leaf trustpoint {
            type string;
          }
          leaf cipher {
            tailf:cli-drop-node-name;
            type enumeration {
              enum "ecdsa-cipher";
              enum "strict-cipher";
            }
          }
        }
      }
    }
  }
  container gatekeeper {
    tailf:cli-add-mode;
    leaf shutdown {
      type empty;
    }
  }
  container telephony-service {
    tailf:cli-add-mode;
    presence "true";
    container mode {
      leaf esrst {
        type empty;
      }
    }
    container srst {
      container mode {
        leaf auto-provision {
          type enumeration {
            enum "none";
            enum "dn";
            enum "all";
          }
        }
      }
      container ephone {
        leaf template {
          type uint8;
        }
      }
      container dn {
        leaf template {
          type uint8;
        }
        leaf line-mode {
          type enumeration {
            enum "single";
            enum "octo";
            enum "dual";
            enum "dual-octo";
          }
        }
      }
    }
    container sdspfarm {
      container conference {
        container mute {
          tailf:cli-drop-node-name;
          tailf:cli-compact-syntax;
          tailf:cli-sequence-commands;
          leaf mute-on {
            type string;
          }
          leaf mute-off {
            type string;
          }
        }
      }
      leaf units {
        type uint8;
      }
      list tag {
        tailf:cli-suppress-mode;
        tailf:cli-compact-syntax;
        key "value";
        leaf value {
          type uint8;
        }
        leaf device-name {
          tailf:cli-drop-node-name;
          type string;
        }
      }
    }
    container conference {
      leaf hardware {
        type empty;
      }
    }
    leaf auto-reg-ephone {
      type boolean;
    }
    container authentication {
      list credential {
        tailf:cli-suppress-mode;
        tailf:cli-compact-syntax;
        key "user-name";
        leaf user-name {
          type string;
        }
        leaf password {
          tailf:cli-drop-node-name;
          type string;
        }
      }
    }
    container em {
      leaf logout {
        tailf:cli-multi-value;
        type string;
      }
    }
    leaf max-ephones {
      type uint16;
    }
    container max-dn {
      leaf number-of-directories {
        tailf:cli-drop-node-name;
        type uint16;
      }
    }
    container ip {
      container source-address {
        tailf:cli-compact-syntax;
        tailf:cli-sequence-commands {
          tailf:cli-reset-siblings;
        }
        leaf address {
          tailf:cli-drop-node-name;
          type inet:ipv4-address;
        }
        leaf port {
          type uint16;
        }
      }
    }
    container calling-number {
      leaf initiator {
        type empty;
      }
    }
    container service {
      list phone {
        key "parameter-name";
        tailf:cli-suppress-mode;
        tailf:cli-compact-syntax;
        leaf parameter-name {
          type string;
        }
        leaf parameter-text {
          tailf:cli-drop-node-name;
          type string;
        }
      }
    }
    container system {
      leaf message {
        tailf:cli-multi-value;
        type string;
      }
    }
    container url {
      leaf directories {
        type string;
      }
      container services {
        leaf url {
          tailf:cli-drop-node-name;
          type string;
        }
      }
      container authentication {
        tailf:cli-compact-syntax;
        tailf:cli-sequence-commands {
          tailf:cli-reset-siblings;
        }
        leaf url {
          tailf:cli-drop-node-name;
          type string;
        }
        leaf username {
          tailf:cli-drop-node-name;
          type string;
        }
        leaf encryption {
          tailf:cli-optional-in-sequence;
          tailf:cli-drop-node-name;
          type enumeration {
            enum "0";
            enum "6";
          }
        }
        leaf secret {
          tailf:cli-drop-node-name;
          type string;
        }
      }
    }
    container cnf-file {
      container location {
        leaf flash {
          tailf:alt-name "flash:";
          type empty;
        }
      }
    }
    list load {
      tailf:cli-suppress-mode;
      tailf:cli-compact-syntax;
      key "ip-phone-module";
      leaf ip-phone-module {
        type string;
      }
      leaf firmware-filename {
        tailf:cli-drop-node-name;
        type string;
      }
    }
    leaf time-zone {
      type uint8;
    }
    leaf voicemail {
      type string;
    }
    container max-conferences {
      tailf:cli-compact-syntax;
      tailf:cli-sequence-commands {
        tailf:cli-reset-siblings;
      }
      leaf no-of-conferences {
        tailf:cli-drop-node-name;
        type uint8;
      }
      leaf gain {
        type int8;
      }
    }
    container call-park {
      container system {
        leaf application {
          type empty;
        }
      }
    }
    container call-forward {
      leaf-list pattern {
        type string;
      }
    }
    leaf moh {
      type string;
    }
    container web {
      container admin {
        container system {
          tailf:cli-compact-syntax;
          leaf name {
            type string;
          }
          leaf password {
            type string;
          }
        }
      }
    }
    leaf dn-webedit {
      type empty;
    }
    leaf time-webedit {
      type empty;
    }
    container transfer-system {
      container full-consult {
        presence "true";
      }
    }
    list transfer-pattern {
      tailf:cli-suppress-mode;
      tailf:cli-delete-when-empty;
      key "pattern";
      leaf pattern {
        type string;
      }
    }
    leaf secondary-dialtone {
      type string;
    }
    container after-hours {
      container block {
        list pattern {
          tailf:cli-suppress-mode;
          tailf:cli-compact-syntax;
          key "index";
          leaf index {
            type uint8;
          }
          leaf digits-string {
            tailf:cli-drop-node-name;
            type string;
          }
          leaf twenty-four-seven {
            tailf:alt-name "7-24";
            type empty;
          }
        }
      }
    }
    container night-service {
      leaf code {
        type string;
      }
      container everyday {
        tailf:cli-compact-syntax;
        tailf:cli-sequence-commands;
        leaf time-to-start {
          tailf:cli-drop-node-name;
          type string;
        }
        leaf time-to-stop {
          tailf:cli-drop-node-name;
          type string;
        }
      }
    }
    container fac {
      leaf standard {
        type empty;
      }
    }
    leaf shutdown {
      type empty;
    }
  }
  list ephone-dn-template {
    key "tag";
    leaf tag {
      type uint8;
    }
    uses ephone-dn-grouping;
  }
  list ephone-template {
    key "tag";
    leaf tag {
      type uint8;
    }
    uses ephone-grouping;
    container softkeys {
      leaf-list hold {
        tailf:cli-flat-list-syntax;
        ordered-by user;
        type enumeration {
          enum "Newcall";
          enum "Join";
          enum "Select";
          enum "Resume";
        }
      }
      leaf-list idle {
        tailf:cli-flat-list-syntax;
        ordered-by user;
        type enumeration {
          enum "Cfwdall";
          enum "ConfList";
          enum "Dnd";
          enum "Gpickup";
          enum "HLog";
          enum "Join";
          enum "Login";
          enum "Mobility";
          enum "Newcall";
          enum "Pickup";
          enum "Redial";
          enum "RmLstC";
        }
      }
      leaf-list seized {
        tailf:cli-flat-list-syntax;
        ordered-by user;
        type enumeration {
          enum "CWOff";
          enum "Callback";
          enum "Cfwdall";
          enum "Endcall";
          enum "Gpickup";
          enum "HLog";
          enum "Meetme";
          enum "Pickup";
          enum "Redial";
        }
      }
      leaf-list alerting {
        tailf:cli-flat-list-syntax;
        ordered-by user;
        type enumeration {
          enum "Acct";
          enum "Callback";
          enum "Endcall";
        }
      }
      leaf-list connected {
        tailf:cli-flat-list-syntax;
        ordered-by user;
        type enumeration {
          enum "Acct";
          enum "ConfList";
          enum "Confrn";
          enum "Endcall";
          enum "Flash";
          enum "HLog";
          enum "Hold";
          enum "Join";
          enum "LiveRcd";
          enum "Mobility";
          enum "Park";
          enum "RmLstC";
          enum "Select";
          enum "TrnsfVM";
          enum "Trnsfer";
        }
      }
      leaf-list ringing {
        tailf:cli-flat-list-syntax;
        ordered-by user;
        type enumeration {
          enum "Answer";
          enum "Dnd";
          enum "HLog";
        }
      }
    }
  }
  list ephone-dn {
    key "tag";
    leaf tag {
      type uint16;
    }
    leaf dual-line {
      tailf:cli-hide-in-submode;
      type empty;
    }
    leaf octo-line {
      tailf:cli-hide-in-submode;
      type empty;
    }
    container number {
      tailf:cli-compact-syntax;
      tailf:cli-sequence-commands {
        tailf:cli-reset-siblings;
      }
      leaf telephone-number {
        tailf:cli-drop-node-name;
        type string;
      }
      leaf secondary {
        tailf:cli-optional-in-sequence;
        type string;
      }
      leaf no-reg {
        type empty;
      }
      leaf not-registered {
        tailf:cli-drop-node-name;
        type enumeration {
          enum "primary";
          enum "both";
        }
      }
    }
    container park-slot {
      tailf:cli-delete-when-empty;
      tailf:cli-compact-syntax;
      presence "true";
      container timeout {
        tailf:cli-compact-syntax;
        tailf:cli-sequence-commands {
          tailf:cli-reset-all-siblings;
        }
        leaf park-timeout {
          tailf:cli-drop-node-name;
          type uint16;
        }
        leaf limit {
          tailf:cli-break-sequence-commands;
          type uint16;
        }
        leaf recall {
          type empty;
        }
        leaf retry {
          type uint16;
        }
        leaf retry-limit {
          tailf:alt-name "limit";
          type uint16;
        }
      }
    }
    leaf label {
      tailf:cli-multi-value;
      type string;
    }
    leaf name {
      tailf:cli-multi-value;
      type string;
    }
    leaf ephone-dn-template {
      type uint8;
    }
    uses ephone-dn-grouping;
    leaf conference {
      type enumeration {
        enum "ad-hoc";
        enum "meetme";
      }
    }
    choice mwi-paging {
      container mwi {
        leaf action {
          tailf:cli-drop-node-name;
          type enumeration {
            enum "off";
            enum "on";
            enum "on-off";
            enum "qsig";
            enum "sip";
          }
        }
      }
      container paging {
        tailf:cli-delete-when-empty;
        presence "true";
        container ip {
          tailf:cli-compact-syntax;
          tailf:cli-sequence-commands;
          leaf multicast-address {
            tailf:cli-drop-node-name;
            type inet:ipv4-address;
          }
          leaf port {
            type uint16;
          }
        }
      }
    }
    leaf transfer-mode {
      type enumeration {
        enum "blind";
        enum "consult";
      }
    }
    container night-service {
      leaf bell {
        type empty;
      }
    }
  }

  grouping ephone-dn-grouping {
    uses description-grouping;
    container allow {
      leaf watch {
        type empty;
      }
    }
    container caller-id {
      leaf block {
        type empty;
      }
    }
    container call-forward {
      leaf all {
        type string;
      }
      container busy {
        tailf:cli-compact-syntax;
        tailf:cli-sequence-commands {
          tailf:cli-reset-siblings;
        }
        leaf digits {
          tailf:cli-drop-node-name;
          type string;
        }
        leaf forward {
          tailf:cli-drop-node-name;
          type enumeration {
            enum "primary";
            enum "secondary";
          }
        }
        leaf dialplan-pattern {
          type empty;
        }
      }
      leaf night-service {
        type string;
      }
      container noan {
        tailf:cli-compact-syntax;
        tailf:cli-sequence-commands {
          tailf:cli-reset-siblings;
        }
        leaf digits {
          tailf:cli-drop-node-name;
          type string;
        }
        leaf timeout {
          type uint16;
        }
      }
    }
    container corlist {
      leaf incoming {
        type string;
      }
      leaf outgoing {
        type string;
      }
    }
    container hold-alert {
      tailf:cli-compact-syntax;
      tailf:cli-sequence-commands {
        tailf:cli-reset-all-siblings;
      }
      leaf timeout {
        tailf:cli-drop-node-name;
        type uint16;
      }
      leaf type {
        tailf:cli-drop-node-name;
        tailf:cli-break-sequence-commands;
        type enumeration {
          enum "idle";
          enum "originator";
          enum "shared";
          enum "shared-idle";
        }
      }
    }
    container translation-profile {
      leaf incoming {
        type string;
      }
      leaf outgoing {
        type string;
      }
    }
  }

  list ephone {
    key "tag";
    leaf tag {
      type uint16;
    }
    leaf multicast-moh {
      type boolean;
    }
    leaf device-security-mode {
      type enumeration {
        enum "none";
        enum "authenticated";
        enum "encrypted";
      }
    }
    leaf mac-address {
      type mac-address-type;
    }
    leaf ephone-template {
      type uint8;
    }
    uses ephone-grouping;
    container username {
      tailf:cli-compact-syntax;
      tailf:cli-sequence-commands {
        tailf:cli-reset-siblings;
      }
      leaf name {
        tailf:cli-drop-node-name;
        type string;
      }
      leaf password {
        type string;
      }
    }
    list blf-speed-dial {
      tailf:cli-suppress-mode;
      tailf:cli-delete-when-empty;
      tailf:cli-compact-syntax;
      tailf:cli-sequence-commands;
      key "index";
      leaf index {
        type uint8;
      }
      leaf phone-number {
        tailf:cli-drop-node-name;
        type uint64;
      }
      leaf label {
        type string;
      }
    }
    list button {
      tailf:cli-suppress-mode;
      tailf:cli-delete-when-empty;
      ordered-by user;
      key "name";
      leaf name {
        tailf:cli-multi-word-key;
        type string;
      }
    }
    leaf pin {
      type string;
    }
  }

  grouping ephone-grouping {
    uses description-grouping;
    container conference {
      container drop-mode {
        tailf:cli-delete-when-empty;
        presence "true";
        leaf creator {
          type empty;
        }
        leaf local {
          type empty;
        }
      }
      container add-mode {
        tailf:cli-delete-when-empty;
        presence "true";
        leaf creator {
          type empty;
        }
      }
      leaf admin {
        type empty;
      }
    }
    leaf max-calls-per-button {
      type uint8;
    }
    leaf busy-trigger-per-button {
      type uint8;
    }
    list fastdial {
      tailf:cli-suppress-mode;
      tailf:cli-delete-when-empty;
      tailf:cli-compact-syntax;
      tailf:cli-sequence-commands {
        tailf:cli-reset-siblings;
      }
      key "tag";
      leaf tag {
        type uint8;
      }
      leaf phone-number {
        tailf:cli-drop-node-name;
        type string;
      }
      leaf name {
        tailf:cli-multi-value;
        type string;
      }
    }
    list speed-dial {
      tailf:cli-suppress-mode;
      tailf:cli-delete-when-empty;
      tailf:cli-compact-syntax;
      tailf:cli-sequence-commands {
        tailf:cli-reset-siblings;
      }
      key "tag";
      leaf tag {
        type string;
      }
      leaf phone-number {
        tailf:cli-drop-node-name;
        type uint64;
      }
      leaf label {
        type string;
      }
    }
    container type {
      tailf:cli-compact-syntax;
      tailf:cli-sequence-commands {
        tailf:cli-reset-all-siblings;
      }
      leaf ip-phone-module {
        tailf:cli-drop-node-name;
        tailf:cli-break-sequence-commands;
        type string;
      }
      container addon {
        tailf:cli-flatten-container;
        tailf:cli-compact-syntax;
        tailf:cli-sequence-commands;
        leaf module-number-1 {
          tailf:alt-name "1";
          type string;
        }
        leaf module-number-2 {
          tailf:alt-name "2";
          type string;
        }
      }
    }
    container paging-dn {
      tailf:cli-delete-when-empty;
      presence "true";
      leaf ephone-dn-tag {
        tailf:cli-drop-node-name;
        type uint16;
      }
    }
    container night-service {
      leaf bell {
        type empty;
      }
    }
  }

  container parser {
    leaf cache {
      type boolean;
    }
    list view {
      key "name";
      leaf name {
        type string;
      }
      container secret {
        tailf:cli-flatten-container;
        tailf:cli-compact-syntax;
        tailf:cli-sequence-commands;
        leaf type {
          tailf:cli-optional-in-sequence;
          tailf:cli-drop-node-name;
          type enumeration {
            enum "0";
            enum "5";
          }
        }
        leaf secret {
          tailf:cli-drop-node-name;
          type string;
        }
      }
      list commands {
        tailf:cli-suppress-mode;
        tailf:cli-delete-when-empty;
        key "line";
        leaf line {
          tailf:cli-multi-word-key;
          type string;
        }
      }
    }
  }
  container ccm-manager {
    container music-on-hold {
      presence "true";
    }
    container mgcp {
      presence "true";
    }
    container fax {
      container protocol {
        leaf cisco {
          type boolean;
        }
      }
    }
    container config {
      leaf server {
        type inet:host;
      }
    }
    container config-conf {
      tailf:cli-drop-node-name;
      leaf config {
        type empty;
      }
    }
  }
  container configuration {
    container mode {
      container exclusive {
        presence "true";
      }
    }
  }
  container line {
    list console {
      key "first";
      leaf first {
        type enumeration {
          enum "0";
        }
      }
      uses line-grouping;
    }
    list aux {
      key "first";
      leaf first {
        type enumeration {
          enum "0";
        }
      }
      uses line-grouping;
    }
    container vty-single-conf {
      tailf:cli-drop-node-name;
      list vty {
        key "first";
        leaf first {
          type uint16;
        }
        uses line-grouping;
      }
    }
    list vty {
      key "first last";
      leaf first {
        type uint16;
      }
      leaf last {
        type uint16;
      }
      uses line-grouping;
    }
    list number-single-list {
      tailf:cli-drop-node-name;
      key "first";
      leaf first {
        tailf:cli-suppress-range;
        type string;
      }
      uses line-grouping;
    }
  }
  container ztp {
    leaf disable {
      type empty;
    }
  }
  container telemetry {
    container ietf {
      list subscription {
        key "id";
        leaf id {
          type uint32;
        }
        leaf encoding {
          type enumeration {
            enum "encode-kvgpb";
            enum "encode-tdl";
          }
        }
        container filter {
          choice filter-choice {
            leaf xpath {
              type string;
            }
            leaf tdl-transform {
              type string;
            }
            leaf tdl-uri {
              type string;
            }
          }
        }
        leaf source-address {
          type union {
            type inet:ipv4-address;
            type inet:ipv6-address;
          }
        }
        leaf source-vrf {
          type string;
        }
        leaf stream {
          type enumeration {
            enum "native";
            enum "yang-push";
            enum "yang-notif-native";
          }
        }
        container update-policy {
          choice update-policy-choice {
            leaf periodic {
              type uint32;
            }
            leaf on-change {
              type empty;
            }
          }
        }
        container receiver {
          list name {
            tailf:cli-suppress-mode;
            tailf:cli-delete-when-empty;
            key "name";
            leaf name {
              type string;
            }
          }
          container ip {
            list address {
              tailf:cli-suppress-mode;
              tailf:cli-delete-when-empty;
              tailf:cli-compact-syntax;
              tailf:cli-sequence-commands {
                tailf:cli-reset-siblings;
              }
              key "address port";
              leaf address {
                type all-address;
              }
              leaf port {
                type uint16;
              }
              leaf protocol {
                type enumeration {
                  enum "cloud-native";
                  enum "cntp-tcp";
                  enum "cntp-tls";
                  enum "grpc-tcp";
                  enum "grpc-tls";
                  enum "native";
                  enum "tls-native";
                }
              }
              leaf profile {
                type string;
              }
            }
          }
        }
      }
    }
    list transform {
      key "name";
      leaf name {
        type string;
      }
      container input {
        list table {
          key "name";
          leaf name {
            type string;
          }
          list field {
            tailf:cli-suppress-mode;
            tailf:cli-delete-when-empty;
            key "name";
            leaf name {
              type string;
            }
          }
          leaf join-key {
            type string;
          }
          leaf logical-op {
            type enumeration {
              enum "and";
              enum "or";
            }
          }
          leaf type {
            type enumeration {
              enum "mandatory";
              enum "primary";
            }
          }
          leaf uri {
            type string;
          }
        }
      }
      list operation {
        key "id";
        leaf id {
          type uint32;
        }
        list filter {
          key "id";
          leaf id {
            type uint32;
          }
          container event {
            leaf on-change {
              type empty;
            }
          }
          leaf field {
            type string;
          }
          container logical-op {
            leaf next {
              type enumeration {
                enum "and";
                enum "or";
              }
            }
            leaf value {
              tailf:cli-drop-node-name;
              type enumeration {
                enum "and";
                enum "or";
              }
            }
          }
        }
        list output-field {
          key "id";
          leaf id {
            type uint32;
          }
          leaf field {
            type string;
          }
          container output-op {
            container type {
              leaf delta {
                type empty;
              }
            }
          }
        }
      }
      leaf specified {
        type empty;
      }
    }
    container receiver {
      list protocol {
        key "name";
        leaf name {
          type string;
        }
        container host {
          choice host-choice {
            container ip-address {
              tailf:cli-compact-syntax;
              tailf:cli-sequence-commands {
                tailf:cli-reset-siblings;
              }
              leaf address {
                tailf:cli-drop-node-name;
                type union {
                  type inet:ipv4-address;
                  type inet:ipv6-address;
                }
              }
              leaf port {
                tailf:cli-drop-node-name;
                type uint16;
              }
            }
            container name {
              tailf:cli-compact-syntax;
              tailf:cli-sequence-commands {
                tailf:cli-reset-siblings;
              }
              leaf string {
                tailf:cli-drop-node-name;
                type string;
              }
              leaf port {
                tailf:cli-drop-node-name;
                type uint16;
              }
            }
          }
        }
        container protocol {
          tailf:cli-compact-syntax;
          tailf:cli-sequence-commands {
            tailf:cli-reset-siblings;
          }
          leaf name {
            tailf:cli-drop-node-name;
            type enumeration {
              enum "cloud-native";
              enum "cntp-tcp";
              enum "cntp-tls";
              enum "grpc-tcp";
              enum "grpc-tls";
              enum "native";
              enum "tls-native";
            }
          }
          leaf profile {
            type string;
          }
        }
      }
    }
  }
  container module {
    leaf clear-config {
      type empty;
    }
    container provision {
      list list {
        tailf:cli-drop-node-name;
        tailf:cli-suppress-mode;
        tailf:cli-delete-when-empty;
        key "id";
        leaf id {
          type uint8;
        }
        leaf provision {
          tailf:cli-drop-node-name;
          type enumeration {
            enum "first-insert";
          }
        }
      }
      list switch {
        key "id";
        leaf id {
          type uint8;
        }
        container chassis-type {
          tailf:cli-compact-syntax;
          tailf:cli-sequence-commands {
            tailf:cli-reset-siblings;
          }
          leaf value {
            tailf:cli-drop-node-name;
            type uint8;
          }
          leaf base-mac {
            type string;
          }
        }
        list slot {
          tailf:cli-suppress-mode;
          tailf:cli-delete-when-empty;
          tailf:cli-compact-syntax;
          tailf:cli-sequence-commands {
            tailf:cli-reset-siblings;
          }
          key "id";
          leaf id {
            type uint8;
          }
          leaf slot-type {
            type uint16;
          }
          leaf port-type {
            tailf:cli-optional-in-sequence;
            type uint16;
          }
          leaf number {
            tailf:cli-optional-in-sequence;
            type uint16;
          }
          leaf virtual-slot {
            tailf:cli-optional-in-sequence;
            type uint16;
          }
          leaf base-mac {
            type string;
          }
        }
      }
    }
  }
  container exception {
    container data-corruption {
      container buffer {
        leaf truncate {
          type empty;
        }
      }
    }
    container flash {
      tailf:cli-compact-syntax;
      tailf:cli-sequence-commands {
        tailf:cli-reset-siblings;
      }
      leaf memory {
        tailf:cli-drop-node-name;
        type enumeration {
          enum "iomem";
          enum "procmem";
          enum "all";
        }
      }
      leaf device-name {
        tailf:cli-drop-node-name;
        type string;
      }
    }
    choice crashinfo-choice {
      container crashinfo-enable {
        tailf:cli-drop-node-name;
        leaf crashinfo {
          type boolean;
        }
      }
      container crashinfo {
        leaf file {
          type string;
        }
        leaf buffersize {
          type uint16;
        }
        leaf maximum-files {
          type uint8;
        }
        container maximum {
          leaf files {
            type uint8;
          }
        }
      }
    }
    leaf dump {
      type inet:host;
    }
    container coredump {
      presence "true";
    }
    container core-file {
      presence "true";
      leaf name {
        tailf:cli-drop-node-name;
        type string;
      }
    }
  }
  container pnp {
    list profile {
      key "name";
      leaf name {
        type string;
      }
      container transport {
        tailf:cli-compact-syntax;
        tailf:cli-sequence-commands {
          tailf:cli-reset-siblings;
        }
        leaf protocol {
          tailf:cli-drop-node-name;
          type enumeration {
            enum "http";
            enum "https";
            enum "xmpp";
          }
        }
        leaf over {
          tailf:cli-drop-node-name;
          type enumeration {
            enum "socket";
            enum "starttls";
            enum "tls";
          }
        }
        choice address-choice {
          leaf host {
            type inet:host;
          }
          leaf ipv4 {
            type inet:ipv4-address;
          }
          leaf ipv6 {
            type inet:ipv6-address;
          }
        }
        leaf port {
          type uint16;
        }
        leaf vrf {
          tailf:cli-optional-in-sequence;
          type string;
        }
        container source {
          tailf:cli-optional-in-sequence;
          tailf:cli-flatten-container;
          tailf:cli-compact-syntax;
          uses interface-name-grouping;
        }
        leaf localcert {
          tailf:cli-optional-in-sequence;
          type string;
        }
        leaf remotecert {
          type string;
        }
      }
      container reconnect {
        leaf seconds {
          tailf:cli-drop-node-name;
          type uint32;
        }
      }
    }
    leaf startup-vlan {
      type uint16;
    }
    leaf tag {
      type string;
    }
  }
  container onep {
    tailf:cli-add-mode;
    leaf start {
      type boolean;
    }
    container transport {
      container tipc {
        presence "true";
      }
    }
  }
  container logging {
    list discriminator {
      tailf:cli-suppress-mode;
      tailf:cli-delete-when-empty;
      tailf:cli-compact-syntax;
      key "discr-name";
      leaf discr-name {
        type string;
      }
      container severity {
        tailf:cli-flatten-container;
        tailf:cli-compact-syntax;
        uses logging-discriminator-pattern-grouping;
      }
      container facility {
        tailf:cli-flatten-container;
        tailf:cli-compact-syntax;
        uses logging-discriminator-pattern-grouping;
      }
      container mnemonics {
        tailf:cli-flatten-container;
        tailf:cli-compact-syntax;
        uses logging-discriminator-pattern-grouping;
      }
      container msg-body {
        tailf:cli-flatten-container;
        tailf:cli-compact-syntax;
        uses logging-discriminator-pattern-grouping;
      }
    }
    container cmts {
      container ipc-cable {
        leaf log-level {
          type logging-level-type;
        }
      }
      container sea {
        leaf syslog-level {
          type logging-level-type;
        }
      }
    }
    leaf alarm {
      type union {
        type uint8;
        type enumeration {
          enum "critical";
          enum "informational";
          enum "major";
          enum "minor";
        }
      }
    }
    container message-counter {
      leaf log {
        type empty;
      }
      leaf debug {
        type empty;
      }
      leaf syslog {
        type boolean;
      }
    }
    container buffered {
      tailf:cli-compact-syntax;
      tailf:cli-sequence-commands {
        tailf:cli-reset-siblings;
      }
      leaf xxml {
        tailf:alt-name "xml";
        tailf:cli-optional-in-sequence;
        type empty;
      }
      leaf discriminator {
        tailf:cli-optional-in-sequence;
        type string;
      }
      leaf buffer-size {
        tailf:cli-drop-node-name;
        tailf:cli-optional-in-sequence;
        type uint32;
      }
      leaf severity-level {
        tailf:cli-drop-node-name;
        type logging-level-type;
      }
    }
    container persistent {
      tailf:cli-compact-syntax;
      leaf url {
        type string;
      }
      leaf size {
        type uint32;
      }
      leaf filesize {
        type uint32;
      }
    }
    leaf exception {
      type uint32;
    }
    container queue-limit {
      leaf queuesize {
        tailf:cli-drop-node-name;
        type uint32;
      }
    }
    leaf userinfo {
      type empty;
    }

    grouping logging-common-grouping {
      leaf xxml {
        tailf:alt-name "xml";
        tailf:cli-optional-in-sequence;
        type empty;
      }
      leaf discriminator {
        tailf:cli-optional-in-sequence;
        type string;
      }
      leaf filtered {
        tailf:cli-optional-in-sequence;
        type empty;
      }
      leaf severity-level {
        tailf:cli-drop-node-name;
        type logging-level-type;
      }
    }
    container console {
      tailf:cli-compact-syntax;
      tailf:cli-sequence-commands {
        tailf:cli-reset-siblings;
      }
      uses logging-common-grouping;
    }
    container monitor {
      tailf:cli-compact-syntax;
      tailf:cli-sequence-commands {
        tailf:cli-reset-siblings;
      }
      uses logging-common-grouping;
    }
    container snmp-trap {
      leaf emergencies {
        type empty;
      }
      leaf critical {
        type empty;
      }
      leaf errors {
        type empty;
      }
      leaf informational {
        type empty;
      }
      leaf alerts {
        type empty;
      }
      leaf warnings {
        type empty;
      }
      leaf notifications {
        type empty;
      }
      leaf debugging {
        type empty;
      }
    }
    leaf snmp-authfail {
      type empty;
    }
    container event {
      container link-status {
        leaf boot {
          type empty;
        }
        leaf global {
          type empty;
        }
        leaf default {
          type empty;
        }
      }
      container trunk-status {
        leaf global {
          type empty;
        }
      }
    }
    container esm {
      leaf config {
        type empty;
      }
    }
    leaf facility {
      type enumeration {
        enum "auth";
        enum "cron";
        enum "daemon";
        enum "kern";
        enum "local0";
        enum "local1";
        enum "local2";
        enum "local3";
        enum "local4";
        enum "local5";
        enum "local6";
        enum "local7";
        enum "lpr";
        enum "mail";
        enum "news";
        enum "sys10";
        enum "sys11";
        enum "sys12";
        enum "sys13";
        enum "sys14";
        enum "sys9";
        enum "syslog";
        enum "user";
        enum "uucp";
      }
    }
    container history {
      leaf size {
        type uint16;
      }
      leaf severity-level {
        tailf:cli-drop-node-name;
        type logging-level-type;
      }
    }
    list hostname {
      tailf:cli-drop-node-name;
      tailf:cli-suppress-mode;
      tailf:cli-delete-when-empty;
      key "host";
      leaf host {
        type inet:host;
      }
    }
    container host {
      container fqdn {
        list ipv4 {
          tailf:cli-suppress-mode;
          tailf:cli-delete-when-empty;
          tailf:cli-compact-syntax;
          key "host";
          leaf host {
            type string;
          }
          uses logging-host-grouping;
        }
      }
      list ipv4 {
        tailf:cli-drop-node-name;
        tailf:cli-suppress-mode;
        tailf:cli-delete-when-empty;
        tailf:cli-compact-syntax;
        key "host";
        leaf host {
          type inet:host;
        }
        uses logging-host-grouping;
      }
      list ipv4-vrf {
        tailf:cli-drop-node-name;
        tailf:cli-suppress-mode;
        tailf:cli-delete-when-empty;
        tailf:cli-compact-syntax;
        key "host vrf";
        leaf host {
          type inet:host;
        }
        leaf vrf {
          tailf:cli-expose-key-name;
          type string;
        }
        uses logging-host-grouping;
      }
      list ipv6 {
        tailf:cli-suppress-mode;
        tailf:cli-delete-when-empty;
        tailf:cli-compact-syntax;
        key "host";
        leaf host {
          type inet:host;
        }
        uses logging-host-grouping;
      }
      container ipv6-vrf {
        tailf:cli-drop-node-name;
        list ipv6 {
          tailf:cli-suppress-mode;
          tailf:cli-delete-when-empty;
          tailf:cli-compact-syntax;
          key "host vrf";
          leaf host {
            type inet:host;
          }
          leaf vrf {
            tailf:cli-expose-key-name;
            type string;
          }
          uses logging-host-grouping;
        }
      }
    }
    choice rate-limit-choice {
      leaf rate-limit {
        type boolean;
      }
      container rate-limit-conf {
        tailf:cli-drop-node-name;
        container rate-limit {
          tailf:cli-compact-syntax;
          tailf:cli-sequence-commands {
            tailf:cli-reset-siblings;
          }
          leaf console {
            tailf:cli-optional-in-sequence;
            type empty;
          }
          leaf all {
            tailf:cli-optional-in-sequence;
            type empty;
          }
          leaf rate {
            tailf:cli-drop-node-name;
            type uint16;
          }
          leaf except {
            type logging-level-type;
          }
        }
      }
    }
    list source-interface {
      tailf:cli-suppress-mode;
      tailf:cli-delete-when-empty;
      tailf:cli-compact-syntax;
      key "name";
      leaf name {
        type string;
      }
      leaf vrf {
        type string;
      }
    }
    choice logging-trap-choice {
      leaf trap {
        type logging-level-type;
      }
      container trap-syslog-format {
        tailf:cli-drop-node-name;
        container trap {
          tailf:cli-compact-syntax;
          leaf level {
            tailf:cli-drop-node-name;
            type logging-level-type;
          }
          leaf syslog-format {
            type enumeration {
              enum "rfc5424";
            }
          }
        }
      }
    }
    container origin-id {
      choice origin-id-choice {
        leaf hostname {
          type empty;
        }
        leaf ip {
          type empty;
        }
        leaf ipv6 {
          type empty;
        }
        leaf string {
          type string;
        }
      }
    }
    container linecard {
      leaf size {
        tailf:cli-drop-node-name;
        type uint32;
      }
      leaf level {
        tailf:cli-drop-node-name;
        type logging-level-type;
      }
    }
    leaf reload {
      type enumeration {
        enum "alerts";
        enum "critical";
        enum "debugging";
        enum "emergencies";
        enum "errors";
        enum "informational";
        enum "notifications";
        enum "warnings";
      }
    }
    container ip {
      container access-list {
        container cache {
          tailf:cli-compact-syntax;
          leaf entries {
            type uint32;
          }
          leaf interval {
            type uint32;
          }
          leaf threshold {
            type uint32;
          }
        }
      }
    }
  }
  container firewall {
    leaf autostate {
      type empty;
    }
    leaf multiple-vlan-interfaces {
      type empty;
    }
    list module {
      tailf:cli-suppress-mode;
      tailf:cli-delete-when-empty;
      key "id";
      leaf id {
        type uint8;
      }
      leaf-list vlan-group {
        tailf:cli-range-list-syntax;
        type uint16;
      }
    }
    list vlan-group {
      tailf:cli-suppress-mode;
      tailf:cli-delete-when-empty;
      key "id";
      leaf id {
        type uint16;
      }
      leaf-list vlan {
        tailf:cli-drop-node-name;
        tailf:cli-range-list-syntax;
        type uint16;
      }
    }
  }
  container standby {
    leaf redirect {
      type boolean;
    }
  }
  container cpd {
    presence "true";
    leaf cr-id {
      type uint16;
    }
  }
  container nls {
    presence "true";
    leaf resp-timeout {
      type uint8;
    }
  }
  list flow-sampler-map {
    key "name";
    leaf name {
      type string;
    }
    container mode {
      container random {
        leaf one-out-of {
          type uint16;
        }
      }
    }
  }
  container frame-relay {
    leaf switching {
      type empty;
    }
  }
  container scheduler {
    leaf process-watchdog {
      type enumeration {
        enum "normal";
        enum "hang";
        enum "reload";
        enum "terminate";
      }
    }
    container allocate {
      tailf:cli-compact-syntax;
      tailf:cli-sequence-commands;
      leaf interrupt-time {
        tailf:cli-drop-node-name;
        type uint16;
      }
      leaf process-time {
        tailf:cli-drop-node-name;
        type uint16;
      }
    }
    leaf interval {
      type uint32;
    }
    leaf isr-watchdog {
      type empty;
    }
    container runtime {
      leaf netinput {
        type uint16;
      }
    }
  }
  container wsma {
    list agent {
      key "name";
      leaf name {
        type enumeration {
          enum "config";
          enum "exec";
          enum "filesys";
          enum "notify";
        }
      }
      list profile {
        tailf:cli-suppress-mode;
        tailf:cli-delete-when-empty;
        key "name";
        leaf name {
          type string;
        }
      }
    }
    container profile {
      list listener {
        key "name";
        leaf name {
          type string;
        }
        container transport {
          choice transport-choice {
            container http {
              presence "true";
            }
            container https {
              presence "true";
            }
            container ssh {
              presence "true";
            }
          }
        }
      }
      list initiator {
        key "name";
        leaf name {
          type string;
        }
        container transport {
          choice transport-choice {
            container http {
              presence "true";
            }
            container https {
              presence "true";
            }
            container ssh {
              presence "true";
            }
          }
        }
      }
    }
  }
  container process {
    container cpu {
      container threshold {
        container type {
          tailf:cli-compact-syntax;
          container total {
            tailf:cli-compact-syntax;
            tailf:cli-sequence-commands {
              tailf:cli-reset-siblings;
            }
            uses process-cpu-threshold-grouping;
          }
          container interrupt {
            tailf:cli-compact-syntax;
            tailf:cli-sequence-commands {
              tailf:cli-reset-siblings;
            }
            uses process-cpu-threshold-grouping;
          }
          container process {
            tailf:cli-compact-syntax;
            tailf:cli-sequence-commands {
              tailf:cli-reset-siblings;
            }
            uses process-cpu-threshold-grouping;
          }
        }
      }
      container statistics {
        container limit {
          tailf:cli-compact-syntax;
          tailf:cli-sequence-commands {
            tailf:cli-reset-siblings;
          }
          leaf entry-percentage {
            type uint8;
          }
          leaf size {
            type uint32;
          }
        }
      }
      container autoprofile {
        leaf hog {
          type boolean;
        }
      }
    }
  }
  container ntp {
    leaf max-associations {
      type uint32;
    }
    leaf passive {
      type empty;
    }
    leaf logging {
      type empty;
    }
    container panic {
      leaf update {
        type empty;
      }
    }
    list authentication-key {
      tailf:cli-suppress-mode;
      tailf:cli-delete-when-empty;
      tailf:cli-compact-syntax;
      tailf:cli-sequence-commands {
        tailf:cli-reset-siblings;
      }
      key "number";
      leaf number {
        type uint32;
      }
      choice algorithm-choice {
        container md5 {
          tailf:cli-optional-in-sequence;
          tailf:cli-flatten-container;
          tailf:cli-compact-syntax;
          tailf:cli-sequence-commands;
          leaf secret {
            tailf:cli-drop-node-name;
            type string;
          }
          leaf type {
            tailf:cli-drop-node-name;
            type uint32;
          }
        }
        case algorithm {
          leaf algorithm {
            tailf:cli-drop-node-name;
            type enumeration {
              enum "cmac-aes-128";
              enum "hmac-sha1";
              enum "hmac-sha2-256";
              enum "md5";
              enum "sha1";
              enum "sha2";
            }
          }
          leaf secret {
            tailf:cli-drop-node-name;
            type string;
          }
          leaf type {
            tailf:cli-drop-node-name;
            type uint32;
          }
        }
      }
    }
    leaf authenticate {
      type empty;
    }
    list trusted-key {
      tailf:cli-suppress-mode;
      tailf:cli-delete-when-empty;
      tailf:cli-compact-syntax;
      tailf:cli-sequence-commands;
      key "key-number";
      leaf key-number {
        type uint16;
      }
      leaf hyphen {
        tailf:alt-name "-";
        type empty;
      }
      leaf end-key-number {
        tailf:cli-drop-node-name;
        type uint16;
      }
    }
    leaf orphan {
      type uint8;
    }
    leaf mindistance {
      type uint16;
    }
    leaf maxdistance {
      type uint8;
    }
    leaf broadcastdelay {
      type uint32;
    }
    container source {
      uses interface-name-grouping;
    }
    container access-group {
      container peer {
        tailf:cli-compact-syntax;
        tailf:cli-sequence-commands;
        leaf access-list {
          tailf:cli-drop-node-name;
          type std-ip-acl-type;
        }
        leaf kod {
          type empty;
        }
      }
      container query-only {
        tailf:cli-compact-syntax;
        tailf:cli-sequence-commands;
        leaf access-list {
          tailf:cli-drop-node-name;
          type std-ip-acl-type;
        }
        leaf kod {
          type empty;
        }
      }
      container serve {
        tailf:cli-compact-syntax;
        tailf:cli-sequence-commands;
        leaf access-list {
          tailf:cli-drop-node-name;
          type std-ip-acl-type;
        }
        leaf kod {
          type empty;
        }
      }
      container serve-only {
        tailf:cli-compact-syntax;
        tailf:cli-sequence-commands;
        leaf access-list {
          tailf:cli-drop-node-name;
          type std-ip-acl-type;
        }
        leaf kod {
          type empty;
        }
      }
      container ipv6 {
        container peer {
          tailf:cli-compact-syntax;
          tailf:cli-sequence-commands;
          leaf access-list {
            tailf:cli-drop-node-name;
            type std-ip-acl-type;
          }
          leaf kod {
            type empty;
          }
        }
      }
    }
    container master {
      tailf:cli-delete-when-empty;
      presence "true";
      leaf stratum {
        tailf:cli-drop-node-name;
        type uint8;
      }
    }
    container peer {
      uses ntp-peer-grouping;
      container ip {
        tailf:cli-compact-syntax;
        uses ntp-peer-grouping;
      }
      container ipv6 {
        tailf:cli-compact-syntax;
        uses ntp-peer-grouping;
      }
      list vrf {
        tailf:cli-suppress-mode;
        tailf:cli-delete-when-empty;
        tailf:cli-compact-syntax;
        key "name";
        leaf name {
          type string;
        }
        uses ntp-peer-grouping;
      }
    }
    container server {
      uses ntp-peer-grouping;
      container ip {
        tailf:cli-compact-syntax;
        uses ntp-peer-grouping;
      }
      container ipv6 {
        tailf:cli-compact-syntax;
        uses ntp-peer-grouping;
      }
      list vrf {
        tailf:cli-suppress-mode;
        tailf:cli-delete-when-empty;
        tailf:cli-compact-syntax;
        key "name";
        leaf name {
          type string;
        }
        uses ntp-peer-grouping;
      }
    }
    container allow {
      container mode {
        leaf control {
          type uint8;
        }
        leaf private {
          type empty;
        }
      }
    }
    leaf update-calendar {
      type empty;
    }
  }
  container sntp {
    leaf logging {
      type empty;
    }
    list authentication-key {
      tailf:cli-suppress-mode;
      tailf:cli-delete-when-empty;
      tailf:cli-sequence-commands;
      tailf:cli-compact-syntax;
      key "number";
      leaf number {
        type uint32;
      }
      leaf md5 {
        type string;
      }
      leaf encryption-type {
        tailf:cli-drop-node-name;
        type uint32;
      }
    }
    leaf authenticate {
      type empty;
    }
    list trusted-key {
      tailf:cli-suppress-mode;
      tailf:cli-delete-when-empty;
      tailf:cli-sequence-commands;
      tailf:cli-compact-syntax;
      key "key-number";
      leaf key-number {
        type uint16;
      }
      leaf hyphen {
        tailf:alt-name "-";
        type empty;
      }
      leaf end-key-number {
        tailf:cli-drop-node-name;
        type uint16;
      }
    }
    container server {
      uses sntp-server-grouping;
      container ip {
        tailf:cli-compact-syntax;
        uses sntp-server-grouping;
      }
      container ipv6 {
        tailf:cli-compact-syntax;
        uses sntp-server-grouping;
      }
      list vrf {
        tailf:cli-suppress-mode;
        tailf:cli-delete-when-empty;
        tailf:cli-compact-syntax;
        key "name";
        leaf name {
          type string;
        }
        uses sntp-server-grouping;
      }
    }
    container broadcast {
      leaf client {
        type empty;
      }
    }
    container multicast {
      container client {
        tailf:cli-delete-when-empty;
        presence "true";
        leaf address {
          tailf:cli-drop-node-name;
          type union {
            type inet:ipv4-address;
            type inet:ipv6-address;
          }
        }
      }
    }
    container source-interface {
      uses interface-name-grouping;
    }
  }
  container nat64 {
    container prefix {
      leaf stateful {
        type ipv6-prefix;
      }
    }
    container v4 {
      list pool {
        tailf:cli-suppress-mode;
        tailf:cli-delete-when-empty;
        tailf:cli-compact-syntax;
        tailf:cli-sequence-commands;
        key "name";
        leaf name {
          type string;
        }
        leaf start-address-range {
          tailf:cli-drop-node-name;
          type inet:ipv4-address;
        }
        leaf end-address-range {
          tailf:cli-drop-node-name;
          type inet:ipv4-address;
        }
        leaf forced {
          type empty;
        }
      }
    }
    container v6v4 {
      list static {
        tailf:cli-suppress-mode;
        tailf:cli-delete-when-empty;
        tailf:cli-compact-syntax;
        tailf:cli-sequence-commands;
        key "ipv6-address";
        leaf ipv6-address {
          type inet:ipv6-address;
        }
        leaf ipv4-address {
          tailf:cli-drop-node-name;
          type inet:ipv4-address;
        }
        leaf redundancy {
          type uint8;
        }
        leaf mapping-id {
          type uint32;
        }
      }
      list list {
        tailf:cli-suppress-mode;
        tailf:cli-delete-when-empty;
        tailf:cli-compact-syntax;
        tailf:cli-sequence-commands;
        key "name";
        leaf name {
          type string;
        }
        leaf pool {
          type string;
        }
        leaf overload {
          tailf:cli-optional-in-sequence;
          type empty;
        }
        leaf redundancy {
          type uint8;
        }
        leaf mapping-id {
          type uint32;
        }
      }
    }
    container settings {
      container fragmentation {
        container header {
          leaf disable {
            type empty;
          }
        }
      }
    }
  }
  container ptp {
    container clock {
      list profile {
        key "id";
        leaf id {
          type uint8;
        }
        container clock-source1 {
          tailf:cli-compact-syntax;
          tailf:cli-sequence-commands;
          leaf address {
            tailf:cli-drop-node-name;
            type inet:ipv4-address;
          }
          leaf gw {
            type inet:ipv4-address;
          }
        }
      }
      container ordinary {
        list domain {
          key "id";
          leaf id {
            type uint8;
          }
          leaf hybrid {
            tailf:cli-hide-in-submode;
            type empty;
          }
          uses ptp-clock-domain-grouping;
        }
      }
      container boundary {
        list domain {
          key "id";
          leaf id {
            type uint8;
          }
          leaf hybrid {
            tailf:cli-hide-in-submode;
            type empty;
          }
          uses ptp-clock-domain-grouping;
        }
      }
    }
    list r-dti {
      key "id";
      leaf id {
        type uint8;
      }
      leaf profile {
        type string;
      }
      leaf ptp-domain {
        type uint8;
      }
      uses description-grouping;
      list clock-port {
        key "id";
        leaf id {
          type uint8;
        }
        uses description-grouping;
        leaf ethernet {
          type uint8;
        }
        container transport {
          leaf encapsulation {
            tailf:cli-drop-node-name;
            type enumeration {
              enum "ipv4";
              enum "ipv6";
              enum "other";
            }
          }
          leaf dscp {
            type uint8;
          }
        }
        container clock {
          container source {
            tailf:cli-compact-syntax;
            tailf:cli-sequence-commands {
              tailf:cli-reset-siblings;
            }
            leaf protocol {
              tailf:cli-drop-node-name;
              type enumeration {
                enum "ip";
                enum "ipv6";
              }
            }
            leaf address {
              tailf:cli-drop-node-name;
              type union {
                type inet:ipv4-address;
                type inet:ipv6-address;
              }
            }
            container gateway {
              tailf:cli-flatten-container;
              tailf:cli-compact-syntax;
              tailf:cli-sequence-commands {
                tailf:cli-reset-siblings;
              }
              leaf protocol {
                tailf:cli-drop-node-name;
                type enumeration {
                  enum "ip";
                  enum "ipv6";
                }
              }
              leaf address {
                tailf:cli-drop-node-name;
                type union {
                  type inet:ipv4-address;
                  type inet:ipv6-address;
                }
              }
            }
          }
          container source-alternate {
            tailf:cli-drop-node-name;
            container source {
              tailf:cli-compact-syntax;
              tailf:cli-sequence-commands {
                tailf:cli-reset-siblings;
              }
              leaf protocol {
                tailf:cli-drop-node-name;
                type enumeration {
                  enum "ip";
                  enum "ipv6";
                }
              }
              leaf address {
                tailf:cli-drop-node-name;
                type union {
                  type inet:ipv4-address;
                  type inet:ipv6-address;
                }
              }
              leaf alternate {
                type empty;
              }
            }
          }
        }
        container sync {
          leaf interval {
            type int8;
          }
        }
        container delay-req {
          leaf interval {
            type int8;
          }
        }
        leaf local-priority {
          type uint8;
        }
      }
    }
  }
  container mac-flap-syslog {
    leaf enable {
      type empty;
    }
  }
  container qos-overhead-accounting {
    choice overhead-choice {
      leaf negative {
        type uint8;
      }
      leaf positive {
        type uint8;
      }
    }
    container enable {
      list GigabitEthernet {
        tailf:cli-suppress-mode;
        tailf:cli-delete-when-empty;
        key "name";
        leaf name {
          type string;
        }
      }
      list TenGigabitEthernet {
        tailf:cli-suppress-mode;
        tailf:cli-delete-when-empty;
        key "name";
        leaf name {
          type string;
        }
      }
    }
  }
  container mac-address-table {
    container notification {
      leaf mac-move {
        type empty;
      }
    }
    container move {
      container update {
        leaf transmit {
          type empty;
        }
        leaf receive {
          type empty;
        }
      }
    }
    container synchronize {
      presence "true";
      leaf activity-time {
        type uint16;
      }
    }
    container aging-type {
      leaf routed-mac {
        type boolean;
      }
    }
    leaf aging-time {
      type union {
        type uint32;
        type uint32;
      }
    }
    container againg-time-routed-mac {
      tailf:cli-drop-node-name;
      container aging-time {
        tailf:cli-compact-syntax;
        tailf:cli-sequence-commands {
          tailf:cli-reset-siblings;
        }
        leaf speed {
          tailf:cli-drop-node-name;
          type union {
            type uint32;
            type uint32;
          }
        }
        leaf routed-mac {
          type empty;
        }
      }
    }
    container againg-time-vlan {
      tailf:cli-drop-node-name;
      list aging-time {
        tailf:cli-suppress-mode;
        tailf:cli-delete-when-empty;
        tailf:cli-compact-syntax;
        tailf:cli-sequence-commands;
        key "vlan";
        leaf vlan {
          tailf:cli-expose-key-name;
          type uint16;
        }
        leaf speed {
          tailf:cli-drop-node-name;
          tailf:cli-prefix-key;
          type union {
            type uint32;
            type uint32;
          }
        }
      }
    }
    container limit-enable {
      tailf:cli-drop-node-name;
      leaf limit {
        type empty;
      }
    }
    container limit {
      leaf maximum {
        type uint16;
      }
      list vlan {
        tailf:cli-suppress-mode;
        tailf:cli-delete-when-empty;
        tailf:cli-compact-syntax;
        key "id";
        leaf id {
          type uint16;
        }
        leaf maximum {
          type uint16;
        }
        leaf action {
          type enumeration {
            enum "warning";
            enum "limit";
            enum "shutdown";
          }
        }
        leaf flood {
          type empty;
        }
      }
      list bdomain {
        tailf:cli-suppress-mode;
        tailf:cli-delete-when-empty;
        tailf:cli-compact-syntax;
        key "id";
        leaf id {
          type uint16;
        }
        leaf maximum {
          type uint16;
        }
        leaf action {
          type enumeration {
            enum "warning";
            enum "limit";
            enum "shutdown";
          }
        }
        leaf flood {
          type empty;
        }
      }
    }
    container learning {
      container vlan {
        list no-list {
          tailf:cli-suppress-mode;
          tailf:cli-delete-when-empty;
          key "id";
          leaf id {
            type uint16;
          }
          leaf module {
            type uint8;
          }
        }
      }
    }
    list static {
      tailf:cli-suppress-mode;
      tailf:cli-delete-when-empty;
      tailf:cli-compact-syntax;
      key "id vlan";
      leaf id {
        type string;
      }
      leaf vlan {
        tailf:cli-expose-key-name;
        type uint16;
      }
      choice table-choice {
        leaf drop {
          type empty;
        }
        container interface {
          tailf:cli-delete-when-empty;
          presence "true";
          leaf-list list {
            tailf:cli-drop-node-name;
            tailf:cli-flat-list-syntax;
            type string;
          }
        }
      }
    }
  }
  container mac {
    container access-list {
      list extended {
        key "id";
        leaf id {
          type string;
        }
        list entry {
          tailf:cli-drop-node-name;
          tailf:cli-suppress-mode;
          tailf:cli-delete-when-empty;
          tailf:cli-compact-syntax;
          ordered-by user;
          key "rule";
          leaf rule {
            tailf:cli-drop-node-name;
            tailf:cli-multi-word-key;
            type string;
          }
        }
      }
    }
    container address-table {
      leaf aging-time {
        type union {
          type uint32;
          type uint32;
        }
      }
      container aging-time-vlan {
        tailf:cli-drop-node-name;
        list aging-time {
          tailf:cli-suppress-mode;
          tailf:cli-delete-when-empty;
          key "vlan";
          leaf vlan {
            tailf:cli-expose-key-name;
            type uint16;
          }
          leaf aging-time {
            tailf:cli-drop-node-name;
            tailf:cli-prefix-key;
            type union {
              type uint32;
              type uint32;
            }
          }
        }
      }
      container notification {
        leaf change {
          type empty;
        }
        leaf mac-move {
          type empty;
        }
      }
      container move {
        container update {
          leaf transmit {
            type empty;
          }
          leaf receive {
            type empty;
          }
        }
      }
      list static {
        tailf:cli-suppress-mode;
        tailf:cli-delete-when-empty;
        tailf:cli-compact-syntax;
        key "id vlan";
        leaf id {
          type string;
        }
        leaf vlan {
          tailf:cli-expose-key-name;
          type uint16;
        }
        choice table-choice {
          leaf drop {
            type empty;
          }
          leaf-list interface {
            tailf:cli-flat-list-syntax;
            type string;
          }
        }
      }
      container learning {
        container vlan {
          list no-list {
            tailf:cli-suppress-mode;
            tailf:cli-delete-when-empty;
            key "id";
            leaf id {
              type uint16;
            }
          }
        }
      }
    }
  }
  container wireless {
    container mobility {
      container group {
        leaf name {
          type string;
        }
      }
    }
    container aaa {
      list policy {
        key "name";
        leaf name {
          type string;
        }
        container aaa-realm {
          leaf enable {
            type empty;
          }
        }
      }
    }
    container cts-sxp {
      list profile {
        key "name";
        leaf name {
          type string;
        }
      }
    }
    container ipv6 {
      container ra {
        leaf wired {
          type boolean;
        }
      }
    }
    container management {
      leaf trustpoint {
        type string;
      }
      container interface {
        uses interface-name-grouping;
      }
    }
    container profile {
      container ap {
        list packet-capture {
          key "name";
          leaf name {
            type string;
          }
          leaf description {
            type string;
          }
        }
      }
      list airtime-fairness {
        key "name";
        leaf name {
          type string;
        }
        leaf id {
          tailf:cli-drop-node-name;
          tailf:cli-hide-in-submode;
          type uint16;
        }
      }
      list flex {
        key "name";
        leaf name {
          type string;
        }
        leaf description {
          type string;
        }
      }
      list mesh {
        key "name";
        leaf name {
          type string;
        }
        leaf description {
          type string;
        }
      }
      list policy {
        key "name";
        leaf name {
          type string;
        }
        leaf description {
          type string;
        }
        leaf aaa-override {
          type empty;
        }
        leaf accounting-list {
          type string;
        }
        leaf exclusionlist {
          type boolean;
        }
        container exclusionlist-conf {
          tailf:cli-drop-node-name;
          container exclusionlist {
            leaf timeout {
              type uint32;
            }
          }
        }
        container mdns-sd {
          leaf service-policy {
            type string;
          }
        }
        leaf nac {
          type empty;
        }
        container service-policy {
          uses service-policy-grouping;
        }
        leaf vlan {
          type string;
        }
        leaf session-timeout {
          type uint32;
        }
        leaf shutdown {
          type boolean;
        }
      }
    }
    container rfid {
      leaf timeout {
        type uint16;
      }
    }
    container tag {
      list site {
        key "name";
        leaf name {
          type string;
        }
        leaf description {
          type string;
        }
        leaf ap-profile {
          type string;
        }
        leaf flex-profile {
          type string;
        }
        leaf local-site {
          type boolean;
        }
      }
      list policy {
        key "name";
        leaf name {
          type string;
        }
        leaf description {
          type string;
        }
        list wlan {
          tailf:cli-suppress-mode;
          tailf:cli-delete-when-empty;
          key "name";
          leaf name {
            type string;
          }
          leaf policy {
            type string;
          }
        }
      }
      list rf {
        key "name";
        leaf name {
          type string;
        }
        leaf description {
          type string;
        }
        leaf fiveghz-rf-policy {
          tailf:alt-name "5ghz-rf-policy";
          type string;
        }
      }
    }
    container wps {
      container rogue {
        container ap {
          container rldp {
            container alarm-only {
              tailf:cli-delete-when-empty;
              presence "true";
              leaf monitor-ap-only {
                type empty;
              }
            }
          }
        }
        list rule {
          key "name";
          unique "priority";
          leaf name {
            type string;
          }
          leaf priority {
            tailf:cli-hide-in-submode;
            type uint16;
          }
          container classify {
            tailf:cli-compact-syntax;
            tailf:cli-sequence-commands {
              tailf:cli-reset-siblings;
            }
            leaf type {
              tailf:cli-drop-node-name;
              type enumeration {
                enum "custom";
                enum "friendly";
                enum "malicious";
              }
            }
            leaf state {
              type enumeration {
                enum "alert";
                enum "contained";
                enum "external";
                enum "internal";
              }
            }
          }
          container condition {
            leaf duration {
              type uint16;
            }
            leaf rssi {
              type int8;
            }
            container infrastructure {
              leaf ssid {
                type empty;
              }
            }
          }
          leaf match {
            type enumeration {
              enum "all";
              enum "any";
            }
          }
          leaf shutdown {
            type boolean;
          }
        }
      }
    }
    container client {
      leaf onboarding-event {
        type empty;
      }
    }
    leaf rf-network {
      type string;
    }
    container security {
      container dot1x {
        container eapol-key {
          leaf retries {
            type uint8;
          }
          leaf timeout {
            type uint16;
          }
        }
        container identity-request {
          leaf retries {
            type uint8;
          }
          leaf timeout {
            type uint8;
          }
        }
        container request {
          leaf retries {
            type uint8;
          }
          leaf timeout {
            type uint8;
          }
        }
      }
    }
    container multicast {
      leaf address {
        tailf:cli-drop-node-name;
        type inet:ipv4-address;
      }
    }
    container fabric {
      list control-plane {
        key "name";
        leaf name {
          type string;
        }
      }
    }
    list country {
      tailf:cli-suppress-mode;
      tailf:cli-delete-when-empty;
      key "name";
      leaf name {
        type string;
      }
    }
  }
  container nmsp {
    leaf enable {
      type empty;
    }
  }
  container wlan {
    list list {
      tailf:cli-drop-node-name;
      key "name";
      leaf name {
        type string;
      }
      leaf wlan-id {
        tailf:cli-drop-node-name;
        tailf:cli-hide-in-submode;
        type uint16;
      }
      leaf ssid {
        tailf:cli-drop-node-name;
        tailf:cli-hide-in-submode;
        type string;
      }
      leaf description {
        type string;
      }
      leaf band-select {
        type empty;
      }
      container security {
        container wpa {
          container akm {
            leaf dot1x {
              type boolean;
            }
          }
        }
        container dot1x {
          leaf authentication-list {
            type string;
          }
        }
      }
      container dtim {
        container dot11 {
          leaf fiveghz {
            tailf:alt-name "5ghz";
            type uint8;
          }
        }
      }
      leaf radio {
        type enumeration {
          enum "dot11a";
          enum "dot11ag";
          enum "dot11bg";
          enum "dot11g";
        }
      }
      leaf mac-filtering {
        type string;
      }
      container channel-scan {
        leaf defer-priority {
          type uint8;
        }
      }
      leaf shutdown {
        type boolean;
      }
    }
  }
  container ap {
    container dot11 {
      container airtime-fairness {
        list policy-name {
          tailf:cli-suppress-mode;
          tailf:cli-delete-when-empty;
          key "name";
          leaf name {
            type string;
          }
          leaf id {
            tailf:cli-drop-node-name;
            type uint16;
          }
        }
      }
      container twentyfourghz {
        tailf:alt-name "24ghz";
        uses ap-dot11-ghz-grouping;
      }
      container fiveghz {
        tailf:alt-name "5ghz";
        uses ap-dot11-ghz-grouping;
      }
    }
    container fra {
      leaf interval {
        type uint8;
      }
    }
    leaf country {
      type string;
    }
    list tag-source-priority {
      tailf:cli-suppress-mode;
      tailf:cli-delete-when-empty;
      tailf:cli-compact-syntax;
      tailf:cli-sequence-commands {
        tailf:cli-reset-siblings;
      }
      key "id";
      leaf id {
        type uint8;
      }
      leaf source {
        type enumeration {
          enum "ap";
          enum "filter";
        }
      }
    }
    list group {
      key "name";
      leaf name {
        type string;
      }
    }
    list profile {
      key "name";
      leaf name {
        type string;
      }
      leaf description {
        type string;
      }
      leaf packet-capture {
        type string;
      }
      leaf preferred-mode {
        type enumeration {
          enum "disable";
          enum "ipv4";
          enum "ipv6";
        }
      }
      container rogue {
        container detection {
          leaf min-rssi {
            type int8;
          }
        }
      }
      container tcp-adjust-mss {
        leaf size {
          type uint16;
        }
      }
      container capwap {
        container backup {
          container primary {
            tailf:cli-compact-syntax;
            tailf:cli-sequence-commands {
              tailf:cli-reset-siblings;
            }
            leaf wlc-name {
              tailf:cli-drop-node-name;
              type string;
            }
            leaf wlc-ip {
              tailf:cli-drop-node-name;
              type union {
                type inet:ipv4-address;
                type inet:ipv6-address;
              }
            }
          }
          container secondary {
            tailf:cli-compact-syntax;
            tailf:cli-sequence-commands {
              tailf:cli-reset-siblings;
            }
            leaf wlc-name {
              tailf:cli-drop-node-name;
              type string;
            }
            leaf wlc-ip {
              tailf:cli-drop-node-name;
              type union {
                type inet:ipv4-address;
                type inet:ipv6-address;
              }
            }
          }
        }
        leaf fallback {
          type boolean;
        }
      }
      container mgmtuser {
        tailf:cli-compact-syntax;
        tailf:cli-sequence-commands {
          tailf:cli-reset-siblings;
        }
        leaf username {
          type string;
        }
        container password {
          tailf:cli-flatten-container;
          tailf:cli-compact-syntax;
          leaf type {
            tailf:cli-drop-node-name;
            type enumeration {
              enum "0";
              enum "8";
            }
          }
          leaf password {
            tailf:cli-drop-node-name;
            type string;
          }
        }
        container secret {
          tailf:cli-flatten-container;
          tailf:cli-compact-syntax;
          leaf type {
            tailf:cli-drop-node-name;
            type enumeration {
              enum "0";
              enum "8";
            }
          }
          leaf secret {
            tailf:cli-drop-node-name;
            type string;
          }
        }
      }
      leaf ssh {
        type empty;
      }
    }
    list mac-address {
      tailf:cli-drop-node-name;
      key "address";
      leaf address {
        type string;
      }
      leaf policy-tag {
        type string;
      }
      leaf rf-tag {
        type string;
      }
      leaf site-tag {
        type string;
      }
    }
  }
  container app-hosting {
    list appid {
      key "name";
      leaf name {
        type string;
      }
      container app-vnic {
        list gateway {
          tailf:cli-drop-node-name;
          key "name";
          leaf name {
            type enumeration {
              enum "gateway0";
              enum "gateway1";
              enum "gateway2";
              enum "gateway3";
            }
          }
          leaf virtualportgroup {
            tailf:cli-hide-in-submode;
            type string;
          }
          leaf guest-interface {
            tailf:cli-hide-in-submode;
            type string;
          }
        }
      }
      container app-resource {
        list profile {
          key "name";
          leaf name {
            type string;
          }
          leaf cpu {
            type uint16;
          }
          leaf memory {
            type uint16;
          }
        }
      }
    }
  }
  list time-range {
    key "name";
    leaf name {
      type string;
    }
    container absolute {
      tailf:cli-compact-syntax;
      tailf:cli-sequence-commands {
        tailf:cli-reset-siblings;
      }
      container start {
        tailf:cli-optional-in-sequence;
        tailf:cli-flatten-container;
        tailf:cli-compact-syntax;
        tailf:cli-sequence-commands;
        uses time-range-abs-grouping;
      }
      container end {
        tailf:cli-flatten-container;
        tailf:cli-compact-syntax;
        tailf:cli-sequence-commands;
        uses time-range-abs-grouping;
      }
    }
  }

  grouping time-range-abs-grouping {
    leaf time {
      tailf:cli-drop-node-name;
      type hhmm-type;
    }
    leaf date {
      tailf:cli-drop-node-name;
      type uint8;
    }
    leaf month {
      tailf:cli-drop-node-name;
      type month-full-type;
    }
    leaf year {
      tailf:cli-drop-node-name;
      type uint16;
    }
  }

  container privilege {
    container exec {
      container all {
        uses privilege-level-grouping;
      }
      uses privilege-level-grouping;
    }
    container configure {
      container all {
        uses privilege-level-grouping;
      }
      uses privilege-level-grouping;
    }
    list list {
      tailf:cli-drop-node-name;
      tailf:cli-suppress-mode;
      tailf:cli-delete-when-empty;
      key "name";
      leaf name {
        type string;
      }
      container all {
        uses privilege-level-grouping;
      }
      uses privilege-level-grouping;
    }
  }

  grouping privilege-level-grouping {
    list level {
      tailf:cli-suppress-mode;
      tailf:cli-delete-when-empty;
      tailf:cli-compact-syntax;
      key "privilege";
      leaf privilege {
        tailf:cli-suppress-range;
        type uint8;
      }
      list command-list {
        tailf:cli-drop-node-name;
        tailf:cli-suppress-mode;
        tailf:cli-delete-when-empty;
        tailf:cli-suppress-key-abbreviation;
        key "command";
        leaf command {
          tailf:cli-multi-word-key;
          tailf:cli-suppress-range;
          type string;
        }
      }
    }
  }

  container default-value {
    leaf special-character-bits {
      type uint8;
    }
  }
  container spanning-tree {
    container etherchannel {
      container guard {
        leaf misconfig {
          type empty;
        }
      }
    }
    leaf logging {
      type empty;
    }
    container extend {
      leaf system-id {
        type empty;
      }
    }
    leaf backbonefast {
      type empty;
    }
    container loopguard {
      leaf default {
        type empty;
      }
    }
    container mst {
      list instance-range {
        tailf:cli-drop-node-name;
        tailf:cli-suppress-mode;
        tailf:cli-delete-when-empty;
        tailf:cli-range-list-syntax;
        key "id";
        leaf id {
          type uint16;
        }
        leaf priority {
          type uint16;
        }
      }
      container configuration {
        tailf:cli-add-mode;
        leaf revision {
          type uint16;
        }
        leaf name {
          type string;
        }
        list instance {
          tailf:cli-suppress-mode;
          tailf:cli-delete-when-empty;
          key "id";
          leaf id {
            type uint16;
          }
          leaf-list vlan {
            tailf:cli-range-list-syntax;
            type uint16;
          }
        }
      }
      leaf forward-time {
        type uint8;
      }
    }
    container optimize {
      container bpdu {
        leaf transmission {
          type boolean;
        }
      }
    }
    container portfast {
      uses spanning-tree-portfast-grouping;
      container edge {
        uses spanning-tree-portfast-grouping;
      }
    }
    container uplinkfast-conf {
      tailf:cli-drop-node-name;
      container uplinkfast {
        leaf max-update-rate {
          type uint16;
        }
      }
    }
    leaf uplinkfast {
      type empty;
    }
    container pathcost {
      leaf method {
        type enumeration {
          enum "long";
          enum "short";
        }
      }
    }
    leaf mode {
      type enumeration {
        enum "mst";
        enum "pvst";
        enum "rapid-pvst";
      }
    }
    container vlan {
      list no-list {
        tailf:cli-suppress-mode;
        tailf:cli-delete-when-empty;
        tailf:cli-range-list-syntax;
        key "id";
        leaf id {
          type uint16;
        }
      }
      list vlan-list {
        tailf:cli-drop-node-name;
        tailf:cli-suppress-mode;
        tailf:cli-delete-when-empty;
        tailf:cli-range-list-syntax;
        key "id";
        leaf id {
          type uint16;
        }
        leaf hello-time {
          type uint8;
        }
        leaf priority {
          type uint16;
        }
        leaf forward-time {
          type uint8;
        }
        leaf max-age {
          type uint8;
        }
      }
    }
  }
  container lacp {
    leaf system-priority {
      type uint16;
    }
  }
  container dot1x {
    list credentials {
      key "name";
      leaf name {
        type string;
      }
      leaf username {
        type string;
      }
      leaf anonymous-id {
        type string;
      }
      leaf pki-trustpoint {
        type string;
      }
    }
    container critical {
      leaf eapol {
        type empty;
      }
      container recovery {
        leaf delay {
          type uint16;
        }
      }
    }
    leaf system-auth-control {
      type empty;
    }
  }
  container power {
    container enable {
      container module {
        list no-list {
          tailf:cli-suppress-mode;
          tailf:cli-delete-when-empty;
          key "id";
          leaf id {
            type uint8;
          }
        }
      }
    }
    container redundancy-mode {
      tailf:cli-compact-syntax;
      tailf:cli-sequence-commands {
        tailf:cli-reset-siblings;
      }
      choice mode-choice {
        leaf combined {
          type empty;
        }
        case redundant {
          leaf redundant {
            type empty;
          }
          leaf mode {
            tailf:cli-drop-node-name;
            type enumeration {
              enum "n+1";
              enum "n+n";
            }
          }
          leaf-list slot {
            tailf:cli-drop-node-name;
            tailf:cli-flat-list-syntax;
            ordered-by user;
            type uint8;
          }
        }
      }
    }
    container supply {
      container autoLC {
        leaf shutdown {
          type boolean;
        }
        leaf-list priority {
          tailf:cli-flat-list-syntax;
          ordered-by user;
          type uint8;
        }
      }
    }
  }
  container power-supply {
    container dual {
      tailf:cli-delete-when-empty;
      presence "true";
      leaf dc-feed {
        type empty;
      }
    }
  }
  container parameter-map {
    container type {
      list inspect {
        key "name";
        leaf name {
          type string;
        }
        uses parameter-map-grouping;
      }
      list inspect-vrf {
        key "name";
        leaf name {
          type string;
        }
        uses parameter-map-grouping;
      }
      list inspect-zone {
        key "name";
        leaf name {
          type string;
        }
        uses parameter-map-grouping;
      }
      container inspect-global {
        tailf:cli-add-mode;
        uses parameter-map-grouping;
      }
      list regex {
        key "name";
        leaf name {
          type string;
        }
        list pattern {
          tailf:cli-suppress-mode;
          tailf:cli-delete-when-empty;
          key "regexp";
          leaf regexp {
            type string;
          }
        }
      }
      container umbrella {
        container global {
          tailf:cli-add-mode;
          presence "true";
          leaf token {
            type string;
          }
          leaf local-domain {
            type string;
          }
          leaf dnscrypt {
            type boolean;
          }
          leaf public-key {
            type string;
          }
          leaf udp-timeout {
            type uint8;
          }
          container resolver {
            list ipv4 {
              tailf:cli-suppress-mode;
              tailf:cli-delete-when-empty;
              key "address";
              leaf address {
                type inet:ipv4-address;
              }
            }
            list ipv6 {
              tailf:cli-suppress-mode;
              tailf:cli-delete-when-empty;
              key "address";
              leaf address {
                type inet:ipv6-address;
              }
            }
          }
        }
      }
      list webauth {
        key "name";
        leaf name {
          type string;
        }
        leaf type {
          type enumeration {
            enum "authbypass";
            enum "consent";
            enum "webauth";
            enum "webconsent";
          }
        }
      }
      container cws-tunnel {
        container global {
          tailf:cli-add-mode;
          leaf logging {
            type empty;
          }
          leaf fail-open {
            type empty;
          }
          container primary {
            tailf:cli-add-mode;
            container tower {
              leaf ipv4 {
                type inet:ipv4-address;
              }
            }
          }
          container secondary {
            tailf:cli-add-mode;
            container tower {
              leaf ipv4 {
                type inet:ipv4-address;
              }
            }
          }
          container license {
            tailf:cli-compact-syntax;
            tailf:cli-sequence-commands;
            leaf type {
              tailf:cli-drop-node-name;
              type enumeration {
                enum "0";
                enum "7";
              }
            }
            leaf secret {
              tailf:cli-drop-node-name;
              type string;
            }
          }
          leaf redirect-list {
            type union {
              type uint16;
              type uint16;
            }
          }
          container whitelist {
            tailf:cli-add-mode;
            container acl {
              leaf name {
                type string;
              }
            }
          }
        }
      }
    }
  }
  container vpdn {
    leaf enable {
      type empty;
    }
    leaf authen-before-forward {
      type empty;
    }
    leaf session-limit {
      type uint32;
    }
    leaf-list search-order {
      tailf:cli-flat-list-syntax;
      ordered-by user;
      type enumeration {
        enum "dnis";
        enum "domain";
        enum "multihop-hostname";
      }
    }
  }
  list vpdn-group {
    key "name";
    leaf name {
      type string;
    }
    container accept-dialin {
      tailf:cli-add-mode;
      leaf protocol {
        type enumeration {
          enum "any";
          enum "l2tp";
          enum "pptp";
        }
      }
      leaf virtual-template {
        type uint16;
      }
    }
    leaf description {
      tailf:cli-multi-value;
      type string;
    }
    leaf dsl-line-info-forwarding {
      type empty;
    }
    leaf force-local-chap {
      type empty;
    }
    container ip {
      leaf mtu {
        type enumeration {
          enum "adjust";
        }
      }
      leaf pmtu {
        type empty;
      }
      leaf precedence {
        type enumeration {
          enum "critical";
          enum "flash";
          enum "flash-override";
          enum "immediate";
          enum "internet";
          enum "network";
          enum "priority";
          enum "routine";
        }
      }
      leaf tos {
        type union {
          type uint8;
          type enumeration {
            enum "max-reliability";
            enum "max-throughput";
            enum "min-delay";
            enum "min-monetary-cost";
            enum "normal";
            enum "reflect";
          }
        }
      }
    }
    container l2tp {
      container attribute {
        container clid {
          tailf:cli-compact-syntax;
          tailf:cli-sequence-commands {
            tailf:cli-reset-siblings;
          }
          container mask-method {
            container remove {
              presence "true";
              leaf match {
                type string;
              }
            }
            container right {
              tailf:cli-compact-syntax;
              tailf:cli-sequence-commands {
                tailf:cli-reset-siblings;
              }
              leaf character {
                tailf:cli-drop-node-name;
                type string;
              }
              leaf bytes {
                tailf:cli-drop-node-name;
                type uint8;
              }
              leaf match {
                type string;
              }
            }
          }
        }
      }
      leaf drop {
        type enumeration {
          enum "out-of-order";
        }
      }
      leaf hidden {
        type empty;
      }
      leaf ignore {
        type enumeration {
          enum "tx-speed";
        }
      }
      container ip {
        leaf udp {
          type enumeration {
            enum "checksum";
          }
        }
      }
      container rx-speed {
        tailf:cli-compact-syntax;
        tailf:cli-sequence-commands {
          tailf:cli-reset-siblings;
        }
        leaf ANCP {
          tailf:cli-optional-in-sequence;
          type empty;
        }
        leaf RAM-min {
          tailf:cli-optional-in-sequence;
          type empty;
        }
        leaf rx-speed {
          tailf:cli-drop-node-name;
          type uint32;
        }
      }
      leaf sequencing {
        type empty;
      }
      container tunnel {
        leaf authentication {
          type empty;
        }
        container bearer {
          leaf capabilities {
            type enumeration {
              enum "all";
              enum "analog";
              enum "digital";
              enum "none";
            }
          }
        }
        container busy {
          leaf timeout {
            type uint16;
          }
        }
        container framing {
          leaf capabilities {
            type enumeration {
              enum "all";
              enum "asynchronous";
              enum "none";
              enum "synchronous";
            }
          }
        }
        leaf hello {
          type uint16;
        }
        container password {
          tailf:cli-compact-syntax;
          tailf:cli-sequence-commands;
          uses password-grouping {
            refine "secret";
          }
        }
        leaf receive-window {
          type uint16;
        }
        leaf resync {
          type uint16;
        }
        container retransmit {
          container initial {
            leaf retries {
              type uint16;
            }
            container timeout {
              leaf max {
                type uint8;
              }
              leaf min {
                type uint8;
              }
            }
          }
          leaf retries {
            type uint16;
          }
          container timeout {
            leaf max {
              type uint8;
            }
            leaf min {
              type uint8;
            }
          }
        }
        container timeout {
          leaf no-session {
            type union {
              type uint32;
              type enumeration {
                enum "never";
              }
            }
          }
          leaf setup {
            type uint16;
          }
        }
        container zlb {
          leaf delay {
            type uint8;
          }
        }
      }
      container tx-speed {
        tailf:cli-compact-syntax;
        tailf:cli-sequence-commands {
          tailf:cli-reset-siblings;
        }
        leaf ANCP {
          tailf:cli-optional-in-sequence;
          type empty;
        }
        leaf RAM-min {
          tailf:cli-optional-in-sequence;
          type empty;
        }
        leaf tx-speed {
          tailf:cli-drop-node-name;
          type uint32;
        }
      }
    }
    container lcp {
      leaf renegotiation {
        type enumeration {
          enum "always";
          enum "on-mismatch";
        }
      }
    }
    container local {
      leaf name {
        type string;
      }
    }
    container pptp {
      container flow-control {
        leaf receive-window {
          type uint8;
        }
        leaf static-rtt {
          type uint16;
        }
      }
      container relay {
        container pppoe {
          leaf bba-group {
            type string;
          }
        }
      }
      container tunnel {
        leaf echo {
          type uint16;
        }
      }
    }
    container redirect {
      leaf identifier {
        type string;
      }
    }
    container source {
      leaf vpdn-template {
        type string;
      }
    }
    leaf source-ip {
      type inet:ipv4-address;
    }
    container terminate-from {
      leaf hostname {
        type string;
      }
    }
    container vpn {
      leaf id {
        type string;
      }
      leaf vrf {
        type string;
      }
    }
  }
  container bba-group {
    list pppoe {
      key "id";
      leaf id {
        type union {
          type string;
          type enumeration {
            enum "global";
          }
        }
      }
      container vendor-tag {
        container circuit-id {
          leaf service {
            type empty;
          }
        }
        container dsl-sync-rate {
          leaf service {
            type empty;
          }
        }
        container remote-id {
          leaf service {
            type empty;
          }
        }
        leaf strip {
          type empty;
        }
      }
      leaf virtual-template {
        type uint16;
      }
      container service {
        leaf profile {
          type string;
        }
      }
      container nas-port-id {
        container format {
          leaf c {
            type empty;
          }
        }
      }
      container sessions {
        container max {
          container limit {
            tailf:cli-compact-syntax;
            tailf:cli-sequence-commands {
              tailf:cli-reset-siblings;
            }
            leaf value {
              tailf:cli-drop-node-name;
              type uint16;
            }
            leaf threshold {
              type uint16;
            }
          }
        }
        container per-mac {
          container limit {
            leaf value {
              tailf:cli-drop-node-name;
              type uint16;
            }
          }
          container iwf {
            container limit {
              leaf value {
                tailf:cli-drop-node-name;
                type uint16;
              }
            }
          }
        }
        container per-vlan {
          container limit {
            tailf:cli-compact-syntax;
            tailf:cli-sequence-commands {
              tailf:cli-reset-siblings;
            }
            leaf value {
              tailf:cli-drop-node-name;
              type uint16;
            }
            leaf inner {
              type uint16;
            }
          }
        }
        container auto {
          leaf cleanup {
            type empty;
          }
        }
      }
    }
  }
  container tacacs-server {
    leaf administration {
      type empty;
    }
    leaf attempts {
      type uint16;
    }
    container attribute {
      container allow {
        leaf unknown {
          type empty;
        }
      }
    }
    list host {
      tailf:cli-suppress-mode;
      tailf:cli-delete-when-empty;
      tailf:cli-compact-syntax;
      ordered-by user;
      key "name";
      leaf name {
        type inet:host;
      }
      leaf port {
        type uint16;
      }
      leaf timeout {
        type uint16;
      }
      container key {
        tailf:cli-flatten-container;
        tailf:cli-compact-syntax;
        tailf:cli-sequence-commands;
        uses password-grouping {
          refine "secret";
        }
      }
    }
    leaf timeout {
      type uint16;
    }
    container directed-request {
      tailf:cli-compact-syntax;
      tailf:cli-sequence-commands;
      presence "true";
      leaf restricted {
        tailf:cli-optional-in-sequence;
        type empty;
      }
      leaf no-truncate {
        type empty;
      }
    }
    container key {
      tailf:cli-compact-syntax;
      tailf:cli-sequence-commands;
      uses password-grouping {
        refine "secret";
      }
    }
    leaf last-resort {
      type enumeration {
        enum "password";
        enum "succeed";
      }
    }
  }
  container tacacs {
    list server {
      key "name";
      leaf name {
        type string;
      }
      container address {
        choice address-choice {
          leaf ipv4 {
            type inet:host;
          }
          leaf ipv6 {
            tailf:cli-case-insensitive;
            type inet:host;
          }
          leaf fqdn {
            type string;
          }
        }
      }
      container key {
        tailf:cli-compact-syntax;
        tailf:cli-sequence-commands;
        uses password-grouping {
          refine "secret";
        }
      }
      leaf port {
        type uint16;
      }
      leaf timeout {
        type uint16;
      }
      leaf single-connection {
        type empty;
      }
      leaf send-nat-address {
        type empty;
      }
    }
  }
  container udld {
    leaf enable {
      type empty;
    }
    leaf aggressive {
      type empty;
    }
    container message {
      leaf time {
        type uint8;
      }
    }
    leaf recovery {
      type empty;
    }
    container recovery-conf {
      tailf:cli-drop-node-name;
      container recovery {
        leaf interval {
          type uint32;
        }
      }
    }
  }
  container rep {
    container admin {
      list vlan {
        key "name";
        leaf name {
          type uint16;
        }
      }
    }
  }
  container x29 {
    list profile {
      tailf:cli-suppress-mode;
      tailf:cli-delete-when-empty;
      key "name";
      leaf name {
        type string;
      }
      leaf values {
        tailf:cli-drop-node-name;
        tailf:cli-multi-value;
        type string;
      }
    }
  }
  container xconnect {
    container logging {
      container pseudowire {
        leaf status {
          type empty;
        }
      }
      leaf redundancy {
        type empty;
      }
    }
  }
  list template {
    key "name";
    leaf name {
      type string;
    }
    leaf type {
      tailf:cli-prefix-key;
      type enumeration {
        enum "pseudowire";
      }
    }
    leaf encapsulation {
      type enumeration {
        enum "l2tpv3";
        enum "mpls";
      }
    }
    container vc {
      leaf type {
        type enumeration {
          enum "vlan" {
            value 4;
          }
          enum "ethernet" {
            value 5;
          }
        }
      }
    }
    leaf mtu {
      type uint16;
    }
    leaf control-word {
      type enumeration {
        enum "exclude";
        enum "include";
      }
    }
    container preferred-path {
      tailf:cli-compact-syntax;
      tailf:cli-sequence-commands {
        tailf:cli-reset-siblings;
      }
      choice interface-or-peer {
        leaf interface {
          type string;
        }
        leaf peer {
          type inet:host;
        }
        container segment-routing {
          tailf:cli-flatten-container;
          container traffic-eng {
            choice te-choice {
              leaf attribute-set {
                type string;
              }
              leaf policy {
                type string;
              }
            }
          }
        }
      }
      leaf disable-fallback {
        type empty;
      }
    }
    container signaling {
      leaf protocol {
        type enumeration {
          enum "ldp";
          enum "none";
        }
      }
    }
    container dot1x {
      leaf pae {
        type enumeration {
          enum "authenticator";
          enum "supplicant";
        }
      }
      container timeout {
        leaf supp-timeout {
          type uint16;
        }
        leaf tx-period {
          type uint16;
        }
      }
      leaf max-req {
        type uint8;
      }
    }
    container spanning-tree {
      container portfast {
        tailf:cli-compact-syntax;
        tailf:cli-delete-when-empty;
        presence "true";
        choice portfast-choice {
          leaf disable {
            type empty;
          }
          leaf network {
            type empty;
          }
          case trunk-mode {
            leaf edge {
              type empty;
            }
            leaf trunk {
              type empty;
            }
          }
        }
      }
      leaf guard {
        type enumeration {
          enum "loop";
          enum "none";
          enum "root";
        }
      }
    }
    container mab {
      presence "true";
      leaf eap {
        type empty;
      }
    }
    container access-session {
      leaf control-direction {
        type enumeration {
          enum "both";
          enum "in";
        }
      }
      leaf closed {
        type empty;
      }
      leaf port-control {
        type enumeration {
          enum "auto";
          enum "force-authorized";
          enum "force-unauthorized";
        }
      }
    }
    container authentication {
      leaf periodic {
        type empty;
      }
      container timer {
        leaf reauthenticate {
          type union {
            type enumeration {
              enum "server";
            }
            type uint16;
          }
        }
      }
    }
    container service-policy {
      container type {
        container control {
          leaf subscriber {
            type string;
          }
        }
      }
    }
  }
  container source {
    leaf template {
      type string;
    }
  }
  container fabric {
    container switching-mode {
      container allow {
        choice allow-choice {
          leaf bus-mode {
            type empty;
          }
          container truncated {
            presence "true";
            leaf threshold {
              type uint8;
            }
          }
          leaf dcef-only {
            type empty;
          }
        }
      }
      container force {
        leaf bus-mode {
          type empty;
        }
      }
    }
    container buffer-reserve {
      leaf queue {
        type empty;
      }
    }
    leaf required {
      type empty;
    }
    leaf timer {
      type uint16;
    }
  }
  container port-channel {
    container per-module {
      leaf load-balance {
        type empty;
      }
    }
    container load-balance {
      tailf:cli-compact-syntax;
      tailf:cli-sequence-commands {
        tailf:cli-reset-siblings;
      }
      leaf value {
        tailf:cli-drop-node-name;
        type enumeration {
          enum "dst-ip";
          enum "dst-mac";
          enum "dst-mixed-ip-port";
          enum "dst-port";
          enum "mpls";
          enum "src-dst-ip";
          enum "src-dst-mac";
          enum "src-dst-mixed-ip-port";
          enum "src-dst-port";
          enum "src-ip";
          enum "src-mac";
          enum "src-mixed-ip-port";
          enum "src-port";
        }
      }
      container exclude {
        tailf:cli-flatten-container;
        leaf vlan {
          type empty;
        }
      }
    }
    leaf load-balance-hash-algo {
      type string;
    }
  }
  container l2protocol-tunnel {
    leaf cos {
      type uint8;
    }
    container global {
      leaf drop-threshold {
        type uint16;
      }
    }
  }
  container l2vpn {
    tailf:cli-add-mode;
    presence "true";
    container logging {
      container pseudowire {
        leaf status {
          type empty;
        }
      }
      leaf redundancy {
        type empty;
      }
    }
    leaf router-id {
      type inet:ipv4-address;
    }
  }
  container l2vpn-vfi {
    tailf:cli-drop-node-name;
    container l2vpn {
      container vfi {
        list context {
          key "name";
          leaf name {
            type string;
          }
          container vpn {
            leaf id {
              type uint32;
            }
          }
          container l2protocol {
            container forward {
              presence "true";
            }
          }
          container autodiscovery {
            container bgp {
              container signaling {
                tailf:cli-add-mode;
                presence "true";
                choice protocol-choice {
                  leaf bgp {
                    tailf:cli-hide-in-submode;
                    type empty;
                  }
                  leaf ldp {
                    tailf:cli-hide-in-submode;
                    type empty;
                  }
                }
                leaf template {
                  tailf:cli-hide-in-submode;
                  type string;
                }
                container ve {
                  leaf id {
                    type uint16;
                  }
                  leaf range {
                    type uint8;
                  }
                }
                leaf rd {
                  type rd-type;
                }
                leaf vpls-id {
                  type asn-ip-type;
                }
                container route-target {
                  uses route-target-grouping;
                }
                leaf auto-route-target {
                  type boolean;
                }
              }
            }
          }
          container member {
            list ip-address-list {
              tailf:cli-drop-node-name;
              tailf:cli-suppress-mode;
              tailf:cli-delete-when-empty;
              tailf:cli-compact-syntax;
              key "ip-address";
              leaf ip-address {
                type inet:ipv4-address;
              }
              choice encapsulation-template-choice {
                leaf encapsulation {
                  type enumeration {
                    enum "mpls";
                  }
                }
                leaf template {
                  type string;
                }
              }
            }
            list ip-address-vc-id-list {
              tailf:cli-drop-node-name;
              tailf:cli-suppress-mode;
              tailf:cli-delete-when-empty;
              tailf:cli-compact-syntax;
              key "ip-address vc-id";
              leaf ip-address {
                type inet:ipv4-address;
              }
              leaf vc-id {
                type uint32;
              }
              choice encapsulation-template-choice {
                leaf encapsulation {
                  type enumeration {
                    enum "mpls";
                  }
                }
                leaf template {
                  type string;
                }
              }
            }
            list pseudowire {
              tailf:cli-suppress-mode;
              tailf:cli-delete-when-empty;
              tailf:cli-compact-syntax;
              tailf:cli-sequence-commands;
              tailf:cli-allow-join-with-key;
              key "name";
              leaf name {
                type uint32;
              }
              leaf ip-address {
                tailf:cli-drop-node-name;
                type inet:ipv4-address;
              }
              leaf vc-id {
                tailf:cli-drop-node-name;
                tailf:cli-optional-in-sequence;
                type uint32;
              }
              choice encapsulation-template-choice {
                leaf encapsulation {
                  type enumeration {
                    enum "mpls";
                  }
                }
                leaf template {
                  type string;
                }
              }
            }
          }
          leaf mtu {
            type uint16;
          }
          leaf evc {
            type string;
          }
        }
      }
    }
  }
  container l2vpn-xconnect {
    tailf:cli-drop-node-name;
    container l2vpn {
      container xconnect {
        list context {
          key "name";
          leaf name {
            type string;
          }
          uses description-grouping;
          container remote {
            container link {
              container failure {
                leaf notification {
                  type boolean;
                }
              }
            }
          }
          leaf interworking {
            type enumeration {
              enum "ethernet";
              enum "ip";
              enum "vlan";
            }
          }
          container member {
            list interface-list {
              tailf:cli-drop-node-name;
              tailf:cli-suppress-mode;
              tailf:cli-delete-when-empty;
              tailf:cli-compact-syntax;
              tailf:cli-sequence-commands {
                tailf:cli-reset-siblings;
              }
              key "name";
              leaf name {
                type string;
              }
              leaf cem-group {
                tailf:cli-drop-node-name;
                tailf:cli-optional-in-sequence;
                type uint16;
              }
              leaf group {
                type string;
              }
              leaf priority {
                type uint8;
              }
            }
            list member-list {
              tailf:cli-drop-node-name;
              tailf:cli-suppress-mode;
              tailf:cli-delete-when-empty;
              tailf:cli-compact-syntax;
              tailf:cli-sequence-commands {
                tailf:cli-reset-siblings;
              }
              key "name service-instance";
              leaf name {
                type string;
              }
              leaf service-instance {
                tailf:cli-expose-key-name;
                type uint32;
              }
              leaf group {
                type string;
              }
              leaf priority {
                type uint8;
              }
            }
            list address-list {
              tailf:cli-drop-node-name;
              tailf:cli-suppress-mode;
              tailf:cli-delete-when-empty;
              tailf:cli-compact-syntax;
              tailf:cli-sequence-commands {
                tailf:cli-reset-siblings;
              }
              key "name vcid";
              leaf name {
                type inet:ipv4-address;
              }
              leaf vcid {
                type uint32;
              }
              choice encap-or-termplate {
                leaf encapsulation {
                  type enumeration {
                    enum "mpls";
                  }
                }
                leaf template {
                  type string;
                }
              }
              leaf group {
                type string;
              }
              leaf priority {
                type uint8;
              }
            }
          }
          container redundancy {
            leaf predictive {
              type enumeration {
                enum "disabled";
                enum "enabled";
              }
            }
            list delay {
              tailf:cli-suppress-mode;
              tailf:cli-delete-when-empty;
              tailf:cli-compact-syntax;
              tailf:cli-sequence-commands;
              key "group";
              leaf group {
                tailf:cli-expose-key-name;
                type string;
              }
              leaf enable-delay {
                tailf:cli-drop-node-name;
                tailf:cli-prefix-key;
                type uint8;
              }
              leaf disable-delay {
                tailf:cli-drop-node-name;
                tailf:cli-prefix-key;
                type union {
                  type uint8;
                  type enumeration {
                    enum "never";
                  }
                }
              }
            }
          }
        }
      }
    }
  }
  container l2vpn-evpn-mode {
    tailf:cli-drop-node-name;
    container l2vpn {
      container evpn {
        tailf:cli-add-mode;
        container replication-type {
          choice replication-choice {
            leaf ingress {
              type empty;
            }
            leaf static {
              type empty;
            }
          }
        }
        container mpls {
          container label {
            leaf mode {
              type enumeration {
                enum "per-bd";
                enum "per-ce";
              }
            }
          }
        }
        container router-id {
          uses interface-name-grouping;
        }
        container default-gateway {
          leaf advertise {
            type empty;
          }
        }
        container ip {
          container duplication {
            tailf:cli-compact-syntax;
            tailf:cli-sequence-commands {
              tailf:cli-reset-siblings;
            }
            leaf limit {
              type uint16;
            }
            leaf time {
              type uint16;
            }
          }
        }
        container mac {
          container duplication {
            tailf:cli-compact-syntax;
            tailf:cli-sequence-commands {
              tailf:cli-reset-siblings;
            }
            leaf limit {
              type uint16;
            }
            leaf time {
              type uint16;
            }
          }
        }
        container route-target {
          container auto {
            leaf vni {
              type empty;
            }
          }
        }
        container logging {
          container vpws {
            leaf vc-state {
              type empty;
            }
          }
        }
      }
    }
  }
  container l2vpn-evpn {
    tailf:cli-drop-node-name;
    container l2vpn {
      container evpn {
        list instance {
          key "id";
          leaf id {
            type uint16;
          }
          leaf vlan-based {
            tailf:cli-hide-in-submode;
            type empty;
          }
          leaf vlan-bundle {
            tailf:cli-hide-in-submode;
            type empty;
          }
          leaf point-to-point {
            tailf:cli-hide-in-submode;
            type empty;
          }
          leaf rd {
            type rd-type;
          }
          container route-target {
            uses route-target-grouping;
          }
          leaf auto-route-target {
            type boolean;
          }
          container vpws {
            list context {
              key "name";
              leaf name {
                type string;
              }
              container service {
                tailf:cli-compact-syntax;
                tailf:cli-sequence-commands;
                leaf target {
                  type uint32;
                }
                leaf source {
                  type uint32;
                }
              }
              container member {
                tailf:cli-compact-syntax;
                tailf:cli-sequence-commands;
                leaf interface {
                  tailf:cli-drop-node-name;
                  type string;
                }
                leaf service-instance {
                  type uint16;
                }
              }
              leaf shutdown {
                type empty;
              }
            }
          }
          container encapsulation {
            leaf vxlan {
              type empty;
            }
          }
          leaf replication-type {
            type enumeration {
              enum "ingress";
              enum "static";
            }
          }
          container ip {
            leaf local-learning {
              type enumeration {
                enum "disable";
                enum "enable";
              }
            }
          }
          container default-gateway {
            leaf advertise {
              type enumeration {
                enum "disable";
                enum "enable";
              }
            }
          }
          container re-originate {
            leaf route-type5 {
              type empty;
            }
          }
        }
      }
    }
  }
  leaf pae {
    type empty;
  }
  container segment-routing {
    container mpls {
      tailf:cli-add-mode;
      presence "true";
      leaf shutdown {
        type empty;
      }
      container set-attributes {
        tailf:cli-add-mode;
        container address-family {
          container ipv4 {
            tailf:cli-add-mode;
            leaf sr-label-preferred {
              type empty;
            }
            leaf explicit-null {
              type empty;
            }
          }
        }
      }
      container global-block {
        tailf:cli-compact-syntax;
        tailf:cli-sequence-commands;
        leaf start {
          tailf:cli-drop-node-name;
          type uint32;
        }
        leaf end {
          tailf:cli-drop-node-name;
          type uint32;
        }
      }
      container local-block {
        tailf:cli-compact-syntax;
        tailf:cli-sequence-commands;
        leaf start {
          tailf:cli-drop-node-name;
          type uint32;
        }
        leaf end {
          tailf:cli-drop-node-name;
          type uint32;
        }
      }
      container connected-prefix-sid-map {
        tailf:cli-add-mode;
        container address-family {
          container ipv4 {
            tailf:cli-add-mode;
            uses sr-connected-prefix-sid-map-af-grouping;
          }
          container ipv4-conf {
            tailf:cli-drop-node-name;
            container ipv4 {
              container strict-spf {
                tailf:cli-add-mode;
                uses sr-connected-prefix-sid-map-af-grouping;
              }
              list algorithm {
                key "id";
                leaf id {
                  type uint8;
                }
                uses sr-connected-prefix-sid-map-af-grouping;
              }
            }
          }
        }
      }
      container mapping-server {
        tailf:cli-add-mode;
        container prefix-sid-map {
          tailf:cli-add-mode;
          container address-family {
            container ipv4 {
              tailf:cli-add-mode;
              list prefix {
                tailf:cli-drop-node-name;
                tailf:cli-suppress-mode;
                tailf:cli-delete-when-empty;
                tailf:cli-compact-syntax;
                tailf:cli-sequence-commands {
                  tailf:cli-reset-siblings;
                }
                key "prefix";
                leaf prefix {
                  type inet:ipv4-prefix;
                }
                leaf index {
                  type uint32;
                }
                leaf range {
                  type uint32;
                }
              }
            }
          }
        }
      }
    }
    container traffic-eng {
      tailf:cli-add-mode;
      presence "true";
      list interface {
        key "name";
        leaf name {
          type string;
        }
        leaf metric {
          type uint32;
        }
        container affinity {
          tailf:cli-add-mode;
          list name {
            tailf:cli-suppress-mode;
            tailf:cli-delete-when-empty;
            key "name";
            leaf name {
              type string;
            }
          }
        }
      }
      container logging {
        container policy {
          leaf status {
            type empty;
          }
        }
      }
      container segment-list {
        list name {
          key "name";
          leaf name {
            type string;
          }
          list index {
            tailf:cli-suppress-mode;
            tailf:cli-delete-when-empty;
            key "id";
            leaf id {
              tailf:cli-suppress-range;
              type uint32;
            }
            container mpls {
              choice mpls-choice {
                leaf adjacency {
                  type inet:ipv4-address;
                }
                leaf label {
                  type uint32;
                }
                container prefix {
                  tailf:cli-compact-syntax;
                  tailf:cli-sequence-commands {
                    tailf:cli-reset-siblings;
                  }
                  leaf address {
                    tailf:cli-drop-node-name;
                    type inet:ipv4-address;
                  }
                  leaf algorithm {
                    type uint8;
                  }
                }
              }
            }
          }
        }
      }
      list policy {
        key "name";
        leaf name {
          type string;
        }
        uses description-grouping;
        container autoroute {
          tailf:cli-add-mode;
          container include {
            leaf all {
              type empty;
            }
          }
          container metric {
            choice metric-choice {
              leaf constant {
                type uint32;
              }
              leaf relative {
                type int8;
              }
            }
          }
        }
        container color {
          tailf:cli-compact-syntax;
          tailf:cli-sequence-commands {
            tailf:cli-reset-siblings;
          }
          leaf id {
            tailf:cli-drop-node-name;
            type uint32;
          }
          leaf end-point {
            type union {
              type inet:ipv4-address;
              type inet:ipv6-address;
            }
          }
        }
        container binding-sid {
          leaf mpls {
            type uint32;
          }
        }
        container candidate-paths {
          tailf:cli-add-mode;
          presence "true";
          list preference {
            key "id";
            leaf id {
              type uint16;
            }
            uses segment-routing-preference-grouping;
          }
        }
        uses srte-perf-meas-grouping;
      }
      container pcc {
        tailf:cli-add-mode;
        container pce {
          list address {
            tailf:cli-suppress-mode;
            tailf:cli-delete-when-empty;
            tailf:cli-compact-syntax;
            key "address";
            leaf address {
              type union {
                type inet:ipv4-address;
                type inet:ipv6-address;
              }
            }
            leaf source-address {
              type inet:ipv4-address;
            }
            leaf preference {
              type uint8;
            }
            container password {
              tailf:cli-flatten-container;
              tailf:cli-compact-syntax;
              tailf:cli-sequence-commands;
              leaf type {
                tailf:cli-drop-node-name;
                type enumeration {
                  enum "clear";
                  enum "encrypted";
                }
              }
              leaf secret {
                tailf:cli-drop-node-name;
                type string;
              }
            }
          }
        }
        leaf report-all {
          type empty;
        }
        list profile {
          key "id";
          leaf id {
            type uint16;
          }
          container autoroute {
            tailf:cli-add-mode;
            container include {
              leaf all {
                type empty;
              }
            }
          }
        }
      }
      container on-demand {
        list color {
          key "id";
          leaf id {
            type uint32;
          }
          uses description-grouping;
          container authorize {
            presence "true";
            container restrict {
              tailf:cli-add-mode;
              presence "true";
              container ipv4 {
                leaf prefix-list {
                  type string;
                }
              }
            }
          }
          container candidate-paths {
            tailf:cli-add-mode;
            presence "true";
            list preference {
              key "id";
              leaf id {
                type uint16;
              }
              uses segment-routing-preference-grouping;
            }
          }
          uses srte-perf-meas-grouping;
        }
      }
      container affinity-map {
        tailf:cli-add-mode;
        list name {
          tailf:cli-suppress-mode;
          tailf:cli-delete-when-empty;
          key "name";
          leaf name {
            type string;
          }
          leaf bit-position {
            type uint8;
          }
        }
      }
    }
    container srv6 {
      tailf:cli-add-mode;
      presence "true";
      container encapsulation {
        tailf:cli-add-mode;
        leaf source-address {
          type inet:ipv6-address;
        }
      }
      container locators {
        tailf:cli-add-mode;
        list locator {
          key "name";
          leaf name {
            type string;
          }
          leaf prefix {
            type ipv6-prefix;
          }
          leaf format {
            type enumeration {
              enum "usid-f3216";
            }
          }
        }
      }
    }
  }

  grouping srte-perf-meas-grouping {
    container performance-measurement {
      tailf:cli-add-mode;
      container delay-measurement {
        tailf:cli-add-mode;
        presence "true";
        leaf profile {
          type string;
        }
        container liveness-detection {
          tailf:cli-add-mode;
          presence "true";
          leaf invalidation-action {
            type enumeration {
              enum "down";
              enum "none";
            }
          }
        }
        container reverse-path {
          tailf:cli-add-mode;
          leaf label {
            type uint32;
          }
        }
      }
    }
  }

  container system {
    container env {
      container temperature {
        container threshold {
          leaf yellow {
            type uint8;
          }
        }
      }
    }
    container mtu {
      leaf size {
        tailf:cli-drop-node-name;
        type uint16;
      }
      leaf jumbo {
        type uint16;
      }
      leaf routing {
        type uint16;
      }
    }
    container flowcontrol {
      container bus {
        leaf auto {
          type empty;
        }
      }
    }
    leaf jumbomtu {
      type uint16;
    }
  }
  container stackmaker {
    leaf name {
      type string;
    }
  }
  container diagnostic {
    container bootup {
      leaf level {
        type enumeration {
          enum "complete";
          enum "minimal";
        }
      }
    }
    container cns {
      leaf publish {
        type string;
      }
      leaf subscribe {
        type string;
      }
    }
    container monitor {
      leaf syslog {
        type empty;
      }
      container interval {
        list Module {
          tailf:cli-suppress-mode;
          tailf:cli-delete-when-empty;
          tailf:cli-compact-syntax;
          tailf:cli-sequence-commands;
          key "id";
          leaf id {
            type string;
          }
          leaf test {
            type string;
          }
          leaf interval {
            tailf:cli-drop-node-name;
            type string;
          }
          leaf milliseconds {
            tailf:cli-drop-node-name;
            type uint16;
          }
          leaf days {
            tailf:cli-drop-node-name;
            type uint8;
          }
          leaf cardindex {
            type uint16;
          }
        }
      }
      list Module {
        tailf:cli-suppress-mode;
        tailf:cli-delete-when-empty;
        tailf:cli-compact-syntax;
        tailf:cli-sequence-commands;
        key "id";
        leaf id {
          type string;
        }
        leaf test {
          type string;
        }
        leaf cardindex {
          type uint16;
        }
        leaf disable {
          type empty;
        }
      }
    }
  }
  container et-analytics {
    tailf:cli-add-mode;
    presence "true";
    container ip {
      container flow-export {
        list destination {
          tailf:cli-suppress-mode;
          tailf:cli-delete-when-empty;
          key "address port";
          leaf address {
            type inet:ipv4-address;
          }
          leaf port {
            type uint16;
          }
        }
        container destination-vrf {
          tailf:cli-drop-node-name;
          list destination {
            tailf:cli-suppress-mode;
            tailf:cli-delete-when-empty;
            key "address port vrf";
            leaf address {
              tailf:cli-suppress-range;
              type inet:ipv4-address;
            }
            leaf port {
              tailf:cli-suppress-range;
              type uint16;
            }
            leaf vrf {
              tailf:cli-expose-key-name;
              tailf:cli-suppress-range;
              type string;
            }
          }
        }
      }
    }
    leaf inactive-timeout {
      type uint32;
    }
    container whitelist {
      leaf acl {
        type exp-ip-acl-type;
      }
    }
  }
  container identity {
    list policy {
      key "name";
      leaf name {
        type string;
      }
      container inactivity-timer {
        tailf:cli-compact-syntax;
        tailf:cli-sequence-commands {
          tailf:cli-reset-siblings;
        }
        leaf value {
          tailf:cli-drop-node-name;
          type uint16;
        }
        leaf probe {
          type empty;
        }
      }
    }
  }
  container errdisable {
    container detect {
      container cause {
        leaf arp-inspection {
          type boolean;
        }
        leaf bpduguard {
          type boolean;
        }
        leaf dhcp-rate-limit {
          type boolean;
        }
        leaf dtp-flap {
          type boolean;
        }
        leaf gbic-invalid {
          type boolean;
        }
        leaf inline-power {
          type boolean;
        }
        leaf l2ptguard {
          type boolean;
        }
        leaf link-flap {
          type boolean;
        }
        leaf loopback {
          type boolean;
        }
        leaf mlacp-minlink {
          type boolean;
        }
        leaf pagp-flap {
          type boolean;
        }
        leaf pppoe-ia-rate-limit {
          type boolean;
        }
        leaf security-violation {
          type boolean;
        }
        leaf sfp-config-mismatch {
          type boolean;
        }
        leaf small-frame {
          type boolean;
        }
        leaf udld {
          type boolean;
        }
        leaf rootguard {
          type boolean;
        }
      }
    }
    container flap-setting {
      container cause {
        container dtp-flap {
          tailf:cli-compact-syntax;
          tailf:cli-sequence-commands;
          leaf max-flaps {
            type uint8;
          }
          leaf time {
            type uint8;
          }
        }
        container link-flap {
          tailf:cli-compact-syntax;
          tailf:cli-sequence-commands;
          leaf max-flaps {
            type uint8;
          }
          leaf time {
            type uint8;
          }
        }
        container pagp-flap {
          tailf:cli-compact-syntax;
          tailf:cli-sequence-commands;
          leaf max-flaps {
            type uint8;
          }
          leaf time {
            type uint8;
          }
        }
      }
    }
    container recovery {
      container cause {
        leaf arp-inspection {
          type empty;
        }
        leaf bpduguard {
          type empty;
        }
        leaf channel-misconfig {
          type empty;
        }
        leaf dhcp-rate-limit {
          type empty;
        }
        leaf dtp-flap {
          type empty;
        }
        leaf gbic-invalid {
          type empty;
        }
        leaf inline-power {
          type empty;
        }
        leaf l2ptguard {
          type empty;
        }
        leaf link-flap {
          type empty;
        }
        leaf link-monitor-failure {
          type empty;
        }
        leaf loopback {
          type empty;
        }
        leaf mac-limit {
          type empty;
        }
        leaf mlacp-minlink {
          type empty;
        }
        container oam-remote-failure-enable {
          tailf:cli-drop-node-name;
          leaf oam-remote-failure {
            type empty;
          }
        }
        container oam-remote-failure {
          leaf critical-event {
            type empty;
          }
          leaf dying-gasp {
            type empty;
          }
          leaf link-fault {
            type empty;
          }
        }
        leaf pagp-flap {
          type empty;
        }
        leaf port-mode-failure {
          type empty;
        }
        leaf pppoe-ia-rate-limit {
          type empty;
        }
        leaf psp {
          type empty;
        }
        leaf psecure-violation {
          type empty;
        }
        leaf security-violation {
          type empty;
        }
        leaf sfp-config-mismatch {
          type empty;
        }
        leaf small-frame {
          type empty;
        }
        leaf storm-control {
          type empty;
        }
        leaf udld {
          type empty;
        }
        leaf unicast-flood {
          type empty;
        }
        leaf vmps {
          type empty;
        }
        leaf mrp-miscabling {
          type empty;
        }
        leaf loopdetect {
          type empty;
        }
      }
      leaf interval {
        type uint32;
      }
    }
  }
  container monitor {
    list session {
      tailf:cli-suppress-mode;
      tailf:cli-delete-when-empty;
      key "id";
      leaf id {
        tailf:cli-suppress-range;
        type uint16;
      }
      container destination {
        list interface {
          tailf:cli-suppress-mode;
          tailf:cli-delete-when-empty;
          tailf:cli-compact-syntax;
          tailf:cli-sequence-commands {
            tailf:cli-reset-siblings;
          }
          key "id";
          leaf id {
            tailf:cli-suppress-range;
            type string;
          }
          leaf encapsulation {
            tailf:cli-optional-in-sequence;
            type enumeration {
              enum "dot1q";
              enum "isl";
              enum "replicate";
            }
          }
          leaf ingress {
            type empty;
          }
          choice ingress-choice {
            leaf vlan {
              tailf:cli-optional-in-sequence;
              type uint16;
            }
            leaf learning {
              type empty;
            }
          }
        }
        container remote {
          leaf vlan {
            type uint16;
          }
        }
      }
      container source {
        list interface {
          tailf:cli-suppress-mode;
          tailf:cli-delete-when-empty;
          key "id";
          leaf id {
            tailf:cli-suppress-range;
            type string;
          }
          leaf mode {
            tailf:cli-drop-node-name;
            type enumeration {
              enum "rx";
              enum "tx";
              enum "both";
            }
          }
        }
        list vlan {
          tailf:cli-suppress-mode;
          tailf:cli-delete-when-empty;
          key "id";
          leaf id {
            tailf:cli-suppress-range;
            type uint16;
          }
          leaf mode {
            tailf:cli-drop-node-name;
            type enumeration {
              enum "rx";
              enum "tx";
              enum "both";
            }
          }
        }
        container remote {
          leaf vlan {
            type uint16;
          }
        }
      }
      container filter {
        leaf-list vlan {
          tailf:cli-range-list-syntax;
          type uint16;
        }
        container packet-type {
          container good {
            leaf rx {
              type empty;
            }
          }
          container bad {
            leaf rx {
              type empty;
            }
          }
        }
        container ip {
          leaf access-group {
            type exp-ip-acl-type;
          }
        }
        container mac {
          leaf access-group {
            type string;
          }
        }
        container ipv6 {
          leaf access-group {
            type string;
          }
        }
        list address-type {
          tailf:cli-suppress-mode;
          tailf:cli-delete-when-empty;
          key "id";
          leaf id {
            type enumeration {
              enum "broadcast";
              enum "multicast";
              enum "unicast";
            }
          }
          leaf rx {
            type empty;
          }
          leaf tx {
            type empty;
          }
        }
      }
    }
    container session-local {
      tailf:cli-drop-node-name;
      list session {
        key "id type";
        leaf id {
          tailf:cli-suppress-range;
          type uint16;
        }
        leaf type {
          tailf:cli-expose-key-name;
          type enumeration {
            enum "local";
          }
        }
        uses description-quote-grouping;
        leaf shutdown {
          type empty;
        }
        container source {
          list interface {
            tailf:cli-suppress-mode;
            tailf:cli-delete-when-empty;
            key "id";
            leaf id {
              type string;
            }
          }
          list vlan {
            tailf:cli-suppress-mode;
            tailf:cli-delete-when-empty;
            key "id";
            leaf id {
              tailf:cli-suppress-range;
              type uint16;
            }
            leaf mode {
              tailf:cli-drop-node-name;
              type enumeration {
                enum "rx";
                enum "tx";
                enum "both";
              }
            }
          }
        }
        container destination {
          list interface {
            tailf:cli-suppress-mode;
            tailf:cli-delete-when-empty;
            key "id";
            leaf id {
              type string;
            }
          }
        }
      }
    }
    container session-rspan-source {
      tailf:cli-drop-node-name;
      list session {
        key "id";
        leaf id {
          tailf:cli-suppress-range;
          type uint16;
        }
        leaf type {
          tailf:cli-hide-in-submode;
          type enumeration {
            enum "rspan-source";
          }
        }
        uses description-quote-grouping;
        leaf shutdown {
          type empty;
        }
        container source {
          list interface {
            tailf:cli-suppress-mode;
            tailf:cli-delete-when-empty;
            key "id";
            leaf id {
              type string;
            }
          }
        }
        container destination {
          container remote {
            leaf vlan {
              type uint16;
            }
          }
        }
      }
    }
    container session-rspan-destination {
      tailf:cli-drop-node-name;
      list session {
        key "id";
        leaf id {
          tailf:cli-suppress-range;
          type uint16;
        }
        leaf type {
          tailf:cli-hide-in-submode;
          type enumeration {
            enum "rspan-destination";
          }
        }
        uses description-quote-grouping;
        container source {
          container remote {
            leaf vlan {
              type uint16;
            }
          }
        }
        container destination {
          list interface {
            tailf:cli-suppress-mode;
            tailf:cli-delete-when-empty;
            key "id";
            leaf id {
              type string;
            }
          }
        }
      }
    }
    container session-erspan-source {
      tailf:cli-drop-node-name;
      list session {
        key "id";
        leaf id {
          tailf:cli-suppress-range;
          type uint16;
        }
        leaf type {
          tailf:cli-hide-in-submode;
          type enumeration {
            enum "erspan-source";
          }
        }
        uses description-quote-grouping;
        leaf shutdown {
          type empty;
        }
        container filter {
          leaf-list vlan {
            tailf:cli-range-list-syntax;
            type uint16;
          }
        }
        container source {
          list vlan {
            tailf:cli-suppress-mode;
            tailf:cli-delete-when-empty;
            key "id";
            leaf id {
              tailf:cli-suppress-range;
              type uint16;
            }
            leaf mode {
              tailf:cli-drop-node-name;
              type enumeration {
                enum "rx";
                enum "tx";
                enum "both";
              }
            }
          }
          list interface {
            tailf:cli-suppress-mode;
            tailf:cli-delete-when-empty;
            key "id";
            leaf id {
              tailf:cli-suppress-range;
              type string;
            }
            leaf mode {
              tailf:cli-drop-node-name;
              type enumeration {
                enum "rx";
                enum "tx";
                enum "both";
              }
            }
          }
        }
        container destination {
          tailf:cli-add-mode;
          leaf erspan-id {
            type uint16;
          }
          leaf mtu {
            type uint16;
          }
          container ip {
            leaf address {
              type inet:ipv4-address;
            }
          }
          container ipv6 {
            leaf address {
              type inet:ipv6-address;
            }
          }
          container origin {
            container ip {
              leaf address {
                type inet:ipv4-address;
              }
            }
            container ipv6 {
              leaf address {
                type inet:ipv6-address;
              }
            }
          }
          leaf vrf {
            type string;
          }
        }
      }
    }
    container session-erspan-destination {
      tailf:cli-drop-node-name;
      list session {
        key "id";
        leaf id {
          tailf:cli-suppress-range;
          type uint16;
        }
        leaf type {
          tailf:cli-hide-in-submode;
          type enumeration {
            enum "erspan-destination";
          }
        }
        uses description-quote-grouping;
        leaf shutdown {
          type empty;
        }
        container destination {
          list interface {
            tailf:cli-suppress-mode;
            tailf:cli-delete-when-empty;
            key "id";
            leaf id {
              type string;
            }
          }
        }
        container source {
          tailf:cli-add-mode;
          leaf erspan-id {
            type uint16;
          }
          container ip {
            tailf:cli-compact-syntax;
            tailf:cli-sequence-commands {
              tailf:cli-reset-siblings;
            }
            leaf address {
              type inet:ipv4-address;
            }
            leaf force {
              type empty;
            }
          }
          leaf vrf {
            type string;
          }
        }
      }
    }
    container session-capture {
      tailf:cli-drop-node-name;
      list session {
        key "id";
        leaf id {
          tailf:cli-suppress-range;
          type uint16;
        }
        leaf type {
          tailf:cli-hide-in-submode;
          type enumeration {
            enum "capture";
          }
        }
        uses description-quote-grouping;
        leaf buffer-size {
          type uint16;
        }
        leaf rate-limit {
          type uint32;
        }
        container filter {
          container length {
            tailf:cli-compact-syntax;
            tailf:cli-sequence-commands {
              tailf:cli-reset-siblings;
            }
            leaf min {
              tailf:cli-drop-node-name;
              type uint16;
            }
            leaf max {
              tailf:cli-drop-node-name;
              type uint16;
            }
          }
          leaf access-group {
            type exp-ip-acl-type;
          }
          leaf-list vlan {
            tailf:cli-range-list-syntax;
            type uint16;
          }
        }
        container source {
          list vlan {
            tailf:cli-suppress-mode;
            tailf:cli-delete-when-empty;
            key "id";
            leaf id {
              tailf:cli-suppress-range;
              type uint16;
            }
            leaf mode {
              tailf:cli-drop-node-name;
              type enumeration {
                enum "rx";
                enum "tx";
                enum "both";
              }
            }
          }
          list interface {
            tailf:cli-suppress-mode;
            tailf:cli-delete-when-empty;
            key "id";
            leaf id {
              type string;
            }
            leaf mode {
              tailf:cli-drop-node-name;
              type enumeration {
                enum "rx";
                enum "tx";
                enum "both";
              }
            }
          }
        }
      }
    }
    container session-conf {
      tailf:cli-drop-node-name;
      container session {
        leaf servicemodule {
          type boolean;
        }
      }
    }
    container event-trace {
      list event-trace-list {
        tailf:cli-drop-node-name;
        tailf:cli-suppress-mode;
        tailf:cli-delete-when-empty;
        tailf:cli-compact-syntax;
        key "name";
        leaf name {
          tailf:cli-multi-word-key;
          type string;
        }
      }
    }
  }
  list network-clock-select {
    tailf:cli-suppress-mode;
    tailf:cli-delete-when-empty;
    tailf:cli-compact-syntax;
    tailf:cli-sequence-commands {
      tailf:cli-reset-siblings;
    }
    key "priority";
    leaf priority {
      type uint8;
    }
    leaf controller {
      tailf:cli-drop-node-name;
      type enumeration {
        enum "E1";
        enum "T1";
        enum "ATM";
        enum "BRI";
      }
    }
    leaf slot-port {
      tailf:cli-drop-node-name;
      type string;
    }
  }
  container network-clock {
    leaf revertive {
      type empty;
    }
    container synchronization {
      leaf automatic {
        type empty;
      }
      container ssm {
        tailf:cli-compact-syntax;
        tailf:cli-sequence-commands {
          tailf:cli-reset-siblings;
        }
        leaf option {
          type enumeration {
            enum "1";
            enum "2";
          }
        }
        leaf generation {
          tailf:cli-drop-node-name;
          type enumeration {
            enum "GEN1";
            enum "GEN2";
          }
        }
      }
      container mode {
        leaf QL-enabled {
          type empty;
        }
      }
    }
    list quality-level {
      tailf:cli-suppress-mode;
      tailf:cli-delete-when-empty;
      tailf:cli-compact-syntax;
      tailf:cli-sequence-commands {
        tailf:cli-reset-siblings;
      }
      key "name";
      leaf direction {
        tailf:cli-drop-node-name;
        tailf:cli-prefix-key;
        type enumeration {
          enum "rx";
          enum "tx";
        }
      }
      leaf value {
        tailf:cli-drop-node-name;
        tailf:cli-prefix-key;
        type enumeration {
          enum "QL-DUS";
          enum "QL-PRS";
          enum "QL-SMC";
          enum "QL-ST2";
          enum "QL-ST3";
          enum "QL-ST3E";
          enum "QL-ST4";
          enum "QL-STU";
          enum "QL-TNC";
        }
      }
      leaf interface {
        tailf:cli-drop-node-name;
        tailf:cli-prefix-key;
        type enumeration {
          enum "External";
        }
      }
      leaf name {
        type string;
      }
      leaf signal-mode {
        tailf:cli-drop-node-name;
        type enumeration {
          enum "10m";
          enum "2m";
          enum "t1";
        }
      }
      leaf frame-mode {
        tailf:cli-drop-node-name;
        type enumeration {
          enum "d4";
          enum "esf";
          enum "sf";
        }
      }
      leaf linecode {
        type enumeration {
          enum "ami";
          enum "b8zs";
          enum "hdb3";
        }
      }
      leaf line-build-out {
        type enumeration {
          enum "0-133ft";
          enum "133-266ft";
          enum "266-399ft";
          enum "399-533ft";
          enum "533-655ft";
        }
      }
    }
    list input-source {
      tailf:cli-suppress-mode;
      tailf:cli-delete-when-empty;
      tailf:cli-compact-syntax;
      key "priority";
      leaf priority {
        type uint8;
      }
      container interface {
        uses interface-name-grouping;
      }
      container ptp {
        leaf domain {
          type uint8;
        }
      }
    }
    container input-source-external {
      tailf:cli-drop-node-name;
      list input-source {
        tailf:cli-suppress-mode;
        tailf:cli-delete-when-empty;
        tailf:cli-compact-syntax;
        tailf:cli-sequence-commands {
          tailf:cli-reset-siblings;
        }
        key "External";
        leaf priority {
          tailf:cli-drop-node-name;
          tailf:cli-prefix-key;
          type uint8;
        }
        leaf External {
          tailf:cli-expose-key-name;
          type string;
        }
        leaf signal-mode {
          tailf:cli-drop-node-name;
          type enumeration {
            enum "2m";
            enum "10m";
            enum "t1";
          }
        }
        leaf frame-signal-mode {
          tailf:cli-drop-node-name;
          type enumeration {
            enum "d4";
            enum "esf";
            enum "sf";
          }
        }
        leaf linecode {
          type enumeration {
            enum "ami";
            enum "b8zs";
            enum "hdb3";
          }
        }
        leaf line-build-out {
          type enumeration {
            enum "0-133ft";
            enum "133-266ft";
            enum "266-399ft";
            enum "399-533ft";
            enum "533-655ft";
          }
        }
      }
    }
    container output-source {
      list system {
        tailf:cli-suppress-mode;
        tailf:cli-delete-when-empty;
        tailf:cli-compact-syntax;
        key "priority";
        leaf priority {
          type uint8;
        }
        list External {
          tailf:cli-suppress-mode;
          tailf:cli-delete-when-empty;
          tailf:cli-compact-syntax;
          key "name";
          leaf name {
            type union {
              type string;
              type enumeration {
                enum "R0";
                enum "R1";
              }
            }
          }
          leaf e1 {
            tailf:cli-optional-in-sequence;
            type enumeration {
              enum "cas";
              enum "crc4";
              enum "fas";
            }
          }
          leaf ohms {
            tailf:cli-drop-node-name;
            tailf:cli-optional-in-sequence;
            type enumeration {
              enum "120ohms";
              enum "75ohms";
            }
          }
          leaf signal-mode {
            tailf:cli-drop-node-name;
            tailf:cli-optional-in-sequence;
            type enumeration {
              enum "2m";
              enum "10m";
              enum "t1";
            }
          }
          leaf frame-signal-mode {
            tailf:cli-drop-node-name;
            tailf:cli-optional-in-sequence;
            type enumeration {
              enum "d4";
              enum "esf";
              enum "sf";
            }
          }
          leaf linecode {
            type enumeration {
              enum "ami";
              enum "b8zs";
              enum "hdb3";
            }
          }
          leaf line-build-out {
            type enumeration {
              enum "0-133ft";
              enum "133-266ft";
              enum "266-399ft";
              enum "399-533ft";
              enum "533-655ft";
            }
          }
        }
      }
    }
    container wait-to-restore {
      tailf:cli-compact-syntax;
      tailf:cli-sequence-commands {
        tailf:cli-reset-siblings;
      }
      leaf seconds {
        tailf:cli-drop-node-name;
        type uint32;
      }
      leaf global {
        type empty;
      }
    }
    container log {
      leaf ql-changes {
        type empty;
      }
    }
  }
  container tod-clock {
    container input-source {
      tailf:cli-compact-syntax;
      tailf:cli-sequence-commands {
        tailf:cli-reset-siblings;
      }
      leaf priority {
        tailf:cli-drop-node-name;
        type uint8;
      }
      leaf internal {
        type empty;
      }
    }
  }
  container esmc {
    leaf process {
      type empty;
    }
  }
  list trapflags {
    tailf:cli-suppress-mode;
    tailf:cli-delete-when-empty;
    key "name";
    leaf name {
      tailf:cli-multi-word-key;
      type string;
    }
  }
  container restconf {
    presence "true";
  }
  container restconf-conf {
    tailf:cli-drop-node-name;
    container restconf {
      container ipv4 {
        container access-list {
          leaf name {
            type string;
          }
        }
      }
    }
  }
  container netconf {
    leaf max-sessions {
      type uint8;
    }
    leaf lock-time {
      type uint16;
    }
    leaf max-message {
      type uint32;
    }
    container ssh {
      tailf:cli-delete-when-empty;
      presence "true";
      leaf acl {
        type uint32;
      }
    }
  }
  container gnxi {
    leaf port {
      type uint16;
    }
    leaf server {
      type empty;
    }
  }
  container netconf-yang {
    container cisco-ia {
      container snmp-trap-control {
        list trap-list {
          key "oid";
          leaf oid {
            type string;
          }
        }
      }
      container logging {
        leaf nes-log-level {
          type netconf-yang-cia-log-level;
        }
        leaf sync-log-level {
          type netconf-yang-cia-log-level;
        }
      }
    }
    container cisco-odm {
      list actions {
        key "name";
        leaf name {
          type string;
        }
      }
      leaf polling-enable {
        type empty;
      }
    }
    container feature {
      leaf candidate-datastore {
        type empty;
      }
    }
    container ssh {
      leaf port {
        type uint16;
      }
      container ipv4 {
        container access-list {
          leaf name {
            type string;
          }
        }
      }
      container ipv6 {
        container access-list {
          leaf name {
            type string;
          }
        }
      }
      container local-vrf {
        container guestshell {
          leaf enable {
            type empty;
          }
        }
      }
    }
  }
  container netconf-yang-enable {
    tailf:cli-drop-node-name;
    leaf netconf-yang {
      type empty;
    }
  }
  list tftp-server {
    tailf:cli-suppress-mode;
    tailf:cli-delete-when-empty;
    tailf:cli-compact-syntax;
    key "name";
    leaf name {
      type string;
    }
    leaf alias {
      type string;
    }
    leaf access-list {
      tailf:cli-drop-node-name;
      type std-ip-acl-type;
    }
  }
  container ftp-server {
    leaf write-enable {
      type boolean;
    }
    leaf enable {
      type empty;
    }
  }
  container radius-server {
    container load-balance {
      container method {
        container least-outstanding {
          tailf:cli-compact-syntax;
          tailf:cli-delete-when-empty;
          presence "true";
          leaf batch-size {
            type uint32;
          }
          leaf ignore-preferred-server {
            type empty;
          }
        }
      }
    }
    container attribute-11 {
      tailf:cli-drop-node-name;
      container attribute {
        tailf:cli-compact-syntax;
        tailf:cli-sequence-commands {
          tailf:cli-reset-siblings;
        }
        leaf id {
          tailf:cli-drop-node-name;
          type enumeration {
            enum "11";
          }
        }
        container default {
          tailf:cli-flatten-container;
          tailf:cli-compact-syntax;
          leaf direction {
            type enumeration {
              enum "in";
              enum "out";
            }
          }
        }
      }
    }
    container attribute {
      list attribute-list {
        tailf:cli-drop-node-name;
        tailf:cli-suppress-mode;
        tailf:cli-delete-when-empty;
        key "id";
        leaf id {
          type union {
            type uint8;
            type enumeration {
              enum "nas-port";
              enum "nas-port-id";
              enum "wireless";
            }
          }
        }
        leaf on-for-login-auth {
          type empty;
        }
        leaf support-multiple {
          type empty;
        }
        leaf mandatory {
          type empty;
        }
        leaf include-in-access-req {
          type empty;
        }
        leaf include-in-accounting-req {
          type empty;
        }
        leaf remote-id {
          type empty;
        }
        container access-request {
          leaf include {
            type empty;
          }
        }
        container send {
          container nas-port-detail {
            tailf:cli-delete-when-empty;
            presence "true";
            leaf mac-only {
              type empty;
            }
          }
        }
        container mac {
          tailf:cli-compact-syntax;
          tailf:cli-sequence-commands {
            tailf:cli-reset-siblings;
          }
          leaf format {
            type enumeration {
              enum "default";
              enum "ietf";
              enum "one-byte";
              enum "three-byte";
              enum "two-byte";
              enum "unformatted";
            }
          }
          leaf case {
            tailf:cli-drop-node-name;
            type enumeration {
              enum "lower-case";
              enum "upper-case";
            }
          }
        }
        container include {
          tailf:cli-compact-syntax;
          tailf:cli-sequence-commands {
            tailf:cli-reset-siblings;
          }
          leaf identifier {
            tailf:cli-drop-node-name;
            type enumeration {
              enum "circuit-id";
              enum "remote-id";
              enum "vendor-class-id";
            }
          }
          leaf plus {
            type enumeration {
              enum "circuit-id";
              enum "remote-id";
              enum "vendor-class-id";
            }
          }
          container plus2 {
            tailf:cli-drop-node-name;
            tailf:cli-optional-in-sequence;
            tailf:cli-flatten-container;
            leaf plus {
              type enumeration {
                enum "circuit-id";
                enum "remote-id";
                enum "vendor-class-id";
              }
            }
          }
          leaf separator {
            type string;
          }
        }
        container authentication {
          leaf call-station-id {
            type enumeration {
              enum "ap-ethmac-only";
              enum "ap-ethmac-ssid";
              enum "ap-group-name";
              enum "ap-label-address";
              enum "ap-label-address-ssid";
              enum "ap-location";
              enum "ap-macaddress";
              enum "ap-macaddress-ssid";
              enum "ap-name";
              enum "ap-name-ssid";
              enum "ipaddress";
              enum "macaddress";
              enum "site-tag-name";
              enum "vlan-id";
            }
          }
        }
      }
    }
    container dead-criteria {
      tailf:cli-compact-syntax;
      leaf time {
        type uint8;
      }
      leaf tries {
        type uint8;
      }
    }
    leaf configure-nas {
      type empty;
    }
    container throttle {
      tailf:cli-compact-syntax;
      tailf:cli-sequence-commands {
        tailf:cli-reset-siblings;
      }
      leaf accounting {
        tailf:cli-optional-in-sequence;
        type uint16;
      }
      leaf access {
        type uint16;
      }
      leaf access-timeout {
        type uint8;
      }
    }
    leaf deadtime {
      type uint16;
    }
    list host {
      tailf:cli-suppress-mode;
      tailf:cli-delete-when-empty;
      tailf:cli-compact-syntax;
      ordered-by user;
      key "id";
      leaf id {
        type inet:host;
      }
      uses radius-server-grouping;
    }
    leaf retransmit {
      type uint8;
    }
    leaf timeout {
      type uint16;
    }
    container vsa {
      container send {
        leaf accounting {
          type boolean;
        }
        leaf authentication {
          type boolean;
        }
      }
    }
    container key {
      tailf:cli-compact-syntax;
      tailf:cli-sequence-commands;
      uses password-grouping {
        refine "secret";
      }
    }
    container authorization {
      container permit {
        container missing {
          leaf service-Type {
            type empty;
          }
        }
      }
    }
  }
  container radius {
    list filter {
      key "id";
      leaf id {
        type string;
      }
      leaf match {
        tailf:cli-drop-node-name;
        tailf:cli-prefix-key;
        type enumeration {
          enum "match-all";
          enum "match-any";
        }
      }
    }
    list server {
      key "id";
      leaf id {
        type string;
      }
      container address {
        container ipv4 {
          tailf:cli-compact-syntax;
          tailf:cli-sequence-commands {
            tailf:cli-reset-siblings;
          }
          leaf host {
            tailf:cli-drop-node-name;
            type inet:host;
          }
          leaf auth-port {
            tailf:cli-optional-in-sequence;
            type uint16;
          }
          leaf acct-port {
            type uint16;
          }
        }
      }
      leaf timeout {
        type uint16;
      }
      leaf retransmit {
        type uint8;
      }
      leaf non-standard {
        type empty;
      }
      container backoff {
        container exponential {
          tailf:cli-compact-syntax;
          tailf:cli-sequence-commands {
            tailf:cli-reset-siblings;
          }
          presence "true";
          leaf max-delay {
            tailf:cli-optional-in-sequence;
            type uint8;
          }
          leaf backoff-retry {
            type uint8;
          }
        }
      }
      choice key-choice {
        container key {
          tailf:cli-compact-syntax;
          tailf:cli-sequence-commands;
          uses password-grouping {
            refine "secret";
          }
        }
        container pac {
          container key {
            tailf:cli-compact-syntax;
            tailf:cli-sequence-commands;
            uses password-grouping {
              refine "secret";
            }
          }
        }
      }
      container automate-tester {
        container username {
          tailf:cli-compact-syntax;
          tailf:cli-sequence-commands {
            tailf:cli-reset-all-siblings;
          }
          leaf name {
            tailf:cli-drop-node-name;
            type string;
          }
          leaf ignore-auth-port {
            tailf:cli-break-sequence-commands;
            type empty;
          }
          leaf ignore-acct-port {
            type empty;
          }
          leaf probe-on {
            type empty;
          }
          leaf idle-time {
            type uint16;
          }
          leaf vrf {
            type string;
          }
        }
      }
    }
  }
  container zone {
    list security {
      key "id";
      leaf id {
        type string;
      }
      leaf description {
        tailf:cli-multi-value;
        type string;
      }
      leaf protection {
        type string;
      }
    }
  }
  container zone-pair {
    list security {
      tailf:cli-sequence-commands {
        tailf:cli-reset-siblings;
      }
      key "id";
      leaf id {
        type string;
      }
      leaf source {
        tailf:cli-hide-in-submode;
        type string;
      }
      leaf destination {
        tailf:cli-hide-in-submode;
        type string;
      }
      leaf description {
        tailf:cli-break-sequence-commands;
        tailf:cli-multi-value;
        type string;
      }
      container service-policy {
        container type {
          leaf inspect {
            type string;
          }
        }
      }
    }
  }
  container alarm-profile {
    list entry-list {
      tailf:cli-drop-node-name;
      tailf:cli-sequence-commands;
      key "name";
      leaf name {
        type string;
      }
      leaf type {
        tailf:cli-drop-node-name;
        tailf:cli-hide-in-submode;
        type enumeration {
          enum "attach";
          enum "card";
          enum "chassis";
          enum "port";
        }
      }
      leaf ains {
        tailf:cli-break-sequence-commands;
        type empty;
      }
      list alarm {
        key "name";
        leaf name {
          type string;
        }
        list property {
          tailf:cli-drop-node-name;
          tailf:cli-suppress-mode;
          tailf:cli-delete-when-empty;
          key "name";
          leaf name {
            type string;
          }
          leaf suppress {
            type empty;
          }
          leaf severity {
            type enumeration {
              enum "INFO";
              enum "MINOR";
              enum "MAJOR";
              enum "CRITICAL";
            }
          }
        }
      }
    }
    container attach-chassis {
      tailf:cli-drop-node-name;
      tailf:cli-compact-syntax;
      tailf:cli-sequence-commands {
        tailf:cli-reset-siblings;
      }
      leaf name {
        tailf:cli-drop-node-name;
        type string;
      }
      leaf attach {
        type empty;
      }
      leaf chassis {
        type empty;
      }
    }
    list attach-card-list {
      tailf:cli-drop-node-name;
      tailf:cli-suppress-mode;
      tailf:cli-delete-when-empty;
      tailf:cli-compact-syntax;
      tailf:cli-sequence-commands {
        tailf:cli-reset-siblings;
      }
      key "card";
      leaf name {
        tailf:cli-drop-node-name;
        tailf:cli-prefix-key;
        type string;
      }
      leaf attach {
        tailf:cli-prefix-key;
        type empty;
      }
      leaf card {
        tailf:cli-expose-key-name;
        type string;
      }
    }
  }
  list alarm-contact {
    tailf:cli-suppress-mode;
    tailf:cli-delete-when-empty;
    key "name";
    leaf name {
      type union {
        type uint8;
        type enumeration {
          enum "all";
        }
      }
    }
    leaf description {
      tailf:cli-multi-value;
      type string;
    }
    leaf severity {
      type enumeration {
        enum "critical";
        enum "major";
        enum "minor";
      }
    }
    leaf trigger {
      type enumeration {
        enum "closed";
        enum "open";
      }
    }
  }
  leaf routing-default-optimize {
    type boolean;
  }
  container mpls {
    container atm {
      leaf disable-headend-vc {
        type empty;
      }
    }
    container oam {
      tailf:cli-add-mode;
      container echo {
        leaf revision {
          type enumeration {
            enum "3";
            enum "4";
          }
        }
      }
    }
    leaf cos-map {
      type uint8;
    }
    leaf ip {
      type boolean;
    }
    container mpls-ip-conf {
      tailf:cli-drop-node-name;
      container ip {
        leaf default-route {
          type empty;
        }
        choice propagate-ttl-choice {
          container propagate-ttl-conf {
            tailf:cli-drop-node-name;
            leaf propagate-ttl {
              type boolean;
            }
          }
          container propagate-ttl {
            leaf forwarded {
              type boolean;
            }
          }
        }
        container ttl-expiration {
          leaf pop {
            type uint8;
          }
        }
      }
    }
    container label {
      container mode {
        container all-vrfs {
          uses mpls-label-mode-grouping;
        }
        list vrf {
          tailf:cli-suppress-mode;
          tailf:cli-delete-when-empty;
          tailf:cli-compact-syntax;
          tailf:cli-sequence-commands {
            tailf:cli-reset-siblings;
          }
          key "name";
          leaf name {
            type string;
          }
          uses mpls-label-mode-grouping;
        }
      }
      container atm {
        leaf disable-headend-vc {
          type empty;
        }
      }
      leaf protocol {
        type enumeration {
          enum "ldp";
          enum "tdp";
        }
      }
      container range {
        tailf:cli-compact-syntax;
        tailf:cli-sequence-commands {
          tailf:cli-reset-siblings;
        }
        leaf min {
          tailf:cli-drop-node-name;
          type uint32;
        }
        leaf max {
          tailf:cli-drop-node-name;
          type uint32;
        }
        leaf static {
          type empty;
        }
        leaf static-min {
          tailf:cli-drop-node-name;
          type uint32;
        }
        leaf static-max {
          tailf:cli-drop-node-name;
          type uint32;
        }
      }
    }
    container feature {
      container php {
        leaf mpls {
          type empty;
        }
      }
    }
    container ldp {
      leaf advertise-labels {
        type boolean;
      }
      leaf nsr {
        type empty;
      }
      container advertise-labels-conf {
        tailf:cli-drop-node-name;
        container advertise-labels {
          list for {
            tailf:cli-suppress-mode;
            tailf:cli-delete-when-empty;
            tailf:cli-compact-syntax;
            tailf:cli-sequence-commands {
              tailf:cli-reset-siblings;
            }
            key "from";
            leaf from {
              type string;
            }
            leaf to {
              type string;
            }
          }
          container interface {
            uses interface-name-grouping;
          }
          leaf oldstyle {
            type empty;
          }
        }
      }
      container password {
        container required {
          tailf:cli-delete-when-empty;
          presence "true";
          leaf for {
            type string;
          }
        }
        container fallback {
          tailf:cli-compact-syntax;
          tailf:cli-sequence-commands;
          choice fallback-choice {
            leaf key-chain {
              type string;
            }
            case password-case {
              uses password-grouping {
                refine "secret";
              }
            }
          }
        }
        list option {
          tailf:cli-suppress-mode;
          tailf:cli-delete-when-empty;
          tailf:cli-compact-syntax;
          tailf:cli-sequence-commands {
            tailf:cli-reset-siblings;
          }
          key "id";
          leaf id {
            type uint16;
          }
          leaf for {
            type string;
          }
          choice password-choice {
            leaf key-chain {
              tailf:cli-optional-in-sequence;
              type string;
            }
            case password {
              uses password-grouping {
                refine "secret";
              }
            }
          }
        }
      }
      container atm {
        leaf control-mode {
          type enumeration {
            enum "independent";
            enum "ordered";
          }
        }
        leaf vc-merge {
          type boolean;
        }
      }
      container backoff {
        tailf:cli-sequence-commands;
        tailf:cli-compact-syntax;
        leaf initial {
          tailf:cli-drop-node-name;
          type uint32;
        }
        leaf max {
          tailf:cli-drop-node-name;
          type uint32;
        }
      }
      container discovery {
        container hello {
          leaf holdtime {
            type uint16;
          }
          leaf interval {
            type uint16;
          }
        }
        container targeted-hello {
          container accept {
            tailf:cli-delete-when-empty;
            presence "true";
            leaf from {
              type string;
            }
          }
          leaf holdtime {
            type uint16;
          }
          leaf interval {
            type uint16;
          }
        }
        leaf quick-start {
          type empty;
        }
      }
      container explicit-null {
        tailf:cli-delete-when-empty;
        presence "true";
        leaf for {
          type string;
        }
        leaf to {
          type string;
        }
      }
      leaf loop-detection {
        type empty;
      }
      container graceful-restart {
        container timers {
          leaf forwarding-holding {
            type uint16;
          }
          leaf max-recovery {
            type uint16;
          }
          leaf neighbor-liveness {
            type uint16;
          }
        }
      }
      container graceful-restart-enable {
        tailf:cli-drop-node-name;
        leaf graceful-restart {
          type empty;
        }
      }
      container tcp {
        leaf pak-priority {
          type empty;
        }
      }
      leaf holdtime {
        type uint32;
      }
      container logging {
        leaf neighbor-changes {
          type boolean;
        }
      }
      leaf maxhops {
        type uint8;
      }
      list neighbor {
        tailf:cli-suppress-mode;
        tailf:cli-delete-when-empty;
        key "address";
        leaf address {
          type inet:ipv4-address;
        }
        leaf implicit-withdraw {
          type empty;
        }
        container labels {
          leaf accept {
            type string;
          }
        }
        container password {
          tailf:cli-flatten-container;
          tailf:cli-compact-syntax;
          tailf:cli-sequence-commands;
          uses password-grouping {
            refine "secret";
          }
        }
        container targeted {
          tailf:cli-delete-when-empty;
          presence "Establish targeted session";
          leaf protocol {
            tailf:cli-drop-node-name;
            type enumeration {
              enum "ldp";
              enum "tdp";
            }
          }
        }
      }
      container request-labels {
        leaf for {
          type string;
        }
      }
      container router-id {
        tailf:cli-compact-syntax;
        tailf:cli-sequence-commands {
          tailf:cli-reset-siblings;
        }
        leaf interface {
          tailf:cli-drop-node-name;
          type string;
        }
        leaf force {
          type empty;
        }
      }
      container session {
        container protection {
          tailf:cli-compact-syntax;
          presence "true";
          leaf duration {
            type union {
              type enumeration {
                enum "infinite";
              }
              type uint32;
            }
          }
          leaf for {
            type string;
          }
        }
      }
      container label {
        tailf:cli-add-mode;
        container allocate {
          container global {
            tailf:cli-delete-when-empty;
            presence "true";
            choice global-choice {
              leaf host-routes {
                type empty;
              }
              leaf prefix-list {
                type string;
              }
            }
          }
        }
      }
      container igp {
        container sync {
          leaf holddown {
            type uint32;
          }
        }
      }
    }
    leaf mldp {
      type boolean;
    }
    container mldp-conf {
      tailf:cli-drop-node-name;
      container mldp {
        container forwarding {
          leaf recursive {
            type boolean;
          }
        }
        container path {
          leaf traffic-eng {
            type empty;
          }
        }
        container logging {
          leaf notifications {
            type empty;
          }
        }
      }
    }
    container prefix-map {
      tailf:cli-compact-syntax;
      tailf:cli-sequence-commands;
      leaf nr {
        tailf:cli-drop-node-name;
        type uint8;
      }
      leaf access-list {
        type uint8;
      }
      leaf cos-map {
        type uint8;
      }
    }
    container traffic-eng {
      container auto-bw {
        choice timers-choice {
          container timers-conf {
            tailf:cli-drop-node-name;
            container timers {
              leaf frequency {
                type uint32;
              }
            }
          }
          leaf timers {
            type boolean;
          }
        }
      }
      container link-management {
        container timers {
          leaf bandwidth-hold {
            type uint16;
          }
          leaf periodic-flooding {
            type uint16;
          }
        }
      }
      container logging {
        container lsp {
          container path-errors {
            tailf:cli-delete-when-empty;
            presence "true";
            leaf access-list {
              type exp-ip-acl-type;
            }
          }
          container preemption {
            tailf:cli-delete-when-empty;
            presence "true";
            leaf access-list {
              tailf:cli-drop-node-name;
              type exp-ip-acl-type;
            }
          }
          container reservation-errors {
            tailf:cli-delete-when-empty;
            presence "true";
            leaf access-list {
              tailf:cli-drop-node-name;
              type exp-ip-acl-type;
            }
          }
          container setups {
            tailf:cli-delete-when-empty;
            presence "true";
            leaf access-list {
              tailf:cli-drop-node-name;
              type exp-ip-acl-type;
            }
          }
          container teardowns {
            tailf:cli-delete-when-empty;
            presence "true";
            leaf access-list {
              tailf:cli-drop-node-name;
              type exp-ip-acl-type;
            }
          }
        }
        container tunnel {
          container lsp-switchover {
            tailf:cli-delete-when-empty;
            presence "true";
            leaf access-list {
              tailf:cli-drop-node-name;
              type exp-ip-acl-type;
            }
          }
          container lsp-selection {
            tailf:cli-delete-when-empty;
            presence "true";
            leaf access-list {
              tailf:cli-drop-node-name;
              type exp-ip-acl-type;
            }
          }
          container path {
            container change {
              tailf:cli-delete-when-empty;
              presence "true";
              leaf access-list {
                tailf:cli-drop-node-name;
                type exp-ip-acl-type;
              }
            }
          }
        }
      }
      container pcc {
        list peer {
          tailf:cli-suppress-mode;
          tailf:cli-delete-when-empty;
          tailf:cli-compact-syntax;
          tailf:cli-sequence-commands {
            tailf:cli-reset-siblings;
          }
          key "address";
          leaf address {
            type inet:host;
          }
          leaf source {
            tailf:cli-optional-in-sequence;
            type inet:host;
          }
          leaf precedence {
            tailf:cli-optional-in-sequence;
            type uint8;
          }
          choice option-choice {
            container password {
              tailf:cli-flatten-container;
              tailf:cli-compact-syntax;
              tailf:cli-sequence-commands;
              leaf type {
                tailf:cli-drop-node-name;
                type enumeration {
                  enum "clear";
                  enum "encrypted";
                }
              }
              leaf secret {
                tailf:cli-drop-node-name;
                type string;
              }
            }
            leaf force-autoroute {
              type empty;
            }
          }
        }
        leaf report-all {
          type empty;
        }
      }
      container auto-tunnel {
        container backup {
          presence "true";
          leaf nhop-only {
            type empty;
          }
        }
        container backup-conf {
          tailf:cli-drop-node-name;
          container backup {
            container config {
              container unnumbered-interface {
                uses interface-name-grouping;
              }
              container affinity {
                tailf:cli-compact-syntax;
                tailf:cli-sequence-commands {
                  tailf:cli-reset-siblings;
                }
                leaf value {
                  tailf:cli-drop-node-name;
                  type string;
                }
                leaf mask {
                  type string;
                }
              }
            }
            container timers {
              container removal {
                container unused {
                  tailf:cli-compact-syntax;
                  tailf:cli-sequence-commands {
                    tailf:cli-reset-siblings;
                  }
                  leaf sec-canning {
                    tailf:cli-drop-node-name;
                    type uint32;
                  }
                  leaf sec-unused {
                    tailf:cli-drop-node-name;
                    type uint32;
                  }
                }
              }
            }
            container tunnel-num {
              tailf:cli-compact-syntax;
              tailf:cli-sequence-commands {
                tailf:cli-reset-siblings;
              }
              leaf min {
                type uint16;
              }
              leaf max {
                type uint16;
              }
            }
            container srlg {
              leaf exclude {
                type enumeration {
                  enum "force";
                  enum "preferred";
                }
              }
            }
          }
        }
        container primary {
          leaf onehop {
            type empty;
          }
          container config {
            container mpls {
              leaf ip {
                type empty;
              }
            }
          }
          container tunnel-num {
            tailf:cli-compact-syntax;
            tailf:cli-sequence-commands;
            leaf min {
              type uint16;
            }
            leaf max {
              type uint16;
            }
          }
        }
        container p2p {
          presence "true";
          container config {
            container unnumbered-interface {
              uses interface-name-grouping;
            }
          }
          container tunnel-num {
            tailf:cli-compact-syntax;
            tailf:cli-sequence-commands {
              tailf:cli-reset-siblings;
            }
            leaf min {
              type uint16;
            }
            leaf max {
              type uint16;
            }
          }
        }
      }
      container path-selection {
        leaf metric {
          type enumeration {
            enum "igp";
            enum "te";
          }
        }
        container overload {
          leaf allow {
            type enumeration {
              enum "head";
              enum "middle";
              enum "tail";
            }
          }
        }
      }
      leaf fault-oam {
        type empty;
      }
      container fast-reroute {
        container timers {
          leaf promotion {
            type uint32;
          }
        }
      }
      container reoptimize {
        container events {
          leaf link-up {
            type empty;
          }
        }
        container timers {
          container delay {
            leaf cleanup {
              type uint16;
            }
            leaf installation {
              type uint16;
            }
          }
          leaf frequency {
            type uint32;
          }
        }
      }
      container signalling {
        container advertise {
          container explicit-null {
            presence "true";
          }
          container implicit-null {
            presence "true";
            leaf nr {
              tailf:cli-drop-node-name;
              type uint8;
            }
          }
        }
        container forwarding {
          leaf sync {
            type empty;
          }
        }
        container restart {
          container neighbors {
            tailf:cli-delete-when-empty;
            presence "true";
            leaf nr {
              tailf:cli-drop-node-name;
              type uint8;
            }
          }
        }
      }
      container topology {
        container holddown {
          leaf sigerr {
            type uint16;
          }
        }
      }
      leaf tunnels {
        type empty;
      }
      container lsp {
        list attributes {
          key "name";
          leaf name {
            type string;
          }
          container affinity {
            tailf:cli-compact-syntax;
            tailf:cli-sequence-commands {
              tailf:cli-reset-siblings;
            }
            leaf attributes {
              tailf:cli-drop-node-name;
              type string;
            }
            leaf mask {
              type string;
            }
          }
          container priority {
            tailf:cli-compact-syntax;
            tailf:cli-sequence-commands {
              tailf:cli-reset-siblings;
            }
            leaf setup {
              tailf:cli-drop-node-name;
              type uint8;
            }
            leaf hold {
              tailf:cli-drop-node-name;
              type uint8;
            }
          }
          container path-selection {
            leaf invalidation {
              type uint16;
            }
            leaf metric {
              type enumeration {
                enum "igp";
                enum "te";
              }
            }
            container segment-routing {
              leaf adjacency {
                type enumeration {
                  enum "protected";
                  enum "unprotected";
                }
              }
            }
          }
          leaf record-route {
            type empty;
          }
          container pce {
            tailf:cli-delete-when-empty;
            presence "true";
            container disjoint-path {
              tailf:cli-compact-syntax;
              tailf:cli-sequence-commands;
              leaf source {
                type inet:ipv4-address;
              }
              leaf type {
                type enumeration {
                  enum "link";
                  enum "node";
                  enum "srlg";
                }
              }
              leaf group-id {
                type uint32;
              }
            }
          }
          container autoroute {
            leaf destination {
              type empty;
            }
          }
          container lockdown {
            tailf:cli-delete-when-empty;
            presence "true";
            leaf sticky {
              type empty;
            }
          }
        }
      }
      leaf nsr {
        type empty;
      }
    }
    leaf propagate-cos {
      type empty;
    }
    container discovery {
      container vpn {
        leaf interval {
          type uint32;
        }
        leaf next-hop {
          type empty;
        }
      }
    }
    leaf static {
      type empty;
    }
    container static-binding {
      tailf:cli-drop-node-name;
      container static {
        container binding {
          list ipv4 {
            tailf:cli-suppress-mode;
            tailf:cli-delete-when-empty;
            key "prefix mask";
            leaf prefix {
              tailf:cli-suppress-range;
              type inet:ipv4-address;
            }
            leaf mask {
              tailf:cli-suppress-range;
              type inet:ipv4-address;
            }
            leaf input {
              tailf:cli-drop-node-name;
              type uint32;
            }
            list output {
              tailf:cli-suppress-mode;
              tailf:cli-delete-when-empty;
              key "nexthop";
              leaf nexthop {
                tailf:cli-suppress-range;
                type inet:ipv4-address;
              }
              choice label-choice {
                leaf label {
                  tailf:cli-drop-node-name;
                  type uint32;
                }
                leaf explicit-null {
                  type empty;
                }
                leaf implicit-null {
                  type empty;
                }
              }
            }
          }
        }
      }
    }
  }
  container clns {
    leaf routing {
      type empty;
    }
    list filter-set {
      tailf:cli-suppress-mode;
      tailf:cli-delete-when-empty;
      tailf:cli-compact-syntax;
      tailf:cli-sequence-commands;
      key "name";
      leaf name {
        type string;
      }
      leaf operation {
        tailf:cli-drop-node-name;
        type enumeration {
          enum "deny";
          enum "permit";
        }
      }
      leaf template {
        tailf:cli-drop-node-name;
        type string;
      }
    }
  }
  container isis {
    container optimize {
      leaf inline {
        type boolean;
      }
      leaf lspdb-walk {
        type boolean;
      }
    }
  }
  container call {
    container admission {
      leaf new-model {
        type empty;
      }
      leaf limit {
        type uint32;
      }
      leaf cpu-limit {
        type uint8;
      }
      container vpdn {
        tailf:cli-compact-syntax;
        tailf:cli-sequence-commands {
          tailf:cli-reset-siblings;
        }
        leaf charge {
          tailf:cli-drop-node-name;
          type uint16;
        }
        leaf lifetime {
          tailf:cli-drop-node-name;
          type uint8;
        }
      }
      container pppoe {
        tailf:cli-compact-syntax;
        tailf:cli-sequence-commands {
          tailf:cli-reset-siblings;
        }
        leaf charge {
          tailf:cli-drop-node-name;
          type uint16;
        }
        leaf lifetime {
          tailf:cli-drop-node-name;
          type uint8;
        }
      }
    }
    leaf rsvp-sync {
      type boolean;
    }
  }
  container fax {
    container interface-type {
      leaf fax-mail {
        type empty;
      }
    }
  }
  container mta {
    container receive {
      leaf maximum-recipients {
        type uint16;
      }
    }
  }
  container location {
    leaf admin-tag {
      type string;
    }
    container expiry {
      leaf calibrating-client {
        type uint16;
      }
      leaf client {
        type uint16;
      }
      leaf tags {
        type uint16;
      }
    }
  }
  container l3-over-l2 {
    container flush {
      leaf buffers {
        type empty;
      }
    }
  }
  container l3vpn {
    container encapsulation {
      list ip {
        key "name";
        leaf name {
          type string;
        }
        container transport {
          container ipv4 {
            presence "true";
            container source {
              uses interface-name-grouping;
            }
          }
        }
      }
    }
  }
  container router {
    container mobile {
      tailf:cli-add-mode;
      presence "true";
    }
    list bgp {
      key "as-no";
      leaf as-no {
        tailf:cli-suppress-range;
        type bgp-as-no-type;
      }
      container template {
        list peer-policy {
          key "name";
          leaf name {
            type string;
          }
          container inherit {
            tailf:cli-compact-syntax;
            tailf:cli-sequence-commands {
              tailf:cli-reset-siblings;
            }
            leaf peer-policy {
              type string;
            }
            leaf sequence {
              tailf:cli-drop-node-name;
              type uint16;
            }
          }
          uses router-bgp-peer-policy-grouping;
        }
        list peer-session {
          key "name";
          leaf name {
            type string;
          }
          leaf remote-as {
            type string;
          }
          uses description-grouping;
          container inherit {
            leaf peer-session {
              type string;
            }
          }
          leaf log-neighbor-changes {
            type empty;
          }
          container ha-mode {
            container graceful-restart {
              tailf:cli-delete-when-empty;
              presence "true";
              leaf disable {
                type empty;
              }
            }
          }
          uses router-bgp-peer-session-grouping;
        }
      }
      uses router-bgp-bgp-grouping;
      uses router-bgp-af-grouping {
        refine "neighbor/password/text";
        refine "neighbor/peer-group";
        refine "neighbor/remote-as";
        refine "neighbor";
        refine "neighbor-tag/neighbor";
      }
      container address-family {
        list ipv4 {
          tailf:cli-delete-when-empty;
          key "af";
          leaf af {
            type enumeration {
              enum "unicast";
              enum "multicast";
              enum "mdt";
              enum "tunnel";
              enum "labeled-unicast";
              enum "flowspec";
              enum "mvpn";
            }
          }
          uses router-bgp-af-grouping {
            refine "neighbor";
          }
          uses router-bgp-af2-grouping;
        }
        list ipv6 {
          tailf:cli-delete-when-empty;
          key "af";
          leaf af {
            type enumeration {
              enum "unicast";
              enum "multicast";
              enum "flowspec";
              enum "mvpn";
            }
          }
          uses router-bgp-af-grouping {
            refine "neighbor";
          }
          uses router-bgp-af2-grouping;
        }
        container with-vrf {
          tailf:cli-drop-node-name;
          list ipv4 {
            tailf:cli-suppress-mode;
            tailf:cli-delete-when-empty;
            key "af";
            leaf af {
              type enumeration {
                enum "unicast";
                enum "multicast";
                enum "mdt";
                enum "tunnel";
                enum "labeled-unicast";
                enum "flowspec";
              }
            }
            list vrf {
              tailf:cli-delete-when-empty;
              key "name";
              leaf name {
                type string;
              }
              uses router-bgp-bgp-grouping;
              uses router-bgp-af-grouping {
                refine "neighbor";
                refine "neighbor/remote-as";
              }
              uses router-bgp-af-ipvx-vrf-advertise-l2vpn-grouping;
            }
          }
        }
        container ipv6-with-vrf {
          tailf:cli-drop-node-name;
          list ipv6 {
            tailf:cli-suppress-mode;
            tailf:cli-delete-when-empty;
            key "af";
            leaf af {
              type enumeration {
                enum "unicast";
                enum "multicast";
                enum "flowspec";
              }
            }
            list vrf {
              tailf:cli-delete-when-empty;
              key "name";
              leaf name {
                type string;
              }
              uses router-bgp-bgp-grouping;
              uses router-bgp-af-grouping {
                refine "neighbor";
              }
              uses router-bgp-af-ipvx-vrf-advertise-l2vpn-grouping;
            }
          }
        }
        list vpnv4 {
          tailf:cli-delete-when-empty;
          key "af";
          leaf af {
            type enumeration {
              enum "unicast";
              enum "multicast";
              enum "flowspec";
            }
          }
          uses router-bgp-af-grouping {
            refine "neighbor";
          }
        }
        list vpnv6 {
          tailf:cli-delete-when-empty;
          key "af";
          leaf af {
            type enumeration {
              enum "unicast";
              enum "multicast";
              enum "flowspec";
            }
          }
          uses router-bgp-af-grouping {
            refine "neighbor";
          }
        }
        list l2vpn {
          tailf:cli-delete-when-empty;
          key "af";
          leaf af {
            type enumeration {
              enum "evpn";
              enum "vpls";
            }
          }
          uses router-bgp-af-grouping {
            refine "neighbor";
          }
        }
        list nsap {
          tailf:cli-delete-when-empty;
          key "af";
          leaf af {
            type enumeration {
              enum "unicast";
            }
          }
          uses router-bgp-af-grouping {
            refine "neighbor";
          }
        }
        list rtfilter {
          tailf:cli-delete-when-empty;
          key "af";
          leaf af {
            type enumeration {
              enum "unicast";
            }
          }
          uses router-bgp-af-grouping {
            refine "neighbor";
          }
        }
        container link-state {
          tailf:cli-add-mode;
          presence "true";
          leaf af {
            tailf:cli-drop-node-name;
            tailf:cli-hide-in-submode;
            type enumeration {
              enum "link-state";
            }
          }
          uses router-bgp-af-grouping {
            refine "neighbor";
          }
        }
      }
    }
    container eigrp-virtual-instance {
      tailf:cli-drop-node-name;
      list eigrp {
        key "name";
        leaf name {
          type string;
        }
        container service-family {
          container ipv4 {
            list autonomous-system {
              key "id";
              leaf id {
                type uint16;
              }
              container eigrp {
                leaf router-id {
                  type inet:ipv4-address;
                }
              }
              container sf-interface {
                container default {
                  tailf:cli-add-mode;
                  uses router-eigrp-srv-af-sf-if-grouping {
                    refine "shutdown";
                  }
                }
                list list {
                  tailf:cli-drop-node-name;
                  key "name";
                  leaf name {
                    type string;
                  }
                  uses router-eigrp-srv-af-sf-if-grouping {
                    refine "shutdown";
                  }
                }
              }
              container topology {
                container base {
                  tailf:cli-add-mode;
                  presence "true";
                  container timers {
                    leaf active-time {
                      type union {
                        type enumeration {
                          enum "disabled";
                        }
                        type uint16;
                      }
                    }
                  }
                }
              }
              list neighbor {
                tailf:cli-suppress-mode;
                tailf:cli-delete-when-empty;
                key "address interface";
                leaf address {
                  type inet:ipv4-address;
                }
                leaf interface {
                  type string;
                }
                leaf remote {
                  type uint8;
                }
              }
            }
          }
        }
        container address-family {
          container ipv4-vrf {
            tailf:cli-drop-node-name;
            container ipv4 {
              container unicast {
                list vrf {
                  tailf:cli-sequence-commands;
                  key "name";
                  leaf name {
                    type string;
                  }
                  leaf autonomous-system {
                    tailf:cli-hide-in-submode;
                    type uint16;
                  }
                  uses router-eigrp-af-virtual-instance-grouping;
                }
              }
            }
          }
          container ipv4 {
            tailf:cli-add-mode;
            tailf:cli-sequence-commands;
            presence "true";
            leaf af {
              tailf:cli-drop-node-name;
              tailf:cli-hide-in-submode;
              type enumeration {
                enum "unicast";
                enum "multicast";
              }
            }
            leaf autonomous-system {
              tailf:cli-hide-in-submode;
              type uint16;
            }
            uses router-eigrp-af-virtual-instance-grouping;
          }
          container ipv6-vrf {
            tailf:cli-drop-node-name;
            container ipv6 {
              container unicast {
                list vrf {
                  tailf:cli-sequence-commands;
                  key "name";
                  leaf name {
                    type string;
                  }
                  leaf autonomous-system {
                    tailf:cli-hide-in-submode;
                    type uint16;
                  }
                  uses router-eigrp-af-virtual-instance-grouping;
                }
              }
            }
          }
          container ipv6 {
            tailf:cli-add-mode;
            tailf:cli-sequence-commands;
            presence "true";
            leaf af {
              tailf:cli-drop-node-name;
              tailf:cli-hide-in-submode;
              type enumeration {
                enum "unicast";
                enum "multicast";
              }
            }
            leaf autonomous-system {
              tailf:cli-hide-in-submode;
              type uint16;
            }
            uses router-eigrp-af-virtual-instance-grouping;
          }
        }
      }
    }
    list eigrp {
      key "as-no";
      leaf as-no {
        type uint16;
      }
      container address-family {
        container ipv4 {
          list vrf {
            key "name";
            leaf name {
              type string;
            }
            leaf autonomous-system {
              type uint16;
            }
            uses router-eigrp-grouping;
            uses router-eigrp-base-grouping;
          }
        }
      }
      uses router-eigrp-grouping;
      uses router-eigrp-base-grouping;
    }
    list ospfv3 {
      key "id";
      leaf id {
        tailf:cli-suppress-range;
        type uint16;
      }
      uses router-ospfv3-grouping;
      uses router-ospfv3-common-grouping;
      leaf shutdown {
        type empty;
      }
      container address-family {
        container ipv4 {
          container unicast {
            tailf:cli-add-mode;
            uses router-ospfv3-grouping;
            uses router-ospfv3-common-grouping;
            uses router-ospf-common-af-grouping;
            uses router-ospfv3-af-grouping;
          }
        }
        container ipv6 {
          container unicast {
            tailf:cli-add-mode;
            uses router-ospfv3-grouping;
            uses router-ospfv3-common-grouping;
            uses router-ospf-common-af-grouping;
            uses router-ospfv3-af-grouping;
          }
        }
        container ipv4-vrf {
          tailf:cli-drop-node-name;
          container ipv4 {
            container unicast {
              list vrf {
                key "name";
                leaf name {
                  type string;
                }
                uses router-ospfv3-grouping;
                uses router-ospfv3-common-grouping;
                uses router-ospf-common-af-grouping;
                uses router-ospfv3-af-grouping;
              }
            }
          }
        }
        container ipv6-vrf {
          tailf:cli-drop-node-name;
          container ipv6 {
            container unicast {
              list vrf {
                key "name";
                leaf name {
                  type string;
                }
                uses router-ospfv3-grouping;
                uses router-ospfv3-common-grouping;
                uses router-ospf-common-af-grouping;
                uses router-ospfv3-af-grouping;
              }
            }
          }
        }
      }
    }
    list ospf {
      tailf:cli-sequence-commands {
        tailf:cli-reset-siblings;
      }
      key "id";
      leaf id {
        tailf:cli-suppress-range;
        type uint16;
      }
      leaf vrf {
        tailf:cli-hide-in-submode;
        type string;
      }
      uses router-ospf-common-grouping {
        refine "area" {
          tailf:cli-break-sequence-commands;
        }
      }
      uses router-ospf-common-af-grouping;
      uses router-ospf-grouping;
    }
    container isis {
      tailf:cli-add-mode;
      presence "true";
      uses router-isis-grouping;
    }
    container isis-container {
      tailf:cli-drop-node-name;
      list isis {
        key "area-tag";
        leaf area-tag {
          type string;
        }
        uses router-isis-grouping;
      }
    }
    container rip {
      tailf:cli-add-mode;
      uses router-rip-grouping;
      container address-family {
        container ipv4 {
          container unicast {
            tailf:cli-add-mode;
            uses router-rip-grouping;
          }
          list vrf {
            key "name";
            leaf name {
              type string;
            }
            uses router-rip-af-grouping;
          }
        }
      }
    }
    container lisp {
      tailf:cli-add-mode;
      presence "true";
      uses router-lisp-grouping {
        refine "eid-table/vrf/name";
      }
    }
    container router-lisp {
      tailf:cli-drop-node-name;
      list lisp {
        key "id";
        leaf id {
          type uint8;
        }
        uses router-lisp-grouping {
          refine "eid-table/vrf/name";
        }
      }
    }
    container odr {
      tailf:cli-add-mode;
      presence "true";
    }
  }
  container vstack-conf {
    tailf:cli-drop-node-name;
    container vstack {
      leaf director {
        type inet:ipv4-address;
      }
      leaf basic {
        type empty;
      }
    }
  }
  container vstack-no {
    tailf:cli-drop-node-name;
    leaf vstack {
      type boolean;
    }
  }
  container snmp {
    container ifmib {
      container ifindex {
        leaf persist {
          type empty;
        }
      }
      container ifalias {
        leaf long {
          type empty;
        }
      }
      container trap {
        leaf throttle {
          type empty;
        }
      }
    }
    container mib {
      list community-map {
        tailf:cli-suppress-mode;
        tailf:cli-delete-when-empty;
        tailf:cli-compact-syntax;
        tailf:cli-sequence-commands {
          tailf:cli-reset-siblings;
        }
        key "name";
        leaf name {
          type string;
        }
        leaf context {
          tailf:cli-optional-in-sequence;
          type string;
        }
        leaf engineid {
          tailf:cli-optional-in-sequence;
          type string;
        }
        leaf security-name {
          tailf:cli-optional-in-sequence;
          type string;
        }
        leaf target-list {
          type string;
        }
      }
      container bulkstat {
        list object-list {
          tailf:cli-suppress-mode;
          tailf:cli-delete-when-empty;
          key "name";
          leaf name {
            type string;
          }
        }
      }
      container persist {
        leaf v3mibs {
          type empty;
        }
        leaf dsmib {
          type empty;
        }
        leaf cbqos {
          type empty;
        }
        leaf circuit {
          type empty;
        }
      }
      leaf nhrp {
        type empty;
      }
      container flash {
        container cache {
          tailf:cli-delete-when-empty;
          presence "true";
          leaf interval {
            type uint8;
          }
        }
      }
    }
  }
  list menu {
    tailf:cli-suppress-mode;
    tailf:cli-delete-when-empty;
    key "name";
    leaf name {
      type string;
    }
    leaf title {
      type string;
    }
    leaf prompt {
      type string;
    }
    list text {
      tailf:cli-suppress-mode;
      tailf:cli-delete-when-empty;
      key "item";
      leaf item {
        type string;
      }
      leaf line {
        tailf:cli-drop-node-name;
        tailf:cli-multi-value;
        type string;
      }
    }
    list command {
      tailf:cli-suppress-mode;
      tailf:cli-delete-when-empty;
      key "item";
      leaf item {
        type string;
      }
      leaf command {
        tailf:cli-drop-node-name;
        tailf:cli-multi-value;
        type string;
      }
    }
    list options {
      tailf:cli-suppress-mode;
      tailf:cli-delete-when-empty;
      tailf:cli-compact-syntax;
      tailf:cli-sequence-commands {
        tailf:cli-reset-siblings;
      }
      key "item";
      leaf item {
        type string;
      }
      leaf pause {
        tailf:cli-optional-in-sequence;
        type empty;
      }
      leaf login {
        type empty;
      }
    }
    leaf clear-screen {
      type empty;
    }
    leaf status-line {
      type empty;
    }
    leaf line-mode {
      type empty;
    }
    leaf single-space {
      type empty;
    }
  }
  container cpu {
    container traffic {
      container qos {
        container cos {
          leaf value {
            tailf:cli-drop-node-name;
            type uint8;
          }
        }
      }
    }
  }
  container snmp-server {
    list user {
      tailf:cli-suppress-mode;
      tailf:cli-delete-when-empty;
      tailf:cli-compact-syntax;
      tailf:cli-sequence-commands {
        tailf:cli-reset-siblings;
      }
      key "name";
      leaf name {
        type string;
      }
      leaf group {
        tailf:cli-drop-node-name;
        type string;
      }
      uses snmp-server-user-grouping;
    }
    container user-remote {
      tailf:cli-drop-node-name;
      list user {
        tailf:cli-suppress-mode;
        tailf:cli-delete-when-empty;
        tailf:cli-compact-syntax;
        tailf:cli-sequence-commands {
          tailf:cli-reset-siblings;
        }
        key "name remote";
        leaf name {
          type string;
        }
        leaf group {
          tailf:cli-drop-node-name;
          tailf:cli-prefix-key {
            tailf:cli-before-key "2";
          }
          type string;
        }
        leaf remote {
          tailf:cli-expose-key-name;
          type inet:host;
        }
        leaf udp-port {
          tailf:cli-optional-in-sequence;
          type uint16;
        }
        uses snmp-server-user-grouping;
      }
    }
    leaf chassis-id {
      tailf:cli-multi-value;
      type string;
    }
    list community {
      tailf:cli-suppress-mode;
      tailf:cli-delete-when-empty;
      tailf:cli-compact-syntax;
      tailf:cli-sequence-commands {
        tailf:cli-reset-siblings;
      }
      key "name";
      leaf name {
        type string;
      }
      leaf view {
        tailf:cli-optional-in-sequence;
        type string;
      }
      choice access-choice {
        leaf RO {
          tailf:cli-optional-in-sequence;
          type empty;
        }
        leaf RW {
          tailf:cli-optional-in-sequence;
          type empty;
        }
      }
      leaf ipv6 {
        tailf:cli-optional-in-sequence;
        type string;
      }
      leaf access-list-name {
        tailf:cli-drop-node-name;
        type std-ip-acl-type;
      }
    }
    leaf contact {
      type string;
    }
    list context {
      tailf:cli-suppress-mode;
      tailf:cli-delete-when-empty;
      key "name";
      leaf name {
        type string;
      }
    }
    container drop {
      container report {
        container access {
          choice acl-choice {
            leaf ipv6 {
              type string;
            }
            leaf acl {
              tailf:cli-drop-node-name;
              type union {
                type uint8;
                type string;
              }
            }
          }
        }
      }
      leaf vrf-traffic {
        type empty;
      }
    }
    container enable {
      choice enable-choice {
        leaf informs {
          type empty;
        }
        list traps {
          tailf:cli-suppress-mode;
          tailf:cli-delete-when-empty;
          key "name";
          leaf name {
            tailf:cli-multi-word-key;
            type string;
          }
        }
        leaf all-traps {
          type empty;
        }
      }
    }
    container engineID {
      leaf local {
        type string;
      }
      list remote {
        tailf:cli-suppress-mode;
        tailf:cli-delete-when-empty;
        tailf:cli-compact-syntax;
        tailf:cli-sequence-commands;
        key "address";
        leaf address {
          type inet:host;
        }
        leaf udp-port {
          tailf:cli-optional-in-sequence;
          type uint16;
        }
        leaf vrf {
          tailf:cli-optional-in-sequence;
          type string;
        }
        leaf engineid-string {
          tailf:cli-drop-node-name;
          type string;
        }
      }
    }
    list group {
      tailf:cli-suppress-mode;
      tailf:cli-delete-when-empty;
      tailf:cli-compact-syntax;
      tailf:cli-sequence-commands {
        tailf:cli-reset-siblings;
      }
      key "id model";
      leaf id {
        tailf:cli-suppress-range;
        type string;
      }
      leaf model {
        tailf:cli-suppress-range;
        type enumeration {
          enum "v1";
          enum "v2c";
          enum "v3";
        }
      }
      list level {
        tailf:cli-drop-node-name;
        tailf:cli-suppress-mode;
        tailf:cli-delete-when-empty;
        tailf:cli-compact-syntax;
        tailf:cli-sequence-commands {
          tailf:cli-reset-siblings;
        }
        key "name";
        leaf name {
          tailf:cli-suppress-range;
          type enumeration {
            enum "auth";
            enum "noauth";
            enum "priv";
          }
        }
        uses snmp-server-group-grouping;
      }
      uses snmp-server-group-grouping;
    }
    container group-context {
      tailf:cli-drop-node-name;
      list group {
        tailf:cli-suppress-mode;
        tailf:cli-delete-when-empty;
        tailf:cli-compact-syntax;
        tailf:cli-sequence-commands {
          tailf:cli-reset-siblings;
        }
        key "id model context";
        leaf id {
          tailf:cli-suppress-range;
          type string;
        }
        leaf model {
          tailf:cli-suppress-range;
          type enumeration {
            enum "v1";
            enum "v2c";
          }
        }
        leaf context {
          tailf:cli-suppress-range;
          tailf:cli-expose-key-name;
          type string;
        }
        uses snmp-server-group-grouping;
      }
    }
    container group-v3-context {
      tailf:cli-drop-node-name;
      list group {
        tailf:cli-suppress-mode;
        tailf:cli-delete-when-empty;
        tailf:cli-compact-syntax;
        tailf:cli-sequence-commands {
          tailf:cli-reset-siblings;
        }
        key "id model level context";
        leaf id {
          tailf:cli-suppress-range;
          type string;
        }
        leaf model {
          tailf:cli-suppress-range;
          type enumeration {
            enum "v3";
          }
        }
        leaf level {
          tailf:cli-suppress-range;
          type enumeration {
            enum "auth";
            enum "noauth";
            enum "priv";
          }
        }
        leaf context {
          tailf:cli-suppress-range;
          tailf:cli-expose-key-name;
          type string;
        }
        uses snmp-server-group-grouping;
      }
    }
    container community-list {
      tailf:cli-drop-node-name;
      list host {
        tailf:cli-suppress-mode;
        tailf:cli-delete-when-empty;
        tailf:cli-compact-syntax;
        tailf:cli-sequence-commands {
          tailf:cli-reset-siblings;
        }
        key "ip-address message-type version community-string";
        leaf ip-address {
          tailf:cli-case-sensitive;
          tailf:cli-suppress-range;
          type inet:host;
        }
        uses snmp-server-host-new-grouping;
      }
      container host-vrf {
        tailf:cli-drop-node-name;
        list host {
          tailf:cli-suppress-mode;
          tailf:cli-delete-when-empty;
          tailf:cli-compact-syntax;
          tailf:cli-sequence-commands {
            tailf:cli-reset-siblings;
          }
          key "ip-address vrf message-type version community-string";
          leaf ip-address {
            tailf:cli-case-sensitive;
            tailf:cli-suppress-range;
            type inet:host;
          }
          leaf vrf {
            tailf:cli-expose-key-name;
            type string;
          }
          uses snmp-server-host-new-grouping;
        }
      }
    }
    list host {
      tailf:cli-suppress-mode;
      tailf:cli-delete-when-empty;
      tailf:cli-compact-syntax;
      tailf:cli-sequence-commands {
        tailf:cli-reset-all-siblings;
      }
      key "ip-address message-type";
      leaf ip-address {
        tailf:cli-case-sensitive;
        tailf:cli-suppress-range;
        type inet:host;
      }
      uses snmp-server-host-grouping;
    }
    container host-vrf {
      tailf:cli-drop-node-name;
      list host {
        tailf:cli-suppress-mode;
        tailf:cli-delete-when-empty;
        tailf:cli-compact-syntax;
        tailf:cli-sequence-commands {
          tailf:cli-reset-all-siblings;
        }
        key "ip-address vrf message-type";
        leaf ip-address {
          tailf:cli-case-sensitive;
          tailf:cli-suppress-range;
          type inet:host;
        }
        leaf vrf {
          tailf:cli-expose-key-name;
          type string;
        }
        uses snmp-server-host-grouping;
      }
    }
    container ip {
      leaf dscp {
        type uint8;
      }
      leaf precedence {
        type uint8;
      }
    }
    container ifindex {
      leaf persist {
        type empty;
      }
    }
    leaf location {
      type string;
    }
    container manager {
      presence "true";
      leaf session-timeout {
        type uint32;
      }
    }
    leaf packetsize {
      type uint16;
    }
    leaf queue-length {
      type uint16;
    }
    container queue-limit {
      leaf notification-host {
        type uint16;
      }
    }
    leaf tftp-server-list {
      type std-acl-type;
    }
    leaf system-shutdown {
      type empty;
    }
    container file-transfer {
      list access-group {
        tailf:cli-suppress-mode;
        tailf:cli-delete-when-empty;
        key "name";
        leaf name {
          type std-ip-acl-type;
        }
        leaf-list protocol {
          type enumeration {
            enum "ftp";
            enum "rcp";
            enum "scp";
            enum "sftp";
            enum "tftp";
          }
        }
      }
    }
    container source-interface {
      container informs {
        uses interface-name-grouping;
      }
      container traps {
        uses interface-name-grouping;
      }
    }
    container trap {
      leaf timeout {
        type uint16;
      }
      leaf timestamp {
        type empty;
      }
      container authentication {
        leaf vrf {
          type boolean;
        }
        leaf unknown-context {
          type boolean;
        }
      }
      container link {
        leaf ietf {
          type empty;
        }
        leaf switchover {
          type empty;
        }
      }
    }
    leaf sparse-tables {
      type boolean;
    }
    container trap-source {
      uses interface-name-grouping;
    }
    leaf trap-timeout {
      type uint16;
    }
    list view {
      tailf:cli-suppress-mode;
      tailf:cli-delete-when-empty;
      tailf:cli-compact-syntax;
      key "name mib";
      leaf name {
        type string;
      }
      leaf mib {
        type string;
      }
      leaf inc-exl {
        tailf:cli-drop-node-name;
        type enumeration {
          enum "excluded";
          enum "included";
        }
      }
    }
    container inform {
      tailf:cli-compact-syntax;
      leaf retries {
        type uint8;
      }
      leaf timeout {
        type uint32;
      }
      leaf pending {
        type uint32;
      }
    }
  }
  container rtr {
    list entry {
      tailf:cli-drop-node-name;
      key "id";
      leaf id {
        type uint32;
      }
      container type {
        choice type-choice {
          container echo {
            tailf:cli-compact-syntax;
            tailf:cli-sequence-commands {
              tailf:cli-reset-siblings;
            }
            leaf protocol {
              type enumeration {
                enum "ipIcmpEcho";
              }
            }
            leaf ipaddr {
              tailf:cli-drop-node-name;
              type inet:host;
            }
            leaf source-ipaddr {
              type inet:host;
            }
          }
        }
      }
      leaf owner {
        tailf:cli-multi-value;
        type string;
      }
      leaf tag {
        tailf:cli-multi-value;
        type string;
      }
      leaf threshold {
        type uint32;
      }
      leaf frequency {
        type uint32;
      }
    }
    list schedule {
      tailf:cli-suppress-mode;
      tailf:cli-delete-when-empty;
      tailf:cli-compact-syntax;
      key "id";
      leaf id {
        type uint32;
      }
      container start-time {
        choice time-choice {
          container now {
            presence "true";
          }
        }
      }
    }
    container responder {
      presence "true";
    }
    leaf key-chain {
      type string;
    }
  }
  container ipc {
    container zone {
      container default {
        tailf:cli-add-mode;
        presence "true";
      }
    }
  }
  container cts {
    container server {
      list test {
        tailf:cli-suppress-mode;
        tailf:cli-delete-when-empty;
        key "name";
        leaf name {
          type union {
            type inet:ipv4-address;
            type enumeration {
              enum "all";
            }
          }
        }
        leaf no-enable {
          type empty;
        }
        leaf deadtime {
          type uint32;
        }
      }
    }
    container authorization {
      leaf list {
        type string;
      }
    }
    container credentials {
      tailf:cli-compact-syntax;
      tailf:cli-sequence-commands;
      leaf id {
        type string;
      }
      leaf password {
        type tailf:aes-cfb-128-encrypted-string;
      }
    }
    leaf sgt {
      type uint16;
    }
    container logging {
      leaf verbose {
        type empty;
      }
    }
    container role-based {
      list sgt-map {
        tailf:cli-suppress-mode;
        tailf:cli-delete-when-empty;
        key "address";
        leaf address {
          type string;
        }
        leaf sgt {
          type uint16;
        }
      }
      container sgt-map-vrf {
        tailf:cli-drop-node-name;
        list sgt-map {
          tailf:cli-suppress-mode;
          tailf:cli-delete-when-empty;
          key "vrf address";
          leaf vrf {
            tailf:cli-expose-key-name;
            type string;
          }
          leaf address {
            type string;
          }
          leaf sgt {
            type uint16;
          }
        }
      }
      leaf enforcement {
        type empty;
      }
      container enforcement-conf {
        tailf:cli-drop-node-name;
        container enforcement {
          leaf-list vlan-list {
            tailf:cli-range-list-syntax;
            type uint16;
          }
          leaf logging-interval {
            type uint32;
          }
        }
      }
    }
    container sxp {
      leaf enable {
        type empty;
      }
      container default {
        leaf source-ip {
          type inet:ipv4-address;
        }
        container password {
          tailf:cli-compact-syntax;
          tailf:cli-sequence-commands;
          uses password-grouping {
            refine "secret";
          }
        }
      }
      container retry {
        leaf period {
          type uint32;
        }
      }
      container connection {
        list peer {
          tailf:cli-suppress-mode;
          tailf:cli-delete-when-empty;
          tailf:cli-compact-syntax;
          tailf:cli-sequence-commands {
            tailf:cli-reset-siblings;
          }
          key "address";
          leaf address {
            type inet:ipv4-address;
          }
          leaf source {
            tailf:cli-optional-in-sequence;
            type inet:ipv4-address;
          }
          leaf password {
            type enumeration {
              enum "default";
              enum "none";
            }
          }
          leaf mode {
            type enumeration {
              enum "local";
              enum "peer";
            }
          }
          leaf direction {
            tailf:cli-drop-node-name;
            type enumeration {
              enum "listener";
              enum "speaker";
              enum "both";
            }
          }
          leaf hold-time {
            tailf:cli-optional-in-sequence;
            type uint16;
          }
          leaf vrf {
            type string;
          }
        }
      }
    }
  }
  container mab {
    container request {
      container format {
        container attribute {
          container thirtytwo {
            tailf:alt-name "32";
            container vlan {
              leaf access-vlan {
                type empty;
              }
            }
          }
        }
      }
    }
  }
  container pfr {
    container master {
      tailf:cli-add-mode;
      presence "true";
      leaf policy-rules {
        type string;
      }
      container max-range-utilization {
        leaf percent {
          type uint8;
        }
      }
      leaf logging {
        type empty;
      }
      list border {
        key "address";
        leaf address {
          type inet:ipv4-address;
        }
        leaf key-chain {
          tailf:cli-hide-in-submode;
          type string;
        }
        list interface {
          tailf:cli-suppress-mode;
          tailf:cli-delete-when-empty;
          key "name";
          leaf name {
            type string;
          }
          leaf internal {
            type empty;
          }
        }
        container interface-external {
          tailf:cli-drop-node-name;
          list interface {
            key "name";
            leaf name {
              type string;
            }
            leaf external {
              tailf:cli-hide-in-submode;
              type empty;
            }
            leaf shutdown {
              type empty;
            }
            container max-xmit-utilization {
              choice max-xmit-utilization {
                leaf absolute {
                  type uint32;
                }
                leaf percentage {
                  type uint8;
                }
              }
            }
          }
        }
      }
      container learn {
        tailf:cli-add-mode;
        container prefixes {
          tailf:cli-compact-syntax;
          tailf:cli-sequence-commands {
            tailf:cli-reset-siblings;
          }
          leaf value {
            tailf:cli-drop-node-name;
            type uint32;
          }
          leaf applications {
            type uint32;
          }
        }
        container traffic-class {
          container filter {
            leaf access-list {
              type string;
            }
          }
        }
        list list {
          key "seq";
          leaf seq {
            tailf:cli-expose-key-name;
            type uint16;
          }
          leaf refname {
            tailf:cli-hide-in-submode;
            type string;
          }
          container traffic-class {
            container access-list {
              tailf:cli-compact-syntax;
              tailf:cli-sequence-commands {
                tailf:cli-reset-siblings;
              }
              leaf name {
                tailf:cli-drop-node-name;
                type string;
              }
              leaf filter {
                type string;
              }
            }
          }
          container aggregation-type {
            leaf prefix-length {
              type uint8;
            }
          }
          container count {
            tailf:cli-compact-syntax;
            tailf:cli-sequence-commands {
              tailf:cli-reset-siblings;
            }
            leaf value {
              tailf:cli-drop-node-name;
              type uint32;
            }
            leaf max {
              type uint32;
            }
          }
          leaf throughput {
            type empty;
          }
        }
      }
      container max {
        container range {
          container receive {
            leaf percent {
              type uint8;
            }
          }
        }
      }
      leaf holddown {
        type uint16;
      }
      container backoff {
        tailf:cli-compact-syntax;
        tailf:cli-sequence-commands {
          tailf:cli-reset-siblings;
        }
        leaf minimum {
          tailf:cli-drop-node-name;
          type uint16;
        }
        leaf maximum {
          tailf:cli-drop-node-name;
          type uint16;
        }
        leaf optional {
          tailf:cli-drop-node-name;
          type uint16;
        }
      }
      container mode {
        container monitor {
          container active {
            tailf:cli-delete-when-empty;
            presence "true";
            leaf throughput {
              type empty;
            }
          }
        }
      }
      container resolve {
        container delay {
          tailf:cli-compact-syntax;
          tailf:cli-sequence-commands {
            tailf:cli-reset-siblings;
          }
          leaf priority {
            type uint8;
          }
          leaf variance {
            type uint8;
          }
        }
      }
    }
    container border {
      tailf:cli-add-mode;
      presence "true";
      leaf shutdown {
        type empty;
      }
      container local {
        tailf:cli-flatten-container;
        tailf:cli-compact-syntax;
        uses interface-name-grouping;
      }
      container master {
        tailf:cli-compact-syntax;
        tailf:cli-sequence-commands {
          tailf:cli-reset-siblings;
        }
        leaf address {
          tailf:cli-drop-node-name;
          type inet:ipv4-address;
        }
        leaf key-chain {
          type string;
        }
      }
    }
  }
  list pfr-map {
    key "name id";
    leaf name {
      type string;
    }
    leaf id {
      type uint16;
    }
    container match {
      container pfr {
        container learn {
          leaf delay {
            type empty;
          }
          leaf inside {
            type empty;
          }
          leaf throughput {
            type empty;
          }
          leaf list {
            type string;
          }
        }
      }
    }
    container set {
      container mode {
        container route {
          tailf:cli-delete-when-empty;
          presence "true";
          choice route-choice {
            leaf control {
              type empty;
            }
            leaf observe {
              type empty;
            }
          }
        }
      }
    }
  }
  container license {
    container accept {
      container end {
        container user {
          tailf:cli-compact-syntax;
          tailf:cli-sequence-commands {
            tailf:cli-reset-siblings;
          }
          leaf agreement {
            type empty;
          }
          leaf force {
            type empty;
          }
        }
      }
    }
    list feature {
      tailf:cli-suppress-mode;
      tailf:cli-delete-when-empty;
      ordered-by user;
      key "line";
      leaf line {
        tailf:cli-multi-word-key;
        type string;
      }
    }
    list boot {
      tailf:cli-suppress-mode;
      tailf:cli-delete-when-empty;
      ordered-by user;
      key "line";
      leaf line {
        tailf:cli-multi-word-key;
        type string;
      }
    }
    container smart {
      leaf enable {
        type empty;
      }
      container usage {
        leaf interval {
          type uint16;
        }
      }
      container utility {
        container customer_info {
          leaf id {
            type string;
          }
          leaf name {
            type string;
          }
          leaf street {
            type string;
          }
          leaf city {
            type string;
          }
          leaf state {
            type string;
          }
          leaf country {
            type string;
          }
          leaf postalcode {
            type string;
          }
        }
      }
      container utility-enable {
        tailf:cli-drop-node-name;
        leaf utility {
          type empty;
        }
      }
      leaf url {
        type string;
      }
      container url-cslu {
        tailf:cli-drop-node-name;
        container url {
          leaf cslu {
            type string;
          }
        }
      }
      container url-smart {
        tailf:cli-drop-node-name;
        container url {
          leaf smart {
            type string;
          }
        }
      }
      container url-utility {
        tailf:cli-drop-node-name;
        container url {
          leaf utility {
            type string;
          }
        }
      }
      leaf transport {
        type enumeration {
          enum "smart";
          enum "callhome";
          enum "off";
          enum "cslu";
          enum "automatic";
        }
      }
      leaf reservation {
        type empty;
      }
      container proxy {
        leaf address {
          type string;
        }
        leaf port {
          type string;
        }
      }
    }
    container solution {
      container level {
        leaf securityk9 {
          type empty;
        }
      }
    }
  }
  container vxml {
    leaf logging-tag {
      type empty;
    }
  }
  container setup {
    leaf express {
      type boolean;
    }
  }
  container trunk {
    list group {
      key "name";
      leaf name {
        type string;
      }
      container hunt-scheme {
        choice hunt-scheme-choice {
          container round-robin {
            tailf:cli-compact-syntax;
            tailf:cli-delete-when-empty;
            presence "true";
          }
          leaf random {
            type empty;
          }
          leaf sequential {
            type empty;
          }
        }
      }
    }
  }
  container gw-accounting {
    choice gw-accounting-choice {
      container syslog {
        tailf:cli-delete-when-empty;
        presence "true";
        leaf stats {
          type empty;
        }
      }
      leaf aaa {
        type empty;
      }
      leaf file {
        type empty;
      }
      container h323 {
        tailf:cli-delete-when-empty;
        presence "true";
        leaf vsa {
          type empty;
        }
      }
      leaf voip {
        type empty;
      }
    }
  }
  list voice-card {
    key "slot";
    leaf slot {
      type string;
    }
    container codec {
      container complexity {
        leaf setting {
          tailf:cli-drop-node-name;
          type enumeration {
            enum "flex";
            enum "high";
            enum "medium";
            enum "secure";
          }
        }
      }
    }
    leaf dspfarm {
      type empty;
    }
    container dsp {
      container services {
        leaf dspfarm {
          type empty;
        }
      }
    }
    leaf watchdog {
      type boolean;
    }
  }
  container voice {
    container rtp {
      leaf send-recv {
        type empty;
      }
    }
    container service {
      container voip {
        tailf:cli-add-mode;
        presence "true";
        container ip {
          container address {
            container trusted {
              container list {
                tailf:cli-add-mode;
                presence "true";
                list ipv4 {
                  tailf:cli-suppress-mode;
                  tailf:cli-delete-when-empty;
                  key "address";
                  leaf address {
                    type inet:ipv4-address;
                  }
                }
                container ipv4-network {
                  tailf:cli-drop-node-name;
                  list ipv4 {
                    tailf:cli-suppress-mode;
                    tailf:cli-delete-when-empty;
                    key "address mask";
                    leaf address {
                      type inet:ipv4-address;
                    }
                    leaf mask {
                      type inet:ipv4-address;
                    }
                  }
                }
              }
            }
          }
        }
        leaf trace {
          type empty;
        }
        container notify {
          container redirect {
            leaf ip2pots {
              type empty;
            }
            leaf ip2ip {
              type boolean;
            }
          }
        }
        container mode {
          container border-element {
            presence "true";
          }
        }
        container qsig {
          leaf decode {
            type empty;
          }
        }
        container media {
          leaf disable-detailed-stats {
            type empty;
          }
        }
        container allow-connections {
          container h323 {
            container to {
              leaf h323 {
                type empty;
              }
              leaf sip {
                type empty;
              }
            }
          }
          container sip {
            container to {
              leaf h323 {
                type empty;
              }
              leaf sip {
                type empty;
              }
            }
          }
        }
        container supplementary-service {
          leaf h450.2 {
            type boolean;
          }
          leaf h450.3 {
            type boolean;
          }
          leaf h450.7 {
            type boolean;
          }
          container h450.12 {
            tailf:cli-delete-when-empty;
            presence "true";
            leaf advertise-only {
              type empty;
            }
          }
          container sip {
            leaf moved-temporarily {
              type boolean;
            }
            leaf refer {
              type boolean;
            }
            leaf handle-replaces {
              type boolean;
            }
          }
        }
        container fax {
          container protocol {
            choice protoco-choice {
              container t38 {
                tailf:cli-compact-syntax;
                leaf version {
                  type enumeration {
                    enum "0";
                    enum "3";
                  }
                }
                leaf ls-redundancy {
                  type uint8;
                }
                leaf hs-redundancy {
                  type uint8;
                }
                leaf fallback {
                  type enumeration {
                    enum "none";
                    enum "cisco";
                    enum "pass-through";
                  }
                }
              }
            }
          }
        }
        container redirect {
          leaf ip2ip {
            type empty;
          }
        }
        container modem {
          container passthrough {
            container nse {
              leaf codec {
                type enumeration {
                  enum "g711alaw";
                  enum "g711ulaw";
                }
              }
            }
          }
        }
        container h323 {
          tailf:cli-add-mode;
          presence "true";
          container h225 {
            container display-ie {
              leaf ccm-compatible {
                type empty;
              }
            }
          }
        }
        container sip {
          tailf:cli-add-mode;
          presence "true";
          leaf e911 {
            type empty;
          }
          container bind {
            container control {
              container source-interface {
                tailf:cli-compact-syntax;
                uses interface-name-grouping;
              }
            }
            container media {
              container source-interface {
                tailf:cli-compact-syntax;
                uses interface-name-grouping;
              }
            }
          }
          container registrar {
            container server {
              tailf:cli-compact-syntax;
              tailf:cli-sequence-commands {
                tailf:cli-reset-siblings;
              }
              tailf:cli-delete-when-empty;
              presence "true";
              container expires {
                tailf:cli-flatten-container;
                tailf:cli-compact-syntax;
                leaf max {
                  type uint32;
                }
                leaf min {
                  type uint16;
                }
              }
            }
          }
          container sip-profiles {
            leaf id {
              tailf:cli-drop-node-name;
              type uint16;
            }
          }
        }
      }
      container saf {
        tailf:cli-add-mode;
        presence "true";
        list channel {
          key "id";
          leaf id {
            type uint16;
          }
          leaf vrouter {
            tailf:cli-hide-in-submode;
            type string;
          }
          leaf asystem {
            tailf:cli-hide-in-submode;
            type uint16;
          }
          container subscribe {
            container callcontrol {
              leaf wildcarded {
                type empty;
              }
            }
          }
        }
      }
    }
    container class {
      list uri {
        key "name";
        leaf name {
          type string;
        }
        leaf type {
          tailf:cli-drop-node-name;
          tailf:cli-hide-in-submode;
          type enumeration {
            enum "sip";
            enum "tel";
          }
        }
        list host {
          tailf:cli-suppress-mode;
          tailf:cli-delete-when-empty;
          key "name";
          leaf name {
            type string;
          }
        }
      }
      list codec {
        key "id";
        leaf id {
          type uint16;
        }
        container codec {
          list preference {
            tailf:cli-suppress-mode;
            tailf:cli-delete-when-empty;
            tailf:cli-compact-syntax;
            tailf:cli-sequence-commands {
              tailf:cli-reset-siblings;
            }
            key "value";
            leaf value {
              type uint8;
            }
            leaf codec-type {
              tailf:cli-drop-node-name;
              type enumeration {
                enum "aacld";
                enum "clear-channel";
                enum "g711alaw";
                enum "g711ulaw";
                enum "g722-48";
                enum "g722-56";
                enum "g722-64";
                enum "g723ar53";
                enum "g723ar63";
                enum "g723r53";
                enum "g723r63";
                enum "g726r16";
                enum "g726r24";
                enum "g726r32";
                enum "g728";
                enum "g729br8";
                enum "g729r8";
                enum "ilbc";
                enum "isac";
              }
            }
            leaf bytes {
              type uint8;
            }
          }
        }
      }
      list custom-cptone {
        key "name";
        leaf name {
          type string;
        }
        list dualtone {
          key "name";
          leaf name {
            type enumeration {
              enum "busy";
              enum "conference";
              enum "disconnect";
              enum "number-unobtainable";
              enum "out-of-service";
              enum "reorder";
              enum "ringback";
            }
          }
          container frequency {
            tailf:cli-compact-syntax;
            tailf:cli-sequence-commands {
              tailf:cli-reset-siblings;
            }
            leaf value-1 {
              tailf:cli-drop-node-name;
              type uint16;
            }
            leaf value-2 {
              tailf:cli-drop-node-name;
              type uint16;
            }
          }
          container cadence {
            tailf:cli-compact-syntax;
            tailf:cli-sequence-commands {
              tailf:cli-reset-siblings;
            }
            leaf cycle-1-on-time {
              tailf:cli-drop-node-name;
              type uint16;
            }
            leaf cycle-1-off-time {
              tailf:cli-drop-node-name;
              tailf:cli-optional-in-sequence;
              type uint16;
            }
            leaf cycle-2-on-time {
              tailf:cli-drop-node-name;
              tailf:cli-optional-in-sequence;
              type uint16;
            }
            leaf cycle-2-off-time {
              tailf:cli-drop-node-name;
              tailf:cli-optional-in-sequence;
              type uint16;
            }
            leaf cycle-3-on-time {
              tailf:cli-drop-node-name;
              tailf:cli-optional-in-sequence;
              type uint16;
            }
            leaf cycle-3-off-time {
              tailf:cli-drop-node-name;
              tailf:cli-optional-in-sequence;
              type uint16;
            }
            leaf cycle-4-on-time {
              tailf:cli-drop-node-name;
              tailf:cli-optional-in-sequence;
              type uint16;
            }
            leaf cycle-4-off-time {
              tailf:cli-drop-node-name;
              tailf:cli-optional-in-sequence;
              type uint16;
            }
            leaf continuous {
              type empty;
            }
          }
        }
      }
      list e164-pattern-map {
        key "id";
        leaf id {
          type uint16;
        }
        uses description-grouping;
        list e164 {
          tailf:cli-suppress-mode;
          tailf:cli-delete-when-empty;
          key "name";
          leaf name {
            type string;
          }
        }
      }
      list server-group {
        key "id";
        leaf id {
          type uint16;
        }
        list ipv4 {
          tailf:cli-suppress-mode;
          tailf:cli-delete-when-empty;
          tailf:cli-compact-syntax;
          key "address";
          leaf address {
            type inet:ipv4-address;
          }
          leaf port {
            type uint16;
          }
          leaf preference {
            type uint8;
          }
        }
        uses description-grouping;
      }
      list h323 {
        key "id";
        leaf id {
          type uint16;
        }
        container h225 {
          container timeout {
            container tcp {
              leaf establish {
                type uint8;
              }
            }
            leaf setup {
              type uint8;
            }
          }
        }
      }
      list sip-profiles {
        key "id";
        leaf id {
          type uint16;
        }
        list response {
          tailf:cli-suppress-mode;
          tailf:cli-delete-when-empty;
          tailf:cli-compact-syntax;
          tailf:cli-sequence-commands {
            tailf:cli-reset-siblings;
          }
          key "code sip-header";
          leaf code {
            type string;
          }
          leaf sip-header {
            tailf:cli-expose-key-name;
            type string;
          }
          container modify {
            tailf:cli-flatten-container;
            tailf:cli-compact-syntax;
            tailf:cli-sequence-commands {
              tailf:cli-reset-siblings;
            }
            leaf match-pattern {
              tailf:cli-drop-node-name;
              type string;
            }
            leaf replace-pattern {
              tailf:cli-drop-node-name;
              type string;
            }
          }
        }
      }
      list sip-options-keepalive {
        key "id";
        leaf id {
          type uint16;
        }
        uses description-grouping;
        leaf down-interval {
          type uint16;
        }
        leaf up-interval {
          type uint16;
        }
        leaf retry {
          type uint8;
        }
        leaf transport {
          type enumeration {
            enum "system";
            enum "tcp";
            enum "udp";
          }
        }
        leaf shutdown {
          type empty;
        }
      }
    }
    container iec {
      leaf syslog {
        type empty;
      }
    }
    container register {
      container global {
        tailf:cli-add-mode;
        presence "true";
        leaf mode {
          type enumeration {
            enum "cme";
            enum "esrst";
          }
        }
        container authenticate {
          leaf register {
            type empty;
          }
          leaf realm {
            type string;
          }
        }
        container source-address {
          tailf:cli-compact-syntax;
          tailf:cli-sequence-commands {
            tailf:cli-reset-siblings;
          }
          leaf address {
            tailf:cli-drop-node-name;
            type inet:ipv4-address;
          }
          leaf port {
            type uint16;
          }
        }
        leaf allow-hash-in-dn {
          type boolean;
        }
        container timeouts {
          leaf interdigit {
            type uint8;
          }
        }
        container system {
          leaf message {
            tailf:cli-multi-value;
            type string;
          }
        }
        leaf max-dn {
          type uint16;
        }
        leaf max-pool {
          type uint16;
        }
        leaf tftp-path {
          type string;
        }
        list dialplan-pattern {
          tailf:cli-suppress-mode;
          tailf:cli-delete-when-empty;
          tailf:cli-compact-syntax;
          tailf:cli-sequence-commands {
            tailf:cli-reset-siblings;
          }
          key "id";
          leaf id {
            type uint8;
          }
          leaf pattern {
            tailf:cli-drop-node-name;
            type string;
          }
          leaf extension-length {
            type uint8;
          }
          leaf demote {
            type empty;
          }
        }
        container url {
          leaf directory {
            type string;
          }
        }
        list load {
          tailf:cli-suppress-mode;
          tailf:cli-delete-when-empty;
          tailf:cli-compact-syntax;
          tailf:cli-sequence-commands {
            tailf:cli-reset-siblings;
          }
          key "name";
          leaf name {
            type string;
          }
          leaf file {
            tailf:cli-drop-node-name;
            type string;
          }
        }
        leaf date-format {
          type string;
        }
        leaf auto-register {
          type empty;
        }
      }
      list dn {
        key "id";
        leaf id {
          type uint16;
        }
        leaf number {
          type string;
        }
        leaf label {
          tailf:cli-multi-value;
          type string;
        }
        leaf mobility {
          type empty;
        }
      }
      list pool {
        key "tag";
        leaf tag {
          type uint16;
        }
        leaf busy-trigger-per-button {
          type uint8;
        }
        container id {
          container network {
            container ipv4 {
              tailf:cli-drop-node-name;
              tailf:cli-compact-syntax;
              tailf:cli-sequence-commands;
              leaf address {
                tailf:cli-drop-node-name;
                type inet:ipv4-address;
              }
              leaf mask {
                type inet:ipv4-address;
              }
            }
            leaf ip6 {
              tailf:cli-drop-node-name;
              type ipv6-prefix;
            }
          }
          leaf mac {
            type mac-address-type;
          }
        }
        leaf session-transport {
          type enumeration {
            enum "tcp";
            enum "udp";
          }
        }
        leaf type {
          type string;
        }
        list number {
          tailf:cli-suppress-mode;
          tailf:cli-delete-when-empty;
          tailf:cli-compact-syntax;
          tailf:cli-sequence-commands {
            tailf:cli-reset-siblings;
          }
          key "id";
          leaf id {
            type string;
          }
          leaf dn {
            type uint16;
          }
        }
        container presence {
          leaf call-list {
            type empty;
          }
        }
        leaf-list dtmf-relay {
          tailf:cli-flat-list-syntax;
          ordered-by user;
          type enumeration {
            enum "cisco-rtp";
            enum "rtp-nte";
            enum "sip-kpml";
            enum "sip-notify";
          }
        }
        container voice-class {
          leaf codec {
            type uint16;
          }
        }
        container username {
          tailf:cli-compact-syntax;
          tailf:cli-sequence-commands {
            tailf:cli-reset-siblings;
          }
          leaf name {
            tailf:cli-drop-node-name;
            type string;
          }
          leaf password {
            type string;
          }
        }
        container call-forward {
          container b2bua {
            leaf all {
              type string;
            }
            leaf busy {
              type string;
            }
            leaf mailbox {
              type string;
            }
            container noan {
              tailf:cli-compact-syntax;
              tailf:cli-sequence-commands {
                tailf:cli-reset-siblings;
              }
              leaf target-number {
                tailf:cli-drop-node-name;
                type string;
              }
              leaf timeout {
                type uint16;
              }
            }
            leaf unreachable {
              type string;
            }
          }
        }
        leaf vad {
          type boolean;
        }
        container phone-mode {
          leaf phone-only {
            type empty;
          }
        }
      }
    }
    list translation-rule {
      key "tag";
      leaf tag {
        type uint32;
      }
      list rule {
        tailf:cli-suppress-mode;
        tailf:cli-delete-when-empty;
        tailf:cli-compact-syntax;
        tailf:cli-sequence-commands {
          tailf:cli-reset-siblings;
        }
        key "tag";
        leaf tag {
          type uint8;
        }
        leaf reject {
          tailf:cli-optional-in-sequence;
          type empty;
        }
        leaf matching-pattern {
          tailf:cli-drop-node-name;
          type string;
        }
        leaf replacement-pattern {
          tailf:cli-drop-node-name;
          type string;
        }
      }
    }
    list translation-profile {
      key "name";
      leaf name {
        type string;
      }
      container translate {
        container calling {
          leaf tag {
            tailf:cli-drop-node-name;
            type uint32;
          }
        }
        container redirect-called {
          leaf tag {
            tailf:cli-drop-node-name;
            type uint32;
          }
        }
        container called {
          leaf tag {
            tailf:cli-drop-node-name;
            type uint32;
          }
        }
      }
    }
  }
  container event {
    container manager {
      list environment {
        tailf:cli-suppress-mode;
        tailf:cli-delete-when-empty;
        key "name";
        leaf name {
          type string;
        }
        leaf value {
          tailf:cli-drop-node-name;
          tailf:cli-multi-value;
          type string;
        }
      }
      container session {
        container cli {
          tailf:cli-compact-syntax;
          tailf:cli-sequence-commands {
            tailf:cli-reset-siblings;
          }
          leaf username {
            type string;
          }
          leaf privilege {
            type uint8;
          }
        }
      }
      container directory {
        container user {
          leaf policy {
            type string;
          }
          leaf repository {
            type string;
          }
        }
      }
      list applet {
        key "name";
        leaf name {
          type string;
        }
        leaf description {
          tailf:cli-multi-value;
          type string;
        }
        leaf authorization {
          tailf:cli-hide-in-submode;
          type enumeration {
            enum "bypass";
          }
        }
        leaf class {
          tailf:cli-hide-in-submode;
          type string;
        }
        leaf trap {
          tailf:cli-hide-in-submode;
          type empty;
        }
        container event {
          uses event-manager-applet-event-grouping;
          list tag {
            tailf:cli-suppress-mode;
            tailf:cli-delete-when-empty;
            key "name";
            leaf name {
              type string;
            }
            uses event-manager-applet-event-grouping;
          }
        }
        list action {
          tailf:cli-suppress-mode;
          tailf:cli-delete-when-empty;
          tailf:cli-compact-syntax;
          ordered-by user;
          key "name";
          leaf name {
            type string;
          }
          choice action-choice {
            container cli {
              tailf:cli-compact-syntax;
              leaf command {
                type string;
              }
              leaf pattern {
                type string;
              }
            }
            leaf regexp {
              type string;
            }
            leaf string {
              type string;
            }
            leaf comment {
              type string;
            }
            leaf wait {
              type uint32;
            }
            container syslog {
              tailf:cli-compact-syntax;
              leaf priority {
                type logging-level-type;
              }
              leaf msg {
                type string;
              }
              leaf facility {
                type string;
              }
              leaf filter {
                type enumeration {
                  enum "esm";
                }
              }
            }
            container snmp-trap {
              tailf:cli-compact-syntax;
              leaf intdata1 {
                type int32;
              }
              leaf intdata2 {
                type int32;
              }
              leaf strdata {
                type string;
              }
            }
            container puts {
              tailf:cli-compact-syntax;
              tailf:cli-sequence-commands {
                tailf:cli-reset-siblings;
              }
              leaf nonewline {
                tailf:cli-optional-in-sequence;
                type empty;
              }
              leaf data {
                tailf:cli-drop-node-name;
                type string;
              }
            }
            leaf cmd {
              tailf:cli-drop-node-name;
              tailf:cli-multi-value;
              type string;
            }
          }
        }
        container trigger {
          tailf:cli-add-mode;
          tailf:cli-flatten-container;
          presence "true";
          leaf occurs {
            tailf:cli-hide-in-submode;
            type uint32;
          }
          leaf period {
            tailf:cli-hide-in-submode;
            type string;
          }
          leaf period-start {
            tailf:cli-hide-in-submode;
            type string;
          }
          leaf delay {
            tailf:cli-hide-in-submode;
            type string;
          }
          container correlate {
            leaf statement {
              tailf:cli-drop-node-name;
              tailf:cli-multi-value;
              type string;
            }
          }
        }
      }
      list policy {
        tailf:cli-suppress-mode;
        tailf:cli-delete-when-empty;
        tailf:cli-compact-syntax;
        key "name";
        leaf name {
          type string;
        }
        leaf type {
          type enumeration {
            enum "system";
            enum "user";
          }
        }
        leaf authorization {
          type enumeration {
            enum "bypass";
          }
        }
      }
    }
  }
  leaf disable-eadi {
    type empty;
  }
  container memory-size {
    leaf iomem {
      type uint8;
    }
  }
  container memory {
    container free {
      container low-watermark {
        leaf processor {
          type uint32;
        }
      }
    }
  }
  container ucse {
    list subslot {
      key "name";
      leaf name {
        type string;
      }
      container imc {
        leaf vlan {
          type uint16;
        }
        container access-port {
          container shared-lom {
            choice shared-lom-choice {
              leaf console {
                type empty;
              }
              leaf ge1 {
                type empty;
              }
              leaf ge2 {
                type empty;
              }
            }
          }
        }
        container ip {
          choice ip-choice {
            container address {
              tailf:cli-compact-syntax;
              tailf:cli-sequence-commands {
                tailf:cli-reset-siblings;
              }
              leaf address {
                tailf:cli-drop-node-name;
                type inet:ipv4-address;
              }
              leaf mask {
                tailf:cli-drop-node-name;
                type inet:ipv4-address;
              }
              leaf default-gateway {
                type inet:ipv4-address;
              }
            }
            leaf dhcp {
              type empty;
            }
          }
        }
      }
    }
  }
  container transceiver {
    container type {
      container all {
        tailf:cli-add-mode;
        container monitoring {
          presence "true";
          leaf interval {
            type uint32;
          }
        }
      }
    }
  }
  container define {
    list interface-range {
      tailf:cli-suppress-mode;
      tailf:cli-delete-when-empty;
      key "name";
      leaf name {
        type string;
      }
      leaf interface {
        tailf:cli-drop-node-name;
        tailf:cli-multi-value;
        type string;
      }
    }
  }
  list alias {
    tailf:cli-suppress-mode;
    tailf:cli-delete-when-empty;
    key "mode name";
    leaf mode {
      type string;
    }
    leaf name {
      type string;
    }
    leaf line {
      tailf:cli-drop-node-name;
      tailf:cli-multi-value;
      type string;
    }
  }
  container spd {
    leaf enable {
      type boolean;
    }
    leaf headroom {
      type uint16;
    }
    leaf extended-headroom {
      type uint16;
    }
  }
  container audit-enable {
    tailf:cli-drop-node-name;
    leaf audit {
      type empty;
    }
  }
  container audit {
    leaf interval {
      type uint16;
    }
  }
  container cached-show {
    container version {
      leaf version {
        type string;
      }
      leaf xe-version {
        type string;
      }
      leaf model {
        type string;
      }
      container license {
        leaf level {
          type string;
        }
        leaf type {
          type string;
        }
      }
    }
    list inventory {
      tailf:cli-suppress-mode;
      key "name";
      leaf name {
        tailf:cli-expose-key-name;
        type string;
      }
      leaf sn {
        type string;
      }
    }
  }
  leaf xxyyzztop {
    type uint16;
  }
  leaf xxyyzzfail {
    type empty;
  }
}
