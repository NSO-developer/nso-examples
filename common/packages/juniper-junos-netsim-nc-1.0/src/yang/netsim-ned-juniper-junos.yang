module netsim-ned-juniper-junos {
  namespace "http://xml.juniper.net/xnm/1.1/xnm";
  prefix junos;

  import tailf-common {
    prefix tailf;
  }
  import ietf-inet-types {
    prefix inet;
  }

  typedef key-attribute-long-type {
    type int64;
  }

  typedef key-attribute-string-type {
    type string;
  }

  typedef key-attribute-ulong-type {
    type uint64;
  }

  typedef filename {
    type string;
  }

  typedef client-filename {
    type string;
  }

  typedef hostname {
    type string;
  }

  typedef ipaddr {
    type string;
  }

  typedef ipaddr-scoped {
    type string;
  }

  typedef sysid {
    type string;
  }

  typedef interface-device {
    type string;
  }

  typedef isoaddr {
    type string;
  }

  typedef ipprefix {
    type string;
  }

  typedef ipprefix-mandatory {
    type string;
  }

  typedef interface-unit {
    type string;
  }

  typedef ipaddr-or-interface {
    type string;
  }

  typedef areaid {
    type string;
  }

  typedef interface-name {
    type string;
  }

  typedef community {
    type string;
  }

  typedef interface-wildcard {
    type string;
  }

  typedef unreadable {
    type string;
  }

  typedef ipprefix-optional {
    type string;
  }

  typedef policy-algebra {
    type string;
  }

  typedef regular-expression {
    type string;
  }

  typedef group-glob {
    type string;
  }

  typedef atm-vci {
    type string;
  }

  typedef ipprefix-only {
    type string;
  }

  typedef ipv4addr {
    type string;
  }

  typedef ipv4prefix {
    type string;
  }

  typedef ipv4prefix-mandatory {
    type string;
  }

  typedef ipv4addr-or-interface {
    type string;
  }

  typedef ipv4prefix-optional {
    type string;
  }

  typedef ipv4prefix-only {
    type string;
  }

  typedef ipv6addr {
    type string;
  }

  typedef ipv6prefix {
    type string;
  }

  typedef ipv6prefix-mandatory {
    type string;
  }

  typedef ipv6addr-or-interface {
    type string;
  }

  typedef ipv6prefix-optional {
    type string;
  }

  typedef ipv6prefix-only {
    type string;
  }

  typedef interface-device-wildcard {
    type string;
  }

  typedef interface-unit-wildcard {
    type string;
  }

  typedef time {
    type string;
  }

  typedef mac-addr {
    type string;
  }

  typedef mac-addr-prefix {
    type string;
  }

  typedef mac-unicaset {
    type string;
  }

  typedef mac-unicast {
    type string;
  }

  typedef mac-unicast-prefix {
    type string;
  }

  typedef mac-multicast {
    type string;
  }

  typedef mac-multicast-prefix {
    type string;
  }

  typedef mpls-label {
    type string;
  }

  typedef float {
    type string;
  }

  typedef unsigned-float {
    type string;
  }

  typedef isoprefix {
    type string;
  }

  typedef isosysid {
    type string;
  }

  typedef interface-range-wild {
    type string;
  }

  typedef fc-addr {
    type string;
  }

  typedef wwn {
    type string;
  }

  typedef logfilename {
    type string;
  }

  typedef esi {
    type string;
  }

  typedef time-of-day {
    type string;
  }

  typedef date {
    type string;
  }

  grouping apply-group {
    leaf-list apply-groups {
      ordered-by user;
      type string;
    }
    leaf-list apply-groups-except {
      ordered-by user;
      type string;
    }
  }

  grouping apply-macro {
    list apply-macro {
      key "name";
      ordered-by user;
      leaf name {
        type string;
      }
      list data {
        key "name";
        ordered-by user;
        leaf name {
          type string;
        }
        leaf value {
          type string;
        }
      }
    }
  }

  grouping apply-advanced {
    container apply-advanced {
      uses apply-group;
      uses apply-macro;
    }
  }

  grouping domain-id-type {
    leaf name {
      type string;
    }
    uses apply-advanced;
  }

  grouping write-option-82-type {
    uses apply-group;
    uses apply-macro;
  }

  typedef group-wildcard-key {
    type string;
  }

  container configuration {
    uses apply-group;
    uses apply-macro;
    list groups {
      ordered-by user;
      key "name";
      leaf name {
        type string;
      }
      container when {
        container time {
          leaf start-time {
            type string;
          }
          container to {
            leaf end-time {
              type string;
            }
          }
        }
      }
      container undocumented {
        container apply-flags {
          leaf omit {
            type empty;
          }
        }
      }
      uses top-configuration;
    }
    uses top-configuration;
  }

  grouping upgrade-group-type {
    leaf name {
      type key-attribute-string-type;
    }
    uses apply-group;
    uses apply-macro;
    leaf-list satellite {
      ordered-by user;
      type string;
    }
  }

  grouping control_as_list_type {
    leaf list-type {
      type string;
    }
    leaf list-name {
      type string;
    }
    uses apply-group;
    uses apply-macro;
  }

  grouping redundancy-group-type {
    leaf name {
      type key-attribute-string-type;
    }
    uses apply-group;
    uses apply-macro;
    leaf redundancy-group-id {
      mandatory true;
      type uint32;
    }
    list peer-chassis-id {
      key "name";
      ordered-by user;
      leaf name {
        type key-attribute-ulong-type;
      }
      uses apply-group;
      uses apply-macro;
      leaf no-auto-vlan-provisioning {
        type empty;
      }
      leaf inter-chassis-link {
        mandatory true;
        type interface-device;
      }
      leaf no-auto-iccp-provisioning {
        type empty;
      }
      leaf session-establishment-hold-time {
        units "seconds";
        type uint32;
      }
      container liveness-detection {
        presence "enable liveness-detection";
        uses apply-group;
        uses apply-macro;
        leaf version {
          type string;
        }
        leaf minimum-interval {
          units "milliseconds";
          type uint32;
        }
        leaf minimum-transmit-interval {
          units "milliseconds";
          type uint32;
        }
        leaf minimum-receive-interval {
          units "milliseconds";
          type uint32;
        }
        leaf multiplier {
          type uint32;
        }
        leaf no-adaptation {
          type empty;
        }
        container transmit-interval {
          uses apply-group;
          uses apply-macro;
          leaf minimum-interval {
            units "milliseconds";
            type uint32;
          }
          leaf threshold {
            type uint32;
            units "milliseconds";
          }
        }
        container detection-time {
          uses apply-group;
          uses apply-macro;
          leaf threshold {
            type uint32;
            units "milliseconds";
          }
        }
      }
      leaf authentication-key {
        type unreadable;
      }
      container traceoptions {
        uses apply-group;
        uses apply-macro;
        leaf no-remote-trace {
          type empty;
        }
        container file {
          leaf filename {
            type string;
          }
          leaf size {
            type string;
          }
          leaf files {
            type uint32;
          }
          leaf world-readable {
            type empty;
          }
          leaf no-world-readable {
            type empty;
          }
          leaf match {
            type regular-expression;
          }
        }
        list flag {
          key "name";
          ordered-by user;
          leaf name {
            type string;
          }
        }
      }
    }
    leaf-list satellite {
      ordered-by user;
      type string;
    }
    leaf system-mac-address {
      type mac-unicast;
    }
    list cluster {
      key "name";
      leaf name {
        type string;
      }
      uses apply-group;
      uses apply-macro;
    }
  }

  grouping optics-options-grouping {
    container optics-options {
      uses apply-group;
      uses apply-macro;
      leaf wavelength {
        type string;
      }
      leaf tx-power {
        type string;
        units "dBm";
      }
      container loopback {
        presence "enable loopback";
        uses apply-advanced;
        leaf loopbacktype {
          type string;
        }
      }
      leaf los-warning-threshold {
        units "dBm";
        type string;
      }
      leaf los-alarm-threshold {
        units "dBm";
        type string;
      }
      leaf modulation-format {
        type string;
      }
      choice laser-enable-choice {
        leaf laser-enable {
          type empty;
        }
        leaf no-laser-enable {
          type empty;
        }
      }
      choice is-ma-choice {
        leaf is-ma {
          type empty;
        }
        leaf no-is-ma {
          type empty;
        }
      }
      leaf encoding {
        type string;
      }
      leaf fec {
        type string;
      }
      leaf high-polarization {
        type empty;
      }
      container application {
        uses apply-advanced;
        leaf hostid {
          type string;
        }
        leaf mediaid {
          type string;
        }
        leaf domainid {
          type string;
        }
      }
      container signal-degrade {
        uses apply-advanced;
        leaf interval {
          units "milliseconds";
          type string;
        }
        leaf ber-threshold-clear {
          type string;
        }
        leaf ber-threshold-signal-degrade {
          type string;
        }
        leaf q-threshold-signal-degrade-clear {
          units "dB";
          type string;
        }
        leaf q-threshold-signal-degrade {
          units "dB";
          type string;
        }
      }
      list alarm {
        key "name";
        ordered-by user;
        leaf name {
          type string;
        }
        uses apply-group;
        uses apply-macro;
        choice choice-syslog {
          leaf syslog {
            type empty;
          }
          leaf link-down {
            type empty;
          }
        }
      }
      list warning {
        key "name";
        ordered-by user;
        leaf name {
          type string;
        }
        uses apply-group;
        uses apply-macro;
        choice choice-syslog {
          leaf syslog {
            type empty;
          }
          leaf link-down {
            type empty;
          }
        }
      }
      container trace-tone {
        uses apply-group;
        uses apply-macro;
        leaf receive {
          type string;
        }
        leaf transmit {
          type string;
        }
      }
    }
  }

  grouping top-configuration {
    leaf rcsid {
      type string;
    }
    leaf version {
      type string;
    }
    container system {
      uses juniper-system;
    }
    list dynamic-profiles {
      key "name";
      uses juniper-dynamic-profile-object;
    }
    list logical-systems {
      key "name";
      uses juniper-logical-system;
    }
    container chassis {
      uses chassis-type;
    }
    container interfaces {
      uses apply-group;
      uses apply-macro;
      list pic-set {
        key "name";
        ordered-by user;
        leaf name {
          type key-attribute-string-type;
        }
        uses apply-group;
        uses apply-macro;
        list interface {
          key "name";
          ordered-by user;
          leaf name {
            type key-attribute-string-type;
          }
          uses apply-group;
          uses apply-macro;
        }
        list fpc {
          key "name";
          ordered-by user;
          leaf name {
            type string;
          }
          uses apply-group;
          uses apply-macro;
          list pic {
            key "name";
            ordered-by user;
            leaf name {
              type string;
            }
            uses apply-group;
            uses apply-macro;
          }
        }
      }
      list interface-set {
        key "name";
        ordered-by user;
        leaf name {
          type string;
        }
        uses apply-group;
        uses apply-macro;
        list interface {
          key "name";
          ordered-by user;
          leaf name {
            type interface-device;
          }
          uses apply-group;
          uses apply-macro;
          list unit {
            key "name";
            leaf name {
              type string;
            }
            uses apply-group;
            uses apply-macro;
          }
          list vlan-tags-outer {
            key "name";
            leaf name {
              type string;
            }
            uses apply-group;
            uses apply-macro;
          }
        }
      }
      container traceoptions {
        uses apply-group;
        uses apply-macro;
        leaf no-remote-trace {
          type empty;
        }
        container file {
          leaf filename {
            type string;
          }
          leaf size {
            type string;
          }
          leaf files {
            type uint32;
          }
          leaf world-readable {
            type empty;
          }
          leaf no-world-readable {
            type empty;
          }
          leaf match {
            type regular-expression;
          }
        }
        list flag {
          key "name";
          leaf name {
            type string;
          }
          leaf disable {
            type empty;
          }
        }
      }
      list interface-range {
        key "name";
        ordered-by user;
        leaf name {
          type key-attribute-string-type;
        }
        uses apply-group;
        uses apply-macro;
        list member {
          key "name";
          ordered-by user;
          leaf name {
            type interface-range-wild;
          }
          uses apply-group;
          uses apply-macro;
        }
        list member-range {
          key "name";
          ordered-by user;
          leaf name {
            type interface-device;
          }
          leaf end-range {
            type interface-device;
          }
        }
        leaf description {
          type string;
        }
        choice choice-9 {
          leaf disable {
            type empty;
          }
        }
        leaf promiscuous-mode {
          type empty;
        }
        leaf multicast-statistics {
          type empty;
        }
        container fabric-options {
          uses apply-group;
          uses apply-macro;
          list member-interfaces {
            key "name";
            leaf name {
              type interface-device;
            }
            uses apply-group;
            uses apply-macro;
          }
        }
        container traceoptions {
          presence "enable traceoptions";
          uses apply-group;
          uses apply-macro;
          list flag {
            key "name";
            ordered-by user;
            leaf name {
              type string;
            }
          }
        }
        leaf passive-monitor-mode {
          type empty;
        }
        choice choice-20 {
          container keepalives {
            presence "enable keepalives";
            uses keepalives-type;
          }
          leaf no-keepalives {
            type empty;
          }
        }
        leaf traps {
          type empty;
        }
        leaf no-traps {
          type empty;
        }
        leaf accounting-profile {
          type string;
        }
        choice choice-27 {
          leaf per-unit-scheduler {
            type empty;
          }
          leaf shared-scheduler {
            type empty;
          }
          container hierarchical-scheduler {
            presence "enable hierarchical-scheduler";
            leaf maximum-hierarchy-levels {
              type uint32;
            }
            leaf maximum-l2-nodes {
              type uint32;
            }
            leaf implicit-hierarchy {
              type empty;
            }
          }
        }
        leaf schedulers {
          type uint32;
        }
        leaf interface-transmit-statistics {
          type empty;
        }
        leaf dce {
          type empty;
        }
        choice choice-34 {
          leaf vlan-tagging {
            type empty;
          }
          leaf stacked-vlan-tagging {
            type empty;
          }
          leaf flexible-vlan-tagging {
            type empty;
          }
          leaf vlan-vci-tagging {
            type empty;
          }
        }
        leaf native-vlan-id {
          type uint32;
        }
        leaf speed {
          type string;
        }
        container auto-configure {
          uses auto-configure-vlan-type;
        }
        leaf mtu {
          type uint32;
        }
        container hold-time {
          presence "";
          leaf up {
            type uint32;
          }
          leaf down {
            type uint32;
          }
        }
        container satop-options {
          uses apply-group;
          uses apply-macro;
          leaf idle-pattern {
            type uint32;
          }
          leaf payload-size {
            type uint32;
          }
          container excessive-packet-loss-rate {
            uses apply-group;
            uses apply-macro;
            leaf threshold {
              type uint8;
            }
            leaf sample-period {
              type uint32;
            }
          }
          choice choice-9 {
            leaf jitter-buffer-packets {
              type uint32;
            }
            leaf jitter-buffer-latency {
              type uint32;
            }
            leaf jitter-buffer-auto-adjust {
              type empty;
            }
          }
          leaf bit-rate {
            type uint32;
          }
        }
        container cesopsn-options {
          uses apply-group;
          uses apply-macro;
          leaf idle-pattern {
            type uint32;
          }
          leaf packetization-latency {
            units "microseconds";
            type uint32;
          }
          container excessive-packet-loss-rate {
            uses apply-group;
            uses apply-macro;
            leaf threshold {
              type uint8;
            }
            leaf sample-period {
              type uint32;
            }
          }
          choice choice-jitter-buffer-packets {
            leaf jitter-buffer-packets {
              type uint32;
            }
            leaf jitter-buffer-latency {
              units "milliseconds";
              type uint32;
            }
            leaf jitter-buffer-auto-adjust {
              type empty;
            }
          }
          leaf bit-rate {
            type uint32;
          }
        }
        container ima-group-options {
          uses apply-group;
          uses apply-macro;
          leaf frame-length {
            type string;
          }
          leaf symmetry {
            type string;
          }
          leaf transmit-clock {
            type string;
          }
          leaf version {
            type string;
          }
          container minimum-links {
            choice choice-3 {
              leaf symmetrical {
                type uint32;
              }
            }
          }
          container frame-synchronization {
            uses apply-group;
            uses apply-macro;
            leaf alpha {
              type uint32;
            }
            leaf beta {
              type uint32;
            }
            leaf gamma {
              type uint32;
            }
          }
          container test-procedure {
            uses apply-group;
            uses apply-macro;
            leaf period {
              type uint32;
            }
            leaf interface {
              type interface-device;
            }
            leaf pattern {
              type uint32;
            }
          }
          leaf differential-delay {
            type uint32;
          }
        }
        container ima-link-options {
          uses apply-group;
          uses apply-macro;
          leaf group-id {
            type uint32;
          }
        }
        container clocking {
          presence "enable clocking";
          choice choice-3 {
            leaf internal {
              type empty;
            }
            container external {
              presence "enable external";
              uses apply-group;
              uses apply-macro;
            }
          }
        }
        leaf link-mode {
          type string;
        }
        leaf media-type {
          type string;
        }
        leaf encapsulation {
          type string;
        }
        container esi {
          presence "";
          uses apply-group;
          uses apply-macro;
          container apply-advanced {
            uses apply-group;
            uses apply-macro;
          }
          leaf identifier {
            mandatory true;
            type string;
          }
          choice choice-single-active {
            leaf single-active {
              type empty;
            }
            leaf all-active {
              type empty;
            }
          }
        }
        container framing {
          uses apply-group;
          uses apply-macro;
          choice choice-3 {
            leaf lan-phy {
              type empty;
            }
            leaf wan-phy {
              type empty;
            }
            leaf sonet {
              type empty;
            }
            leaf sdh {
              type empty;
            }
          }
        }
        leaf unidirectional {
          type empty;
        }
        container lmi {
          uses apply-group;
          uses apply-macro;
          leaf n391dte {
            type uint16;
          }
          leaf n392dce {
            type uint16;
          }
          leaf n392dte {
            type uint16;
          }
          leaf n393dce {
            type uint16;
          }
          leaf n393dte {
            type uint16;
          }
          leaf t391dte {
            type uint16;
          }
          leaf t392dce {
            type uint16;
          }
          leaf lmi-type {
            type string;
          }
        }
        container mlfr-uni-nni-bundle-options {
          uses apply-group;
          uses apply-macro;
          container cisco-interoperability {
            uses apply-group;
            uses apply-macro;
            leaf send-lip-remove-link-for-link-reject {
              type empty;
            }
          }
          leaf mrru {
            type uint16;
          }
          leaf yellow-differential-delay {
            type uint16;
          }
          leaf red-differential-delay {
            type uint16;
          }
          leaf action-red-differential-delay {
            type string;
          }
          leaf fragment-threshold {
            type uint32;
          }
          leaf drop-timeout {
            type uint16;
          }
          leaf link-layer-overhead {
            type unsigned-float;
          }
          leaf lmi-type {
            type string;
          }
          leaf minimum-links {
            type uint16;
          }
          leaf hello-timer {
            type uint16;
          }
          leaf acknowledge-timer {
            type uint16;
          }
          leaf acknowledge-retries {
            type uint16;
          }
          leaf n391 {
            type uint16;
          }
          leaf n392 {
            type uint16;
          }
          leaf n393 {
            type uint16;
          }
          leaf t391 {
            type uint16;
          }
          leaf t392 {
            type uint16;
          }
        }
        leaf mac {
          type mac-unicaset;
        }
        container receive-bucket {
          uses dcd-rx-bucket-config;
        }
        container transmit-bucket {
          uses dcd-tx-bucket-config;
        }
        leaf shared-interface {
          type empty;
        }
        container sonet-options {
          uses sonet-options-type;
        }
        container aggregated-sonet-options {
          uses apply-group;
          uses apply-macro;
          leaf minimum-links {
            type uint16;
          }
          leaf link-speed {
            type string;
          }
          leaf minimum-bandwidth {
            type uint64;
          }
        }
        container atm-options {
          uses apply-group;
          uses apply-macro;
          leaf pic-type {
            type string;
          }
          leaf cell-bundle-size {
            type uint32;
          }
          leaf plp-to-clp {
            type empty;
          }
          leaf use-null-cw {
            type empty;
          }
          container promiscuous-mode {
            presence "enable promiscuous-mode";
            uses apply-group;
            uses apply-macro;
            list vpi {
              key "name";
              ordered-by user;
              leaf name {
                type string;
              }
            }
          }
          list vpi {
            key "name";
            ordered-by user;
            leaf name {
              type string;
            }
            uses apply-group;
            uses apply-macro;
            leaf maximum-vcs {
              type uint32;
            }
            container shaping {
              uses dcd-shaping-config;
            }
            container oam-period {
              choice choice-3 {
                leaf oam-period {
                  type uint32;
                }
                container disable {
                  presence "enable disable";
                }
              }
            }
            container oam-liveness {
              uses apply-group;
              uses apply-macro;
              leaf up-count {
                type uint32;
              }
              leaf down-count {
                type uint32;
              }
            }
          }
          container ilmi {
            presence "enable ilmi";
            uses apply-group;
            uses apply-macro;
          }
          list linear-red-profiles {
            key "name";
            ordered-by user;
            leaf name {
              type string;
            }
            leaf queue-depth {
              type string;
            }
            leaf high-plp-threshold {
              type uint32;
            }
            leaf low-plp-threshold {
              type uint32;
            }
            leaf high-plp-max-threshold {
              type uint32;
            }
            leaf low-plp-max-threshold {
              type uint32;
            }
          }
          list scheduler-maps {
            key "name";
            ordered-by user;
            leaf name {
              type string;
            }
            uses apply-group;
            uses apply-macro;
            leaf vc-cos-mode {
              type string;
            }
            list forwarding-class {
              key "name";
              ordered-by user;
              leaf name {
                type string;
              }
              uses apply-group;
              uses apply-macro;
              leaf priority {
                type string;
              }
              container transmit-weight {
                choice choice-3 {
                  leaf percent {
                    type uint32;
                  }
                  leaf cells {
                    type string;
                  }
                }
              }
              choice choice-7 {
                container epd-threshold {
                  presence "";
                  uses epd-threshold-config;
                }
                leaf linear-red-profile {
                  type string;
                }
              }
            }
          }
          container mpls {
            uses mpls-ifd-options;
          }
          leaf payload-scrambler {
            type empty;
          }
          leaf no-payload-scrambler {
            type empty;
          }
        }
        container multiservice-options {
          uses apply-group;
          uses apply-macro;
          leaf syslog {
            type empty;
          }
          leaf no-syslog {
            type empty;
          }
          leaf core-dump {
            type empty;
          }
          leaf no-core-dump {
            type empty;
          }
          container flow-control-options {
            uses apply-group;
            uses apply-macro;
            leaf dump-on-flow-control {
              type empty;
            }
            leaf reset-on-flow-control {
              type empty;
            }
            leaf down-on-flow-control {
              type empty;
            }
          }
        }
        container ggsn-options {
          uses apply-group;
          uses apply-macro;
          leaf syslog {
            type empty;
          }
          leaf no-syslog {
            type empty;
          }
          leaf core-dump {
            type empty;
          }
          leaf no-core-dump {
            type empty;
          }
        }
        container ppp-options {
          uses ppp-options-type;
        }
        container redundancy-options {
          presence "";
          uses apply-group;
          uses apply-macro;
          container undocumented {
            uses undocumented-redundancy-peer;
          }
          leaf primary {
            type interface-device;
          }
          leaf secondary {
            type interface-device;
          }
        }
        container lsq-failure-options {
          uses apply-group;
          uses apply-macro;
          list trigger-link-failure {
            key "name";
            ordered-by user;
            leaf name {
              type interface-device;
            }
            uses apply-group;
            uses apply-macro;
          }
          leaf no-termination-request {
            type empty;
          }
          leaf no-no-termination-request {
            type empty;
          }
        }
        container services-options {
          uses apply-group;
          uses apply-macro;
          container syslog {
            uses service-set-syslog-object;
          }
          leaf open-timeout {
            units "seconds";
            type uint32;
          }
          leaf close-timeout {
            units "seconds";
            type uint32;
          }
          leaf inactivity-timeout {
            units "seconds";
            type uint32;
          }
          leaf inactivity-tcp-timeout {
            units "seconds";
            type uint32;
          }
          leaf inactivity-asymm-tcp-timeout {
            units "seconds";
            type uint32;
          }
          leaf inactivity-non-tcp-timeout {
            units "seconds";
            type uint32;
          }
          leaf session-timeout {
            units "seconds";
            type uint32;
          }
          leaf disable-global-timeout-override {
            type empty;
          }
          leaf tcp-tickles {
            type uint8;
          }
          container trio-flow-offload {
            presence "enable trio-flow-offload";
            uses apply-group;
            uses apply-macro;
            leaf minimum-bytes {
              type uint32;
            }
          }
          leaf fragment-limit {
            type uint8;
          }
          leaf reassembly-timeout {
            units "seconds";
            type uint8;
          }
          leaf cgn-pic {
            type empty;
          }
          leaf pba-interim-logging-interval {
            units "seconds";
            type uint32;
          }
          container session-limit {
            presence "enable session-limit";
            uses apply-group;
            uses apply-macro;
            leaf maximum {
              type string;
            }
            leaf rate {
              type string;
            }
          }
          container ignore-errors {
            presence "enable ignore-errors";
            leaf tcp {
              type empty;
            }
            leaf alg {
              type empty;
            }
          }
        }
        container t3-options {
          uses apply-group;
          uses apply-macro;
          leaf loopback {
            type string;
          }
          leaf long-buildout {
            type empty;
          }
          leaf no-long-buildout {
            type empty;
          }
          leaf loop-timing {
            type empty;
          }
          leaf no-loop-timing {
            type empty;
          }
          container compatibility-mode {
            choice choice-3 {
              container larscom {
                presence "enable larscom";
                leaf subrate {
                  type uint32;
                }
              }
              container verilink {
                presence "enable verilink";
                leaf subrate {
                  type uint32;
                }
              }
              container adtran {
                presence "enable adtran";
                leaf subrate {
                  type uint32;
                }
              }
              container kentrox {
                presence "enable kentrox";
                leaf subrate {
                  type uint32;
                }
              }
              container digital-link {
                presence "enable digital-link";
                leaf subrate {
                  type string;
                }
              }
            }
          }
          leaf payload-scrambler {
            type empty;
          }
          leaf no-payload-scrambler {
            type empty;
          }
          leaf cbit-parity {
            type empty;
          }
          leaf no-cbit-parity {
            type empty;
          }
          leaf fcs {
            type string;
          }
          leaf idle-cycle-flag {
            type string;
          }
          leaf start-end-flag {
            type string;
          }
          leaf feac-loop-respond {
            type empty;
          }
          leaf no-feac-loop-respond {
            type empty;
          }
          leaf bert-algorithm {
            type string;
          }
          leaf bert-error-rate {
            type uint32;
          }
          leaf bert-period {
            type uint32;
          }
          leaf buildout {
            type uint32;
          }
          leaf atm-encapsulation {
            type string;
          }
        }
        container e3-options {
          uses apply-group;
          uses apply-macro;
          leaf loopback {
            type string;
          }
          leaf unframed {
            type empty;
          }
          leaf no-unframed {
            type empty;
          }
          container compatibility-mode {
            choice choice-3 {
              leaf larscom {
                type empty;
              }
              container digital-link {
                presence "enable digital-link";
                leaf subrate {
                  type string;
                }
              }
              container kentrox {
                presence "enable kentrox";
                leaf subrate {
                  type uint32;
                }
              }
            }
          }
          leaf payload-scrambler {
            type empty;
          }
          leaf no-payload-scrambler {
            type empty;
          }
          leaf fcs {
            type string;
          }
          leaf idle-cycle-flag {
            type string;
          }
          leaf invert-data {
            type empty;
          }
          leaf start-end-flag {
            type string;
          }
          leaf bert-algorithm {
            type string;
          }
          leaf bert-error-rate {
            type uint32;
          }
          leaf bert-period {
            type uint32;
          }
          leaf buildout {
            type uint32;
          }
          leaf atm-encapsulation {
            type string;
          }
          leaf framing {
            type string;
          }
        }
        container e1-options {
          uses apply-group;
          uses apply-macro;
          leaf timeslots {
            type string;
          }
          leaf loopback {
            type string;
          }
          leaf framing {
            type string;
          }
          leaf fcs {
            type string;
          }
          leaf invert-data {
            type empty;
          }
          leaf idle-cycle-flag {
            type string;
          }
          leaf start-end-flag {
            type string;
          }
          leaf bert-algorithm {
            type string;
          }
          leaf bert-error-rate {
            type uint32;
          }
          leaf bert-period {
            type uint32;
          }
        }
        container t1-options {
          uses apply-group;
          uses apply-macro;
          leaf timeslots {
            type string;
          }
          leaf voice-timeslots {
            type string;
          }
          leaf loopback {
            type string;
          }
          leaf buildout {
            type string;
          }
          leaf byte-encoding {
            type string;
          }
          leaf line-encoding {
            type string;
          }
          leaf invert-data {
            type empty;
          }
          leaf framing {
            type string;
          }
          leaf fcs {
            type string;
          }
          leaf idle-cycle-flag {
            type string;
          }
          leaf start-end-flag {
            type string;
          }
          leaf bert-algorithm {
            type string;
          }
          leaf bert-error-rate {
            type uint32;
          }
          leaf bert-period {
            type uint32;
          }
          leaf remote-loopback-respond {
            type empty;
          }
          leaf crc-major-alarm-threshold {
            type string;
          }
          leaf crc-minor-alarm-threshold {
            type string;
          }
        }
        container ds0-options {
          uses apply-group;
          uses apply-macro;
          leaf loopback {
            type string;
          }
          leaf byte-encoding {
            type string;
          }
          leaf invert-data {
            type empty;
          }
          leaf fcs {
            type string;
          }
          leaf idle-cycle-flag {
            type string;
          }
          leaf start-end-flag {
            type string;
          }
          leaf bert-algorithm {
            type string;
          }
          leaf bert-error-rate {
            type uint32;
          }
          leaf bert-period {
            type uint32;
          }
        }
        container serial-options {
          uses apply-group;
          uses apply-macro;
          leaf line-protocol {
            type string;
          }
          choice choice-5 {
            container dte-options {
              uses apply-group;
              uses apply-macro;
              leaf ignore-all {
                type empty;
              }
              container dtr {
                choice choice-3 {
                  leaf assert {
                    type empty;
                  }
                  leaf de-assert {
                    type empty;
                  }
                  leaf normal {
                    type empty;
                  }
                  container auto-synchronize {
                    presence "enable auto-synchronize";
                    uses apply-group;
                    uses apply-macro;
                    leaf duration {
                      type uint16;
                    }
                    leaf interval {
                      type uint16;
                    }
                  }
                }
              }
              leaf control-signal {
                type string;
              }
              leaf rts {
                type string;
              }
              leaf dcd {
                type string;
              }
              leaf dsr {
                type string;
              }
              leaf cts {
                type string;
              }
              leaf indication {
                type string;
              }
              leaf tm {
                type string;
              }
            }
            container dce-options {
              uses apply-group;
              uses apply-macro;
              leaf ignore-all {
                type empty;
              }
              leaf dtr {
                type string;
              }
              leaf rts {
                type string;
              }
              leaf dcd {
                type string;
              }
              leaf dsr {
                type string;
              }
              leaf cts {
                type string;
              }
              leaf tm {
                type string;
              }
              leaf dce-loopback-override {
                type empty;
              }
            }
          }
          leaf dtr-circuit {
            type string;
          }
          leaf dtr-polarity {
            type string;
          }
          leaf rts-polarity {
            type string;
          }
          leaf control-polarity {
            type string;
          }
          leaf dcd-polarity {
            type string;
          }
          leaf dsr-polarity {
            type string;
          }
          leaf cts-polarity {
            type string;
          }
          leaf indication-polarity {
            type string;
          }
          leaf tm-polarity {
            type string;
          }
          leaf clocking-mode {
            type string;
          }
          leaf transmit-clock {
            type string;
          }
          leaf clock-rate {
            type string;
          }
          leaf loopback {
            type string;
          }
          leaf encoding {
            type string;
          }
          leaf idle-cycle-flag {
            type string;
          }
        }
        leaf gratuitous-arp-reply {
          type empty;
        }
        leaf no-gratuitous-arp-reply {
          type empty;
        }
        leaf no-gratuitous-arp-request {
          type empty;
        }
        leaf no-no-gratuitous-arp-request {
          type empty;
        }
        leaf arp-l2-validate {
          type empty;
        }
        container ether-options {
          uses apply-group;
          uses apply-macro;
          choice loopback-choice {
            leaf loopback {
              type empty;
            }
            leaf no-loopback {
              type empty;
            }
          }
          leaf loopback-remote {
            type empty;
          }
          choice source-filtering-choice {
            leaf source-filtering {
              type empty;
            }
            leaf no-source-filtering {
              type empty;
            }
          }
          container ethernet-switch-profile {
            uses apply-group;
            uses apply-macro;
            leaf-list tag-protocol-id {
              type string;
              ordered-by user;
            }
            container ethernet-policer-profile {
              uses apply-group;
              uses apply-macro;
              container input-priority-map {
                uses cos-policer-input-priority-map;
              }
              container output-priority-map {
                uses cos-policer-output-priority-map;
              }
              list policer {
                key "name";
                ordered-by user;
                uses cos-policer;
              }
            }
            container storm-control {
              presence "";
              uses apply-group;
              uses apply-macro;
              leaf profile-name {
                type string;
              }
            }
            container recovery-timeout {
              leaf time-in-seconds {
                units "seconds";
                type uint32;
              }
            }
            leaf mac-learn-enable {
              type empty;
            }
            leaf no-mac-learn-enable {
              type empty;
            }
          }
          leaf asynchronous-notification {
            type empty;
          }
          list source-address-filter {
            key "name";
            leaf name {
              type mac-addr;
            }
          }
          choice auto-negotiation-choice {
            leaf auto-negotiation {
              type empty;
            }
            leaf no-auto-negotiation {
              type empty;
            }
          }
          choice flow-control-choice {
            leaf flow-control {
              type empty;
            }
            leaf no-flow-control {
              type empty;
            }
          }
          container configured-flow-control {
            presence "";
            uses apply-group;
            uses apply-macro;
            leaf rx-buffers {
              type string;
            }
            leaf tx-buffers {
              type string;
            }
          }
          leaf link-mode {
            type string;
          }
          container mpls {
            uses mpls-ifd-options;
          }
          leaf ignore-l3-incompletes {
            type empty;
          }
          leaf no-auto-mdix {
            type empty;
          }
          container speed {
            choice choice-3 {
              container auto-negotiation {
                presence "enable auto-negotiation";
                leaf auto-negotiate-10-100 {
                  type empty;
                }
              }
              leaf ethernet-10m {
                type empty;
              }
              leaf ethernet-100m {
                type empty;
              }
              leaf ethernet-1g {
                type empty;
              }
              leaf ethernet-10g {
                type empty;
              }
            }
          }
          container ieee-802.3ad {
            uses apply-group;
            uses apply-macro;
            container lacp {
              uses apply-group;
              uses apply-macro;
              leaf force-up {
                type empty;
              }
              leaf port-priority {
                type uint16;
              }
            }
            leaf bundle {
              type interface-device;
            }
            choice choice-7 {
              leaf primary {
                type empty;
              }
              leaf backup {
                type empty;
              }
            }
          }
          leaf ieee-802-3az-eee {
            type empty;
          }
          leaf mdi-mode {
            type string;
          }
        }
        container fibrechannel-options {
          uses apply-group;
          uses apply-macro;
          container apply-advanced {
            uses apply-group;
            uses apply-macro;
          }
          choice loopback-choice {
            leaf loopback {
              type empty;
            }
            leaf no-loopback {
              type empty;
            }
          }
          leaf bb-sc-n {
            type uint16;
          }
          leaf speed {
            type string;
          }
        }
        container gigether-options {
          uses apply-group;
          uses apply-macro;
          choice loopback-choice {
            leaf loopback {
              type empty;
            }
            leaf no-loopback {
              type empty;
            }
          }
          leaf loopback-remote {
            type empty;
          }
          choice flow-control-choice {
            leaf flow-control {
              type empty;
            }
            leaf no-flow-control {
              type empty;
            }
          }
          choice source-filtering-choice {
            leaf source-filtering {
              type empty;
            }
            leaf no-source-filtering {
              type empty;
            }
          }
          choice choice-15 {
            leaf no-auto-negotiation {
              type empty;
            }
            container auto-negotiation {
              presence "enable auto-negotiation";
              leaf remote-fault {
                type string;
              }
            }
          }
          leaf mac-mode {
            type string;
          }
          leaf asynchronous-notification {
            type empty;
          }
          list source-address-filter {
            key "name";
            leaf name {
              type mac-addr;
            }
          }
          leaf pad-to-minimum-frame-size {
            type empty;
          }
          container redundant-parent {
            presence "";
            uses apply-group;
            uses apply-macro;
            leaf parent {
              type interface-device;
            }
          }
          container ieee-802.3ad {
            uses apply-group;
            uses apply-macro;
            container lacp {
              uses apply-group;
              uses apply-macro;
              leaf port-priority {
                type uint16;
              }
            }
            leaf bundle {
              type interface-device;
            }
            leaf link-index {
              type uint16;
            }
            choice choice-9 {
              leaf primary {
                type empty;
              }
              leaf backup {
                type empty;
              }
            }
            leaf distribution-list {
              type string;
            }
          }
          container ethernet-switch-profile {
            uses apply-group;
            uses apply-macro;
            leaf-list tag-protocol-id {
              type string;
              ordered-by user;
            }
            container ethernet-policer-profile {
              uses apply-group;
              uses apply-macro;
              container ieee802.1-priority-map {
                presence "enable ieee802.1-priority-map";
                uses apply-group;
                uses apply-macro;
                leaf-list premium {
                  ordered-by user;
                  type uint32;
                }
              }
              container input-priority-map {
                uses cos-policer-input-priority-map;
              }
              container output-priority-map {
                uses cos-policer-output-priority-map;
              }
              list policer {
                key "name";
                ordered-by user;
                uses cos-policer;
              }
            }
            container accept-from {
              uses apply-group;
              uses apply-macro;
              list mac-address {
                key "name";
                uses mac-list;
              }
            }
            leaf reject-the-rest {
              type empty;
            }
            leaf no-reject-the-rest {
              type empty;
            }
            leaf mac-learn-enable {
              type empty;
            }
            leaf no-mac-learn-enable {
              type empty;
            }
          }
          container mpls {
            uses mpls-ifd-options;
          }
          leaf ignore-l3-incompletes {
            type empty;
          }
          leaf no-auto-mdix {
            type empty;
          }
          leaf ieee-802-3az-eee {
            type empty;
          }
          leaf mru {
            type uint32;
          }
          leaf fec {
            type string;
          }
          leaf speed {
            type string;
          }
        }
        uses optics-options-grouping;
        container otn-options {
          uses otn-options-type;
        }
        container fastether-options {
          uses apply-group;
          uses apply-macro;
          choice loopback-choice {
            leaf loopback {
              type empty;
            }
            leaf no-loopback {
              type empty;
            }
          }
          choice source-filtering-choice {
            leaf source-filtering {
              type empty;
            }
            leaf no-source-filtering {
              type empty;
            }
          }
          choice auto-negotiation-choice {
            leaf auto-negotiation {
              type empty;
            }
            leaf no-auto-negotiation {
              type empty;
            }
          }
          choice flow-control-choice {
            leaf flow-control {
              type empty;
            }
            leaf no-flow-control {
              type empty;
            }
          }
          leaf ingress-rate-limit {
            type uint32;
          }
          list source-address-filter {
            key "name";
            ordered-by user;
            leaf name {
              type mac-addr;
            }
          }
          container redundant-parent {
            presence "";
            uses apply-group;
            uses apply-macro;
            leaf parent {
              type interface-device;
            }
          }
          container ieee-802.3ad {
            uses apply-group;
            uses apply-macro;
            container lacp {
              uses apply-group;
              uses apply-macro;
              leaf port-priority {
                type uint16;
              }
            }
            leaf bundle {
              type interface-device;
            }
            choice choice-7 {
              leaf primary {
                type empty;
              }
              leaf backup {
                type empty;
              }
            }
          }
          container mpls {
            uses mpls-ifd-options;
          }
          leaf ignore-l3-incompletes {
            type empty;
          }
        }
        container redundant-ether-options {
          presence "";
          uses apply-group;
          uses apply-macro;
          leaf redundancy-group {
            type uint16;
          }
          choice loopback-choice {
            leaf loopback {
              type empty;
            }
            leaf no-loopback {
              type empty;
            }
          }
          choice flow-control-choice {
            leaf flow-control {
              type empty;
            }
            leaf no-flow-control {
              type empty;
            }
          }
          choice source-filtering-choice {
            leaf source-filtering {
              type empty;
            }
            leaf no-source-filtering {
              type empty;
            }
          }
          list source-address-filter {
            key "name";
            ordered-by user;
            leaf name {
              type mac-addr;
            }
          }
          leaf link-speed {
            type string;
          }
          leaf minimum-links {
            type uint16;
          }
          container lacp {
            uses apply-group;
            uses apply-macro;
            choice choice-3 {
              leaf active {
                type empty;
              }
              leaf passive {
                type empty;
              }
            }
            leaf periodic {
              type string;
            }
          }
        }
        container aggregated-ether-options {
          uses apply-group;
          uses apply-macro;
          choice loopback-choice {
            leaf loopback {
              type empty;
            }
            leaf no-loopback {
              type empty;
            }
          }
          choice flow-control-choice {
            leaf flow-control {
              type empty;
            }
            leaf no-flow-control {
              type empty;
            }
          }
          choice source-filtering-choice {
            leaf source-filtering {
              type empty;
            }
            leaf no-source-filtering {
              type empty;
            }
          }
          leaf autostate-exclude {
            type empty;
          }
          container link-protection {
            presence "enable link-protection";
            uses apply-group;
            uses apply-macro;
            leaf revertive {
              type empty;
            }
            leaf non-revertive {
              type empty;
            }
            leaf backup-state {
              type string;
            }
            container rtg-config {
              presence "enable rtg-config";
              uses apply-group;
              uses apply-macro;
              leaf preempt-cutover-timer {
                type uint32;
              }
            }
          }
          leaf no-link-protection {
            type empty;
          }
          list source-address-filter {
            key "name";
            ordered-by user;
            leaf name {
              type mac-addr;
            }
          }
          leaf minimum-links {
            type uint16;
          }
          container minimum-bandwidth {
            presence "enable minimum-bandwidth";
            uses apply-group;
            uses apply-macro;
            leaf bw-value {
              type uint64;
            }
            leaf bw-unit {
              type string;
            }
          }
          leaf link-speed {
            type string;
          }
          container lacp {
            uses apply-group;
            uses apply-macro;
            choice choice-3 {
              leaf active {
                type empty;
              }
              leaf passive {
                type empty;
              }
            }
            leaf periodic {
              type string;
            }
            container link-protection {
              presence "enable link-protection";
              uses apply-group;
              uses apply-macro;
              leaf disable {
                type empty;
              }
              choice choice-5 {
                leaf revertive {
                  type empty;
                }
                leaf non-revertive {
                  type empty;
                }
              }
            }
            leaf system-priority {
              type string;
            }
            leaf system-id {
              type mac-addr;
            }
            leaf admin-key {
              type uint16;
            }
          }
          container ethernet-switch-profile {
            uses apply-group;
            uses apply-macro;
            leaf-list tag-protocol-id {
              type string;
              ordered-by user;
            }
          }
          container mc-ae {
            presence "";
            uses apply-group;
            uses apply-macro;
            leaf mc-ae-id {
              type uint16;
            }
            leaf redundancy-group {
              type uint32;
            }
            leaf chassis-id {
              type uint16;
            }
            leaf mode {
              type string;
            }
            leaf status-control {
              type string;
            }
            leaf switchover-mode {
              type string;
            }
            leaf revert-time {
              units "minute";
              type uint32;
            }
            leaf init-delay-time {
              units "seconds";
              type uint16;
            }
            leaf recovery-delay-time {
              units "seconds";
              type uint16;
            }
            container events {
              presence "enable events";
              uses apply-group;
              uses apply-macro;
              container iccp-peer-down {
                presence "enable iccp-peer-down";
                uses apply-group;
                uses apply-macro;
                leaf force-icl-down {
                  type empty;
                }
                leaf prefer-status-control-active {
                  type empty;
                }
              }
            }
          }
        }
        container es-options {
          uses apply-group;
          uses apply-macro;
          leaf backup-interface {
            type interface-device;
          }
        }
        container dsl-options {
          uses apply-group;
          uses apply-macro;
          leaf operating-mode {
            type string;
          }
        }
        container vdsl-options {
          uses apply-group;
          uses apply-macro;
          leaf vdsl-profile {
            type string;
          }
        }
        container shdsl-options {
          uses apply-group;
          uses apply-macro;
          leaf annex {
            type string;
          }
          leaf line-rate {
            type string;
          }
          leaf loopback {
            type string;
          }
          container snr-margin {
            presence "enable snr-margin";
            uses apply-group;
            uses apply-macro;
            leaf current {
              type string;
            }
            leaf snext {
              type string;
            }
          }
        }
        container data-input {
          uses apply-group;
          uses apply-macro;
          choice choice-3 {
            leaf system {
              type empty;
            }
            leaf interface {
              type interface-device;
            }
          }
        }
        container switch-options {
          uses apply-group;
          uses apply-macro;
          list switch-port {
            key "name";
            leaf name {
              type string;
            }
            uses apply-group;
            uses apply-macro;
            leaf auto-negotiation {
              type empty;
            }
            leaf no-auto-negotiation {
              type empty;
            }
            leaf link-mode {
              type string;
            }
            leaf speed {
              type string;
            }
            leaf vlan-id {
              type uint32;
            }
            leaf cascade-port {
              type empty;
            }
          }
        }
        container container-options {
          uses apply-group;
          uses apply-macro;
          container container-type {
            presence "enable container-type";
            uses apply-group;
            uses apply-macro;
            choice choice-3 {
              container aps {
                presence "enable aps";
                uses aps-type;
              }
            }
          }
          container member-interface-type {
            uses apply-group;
            uses apply-macro;
            choice choice-3 {
              container sonet {
                presence "";
                uses apply-group;
                uses apply-macro;
                leaf member-interface-speed {
                  type string;
                }
              }
              container atm {
                presence "";
                uses apply-group;
                uses apply-macro;
                leaf member-interface-speed {
                  type string;
                }
              }
            }
          }
          container redundancy {
            uses apply-group;
            uses apply-macro;
            container hold-time {
              presence "";
              leaf up {
                type uint32;
              }
              leaf down {
                type uint32;
              }
            }
          }
          leaf-list container-list {
            type interface-device;
            ordered-by user;
          }
          leaf primary {
            type empty;
          }
          leaf standby {
            type empty;
          }
          leaf allow-configuration-override {
            type empty;
          }
        }
        container layer2-policer {
          uses apply-group;
          uses apply-macro;
          leaf input-hierarchical-policer {
            type string;
          }
        }
        list unit {
          key "name";
          leaf name {
            type string;
          }
          uses apply-group;
          uses apply-macro;
          container policer-overhead {
            uses apply-group;
            uses apply-macro;
            leaf policer-overhead-value {
              units "bytes";
              type int32;
            }
            leaf ingress {
              units "bytes";
              type int32;
            }
            leaf egress {
              units "bytes";
              type int32;
            }
          }
          leaf alias {
            type string;
          }
          leaf enhanced-convergence {
            type empty;
          }
          leaf proxy-macip-advertisement {
            type empty;
          }
          leaf virtual-gateway-accept-data {
            type empty;
          }
          container peer-psd {
            presence "";
            leaf psd-name {
              type string;
            }
          }
          container peer-interface {
            presence "enable peer-interface";
            uses apply-group;
            uses apply-macro;
            leaf interface-name {
              type interface-unit;
            }
          }
          container interface-shared-with {
            presence "";
            uses apply-group;
            uses apply-macro;
            leaf psd-name {
              type string;
            }
          }
          choice choice-9 {
            leaf disable {
              type empty;
            }
          }
          leaf passive-monitor-mode {
            type empty;
          }
          leaf per-session-scheduler {
            type empty;
          }
          leaf clear-dont-fragment-bit {
            type empty;
          }
          leaf reassemble-packets {
            type empty;
          }
          container rpm {
            uses apply-group;
            uses apply-macro;
            choice choice-3 {
              leaf client {
                type empty;
              }
              leaf server {
                type empty;
              }
              leaf twamp-server {
                type empty;
              }
            }
          }
          leaf description {
            type string;
          }
          container dial-options {
            uses apply-group;
            uses apply-macro;
            choice choice-3 {
              leaf l2tp-interface-id {
                type string;
              }
              leaf ipsec-interface-id {
                type string;
              }
            }
            choice choice-4 {
              leaf dedicated {
                type empty;
              }
              leaf shared {
                type empty;
              }
            }
          }
          leaf-list demux-source {
            ordered-by user;
            type string;
          }
          leaf-list demux-destination {
            ordered-by user;
            type string;
          }
          leaf encapsulation {
            type string;
          }
          leaf mtu {
            type uint32;
          }
          choice choice-32 {
            leaf point-to-point {
              type empty;
            }
            leaf multipoint {
              type empty;
            }
          }
          leaf bandwidth {
            type string;
          }
          container radio-router {
            presence "enable radio-router";
            uses dynamic-ifbw-parms-type;
          }
          leaf traps {
            type empty;
          }
          leaf no-traps {
            type empty;
          }
          container arp-resp {
            presence "enable arp-resp";
            choice choice-3 {
              leaf unrestricted {
                type empty;
              }
              leaf restricted {
                type empty;
              }
            }
          }
          container proxy-arp {
            presence "enable proxy-arp";
            choice choice-3 {
              leaf unrestricted {
                type empty;
              }
              leaf restricted {
                type empty;
              }
            }
          }
          choice choice-45 {
            leaf vlan-id {
              type string;
            }
            leaf vlan-id-range {
              type string;
            }
            leaf-list vlan-id-list {
              type string;
            }
            container vlan-tags {
              presence "";
              leaf outer {
                type string;
              }
              choice choice-5 {
                leaf inner {
                  type string;
                }
                leaf inner-range {
                  type string;
                }
                leaf-list inner-list {
                  type string;
                }
              }
            }
          }
          leaf native-inner-vlan-id {
            type uint32;
          }
          container inner-vlan-id-range {
            presence "";
            leaf start {
              type uint32;
            }
            leaf end {
              type uint32;
            }
          }
          container accept-source-mac {
            uses apply-group;
            uses apply-macro;
            list mac-address {
              key "name";
              uses mac-list;
            }
          }
          container input-vlan-map {
            uses vlan-map;
          }
          container output-vlan-map {
            uses vlan-map;
          }
          leaf receive-lsp {
            type string;
          }
          leaf transmit-lsp {
            type string;
          }
          leaf dlci {
            type uint32;
          }
          leaf multicast-dlci {
            type uint32;
          }
          choice choice-64 {
            leaf vci {
              type atm-vci;
            }
            leaf allow-any-vci {
              type empty;
            }
            leaf vpi {
              type uint32;
            }
            leaf trunk-id {
              type uint32;
            }
          }
          container atm-l2circuit-mode {
            choice choice-3 {
              leaf cell {
                type empty;
              }
              leaf aal5 {
                type empty;
              }
            }
          }
          container vci-range {
            presence "";
            leaf start {
              type uint16;
            }
            leaf end {
              type uint16;
            }
          }
          leaf trunk-bandwidth {
            type string;
          }
          leaf multicast-vci {
            type atm-vci;
          }
          container shaping {
            uses dcd-shaping-config;
          }
          container oam-period {
            choice choice-3 {
              leaf oam-period {
                type uint32;
              }
              container disable {
                presence "enable disable";
              }
            }
          }
          container oam-liveness {
            uses apply-group;
            uses apply-macro;
            leaf up-count {
              type uint32;
            }
            leaf down-count {
              type uint32;
            }
          }
          container ppp-options {
            uses ppp-options-type;
          }
          container pppoe-options {
            presence "";
            uses pppoe-options-type;
          }
          container pppoe-underlying-options {
            uses pppoe-underlying-options-type;
          }
          container demux-options {
            presence "";
            uses demux-options-type;
          }
          choice choice-87 {
            container keepalives {
              presence "enable keepalives";
              uses keepalives-type;
            }
            leaf no-keepalives {
              type empty;
            }
          }
          leaf inverse-arp {
            type empty;
          }
          leaf transmit-weight {
            type uint16;
          }
          container epd-threshold {
            presence "";
            uses epd-threshold-config;
          }
          leaf cell-bundle-size {
            type uint32;
          }
          leaf plp-to-clp {
            type empty;
          }
          leaf atm-scheduler-map {
            type string;
          }
          leaf mrru {
            type uint16;
          }
          leaf short-sequence {
            type empty;
          }
          leaf fragment-threshold {
            type uint32;
          }
          leaf drop-timeout {
            type uint16;
          }
          leaf disable-mlppp-inner-ppp-pfc {
            type empty;
          }
          leaf minimum-links {
            type uint16;
          }
          leaf multilink-max-classes {
            type uint16;
          }
          container compression {
            presence "enable compression";
            uses apply-group;
            uses apply-macro;
            container rtp {
              presence "enable rtp";
              uses apply-group;
              uses apply-macro;
              leaf f-max-period {
                type uint32;
              }
              leaf-list queues {
                ordered-by user;
                type string;
              }
              container port {
                presence "";
                leaf minimum {
                  type uint32;
                }
                leaf maximum {
                  type uint32;
                }
              }
              container maximum-contexts {
                leaf number {
                  type uint32;
                }
              }
            }
          }
          leaf interleave-fragments {
            type empty;
          }
          leaf link-layer-overhead {
            type unsigned-float;
          }
          leaf accounting-profile {
            type string;
          }
          leaf peer-unit {
            type uint32;
          }
          container tunnel {
            presence "";
            uses apply-group;
            uses apply-macro;
            leaf source {
              type ipv4addr;
            }
            leaf destination {
              type ipv4addr;
            }
            leaf key {
              type uint32;
            }
            leaf backup-destination {
              type ipv4addr;
            }
            choice choice-11 {
              leaf allow-fragmentation {
                type empty;
              }
              leaf do-not-fragment {
                type empty;
              }
            }
            leaf ttl {
              type uint32;
            }
            leaf path-mtu-discovery {
              type empty;
            }
            leaf no-path-mtu-discovery {
              type empty;
            }
            container routing-instance {
              uses apply-group;
              uses apply-macro;
              leaf destination {
                type string;
              }
            }
          }
          leaf compression-device {
            type interface-unit;
          }
          container layer2-policer {
            uses apply-group;
            uses apply-macro;
            choice choice-3 {
              leaf input-policer {
                type string;
              }
              leaf input-hierarchical-policer {
                type string;
              }
              leaf input-three-color {
                type string;
              }
            }
            choice choice-4 {
              leaf output-policer {
                type string;
              }
              leaf output-three-color {
                type string;
              }
            }
          }
          container filter {
            uses apply-group;
            uses apply-macro;
            leaf input {
              type string;
            }
            leaf output {
              type string;
            }
          }
          leaf statistics {
            type empty;
          }
          container esi {
            presence "";
            uses apply-group;
            uses apply-macro;
            container apply-advanced {
              uses apply-group;
              uses apply-macro;
            }
            leaf identifier {
              mandatory true;
              type string;
            }
            choice choice-single-active {
              leaf single-active {
                type empty;
              }
              leaf all-active {
                type empty;
              }
            }
          }
          container family {
            uses apply-group;
            uses apply-macro;
            container inet {
              presence "enable inet";
              uses apply-group;
              uses apply-macro;
              container targeted-broadcast {
                presence "enable targeted-broadcast";
                uses apply-group;
                uses apply-macro;
                choice choice-3 {
                  leaf forward-and-send-to-re {
                    type empty;
                  }
                  leaf forward-only {
                    type empty;
                  }
                }
              }
              leaf receive-options-packets {
                type empty;
              }
              leaf receive-ttl-exceeded {
                type empty;
              }
              container accounting {
                uses apply-group;
                uses apply-macro;
                container source-class-usage {
                  uses apply-group;
                  uses apply-macro;
                  leaf input {
                    type empty;
                  }
                  leaf output {
                    type empty;
                  }
                }
                leaf destination-class-usage {
                  type empty;
                }
              }
              leaf mac-validate {
                type string;
              }
              container rpf-check {
                presence "enable rpf-check";
                uses apply-group;
                uses apply-macro;
                leaf fail-filter {
                  type string;
                }
                container mode {
                  leaf loose {
                    type empty;
                  }
                }
              }
              leaf mtu {
                type uint32;
              }
              leaf no-redirects {
                type empty;
              }
              leaf no-neighbor-learn {
                type empty;
              }
              leaf multicast-only {
                type empty;
              }
              leaf primary {
                type empty;
              }
              leaf ipsec-sa {
                type string;
              }
              list demux-source {
                key "name";
                ordered-by user;
                leaf name {
                  type string;
                }
                uses apply-group;
                uses apply-macro;
              }
              list demux-destination {
                key "name";
                ordered-by user;
                leaf name {
                  type string;
                }
                uses apply-group;
                uses apply-macro;
              }
              container filter {
                uses apply-group;
                uses apply-macro;
                choice choice-3 {
                  container input {
                    presence "";
                    leaf filter-name {
                      type string;
                    }
                    leaf precedence {
                      type uint32;
                    }
                  }
                  leaf-list input-list {
                    type string;
                    ordered-by user;
                  }
                }
                choice choice-4 {
                  container output {
                    presence "";
                    leaf filter-name {
                      type string;
                    }
                    leaf precedence {
                      type uint32;
                    }
                  }
                  leaf-list output-list {
                    type string;
                    ordered-by user;
                  }
                }
                container adf {
                  presence "";
                  uses apply-group;
                  uses apply-macro;
                  list rule {
                    key "name";
                    ordered-by user;
                    leaf name {
                      type string;
                    }
                    uses apply-group;
                    uses apply-macro;
                  }
                  leaf counter {
                    type empty;
                  }
                  leaf input-precedence {
                    type uint32;
                  }
                  leaf output-precedence {
                    type uint32;
                  }
                }
                leaf group {
                  type uint32;
                }
              }
              container simple-filter {
                uses apply-group;
                uses apply-macro;
                leaf input {
                  type string;
                }
              }
              leaf input-hierarchical-policer {
                type string;
              }
              container policer {
                uses apply-group;
                uses apply-macro;
                leaf arp {
                  type string;
                }
                leaf input {
                  type string;
                }
                leaf output {
                  type string;
                }
              }
              container sampling {
                uses apply-group;
                uses apply-macro;
                leaf input {
                  type empty;
                }
                leaf output {
                  type empty;
                }
              }
              list next-hop-tunnel {
                key "name";
                ordered-by user;
                leaf name {
                  type string;
                }
                uses apply-group;
                uses apply-macro;
                leaf ipsec-vpn {
                  type string;
                }
              }
              list address {
                key "name";
                ordered-by user;
                leaf name {
                  type ipv4prefix;
                }
                uses apply-group;
                uses apply-macro;
                leaf destination {
                  type ipv4addr;
                }
                leaf destination-profile {
                  type string;
                }
                leaf broadcast {
                  type ipv4addr;
                }
                leaf primary {
                  type empty;
                }
                leaf preferred {
                  type empty;
                }
                leaf master-only {
                  type empty;
                }
                list multipoint-destination {
                  key "name";
                  ordered-by user;
                  leaf name {
                    type ipv4addr;
                  }
                  uses apply-group;
                  uses apply-macro;
                  choice choice-3 {
                    leaf dlci {
                      type uint32;
                    }
                    leaf vci {
                      type atm-vci;
                    }
                  }
                  container shaping {
                    uses dcd-shaping-config;
                  }
                  container oam-period {
                    choice choice-3 {
                      leaf oam_period {
                        type uint32;
                      }
                      container disable {
                        presence "enable disable";
                      }
                    }
                  }
                  container oam-liveness {
                    uses apply-group;
                    uses apply-macro;
                    leaf up-count {
                      type uint32;
                    }
                    leaf down-count {
                      type uint32;
                    }
                  }
                  leaf inverse-arp {
                    type empty;
                  }
                  leaf transmit-weight {
                    type uint16;
                  }
                  container epd-threshold {
                    presence "";
                    uses epd-threshold-config;
                  }
                }
                list arp {
                  key "name";
                  ordered-by user;
                  leaf name {
                    type ipv4addr;
                  }
                  leaf l2-interface {
                    type interface-name;
                  }
                  choice choice-5 {
                    leaf mac {
                      type mac-unicaset;
                    }
                    leaf multicast-mac {
                      type mac-multicast;
                    }
                  }
                  leaf publish {
                    type empty;
                  }
                }
                container web-authentication {
                  uses apply-group;
                  uses apply-macro;
                  leaf http {
                    type empty;
                  }
                }
                list vrrp-group {
                  key "name";
                  ordered-by user;
                  uses vrrp-group;
                }
              }
              container unnumbered-address {
                presence "";
                leaf source {
                  type interface-unit;
                }
                leaf preferred-source-address {
                  type string;
                }
                leaf destination {
                  type ipv4addr;
                }
                leaf destination-profile {
                  type string;
                }
              }
              container location-pool-address {
                presence "enable location-pool-address";
                uses apply-group;
                uses apply-macro;
                leaf pool-name {
                  type string;
                }
              }
              leaf negotiate-address {
                type empty;
              }
              container dhcp {
                presence "enable dhcp";
                uses apply-group;
                uses apply-macro;
                container client-identifier {
                  choice choice-3 {
                    leaf ascii {
                      type string;
                    }
                    leaf hexadecimal {
                      type string;
                    }
                  }
                }
                leaf lease-time {
                  type string;
                }
                leaf retransmission-attempt {
                  type uint32;
                }
                leaf retransmission-interval {
                  type uint32;
                }
                leaf server-address {
                  type ipv4addr;
                }
                leaf update-server {
                  type empty;
                }
                leaf vendor-id {
                  type string;
                }
              }
            }
            container iso {
              presence "enable iso";
              uses apply-group;
              uses apply-macro;
              list address {
                key "name";
                ordered-by user;
                leaf name {
                  type isoaddr;
                }
                uses apply-group;
                uses apply-macro;
              }
              leaf mtu {
                type uint32;
              }
            }
            container inet6 {
              presence "enable inet6";
              uses apply-group;
              uses apply-macro;
              container rpf-check {
                presence "enable rpf-check";
                uses apply-group;
                uses apply-macro;
                leaf fail-filter {
                  type string;
                }
                container mode {
                  leaf loose {
                    type empty;
                  }
                }
              }
              container accounting {
                uses apply-group;
                uses apply-macro;
                container source-class-usage {
                  uses apply-group;
                  uses apply-macro;
                  leaf input {
                    type empty;
                  }
                  leaf output {
                    type empty;
                  }
                }
                leaf destination-class-usage {
                  type empty;
                }
              }
              leaf mtu {
                type uint32;
              }
              leaf no-neighbor-learn {
                type empty;
              }
              container filter {
                uses apply-group;
                uses apply-macro;
                choice choice-3 {
                  container input {
                    presence "";
                    leaf filter-name {
                      type string;
                    }
                    leaf precedence {
                      type uint32;
                    }
                  }
                  leaf-list input-list {
                    type string;
                    ordered-by user;
                  }
                }
                choice choice-4 {
                  container output {
                    presence "";
                    leaf filter-name {
                      type string;
                    }
                    leaf precedence {
                      type uint32;
                    }
                  }
                  leaf-list output-list {
                    type string;
                    ordered-by user;
                  }
                }
                container adf {
                  presence "";
                  uses apply-group;
                  uses apply-macro;
                  list rule {
                    key "name";
                    ordered-by user;
                    leaf name {
                      type string;
                    }
                    uses apply-group;
                    uses apply-macro;
                  }
                  leaf counter {
                    type empty;
                  }
                  leaf input-precedence {
                    type uint32;
                  }
                  leaf output-precedence {
                    type uint32;
                  }
                }
                leaf group {
                  type uint32;
                }
              }
              leaf input-hierarchical-policer {
                type string;
              }
              container policer {
                uses apply-group;
                uses apply-macro;
                leaf input {
                  type string;
                }
                leaf output {
                  type string;
                }
              }
              container sampling {
                uses apply-group;
                uses apply-macro;
                leaf input {
                  type empty;
                }
                leaf output {
                  type empty;
                }
              }
              list address {
                key "name";
                ordered-by user;
                leaf name {
                  type ipv6prefix;
                }
                uses apply-group;
                uses apply-macro;
                leaf destination {
                  type ipv6addr;
                }
                leaf eui-64 {
                  type empty;
                }
                leaf primary {
                  type empty;
                }
                leaf preferred {
                  type empty;
                }
                leaf master-only {
                  type empty;
                }
                list ndp {
                  key "name";
                  ordered-by user;
                  leaf name {
                    type ipv6addr;
                  }
                  leaf l2-interface {
                    type interface-name;
                  }
                  choice choice-5 {
                    leaf mac {
                      type mac-unicaset;
                    }
                    leaf multicast-mac {
                      type mac-multicast;
                    }
                  }
                  leaf publish {
                    type empty;
                  }
                }
                list vrrp-inet6-group {
                  key "name";
                  ordered-by user;
                  uses vrrp-group;
                }
              }
              list demux-source {
                key "name";
                ordered-by user;
                leaf name {
                  type string;
                }
                uses apply-group;
                uses apply-macro;
              }
              list demux-destination {
                key "name";
                ordered-by user;
                leaf name {
                  type string;
                }
                uses apply-group;
                uses apply-macro;
              }
              container unnumbered-address {
                presence "";
                leaf source {
                  type interface-unit;
                }
                leaf preferred-source-address {
                  type string;
                }
              }
              leaf dad-disable {
                type empty;
              }
              leaf no-dad-disable {
                type empty;
              }
            }
            container mpls {
              presence "enable mpls";
              uses apply-group;
              uses apply-macro;
              leaf mtu {
                type uint32;
              }
              leaf maximum-labels {
                type uint32;
              }
              container filter {
                uses apply-group;
                uses apply-macro;
                choice choice-3 {
                  leaf input {
                    type string;
                  }
                  leaf-list input-list {
                    type string;
                    ordered-by user;
                  }
                }
                choice choice-4 {
                  leaf output {
                    type string;
                  }
                  leaf-list output-list {
                    type string;
                    ordered-by user;
                  }
                }
                leaf group {
                  type uint32;
                }
              }
              leaf input-hierarchical-policer {
                type string;
              }
              container policer {
                uses apply-group;
                uses apply-macro;
                leaf input {
                  type string;
                }
                leaf output {
                  type string;
                }
              }
            }
            container mlppp {
              presence "";
              uses apply-group;
              uses apply-macro;
              leaf bundle {
                type interface-unit;
              }
            }
            container mlfr-end-to-end {
              presence "";
              uses apply-group;
              uses apply-macro;
              leaf bundle {
                type interface-unit;
              }
            }
            container mlfr-uni-nni {
              presence "";
              uses apply-group;
              uses apply-macro;
              leaf bundle {
                type interface-unit;
              }
            }
            container ccc {
              presence "enable ccc";
              uses apply-group;
              uses apply-macro;
              container filter {
                uses apply-group;
                uses apply-macro;
                choice choice-3 {
                  leaf input {
                    type string;
                  }
                  leaf-list input-list {
                    type string;
                    ordered-by user;
                  }
                }
                choice choice-4 {
                  leaf output {
                    type string;
                  }
                  leaf-list output-list {
                    type string;
                    ordered-by user;
                  }
                }
                leaf group {
                  type uint32;
                }
              }
              container policer {
                uses apply-group;
                uses apply-macro;
                leaf input {
                  type string;
                }
                leaf output {
                  type string;
                }
              }
              leaf translate-fecn-and-becn {
                type empty;
              }
              choice choice-9 {
                leaf translate-discard-eligible {
                  type empty;
                }
                leaf translate-plp-control-word-de {
                  type empty;
                }
              }
              leaf keep-address-and-control {
                type empty;
              }
            }
            container tcc {
              presence "enable tcc";
              uses apply-group;
              uses apply-macro;
              container policer {
                uses apply-group;
                uses apply-macro;
                leaf input {
                  type string;
                }
                leaf output {
                  type string;
                }
              }
              container proxy {
                presence "enable proxy";
                uses apply-group;
                uses apply-macro;
                leaf inet-address {
                  type ipv4addr;
                }
              }
              container remote {
                presence "enable remote";
                uses apply-group;
                uses apply-macro;
                leaf inet-address {
                  type ipv4addr;
                }
                leaf mac-address {
                  type mac-addr;
                }
              }
              leaf-list protocols {
                ordered-by user;
                type string;
              }
            }
            container vpls {
              presence "enable vpls";
              uses apply-group;
              uses apply-macro;
              leaf core-facing {
                type empty;
              }
              container filter {
                uses apply-group;
                uses apply-macro;
                choice choice-3 {
                  container input {
                    presence "";
                    leaf filter-name {
                      type string;
                    }
                    leaf precedence {
                      type uint32;
                    }
                  }
                  leaf-list input-list {
                    type string;
                    ordered-by user;
                  }
                }
                choice choice-4 {
                  container output {
                    presence "";
                    leaf filter-name {
                      type string;
                    }
                    leaf precedence {
                      type uint32;
                    }
                  }
                  leaf-list output-list {
                    type string;
                    ordered-by user;
                  }
                }
                container adf {
                  presence "";
                  uses apply-group;
                  uses apply-macro;
                  list rule {
                    key "name";
                    ordered-by user;
                    leaf name {
                      type string;
                    }
                    uses apply-group;
                    uses apply-macro;
                  }
                  leaf counter {
                    type empty;
                  }
                  leaf input-precedence {
                    type uint32;
                  }
                  leaf output-precedence {
                    type uint32;
                  }
                }
                leaf group {
                  type uint32;
                }
              }
              container policer {
                uses apply-group;
                uses apply-macro;
                leaf input {
                  type string;
                }
                leaf output {
                  type string;
                }
              }
            }
            container bridge {
              presence "enable bridge";
              uses apply-group;
              uses apply-macro;
              leaf core-facing {
                type empty;
              }
              container filter {
                uses apply-group;
                uses apply-macro;
                choice choice-3 {
                  container input {
                    presence "";
                    leaf filter-name {
                      type string;
                    }
                    leaf precedence {
                      type uint32;
                    }
                  }
                  leaf-list input-list {
                    type string;
                    ordered-by user;
                  }
                }
                choice choice-4 {
                  container output {
                    presence "";
                    leaf filter-name {
                      type string;
                    }
                    leaf precedence {
                      type uint32;
                    }
                  }
                  leaf-list output-list {
                    type string;
                    ordered-by user;
                  }
                }
                container adf {
                  presence "";
                  uses apply-group;
                  uses apply-macro;
                  list rule {
                    key "name";
                    ordered-by user;
                    leaf name {
                      type string;
                    }
                    uses apply-group;
                    uses apply-macro;
                  }
                  leaf counter {
                    type empty;
                  }
                  leaf input-precedence {
                    type uint32;
                  }
                  leaf output-precedence {
                    type uint32;
                  }
                }
                leaf group {
                  type uint32;
                }
              }
              container policer {
                uses apply-group;
                uses apply-macro;
                leaf input {
                  type string;
                }
                leaf output {
                  type string;
                }
              }
              leaf interface-mode {
                type string;
              }
              leaf bridge-domain-type {
                type string;
              }
              choice choice-13 {
                leaf vlan-id {
                  type uint32;
                }
                leaf-list vlan-id-list {
                  type string;
                  ordered-by user;
                }
                leaf-list inner-vlan-id-list {
                  type string;
                  ordered-by user;
                }
              }
              container vlan-rewrite {
                uses apply-group;
                uses apply-macro;
                list translate {
                  key "name";
                  ordered-by user;
                  leaf name {
                    type string;
                  }
                  leaf to-vlan-id {
                    type uint32;
                  }
                }
              }
              choice choice-16 {
                leaf isid-list {
                  type string;
                }
              }
            }
            container ethernet-switching {
              presence "enable ethernet-switching";
              uses ethernet-switching-type;
            }
            container fibre-channel {
              presence "enable fibre-channel";
              uses fibre-channel-type;
            }
            container any {
              presence "enable any";
              uses apply-group;
              uses apply-macro;
              container filter {
                uses apply-group;
                uses apply-macro;
                leaf input {
                  type string;
                }
                leaf group {
                  type uint32;
                }
              }
            }
          }
          leaf service-domain {
            type string;
          }
          leaf copy-tos-to-outer-ip-header {
            type empty;
          }
        }
        container no-partition {
          leaf interface-type {
            type string;
          }
        }
        list partition {
          key "name";
          ordered-by user;
          leaf name {
            type string;
          }
          leaf oc-slice {
            type string;
          }
          leaf timeslots {
            type string;
          }
          leaf interface-type {
            type string;
          }
        }
        container cellular-options {
          presence "enable cellular-options";
          uses apply-group;
          uses apply-macro;
          container gsm-options {
            presence "enable gsm-options";
            uses apply-group;
            uses apply-macro;
            container select-profile {
              presence "";
              leaf profile-id {
                type uint32;
              }
            }
            leaf encrypted-sim-unlock-code {
              type unreadable;
            }
          }
        }
      }
      list interface {
        key "name";
        uses interfaces-type;
      }
    }
    container multi-chassis {
      presence "enable multi-chassis";
      uses apply-group;
      uses apply-macro;
      container mc-lag {
        presence "enable mc-lag";
        uses apply-group;
        uses apply-macro;
        container consistency-check {
          presence "enable consistency-check";
          uses apply-group;
          uses apply-macro;
          leaf comparison-delay-time {
            units "seconds";
            type uint32;
          }
          container traceoptions {
            uses apply-group;
            uses apply-macro;
            leaf no-remote-trace {
              type empty;
            }
            container file {
              leaf filename {
                type string;
              }
              leaf size {
                type string;
              }
              leaf files {
                type uint32;
              }
              leaf world-readable {
                type empty;
              }
              leaf no-world-readable {
                type empty;
              }
              leaf match {
                type regular-expression;
              }
            }
            list flag {
              key "name";
              ordered-by user;
              leaf name {
                type string;
              }
            }
          }
        }
      }
      list multi-chassis-protection {
        key "name";
        uses multi-chassis-protection-group;
      }
    }
    container forwarding-options {
      uses juniper-forwarding-options;
    }
    container event-options {
      uses apply-group;
      uses apply-macro;
      list generate-event {
        key "name";
        ordered-by user;
        leaf name {
          type key-attribute-string-type;
        }
        choice choice-3 {
          leaf time-of-day {
            type time;
          }
          leaf time-interval {
            type uint32;
          }
        }
      }
      list policy {
        key "name";
        ordered-by user;
        leaf name {
          type key-attribute-string-type;
        }
        uses apply-group;
        uses apply-macro;
        leaf-list events {
          type string;
          ordered-by user;
        }
        list within {
          key "name";
          ordered-by user;
          leaf name {
            type string;
          }
          uses apply-group;
          uses apply-macro;
          container trigger {
            presence "";
            choice choice-3 {
              leaf until {
                type empty;
              }
              leaf on {
                type empty;
              }
              leaf after {
                type empty;
              }
            }
            leaf count {
              type uint32;
            }
          }
          leaf-list events {
            type string;
            ordered-by user;
          }
          container not {
            leaf-list events {
              type string;
              ordered-by user;
            }
          }
        }
        list attributes-match {
          key "from-event-attribute condition to-event-attribute-value";
          ordered-by user;
          leaf from-event-attribute {
            type string;
          }
          leaf condition {
            type string;
          }
          leaf to-event-attribute-value {
            type string;
          }
        }
        container then {
          uses apply-group;
          uses apply-macro;
          leaf ignore {
            type empty;
          }
          container priority-override {
            uses apply-group;
            uses apply-macro;
            leaf facility {
              type string;
            }
            leaf severity {
              type string;
            }
          }
          list upload {
            key "filename destination";
            ordered-by user;
            leaf filename {
              type string;
            }
            leaf destination {
              type string;
            }
            uses apply-group;
            uses apply-macro;
            leaf user-name {
              type string;
            }
            leaf transfer-delay {
              type uint32;
            }
            container retry-count {
              presence "";
              leaf retry {
                type uint8;
              }
              leaf retry-interval {
                type uint32;
              }
            }
          }
          container change-configuration {
            presence "";
            uses apply-group;
            uses apply-macro;
            container retry {
              presence "";
              leaf count {
                type uint8;
              }
              leaf interval {
                type uint32;
                units "seconds";
              }
            }
            list commands {
              key "name";
              ordered-by user;
              leaf name {
                type string;
              }
              uses apply-group;
              uses apply-macro;
            }
            leaf user-name {
              type string;
            }
            container commit-options {
              uses apply-group;
              uses apply-macro;
              container check {
                presence "enable check";
                uses apply-group;
                uses apply-macro;
                leaf synchronize {
                  type empty;
                }
              }
              leaf synchronize {
                type empty;
              }
              leaf force {
                type empty;
              }
              leaf log {
                type string;
              }
            }
          }
          container execute-commands {
            presence "";
            uses apply-group;
            uses apply-macro;
            list commands {
              key "name";
              ordered-by user;
              leaf name {
                type string;
              }
              uses apply-group;
              uses apply-macro;
            }
            leaf user-name {
              type string;
            }
            leaf output-filename {
              type string;
            }
            list destination {
              key "name";
              ordered-by user;
              leaf name {
                type string;
              }
              uses apply-group;
              uses apply-macro;
              leaf transfer-delay {
                type uint32;
              }
              container retry-count {
                presence "";
                leaf retry {
                  type uint8;
                }
                leaf retry-interval {
                  type uint32;
                }
              }
            }
            leaf output-format {
              type string;
            }
          }
          list event-script {
            key "name";
            ordered-by user;
            leaf name {
              type key-attribute-string-type;
            }
            uses apply-group;
            uses apply-macro;
            list arguments {
              key "name";
              ordered-by user;
              leaf name {
                type key-attribute-string-type;
              }
              leaf value {
                type string;
              }
            }
            leaf user-name {
              type string;
            }
            leaf output-filename {
              type string;
            }
            list destination {
              key "name";
              ordered-by user;
              leaf name {
                type string;
              }
              uses apply-group;
              uses apply-macro;
              leaf transfer-delay {
                type uint32;
              }
              container retry-count {
                presence "";
                leaf retry {
                  type uint8;
                }
                leaf retry-interval {
                  type uint32;
                }
              }
            }
            leaf output-format {
              type string;
            }
          }
          leaf raise-trap {
            type empty;
          }
        }
      }
      container event-script {
        uses apply-group;
        uses apply-macro;
        leaf optional {
          type empty;
        }
        leaf max-datasize {
          type string;
          units "bytes";
        }
        container dampen {
          presence "enable dampen";
          uses apply-group;
          uses apply-macro;
          container dampen-options {
            uses apply-group;
            uses apply-macro;
            leaf cpu-factor {
              type uint32;
            }
            leaf line-interval {
              type uint32;
            }
            leaf time-interval {
              units "microseconds";
              type uint32;
            }
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
          }
          list flag {
            key "name";
            leaf name {
              type string;
            }
          }
        }
        list file {
          key "name";
          ordered-by user;
          leaf name {
            type key-attribute-string-type;
          }
          uses apply-group;
          uses apply-macro;
          leaf source {
            type string;
          }
          leaf python-script-user {
            type string;
          }
          container dampen {
            presence "enable dampen";
            uses apply-group;
            uses apply-macro;
            container dampen-options {
              uses apply-group;
              uses apply-macro;
              leaf cpu-factor {
                type uint32;
              }
              leaf line-interval {
                type uint32;
              }
              leaf time-interval {
                units "microseconds";
                type uint32;
              }
            }
          }
          leaf routing-instance {
            type string;
          }
          leaf refresh {
            type empty;
          }
          leaf refresh-from {
            type string;
          }
          container checksum {
            uses apply-group;
            uses apply-macro;
            leaf md5 {
              type string;
            }
            leaf sha1 {
              type string;
            }
            leaf sha-256 {
              type string;
            }
          }
          list remote-execution {
            key "name";
            ordered-by user;
            leaf name {
              type key-attribute-string-type;
            }
            uses apply-group;
            uses apply-macro;
            leaf username {
              type string;
            }
            leaf passphrase {
              type unreadable;
            }
          }
        }
        leaf refresh {
          type empty;
        }
        leaf refresh-from {
          type string;
        }
      }
      list destinations {
        key "name";
        ordered-by user;
        leaf name {
          type string;
        }
        uses apply-group;
        uses apply-macro;
        leaf transfer-delay {
          type uint32;
        }
        list archive-sites {
          key "name";
          ordered-by user;
          leaf name {
            type string;
          }
          leaf password {
            type unreadable;
          }
        }
      }
      container traceoptions {
        uses apply-group;
        uses apply-macro;
        leaf no-remote-trace {
          type empty;
        }
        container file {
          leaf filename {
            type string;
          }
          leaf size {
            type string;
          }
          leaf files {
            type uint32;
          }
          leaf world-readable {
            type empty;
          }
          leaf no-world-readable {
            type empty;
          }
          leaf match {
            type regular-expression;
          }
        }
        list flag {
          key "name";
          ordered-by user;
          leaf name {
            type string;
          }
        }
      }
    }
    container snmp {
      uses apply-group;
      uses apply-macro;
      leaf system-name {
        type string;
      }
      leaf description {
        type string;
      }
      leaf location {
        type string;
      }
      leaf contact {
        type string;
      }
      leaf-list interface {
        type interface-name;
        ordered-by user;
      }
      leaf packet-size {
        type string;
      }
      container filter-interfaces {
        presence "enable filter-interfaces";
        uses apply-group;
        uses apply-macro;
        list interfaces {
          key "name";
          ordered-by user;
          leaf name {
            type regular-expression;
          }
          uses apply-group;
          uses apply-macro;
        }
        leaf all-internal-interfaces {
          type empty;
        }
      }
      leaf filter-duplicates {
        type empty;
      }
      container nonvolatile {
        uses apply-group;
        uses apply-macro;
        leaf commit-delay {
          type uint32;
        }
      }
      container v3 {
        uses apply-group;
        uses apply-macro;
        container usm {
          uses apply-group;
          uses apply-macro;
          container local-engine {
            uses apply-group;
            uses apply-macro;
            list user {
              key "name";
              ordered-by user;
              uses v3-user-config;
            }
          }
          list remote-engine {
            key "name";
            ordered-by user;
            leaf name {
              type string;
            }
            uses apply-group;
            uses apply-macro;
            list user {
              key "name";
              ordered-by user;
              uses v3-user-config;
            }
          }
        }
        container vacm {
          uses apply-group;
          uses apply-macro;
          container security-to-group {
            uses apply-group;
            uses apply-macro;
            list security-model {
              key "name";
              ordered-by user;
              leaf name {
                type string;
              }
              uses apply-group;
              uses apply-macro;
              list security-name {
                key "name";
                ordered-by user;
                leaf name {
                  type key-attribute-string-type;
                }
                uses apply-group;
                uses apply-macro;
                leaf group {
                  type string;
                }
              }
            }
          }
          container access {
            uses apply-group;
            uses apply-macro;
            list group {
              key "name";
              ordered-by user;
              leaf name {
                type key-attribute-string-type;
              }
              uses apply-group;
              uses apply-macro;
              container default-context-prefix {
                uses apply-group;
                uses apply-macro;
                list security-model {
                  key "name";
                  ordered-by user;
                  uses security-model-access;
                }
              }
              list context-prefix {
                key "name";
                ordered-by user;
                leaf name {
                  type string;
                }
                uses apply-group;
                uses apply-macro;
                list security-model {
                  key "name";
                  ordered-by user;
                  uses security-model-access;
                }
              }
            }
          }
        }
        list target-address {
          key "name";
          ordered-by user;
          leaf name {
            type key-attribute-string-type;
          }
          uses apply-group;
          uses apply-macro;
          leaf address {
            type ipaddr;
          }
          leaf port {
            type uint16;
          }
          leaf timeout {
            type uint32;
          }
          leaf retry-count {
            type uint32;
          }
          leaf tag-list {
            type string;
          }
          leaf address-mask {
            type ipaddr;
          }
          leaf routing-instance {
            type string;
          }
          leaf logical-system {
            type string;
          }
          leaf target-parameters {
            type string;
          }
        }
        list target-parameters {
          key "name";
          ordered-by user;
          leaf name {
            type key-attribute-string-type;
          }
          uses apply-group;
          uses apply-macro;
          container parameters {
            presence "";
            uses apply-group;
            uses apply-macro;
            leaf message-processing-model {
              type string;
            }
            leaf security-model {
              type string;
            }
            leaf security-level {
              type string;
            }
            leaf security-name {
              type string;
            }
          }
          container notify-filter {
            leaf filter {
              type string;
            }
          }
        }
        list notify {
          key "name";
          ordered-by user;
          leaf name {
            type key-attribute-string-type;
          }
          uses apply-group;
          uses apply-macro;
          leaf type {
            type string;
          }
          leaf tag {
            type string;
          }
        }
        list notify-filter {
          key "name";
          ordered-by user;
          leaf name {
            type key-attribute-string-type;
          }
          uses apply-group;
          uses apply-macro;
          list oid {
            key "name";
            ordered-by user;
            leaf name {
              type string;
            }
            choice choice-3 {
              leaf include {
                type empty;
              }
              leaf exclude {
                type empty;
              }
            }
          }
        }
        leaf management-routing-instance {
          type string;
        }
        list snmp-community {
          key "name";
          ordered-by user;
          leaf name {
            type key-attribute-string-type;
          }
          uses apply-group;
          uses apply-macro;
          leaf community-name {
            type unreadable;
          }
          leaf security-name {
            type string;
          }
          leaf context {
            type string;
          }
          leaf tag {
            type string;
          }
        }
      }
      container engine-id {
        uses apply-group;
        uses apply-macro;
        choice choice-3 {
          leaf use-mac-address {
            type empty;
          }
          leaf use-default-ip-address {
            type empty;
          }
          leaf local {
            type string;
          }
        }
      }
      list view {
        key "name";
        ordered-by user;
        leaf name {
          type string;
        }
        uses apply-group;
        uses apply-macro;
        list oid {
          key "name";
          ordered-by user;
          leaf name {
            type string;
          }
          choice choice-3 {
            leaf include {
              type empty;
            }
            leaf exclude {
              type empty;
            }
          }
        }
      }
      list client-list {
        key "name";
        ordered-by user;
        leaf name {
          type string;
        }
        uses apply-group;
        uses apply-macro;
        list client-address-list {
          key "name";
          ordered-by user;
          uses client-address-object;
        }
      }
      list community {
        key "name";
        ordered-by user;
        leaf name {
          type string;
        }
        uses apply-group;
        uses apply-macro;
        leaf view {
          type string;
        }
        leaf authorization {
          type string;
        }
        choice choice-7 {
          leaf client-list-name {
            type string;
          }
          list clients {
            key "name";
            ordered-by user;
            leaf name {
              type ipprefix;
            }
            leaf restrict {
              type empty;
            }
          }
        }
        list routing-instance {
          key "name";
          ordered-by user;
          leaf name {
            type string;
          }
          uses apply-group;
          uses apply-macro;
          choice choice-3 {
            leaf client-list-name {
              type string;
            }
            list clients {
              key "name";
              ordered-by user;
              leaf name {
                type ipprefix;
              }
              leaf restrict {
                type empty;
              }
            }
          }
        }
        list logical-system {
          key "name";
          ordered-by user;
          leaf name {
            type string;
          }
          uses apply-group;
          uses apply-macro;
          list routing-instance {
            key "name";
            ordered-by user;
            leaf name {
              type string;
            }
            uses apply-group;
            uses apply-macro;
            choice choice-3 {
              leaf client-list-name {
                type string;
              }
              list clients {
                key "name";
                ordered-by user;
                leaf name {
                  type ipprefix;
                }
                leaf restrict {
                  type empty;
                }
              }
            }
          }
        }
      }
      container trap-options {
        presence "enable trap-options";
        uses apply-group;
        uses apply-macro;
        container source-address {
          uses apply-group;
          uses apply-macro;
          choice choice-3 {
            leaf lo0 {
              type empty;
            }
            leaf address {
              type ipv4addr;
            }
          }
        }
        leaf enterprise-oid {
          type empty;
        }
        list routing-instance {
          key "name";
          ordered-by user;
          leaf name {
            type string;
          }
          uses apply-group;
          uses apply-macro;
          container source-address {
            uses apply-group;
            uses apply-macro;
            choice choice-3 {
              leaf lo0 {
                type empty;
              }
              leaf address {
                type ipv4addr;
              }
            }
          }
        }
        list logical-system {
          key "name";
          ordered-by user;
          leaf name {
            type string;
          }
          uses apply-group;
          uses apply-macro;
          list routing-instance {
            key "name";
            ordered-by user;
            leaf name {
              type string;
            }
            uses apply-group;
            uses apply-macro;
            container source-address {
              uses apply-group;
              uses apply-macro;
              choice choice-3 {
                leaf lo0 {
                  type empty;
                }
                leaf address {
                  type ipv4addr;
                }
              }
            }
          }
        }
        leaf agent-address {
          type string;
        }
      }
      list trap-group {
        key "name";
        ordered-by user;
        leaf name {
          type string;
        }
        uses apply-group;
        uses apply-macro;
        leaf version {
          type string;
        }
        leaf destination-port {
          type int32;
        }
        container categories {
          uses apply-group;
          uses apply-macro;
          leaf authentication {
            type empty;
          }
          leaf chassis {
            type empty;
          }
          leaf link {
            type empty;
          }
          leaf remote-operations {
            type empty;
          }
          leaf routing {
            type empty;
          }
          leaf startup {
            type empty;
          }
          leaf ggsn {
            type empty;
          }
          leaf rmon-alarm {
            type empty;
          }
          leaf vrrp-events {
            type empty;
          }
          leaf configuration {
            type empty;
          }
          leaf services {
            type empty;
          }
          leaf chassis-cluster {
            type empty;
          }
          leaf timing-events {
            type empty;
          }
          leaf dot3oam-events {
            type empty;
          }
          container sonet-alarms {
            presence "enable sonet-alarms";
            uses apply-group;
            uses apply-macro;
            leaf loss-of-light {
              type empty;
            }
            leaf pll-lock {
              type empty;
            }
            leaf loss-of-frame {
              type empty;
            }
            leaf loss-of-signal {
              type empty;
            }
            leaf severely-errored-frame {
              type empty;
            }
            leaf line-ais {
              type empty;
            }
            leaf path-ais {
              type empty;
            }
            leaf loss-of-pointer {
              type empty;
            }
            leaf ber-defect {
              type empty;
            }
            leaf ber-fault {
              type empty;
            }
            leaf line-remote-defect-indication {
              type empty;
            }
            leaf path-remote-defect-indication {
              type empty;
            }
            leaf remote-error-indication {
              type empty;
            }
            leaf unequipped {
              type empty;
            }
            leaf path-mismatch {
              type empty;
            }
            leaf loss-of-cell {
              type empty;
            }
            leaf vt-ais {
              type empty;
            }
            leaf vt-loss-of-pointer {
              type empty;
            }
            leaf vt-remote-defect-indication {
              type empty;
            }
            leaf vt-unequipped {
              type empty;
            }
            leaf vt-label-mismatch {
              type empty;
            }
            leaf vt-loss-of-cell {
              type empty;
            }
          }
          container otn-alarms {
            presence "enable otn-alarms";
            uses apply-group;
            uses apply-macro;
            leaf oc-los {
              type empty;
            }
            leaf oc-lof {
              type empty;
            }
            leaf oc-lom {
              type empty;
            }
            leaf wavelength-lock {
              type empty;
            }
            leaf otu-ais {
              type empty;
            }
            leaf otu-bdi {
              type empty;
            }
            leaf otu-ttim {
              type empty;
            }
            leaf otu-iae {
              type empty;
            }
            leaf otu-sd {
              type empty;
            }
            leaf otu-sf {
              type empty;
            }
            leaf otu-fec-exe {
              type empty;
            }
            leaf otu-fec-deg {
              type empty;
            }
            leaf otu-bbe-threshold {
              type empty;
            }
            leaf otu-es-threshold {
              type empty;
            }
            leaf otu-ses-threshold {
              type empty;
            }
            leaf otu-uas-threshold {
              type empty;
            }
            leaf odu-ais {
              type empty;
            }
            leaf odu-oci {
              type empty;
            }
            leaf odu-lck {
              type empty;
            }
            leaf odu-bdi {
              type empty;
            }
            leaf odu-ttim {
              type empty;
            }
            leaf odu-sd {
              type empty;
            }
            leaf odu-sf {
              type empty;
            }
            leaf odu-rx-aps-change {
              type empty;
            }
            leaf odu-bbe-threshold {
              type empty;
            }
            leaf odu-es-threshold {
              type empty;
            }
            leaf odu-ses-threshold {
              type empty;
            }
            leaf odu-uas-threshold {
              type empty;
            }
            leaf opu-ptm {
              type empty;
            }
          }
        }
        list targets {
          key "name";
          ordered-by user;
          leaf name {
            type hostname;
          }
        }
        leaf routing-instance {
          type string;
        }
        leaf logical-system {
          type string;
        }
      }
      container routing-instance-access {
        presence "enable routing-instance-access";
        uses apply-group;
        uses apply-macro;
        list access-list {
          key "name";
          leaf name {
            type string;
          }
          leaf restrict {
            type empty;
          }
        }
      }
      leaf logical-system-trap-filter {
        type empty;
      }
      container traceoptions {
        uses apply-group;
        uses apply-macro;
        leaf no-remote-trace {
          type empty;
        }
        container file {
          leaf size {
            type string;
          }
          leaf files {
            type uint32;
          }
          leaf world-readable {
            type empty;
          }
          leaf no-world-readable {
            type empty;
          }
          leaf match {
            type regular-expression;
          }
        }
        list flag {
          key "name";
          ordered-by user;
          leaf name {
            type string;
          }
        }
      }
      container rmon {
        presence "enable rmon";
        uses apply-group;
        uses apply-macro;
        list history {
          key "name";
          ordered-by user;
          leaf name {
            type string;
          }
          uses apply-group;
          uses apply-macro;
          leaf interface {
            type interface-name;
          }
          leaf bucket-size {
            type uint32;
          }
          leaf interval {
            type uint32;
          }
          leaf owner {
            type string;
          }
        }
        list alarm {
          key "name";
          ordered-by user;
          leaf name {
            type string;
          }
          uses apply-group;
          uses apply-macro;
          leaf description {
            type string;
          }
          leaf interval {
            type uint32;
          }
          leaf falling-threshold-interval {
            type uint32;
          }
          leaf variable {
            type string;
          }
          leaf sample-type {
            type string;
          }
          leaf request-type {
            type string;
          }
          leaf startup-alarm {
            type string;
          }
          leaf rising-threshold {
            type int32;
          }
          leaf falling-threshold {
            type int32;
          }
          leaf rising-event-index {
            type int32;
          }
          leaf falling-event-index {
            type int32;
          }
          leaf syslog-subtag {
            type string;
          }
        }
        list event {
          key "name";
          ordered-by user;
          leaf name {
            type string;
          }
          uses apply-group;
          uses apply-macro;
          leaf description {
            type string;
          }
          leaf type {
            type string;
          }
          leaf community {
            type string;
          }
        }
      }
      container health-monitor {
        presence "enable health-monitor";
        uses apply-group;
        uses apply-macro;
        leaf interval {
          type uint32;
        }
        leaf rising-threshold {
          type uint32;
        }
        leaf falling-threshold {
          type uint32;
        }
        container idp {
          presence "enable idp";
          uses apply-group;
          uses apply-macro;
          leaf interval {
            type uint32;
          }
          leaf rising-threshold {
            type uint32;
          }
          leaf falling-threshold {
            type uint32;
          }
        }
      }
      container undocumented {
        leaf stats-cache-lifetime {
          type uint32;
        }
      }
    }
    container accounting-options {
      uses juniper-accounting-options;
    }
    container routing-options {
      uses juniper-routing-options;
    }
    container multicast-snooping-options {
      uses juniper-multicast-snooping-options;
    }
    container protocols {
      uses juniper-protocols;
    }
    container policy-options {
      uses juniper-policy-options;
    }
    container class-of-service {
      uses juniper-class-of-service-options;
    }
    container security {
      uses apply-group;
      uses apply-macro;
      container alarms {
        uses apply-group;
        uses apply-macro;
        container audible {
          presence "enable audible";
          uses apply-group;
          uses apply-macro;
          leaf continuous {
            type empty;
          }
        }
        container potential-violation {
          uses apply-group;
          uses apply-macro;
          leaf authentication {
            type uint32;
          }
          leaf cryptographic-self-test {
            type empty;
          }
          container decryption-failures {
            presence "enable decryption-failures";
            uses apply-group;
            uses apply-macro;
          }
          container encryption-failures {
            presence "enable encryption-failures";
            uses apply-group;
            uses apply-macro;
          }
          container ike-phase1-failures {
            presence "enable ike-phase1-failures";
            uses apply-group;
            uses apply-macro;
          }
          container ike-phase2-failures {
            presence "enable ike-phase2-failures";
            uses apply-group;
            uses apply-macro;
          }
          leaf key-generation-self-test {
            type empty;
          }
          leaf non-cryptographic-self-test {
            type empty;
          }
          container policy {
            uses apply-group;
            uses apply-macro;
          }
          container replay-attacks {
            presence "enable replay-attacks";
            uses apply-group;
            uses apply-macro;
            leaf threshold {
              type uint32;
            }
          }
          leaf security-log-percent-full {
            type uint8;
          }
          leaf idp {
            type empty;
          }
        }
      }
      container certificates {
        uses apply-group;
        uses apply-macro;
        list local {
          key "name";
          ordered-by user;
          uses certificate-object;
        }
        leaf path-length {
          type uint32;
        }
        leaf maximum-certificates {
          type uint32;
        }
        leaf cache-size {
          type string;
        }
        leaf cache-timeout-negative {
          type uint32;
        }
        leaf enrollment-retry {
          type uint32;
        }
        list certification-authority {
          key "name";
          ordered-by user;
          leaf name {
            type string;
          }
          uses apply-group;
          uses apply-macro;
          leaf ca-name {
            type string;
          }
          leaf file {
            type string;
          }
          leaf crl {
            type string;
          }
          leaf enrollment-url {
            type string;
          }
          leaf ldap-url {
            type string;
          }
          leaf encoding {
            type string;
          }
        }
      }
      container authentication-key-chains {
        uses security-authentication-key-chains;
      }
      container ssh-known-hosts {
        uses apply-group;
        uses apply-macro;
        list host {
          key "name";
          ordered-by user;
          leaf name {
            type string;
          }
          uses apply-group;
          uses apply-macro;
          leaf rsa1-key {
            type string;
          }
          leaf rsa-key {
            type string;
          }
          leaf dsa-key {
            type string;
          }
          leaf ecdsa-key {
            type string;
          }
          leaf ecdsa-sha2-nistp256-key {
            type string;
          }
          leaf ecdsa-sha2-nistp384-key {
            type string;
          }
          leaf ecdsa-sha2-nistp521-key {
            type string;
          }
          leaf ed25519-key {
            type string;
          }
        }
      }
      container idp {
        list idp-policy {
          key "name";
          ordered-by user;
          uses idp-policy-type;
        }
        leaf active-policy {
          type string;
        }
        list custom-attack {
          key "name";
          ordered-by user;
          uses custom-attack-type;
        }
        list custom-attack-group {
          key "name";
          ordered-by user;
          uses custom-attack-group-type;
        }
        list dynamic-attack-group {
          key "name";
          ordered-by user;
          uses dynamic-attack-group-type;
        }
        list application-ddos {
          key "name";
          ordered-by user;
          uses application-ddos-type;
        }
        container traceoptions {
          uses idpd-traceoptions-type;
        }
        container security-package {
          uses apply-group;
          uses apply-macro;
          leaf url {
            type string;
          }
          leaf source-address {
            type ipv4addr;
          }
          container install {
            presence "enable install";
            uses apply-group;
            uses apply-macro;
            leaf ignore-version-check {
              type empty;
            }
          }
          container automatic {
            presence "enable automatic";
            uses apply-group;
            uses apply-macro;
            leaf start-time {
              type time;
            }
            leaf interval {
              type string;
            }
            leaf download-timeout {
              type uint32;
            }
            choice choice-9 {
              leaf enable {
                type empty;
              }
            }
          }
        }
        container sensor-configuration {
          container log {
            uses apply-group;
            uses apply-macro;
            leaf cache-size {
              type uint32;
            }
            container suppression {
              presence "enable suppression";
              uses apply-group;
              uses apply-macro;
              choice choice-3 {
                leaf disable {
                  type empty;
                }
              }
              leaf include-destination-address {
                type empty;
              }
              leaf no-include-destination-address {
                type empty;
              }
              leaf start-log {
                type uint32;
              }
              leaf max-logs-operate {
                type uint32;
              }
              leaf max-time-report {
                type uint32;
              }
            }
          }
          container packet-log {
            presence "";
            uses apply-group;
            uses apply-macro;
            leaf total-memory {
              type uint32;
            }
            leaf max-sessions {
              type uint32;
            }
            leaf source-address {
              type ipv4addr;
            }
            container host {
              presence "";
              uses apply-group;
              uses apply-macro;
              leaf ipaddr {
                type ipv4addr;
              }
              leaf port {
                type uint16;
              }
            }
          }
          container application-identification {
            presence "enable application-identification";
            uses apply-group;
            uses apply-macro;
            choice choice-3 {
              leaf disable {
                type empty;
              }
            }
            leaf application-system-cache {
              type empty;
            }
            leaf no-application-system-cache {
              type empty;
            }
            leaf max-tcp-session-packet-memory {
              type uint32;
            }
            leaf max-udp-session-packet-memory {
              type uint32;
            }
            leaf max-sessions {
              type uint32;
            }
            leaf max-packet-memory {
              type uint32;
            }
            leaf application-system-cache-timeout {
              type uint32;
            }
          }
          container flow {
            uses apply-group;
            uses apply-macro;
            leaf log-errors {
              type empty;
            }
            leaf no-log-errors {
              type empty;
            }
            leaf reset-on-policy {
              type empty;
            }
            leaf no-reset-on-policy {
              type empty;
            }
            leaf allow-icmp-without-flow {
              type empty;
            }
            leaf no-allow-icmp-without-flow {
              type empty;
            }
            leaf hash-table-size {
              type uint32;
            }
            leaf reject-timeout {
              type uint32;
            }
            leaf max-timers-poll-ticks {
              type uint32;
            }
            leaf fifo-max-size {
              type uint32;
            }
            leaf udp-anticipated-timeout {
              type uint32;
            }
            leaf allow-nonsyn-connection {
              type empty;
            }
          }
          container re-assembler {
            uses apply-group;
            uses apply-macro;
            leaf ignore-memory-overflow {
              type empty;
            }
            leaf no-ignore-memory-overflow {
              type empty;
            }
            leaf ignore-reassembly-memory-overflow {
              type empty;
            }
            leaf no-ignore-reassembly-memory-overflow {
              type empty;
            }
            leaf ignore-reassembly-overflow {
              type empty;
            }
            leaf max-packet-mem {
              type uint32;
            }
            leaf max-flow-mem {
              type uint32;
            }
          }
          container ips {
            uses apply-group;
            uses apply-macro;
            leaf process-override {
              type empty;
            }
            leaf no-process-override {
              type empty;
            }
            leaf detect-shellcode {
              type empty;
            }
            leaf no-detect-shellcode {
              type empty;
            }
            leaf process-ignore-s2c {
              type empty;
            }
            leaf no-process-ignore-s2c {
              type empty;
            }
            leaf ignore-regular-expression {
              type empty;
            }
            leaf no-ignore-regular-expression {
              type empty;
            }
            leaf process-port {
              type uint32;
            }
            leaf fifo-max-size {
              type uint32;
            }
            leaf log-supercede-min {
              type uint32;
            }
          }
          container global {
            uses apply-group;
            uses apply-macro;
            leaf enable-packet-pool {
              type empty;
            }
            leaf no-enable-packet-pool {
              type empty;
            }
            leaf enable-all-qmodules {
              type empty;
            }
            leaf no-enable-all-qmodules {
              type empty;
            }
            leaf policy-lookup-cache {
              type empty;
            }
            leaf no-policy-lookup-cache {
              type empty;
            }
            leaf memory-limit-percent {
              type uint32;
            }
            container gtp {
              uses apply-group;
              uses apply-macro;
              leaf decapsulation {
                type empty;
              }
              leaf no-decapsulation {
                type empty;
              }
            }
          }
          container detector {
            uses apply-group;
            uses apply-macro;
            list protocol-name {
              key "name";
              ordered-by user;
              uses proto-object;
            }
          }
          container ssl-inspection {
            uses apply-group;
            uses apply-macro;
            leaf sessions {
              type uint32;
            }
            leaf session-id-cache-timeout {
              type uint32;
            }
            leaf maximum-cache-size {
              type uint32;
            }
            leaf cache-prune-chunk-size {
              type uint32;
            }
          }
          container application-ddos {
            uses apply-group;
            uses apply-macro;
            container statistics {
              presence "enable statistics";
              uses apply-group;
              uses apply-macro;
              leaf interval {
                type uint32;
              }
            }
          }
        }
        container processes {
          uses apply-group;
          uses apply-macro;
        }
      }
      leaf key-protection {
        type empty;
      }
      container ike {
        uses security-ike;
      }
      container ipsec {
        uses security-ipsec-vpn;
      }
      container group-vpn {
        uses security-group-vpn;
      }
      list address-book {
        key "name";
        ordered-by user;
        uses named-address-book-type;
      }
      container pki {
        presence "enable pki";
        uses security-pki;
      }
      container distribution-profile {
        uses apply-group;
        uses apply-macro;
        list profile-entity {
          key "name";
          ordered-by user;
          uses security-distribution-profile;
        }
        leaf fat-core {
          type empty;
        }
      }
      container gprs {
        presence "enable gprs";
        uses apply-group;
        uses apply-macro;
        container gtp {
          presence "enable gtp";
          uses apply-group;
          uses apply-macro;
          leaf enable {
            type empty;
          }
          list profile {
            key "name";
            leaf name {
              type key-attribute-string-type;
            }
            uses apply-group;
            uses apply-macro;
            leaf min-message-length {
              type uint32;
            }
            leaf max-message-length {
              type uint32;
            }
            leaf timeout {
              type uint32;
            }
            leaf rate-limit {
              type uint32;
            }
            container log {
              presence "enable log";
              uses apply-group;
              uses apply-macro;
              leaf forwarded {
                type string;
              }
              leaf state-invalid {
                type string;
              }
              leaf prohibited {
                type string;
              }
              container rate-limited {
                presence "enable rate-limited";
                uses apply-group;
                uses apply-macro;
                choice choice-3 {
                  leaf basic {
                    type empty;
                  }
                  leaf detail {
                    type empty;
                  }
                }
                leaf frequency-number {
                  type uint32;
                }
              }
            }
            leaf remove-r6 {
              type empty;
            }
            container drop {
              presence "enable drop";
              uses apply-group;
              uses apply-macro;
              leaf aa-create-pdp {
                type string;
              }
              leaf aa-delete-pdp {
                type string;
              }
              leaf create-pdp {
                type string;
              }
              leaf data-record {
                type string;
              }
              leaf delete-pdp {
                type string;
              }
              leaf echo {
                type string;
              }
              leaf error-indication {
                type string;
              }
              leaf failure-report {
                type string;
              }
              leaf fwd-relocation {
                type string;
              }
              leaf fwd-srns-context {
                type string;
              }
              leaf g-pdu {
                type string;
              }
              leaf identification {
                type string;
              }
              leaf node-alive {
                type string;
              }
              leaf note-ms-present {
                type string;
              }
              leaf pdu-notification {
                type string;
              }
              leaf ran-info {
                type string;
              }
              leaf redirection {
                type string;
              }
              leaf relocation-cancel {
                type string;
              }
              leaf send-route {
                type string;
              }
              leaf sgsn-context {
                type string;
              }
              leaf supported-extension {
                type string;
              }
              leaf update-pdp {
                type string;
              }
              leaf ver-not-supported {
                type string;
              }
            }
            list apn {
              key "name";
              leaf name {
                type key-attribute-string-type;
              }
              uses apply-group;
              uses apply-macro;
              list mcc-mnc {
                key "name";
                leaf name {
                  type key-attribute-string-type;
                }
                uses apply-group;
                uses apply-macro;
                container action {
                  presence "enable action";
                  uses apply-group;
                  uses apply-macro;
                  choice choice-3 {
                    leaf pass {
                      type empty;
                    }
                    leaf drop {
                      type empty;
                    }
                    container selection {
                      presence "enable selection";
                      uses apply-group;
                      uses apply-macro;
                      leaf ms {
                        type empty;
                      }
                      leaf net {
                        type empty;
                      }
                      leaf vrf {
                        type empty;
                      }
                    }
                  }
                }
              }
            }
            leaf seq-number-validated {
              type empty;
            }
          }
          container traceoptions {
            uses apply-group;
            uses apply-macro;
            leaf no-remote-trace {
              type empty;
            }
            container file {
              leaf filename {
                type string;
              }
              leaf size {
                type string;
              }
              leaf files {
                type uint32;
              }
              leaf world-readable {
                type empty;
              }
              leaf no-world-readable {
                type empty;
              }
              leaf match {
                type regular-expression;
              }
            }
            list flag {
              key "name";
              ordered-by user;
              leaf name {
                type string;
              }
            }
          }
        }
        container sctp {
          presence "enable sctp";
          uses apply-group;
          uses apply-macro;
          list profile {
            key "name";
            leaf name {
              type key-attribute-string-type;
            }
            uses apply-group;
            uses apply-macro;
            leaf association-timeout {
              type uint32;
            }
            leaf handshake-timeout {
              type uint32;
            }
            container drop {
              presence "enable drop";
              uses apply-group;
              uses apply-macro;
              list m3ua-service {
                key "name";
                ordered-by user;
                leaf name {
                  type string;
                }
              }
              list payload-protocol {
                key "name";
                ordered-by user;
                leaf name {
                  type string;
                }
              }
            }
            container limit {
              presence "enable limit";
              uses apply-group;
              uses apply-macro;
              container rate {
                presence "enable rate";
                uses apply-group;
                uses apply-macro;
                leaf sccp {
                  type uint16;
                }
                leaf ssp {
                  type uint16;
                }
                leaf sst {
                  type uint16;
                }
                list address {
                  key "name";
                  ordered-by user;
                  leaf name {
                    type ipv4addr;
                  }
                  uses apply-group;
                  uses apply-macro;
                  leaf sccp {
                    type uint16;
                  }
                  leaf ssp {
                    type uint16;
                  }
                  leaf sst {
                    type uint16;
                  }
                }
              }
            }
          }
          list log {
            key "name";
            ordered-by user;
            leaf name {
              type string;
            }
          }
          container traceoptions {
            uses apply-group;
            uses apply-macro;
            leaf no-remote-trace {
              type empty;
            }
            container file {
              leaf filename {
                type string;
              }
              leaf size {
                type string;
              }
              leaf files {
                type uint32;
              }
              leaf world-readable {
                type empty;
              }
              leaf no-world-readable {
                type empty;
              }
              leaf match {
                type regular-expression;
              }
            }
            list flag {
              key "name";
              ordered-by user;
              leaf name {
                type string;
              }
            }
          }
        }
      }
      container nat {
        uses apply-group;
        uses apply-macro;
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
            leaf syslog {
              type empty;
            }
          }
        }
        container source {
          uses ssg-source-nat-object;
        }
        container destination {
          uses ssg-destination-nat-object;
        }
        container static {
          uses ssg-static-nat-object;
        }
        container proxy-arp {
          uses ssg-proxy-arp-object;
        }
      }
      container log {
        uses log-object;
      }
      container screen {
        uses apply-group;
        uses apply-macro;
        list ids-option {
          key "name";
          uses ids-option-type;
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
      }
      container zones {
        uses apply-group;
        uses apply-macro;
        container functional-zone {
          presence "enable functional-zone";
          uses apply-group;
          uses apply-macro;
          container management {
            presence "enable management";
            uses apply-group;
            uses apply-macro;
            list interfaces {
              key "name";
              ordered-by user;
              uses zone-interface-list-type;
            }
            leaf screen {
              type string;
            }
            container host-inbound-traffic {
              uses zone-host-inbound-traffic-t;
            }
          }
        }
        list security-zone {
          key "name";
          ordered-by user;
          uses security-zone-type;
        }
      }
      container policies {
        presence "enable policies";
        uses policy-object-type;
      }
      container traceoptions {
        uses security-traceoptions;
      }
      container datapath-debug {
        uses apply-group;
        uses apply-macro;
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
        }
        container capture-file {
          presence "";
          leaf filename {
            type string;
          }
          leaf format {
            type string;
          }
          leaf size {
            type string;
          }
          leaf files {
            type uint32;
          }
          leaf world-readable {
            type empty;
          }
          leaf no-world-readable {
            type empty;
          }
        }
        leaf maximum-capture-size {
          type uint32;
        }
        list action-profile {
          key "name";
          ordered-by user;
          uses e2e-action-profile;
        }
        list packet-filter {
          key "name";
          ordered-by user;
          uses end-to-end-debug-filter;
        }
      }
      container alg {
        uses apply-group;
        uses apply-macro;
        container dns {
          leaf disable {
            type empty;
          }
          leaf maximum-message-length {
            type uint32;
          }
          container traceoptions {
            uses apply-group;
            uses apply-macro;
            list flag {
              key "name";
              ordered-by user;
              leaf name {
                type string;
              }
              choice choice-3 {
                leaf extensive {
                  type empty;
                }
              }
            }
          }
        }
        container ftp {
          leaf disable {
            type empty;
          }
          leaf ftps-extension {
            type empty;
          }
          leaf line-break-extension {
            type empty;
          }
          container traceoptions {
            uses apply-group;
            uses apply-macro;
            list flag {
              key "name";
              ordered-by user;
              leaf name {
                type string;
              }
              choice choice-3 {
                leaf extensive {
                  type empty;
                }
              }
            }
          }
        }
        container h323 {
          presence "enable h323";
          uses apply-group;
          uses apply-macro;
          leaf disable {
            type empty;
          }
          leaf endpoint-registration-timeout {
            type uint32;
          }
          leaf media-source-port-any {
            type empty;
          }
          container application-screen {
            uses apply-group;
            uses apply-macro;
            container unknown-message {
              uses apply-group;
              uses apply-macro;
              leaf permit-nat-applied {
                type empty;
              }
              leaf permit-routed {
                type empty;
              }
            }
            container message-flood {
              uses apply-group;
              uses apply-macro;
              container gatekeeper {
                leaf threshold {
                  type uint32;
                }
              }
            }
          }
          container dscp-rewrite {
            uses apply-group;
            uses apply-macro;
            leaf code-point {
              type string;
            }
          }
          container traceoptions {
            uses apply-group;
            uses apply-macro;
            list flag {
              key "name";
              ordered-by user;
              leaf name {
                type string;
              }
              choice choice-3 {
                leaf terse {
                  type empty;
                }
                leaf detail {
                  type empty;
                }
                leaf extensive {
                  type empty;
                }
              }
            }
          }
        }
        container mgcp {
          presence "enable mgcp";
          uses apply-group;
          uses apply-macro;
          leaf disable {
            type empty;
          }
          leaf inactive-media-timeout {
            type uint32;
          }
          leaf transaction-timeout {
            type uint32;
          }
          leaf maximum-call-duration {
            type uint32;
          }
          container application-screen {
            uses apply-group;
            uses apply-macro;
            container unknown-message {
              uses apply-group;
              uses apply-macro;
              leaf permit-nat-applied {
                type empty;
              }
              leaf permit-routed {
                type empty;
              }
            }
            container message-flood {
              leaf threshold {
                type uint32;
              }
            }
            container connection-flood {
              leaf threshold {
                type uint32;
              }
            }
          }
          container dscp-rewrite {
            uses apply-group;
            uses apply-macro;
            leaf code-point {
              type string;
            }
          }
          container traceoptions {
            uses apply-group;
            uses apply-macro;
            list flag {
              key "name";
              ordered-by user;
              leaf name {
                type string;
              }
              choice choice-3 {
                leaf extensive {
                  type empty;
                }
              }
            }
          }
        }
        container msrpc {
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container sunrpc {
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container real {
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container rsh {
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container rtsp {
          presence "enable rtsp";
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container sccp {
          presence "enable sccp";
          uses apply-group;
          uses apply-macro;
          leaf disable {
            type empty;
          }
          leaf inactive-media-timeout {
            type uint32;
          }
          container application-screen {
            uses apply-group;
            uses apply-macro;
            container unknown-message {
              uses apply-group;
              uses apply-macro;
              leaf permit-nat-applied {
                type empty;
              }
              leaf permit-routed {
                type empty;
              }
            }
            container call-flood {
              leaf threshold {
                type uint32;
              }
            }
          }
          container dscp-rewrite {
            uses apply-group;
            uses apply-macro;
            leaf code-point {
              type string;
            }
          }
          container traceoptions {
            uses apply-group;
            uses apply-macro;
            list flag {
              key "name";
              ordered-by user;
              leaf name {
                type string;
              }
              choice choice-3 {
                leaf extensive {
                  type empty;
                }
              }
            }
          }
        }
        container sip {
          presence "enable sip";
          uses apply-group;
          uses apply-macro;
          leaf disable {
            type empty;
          }
          leaf inactive-media-timeout {
            type uint32;
          }
          leaf maximum-call-duration {
            type uint32;
          }
          leaf t1-interval {
            type uint32;
          }
          leaf t4-interval {
            type uint32;
          }
          leaf c-timeout {
            type uint32;
          }
          leaf retain-hold-resource {
            type empty;
          }
          container application-screen {
            uses apply-group;
            uses apply-macro;
            container unknown-message {
              uses apply-group;
              uses apply-macro;
              leaf permit-nat-applied {
                type empty;
              }
              leaf permit-routed {
                type empty;
              }
            }
            container protect {
              uses apply-group;
              uses apply-macro;
              container deny {
                presence "enable deny";
                uses apply-group;
                uses apply-macro;
                choice choice-3 {
                  list destination-ip {
                    key "name";
                    ordered-by user;
                    leaf name {
                      type ipv4addr;
                    }
                    uses apply-group;
                    uses apply-macro;
                  }
                  leaf all {
                    type empty;
                  }
                }
                leaf timeout {
                  type uint32;
                }
              }
            }
          }
          container dscp-rewrite {
            uses apply-group;
            uses apply-macro;
            leaf code-point {
              type string;
            }
          }
          container traceoptions {
            uses apply-group;
            uses apply-macro;
            list flag {
              key "name";
              ordered-by user;
              leaf name {
                type string;
              }
              choice choice-3 {
                leaf terse {
                  type empty;
                }
                leaf detail {
                  type empty;
                }
                leaf extensive {
                  type empty;
                }
              }
            }
          }
        }
        container sql {
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container talk {
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container tftp {
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container pptp {
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container ike-esp-nat {
          uses apply-group;
          uses apply-macro;
          leaf enable {
            type empty;
          }
          leaf esp-gate-timeout {
            type uint32;
          }
          leaf esp-session-timeout {
            type uint32;
          }
          leaf state-timeout {
            type uint32;
          }
          container traceoptions {
            uses apply-group;
            uses apply-macro;
            list flag {
              key "name";
              ordered-by user;
              leaf name {
                type string;
              }
              choice choice-3 {
                leaf extensive {
                  type empty;
                }
              }
            }
          }
        }
      }
      container application-firewall {
        presence "enable application-firewall";
        uses apply-group;
        uses apply-macro;
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
        list profile {
          key "name";
          ordered-by user;
          leaf name {
            type key-attribute-string-type;
          }
          uses apply-group;
          uses apply-macro;
          container block-message {
            presence "";
            uses apply-group;
            uses apply-macro;
            container type {
              uses apply-group;
              uses apply-macro;
              choice choice-custom-text {
                container custom-text {
                  uses apply-group;
                  uses apply-macro;
                  leaf content {
                    type string;
                  }
                }
                container custom-redirect-url {
                  uses apply-group;
                  uses apply-macro;
                  leaf content {
                    type string;
                  }
                }
              }
            }
          }
        }
        list rule-sets {
          key "name";
          ordered-by user;
          leaf name {
            type key-attribute-string-type;
          }
          uses apply-group;
          uses apply-macro;
          list rule {
            key "name";
            ordered-by user;
            uses appfw-rule-type;
          }
          container default-rule {
            presence "enable default-rule";
            uses apply-group;
            uses apply-macro;
            choice choice-permit {
              leaf permit {
                type empty;
              }
              container deny {
                presence "enable deny";
                uses apply-group;
                uses apply-macro;
                leaf block-message {
                  type empty;
                }
              }
              container reject {
                presence "enable reject";
                uses apply-group;
                uses apply-macro;
                leaf block-message {
                  type empty;
                }
              }
            }
          }
          leaf profile {
            type string;
          }
        }
      }
      container forwarding-process {
        presence "";
        uses apply-group;
        uses apply-macro;
        container application-services {
          uses apply-group;
          uses apply-macro;
          leaf maximize-alg-sessions {
            type empty;
          }
          leaf maximize-cp-sessions {
            type empty;
          }
          container maximize-idp-sessions {
            presence "enable maximize-idp-sessions";
            uses apply-group;
            uses apply-macro;
            container weight {
              uses apply-group;
              uses apply-macro;
              choice choice-3 {
                leaf equal {
                  type empty;
                }
                container idp {
                  presence "enable idp";
                  uses apply-group;
                  uses apply-macro;
                }
                leaf firewall {
                  type empty;
                }
              }
            }
            leaf inline-tap {
              type empty;
            }
          }
        }
      }
      container resource-manager {
        uses apply-group;
        uses apply-macro;
        container traceoptions {
          uses apply-group;
          uses apply-macro;
          list flag {
            key "name";
            ordered-by user;
            leaf name {
              type string;
            }
            choice choice-3 {
              leaf terse {
                type empty;
              }
              leaf detail {
                type empty;
              }
              leaf extensive {
                type empty;
              }
            }
          }
        }
      }
      container firewall-authentication {
        uses apply-group;
        uses apply-macro;
        container traceoptions {
          uses apply-group;
          uses apply-macro;
          list flag {
            key "name";
            ordered-by user;
            leaf name {
              type string;
            }
            choice choice-3 {
              leaf terse {
                type empty;
              }
              leaf detail {
                type empty;
              }
              leaf extensive {
                type empty;
              }
            }
          }
        }
      }
      container application-tracking {
        presence "enable application-tracking";
        uses apply-group;
        uses apply-macro;
        choice choice-3 {
          leaf first-update-interval {
            type uint32;
          }
          leaf first-update {
            type empty;
          }
        }
        leaf session-update-interval {
          type uint32;
        }
      }
      container forwarding-options {
        uses apply-group;
        uses apply-macro;
        container family {
          uses apply-group;
          uses apply-macro;
          container inet {
            uses apply-advanced;
            leaf mode {
              type string;
            }
          }
          container inet6 {
            uses apply-group;
            uses apply-macro;
            leaf mode {
              type string;
            }
          }
          container mpls {
            uses apply-group;
            uses apply-macro;
            leaf mode {
              type string;
            }
          }
          container iso {
            uses apply-group;
            uses apply-macro;
            leaf mode {
              type string;
            }
          }
        }
      }
      container flow {
        uses apply-group;
        uses apply-macro;
        leaf enhanced-routing-mode {
          type empty;
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
          leaf rate-limit {
            type uint32;
          }
          list packet-filter {
            key "name";
            ordered-by user;
            uses flow-filter-type;
          }
          container trace-level {
            uses apply-group;
            uses apply-macro;
            choice choice-error {
              leaf error {
                type empty;
              }
              leaf brief {
                type empty;
              }
              leaf detail {
                type empty;
              }
            }
          }
        }
        leaf pending-sess-queue-length {
          type string;
        }
        leaf allow-dns-reply {
          type empty;
        }
        leaf route-change-timeout {
          type uint32;
        }
        leaf syn-flood-protection-mode {
          type string;
        }
        leaf allow-embedded-icmp {
          type empty;
        }
        leaf mcast-buffer-enhance {
          type empty;
        }
        leaf allow-reverse-ecmp {
          type empty;
        }
        leaf sync-icmp-session {
          type empty;
        }
        leaf ipsec-performance-acceleration {
          type empty;
        }
        container aging {
          uses apply-group;
          uses apply-macro;
          leaf early-ageout {
            type uint32;
          }
          leaf low-watermark {
            type uint32;
          }
          leaf high-watermark {
            type uint32;
          }
        }
        container bridge {
          uses apply-group;
          uses apply-macro;
          leaf block-non-ip-all {
            type empty;
          }
          leaf bypass-non-ip-unicast {
            type empty;
          }
          container no-packet-flooding {
            presence "enable no-packet-flooding";
            uses apply-group;
            uses apply-macro;
            leaf no-trace-route {
              type empty;
            }
          }
        }
        container ethernet-switching {
          uses apply-group;
          uses apply-macro;
          leaf block-non-ip-all {
            type empty;
          }
          leaf bypass-non-ip-unicast {
            type empty;
          }
          container no-packet-flooding {
            presence "enable no-packet-flooding";
            uses apply-group;
            uses apply-macro;
            leaf no-trace-route {
              type empty;
            }
          }
          leaf bpdu-vlan-flooding {
            type empty;
          }
        }
        container tcp-mss {
          uses apply-group;
          uses apply-macro;
          container all-tcp {
            presence "";
            uses apply-group;
            uses apply-macro;
            leaf mss {
              type uint32;
            }
          }
          container ipsec-vpn {
            presence "enable ipsec-vpn";
            uses apply-group;
            uses apply-macro;
            leaf mss {
              type uint32;
            }
          }
          container gre-in {
            presence "enable gre-in";
            uses apply-group;
            uses apply-macro;
            leaf mss {
              type uint32;
            }
          }
          container gre-out {
            presence "enable gre-out";
            uses apply-group;
            uses apply-macro;
            leaf mss {
              type uint32;
            }
          }
        }
        container tcp-session {
          uses apply-group;
          uses apply-macro;
          leaf rst-invalidate-session {
            type empty;
          }
          leaf fin-invalidate-session {
            type empty;
          }
          leaf rst-sequence-check {
            type empty;
          }
          leaf no-syn-check {
            type empty;
          }
          leaf strict-syn-check {
            type empty;
          }
          leaf no-syn-check-in-tunnel {
            type empty;
          }
          leaf no-sequence-check {
            type empty;
          }
          leaf tcp-initial-timeout {
            type uint32;
          }
          leaf maximum-window {
            type string;
          }
          container time-wait-state {
            presence "enable time-wait-state";
            uses apply-group;
            uses apply-macro;
            choice choice-3 {
              leaf session-ageout {
                type empty;
              }
              leaf session-timeout {
                type uint32;
              }
            }
            leaf apply-to-half-close-state {
              type empty;
            }
          }
        }
        leaf force-ip-reassembly {
          type empty;
        }
        leaf preserve-incoming-fragment-size {
          type empty;
        }
        container log {
          uses apply-group;
          uses apply-macro;
          leaf dropped-icmp-packet {
            type empty;
          }
          leaf dropped-illegal-packet {
            type empty;
          }
        }
        container advanced-options {
          uses apply-group;
          uses apply-macro;
          leaf drop-matching-reserved-ip-address {
            type empty;
          }
          leaf drop-matching-link-local-address {
            type empty;
          }
          leaf reverse-route-packet-mode-vr {
            type empty;
          }
        }
        container load-distribution {
          uses apply-group;
          uses apply-macro;
          container session-affinity {
            uses apply-group;
            uses apply-macro;
            container ipsec {
              presence "true";
            }
          }
        }
        container packet-log {
          uses apply-group;
          uses apply-macro;
          leaf enable {
            type empty;
          }
          leaf throttle-interval {
            units "milliseconds";
            type uint32;
          }
          list packet-filter {
            key "name";
            ordered-by user;
            uses flow-filter-type;
          }
        }
        leaf power-mode-ipsec {
          type empty;
        }
      }
      container utm {
        uses apply-group;
        uses apply-macro;
        container traceoptions {
          uses utm-traceoptions;
        }
        container application-proxy {
          uses apply-group;
          uses apply-macro;
          container traceoptions {
            uses utm-apppxy-traceoptions;
          }
        }
        container ipc {
          uses apply-group;
          uses apply-macro;
          container traceoptions {
            uses utm-ipc-traceoptions;
          }
        }
        container custom-objects {
          uses apply-group;
          uses apply-macro;
          list mime-pattern {
            key "name";
            ordered-by user;
            uses mime-list-type;
          }
          list filename-extension {
            key "name";
            ordered-by user;
            uses extension-list-type;
          }
          list url-pattern {
            key "name";
            ordered-by user;
            uses url-list-type;
          }
          list custom-url-category {
            key "name";
            ordered-by user;
            uses category-list-type;
          }
          list protocol-command {
            key "name";
            ordered-by user;
            uses command-list-type;
          }
        }
        container feature-profile {
          uses apply-group;
          uses apply-macro;
          container anti-virus {
            uses anti-virus-feature;
          }
          container web-filtering {
            uses webfilter-feature;
          }
          container anti-spam {
            uses anti-spam-feature;
          }
          container content-filtering {
            uses content-filtering-feature;
          }
        }
        list utm-policy {
          key "name";
          ordered-by user;
          uses profile-setting;
        }
      }
      container dynamic-vpn {
        presence "";
        uses apply-group;
        uses apply-macro;
        leaf force-upgrade {
          type empty;
        }
        leaf access-profile {
          type string;
        }
        list clients {
          key "name";
          ordered-by user;
          uses clients-object;
        }
      }
      container analysis {
        uses apply-group;
        uses apply-macro;
        leaf no-report {
          type empty;
        }
      }
      container softwires {
        uses apply-group;
        uses apply-macro;
        list softwire-name {
          key "name";
          uses softwire-option-type;
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
      }
      container macsec {
        uses security-macsec;
      }
    }
    container firewall {
      uses apply-group;
      uses apply-macro;
      container family {
        uses apply-group;
        uses apply-macro;
        container inet {
          uses apply-group;
          uses apply-macro;
          list dialer-filter {
            key "name";
            ordered-by user;
            uses inet-dialer-filter;
          }
          list prefix-action {
            key "name";
            ordered-by user;
            uses prefix-action;
          }
          list filter {
            key "name";
            ordered-by user;
            uses inet-filter;
          }
          list simple-filter {
            key "name";
            ordered-by user;
            uses inet-simple-filter;
          }
          list service-filter {
            key "name";
            ordered-by user;
            uses inet-service-filter;
          }
          list fast-update-filter {
            key "name";
            ordered-by user;
            uses inet-fuf;
          }
        }
        container inet6 {
          uses apply-group;
          uses apply-macro;
          list dialer-filter {
            key "name";
            ordered-by user;
            uses inet6-dialer-filter;
          }
          list filter {
            key "name";
            ordered-by user;
            uses inet6-filter;
          }
          list service-filter {
            key "name";
            ordered-by user;
            uses inet6-service-filter;
          }
          list fast-update-filter {
            key "name";
            ordered-by user;
            uses inet6-fuf;
          }
        }
        container mpls {
          uses apply-group;
          uses apply-macro;
          list dialer-filter {
            key "name";
            ordered-by user;
            uses mpls-dialer-filter;
          }
          list filter {
            key "name";
            ordered-by user;
            uses mpls-filter;
          }
        }
        container vpls {
          uses apply-group;
          uses apply-macro;
          list filter {
            key "name";
            ordered-by user;
            uses vpls-filter;
          }
        }
        container evpn {
          uses apply-group;
          uses apply-macro;
          list filter {
            key "name";
            ordered-by user;
            uses vpls-filter;
          }
        }
        container bridge {
          uses apply-group;
          uses apply-macro;
          list filter {
            key "name";
            ordered-by user;
            uses bridge-filter;
          }
        }
        container ccc {
          uses apply-group;
          uses apply-macro;
          list filter {
            key "name";
            ordered-by user;
            uses ccc-filter;
          }
        }
        container any {
          uses apply-group;
          uses apply-macro;
          list filter {
            key "name";
            ordered-by user;
            uses any-filter;
          }
        }
        container ethernet-switching {
          uses apply-group;
          uses apply-macro;
          list filter {
            key "name";
            ordered-by user;
            uses es-filter;
          }
        }
      }
      list policer {
        key "name";
        ordered-by user;
        uses firewall-policer;
      }
      list flexible-match {
        key "name";
        ordered-by user;
        uses firewall-flexible-match;
      }
      list tunnel-end-point {
        key "name";
        ordered-by user;
        uses tunnel-end-point;
      }
      list hierarchical-policer {
        key "name";
        ordered-by user;
        uses firewall-hierpolicer;
      }
      list interface-set {
        key "name";
        ordered-by user;
        uses interface-set-type;
      }
      list load-balance-group {
        key "name";
        ordered-by user;
        uses firewall-load-balance-group;
      }
      list three-color-policer {
        key "name";
        ordered-by user;
        uses three-color-policer-type;
      }
      list filter {
        key "name";
        ordered-by user;
        uses inet-filter;
      }
    }
    container access {
      uses juniper-access-options;
    }
    container routing-instances {
      uses apply-group;
      uses apply-macro;
      list instance {
        key "name";
        uses juniper-routing-instance;
      }
    }
    container services {
      uses apply-group;
      uses apply-macro;
      container rtlog {
        presence "enable rtlog";
        uses apply-advanced;
        container traceoptions {
          uses apply-advanced;
          container file {
            leaf filename {
              type string;
            }
            leaf size {
              type string;
            }
            leaf files {
              type string;
            }
            choice world-readable-choice {
              leaf world-readable {
                type empty;
              }
              leaf no-world-readable {
                type empty;
              }
            }
            leaf match {
              type regular-expression;
            }
          }
          list flag {
            key "name";
            ordered-by user;
            leaf name {
              type string;
            }
          }
        }
      }
      container policies {
        presence "enable policies";
        uses policy-object-type;
      }
      list address-book {
        key "name";
        ordered-by user;
        uses named-address-book-type;
      }
      container analytics {
        presence "enable analytics";
        uses apply-group;
        uses apply-macro;
        container zero-suppression {
          uses apply-advanced;
          leaf no-zero-suppression {
            type empty;
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            leaf name {
              type string;
            }
            leaf disable {
              type empty;
            }
          }
        }
        list export-profiles {
          key "name";
          ordered-by user;
          leaf name {
            type key-attribute-string-type;
          }
          uses apply-group;
          uses apply-macro;
          leaf stream-format {
            type string;
          }
          container interface {
            presence "enable interface";
            uses apply-group;
            uses apply-macro;
            leaf information {
              type empty;
            }
            container statistics {
              uses apply-group;
              uses apply-macro;
              leaf traffic {
                type empty;
              }
              leaf queue {
                type empty;
              }
            }
            container status {
              uses apply-group;
              uses apply-macro;
              leaf link {
                type empty;
              }
              leaf traffic {
                type empty;
              }
              leaf queue {
                type empty;
              }
            }
          }
          container system {
            presence "enable system";
            uses apply-group;
            uses apply-macro;
            leaf information {
              type empty;
            }
            container status {
              uses apply-group;
              uses apply-macro;
              leaf traffic {
                type empty;
              }
              leaf queue {
                type empty;
              }
            }
          }
        }
        list resource-profiles {
          key "name";
          ordered-by user;
          leaf name {
            type key-attribute-string-type;
          }
          uses apply-group;
          uses apply-macro;
          leaf queue-monitoring {
            type empty;
          }
          leaf no-queue-monitoring {
            type empty;
          }
          leaf traffic-monitoring {
            type empty;
          }
          leaf no-traffic-monitoring {
            type empty;
          }
          container depth-threshold {
            presence "";
            leaf high {
              mandatory true;
              units "bytes";
              type uint32;
            }
            leaf low {
              mandatory true;
              units "bytes";
              type uint32;
            }
          }
          container latency-threshold {
            presence "";
            leaf high {
              mandatory true;
              units "nanoseconds";
              type uint32;
            }
            leaf low {
              mandatory true;
              units "nanoseconds";
              type uint32;
            }
          }
        }
        container resource {
          presence "enable resource";
          uses apply-group;
          uses apply-macro;
          container system {
            uses apply-group;
            uses apply-macro;
            leaf resource-profile {
              type string;
            }
            container polling-interval {
              uses apply-group;
              uses apply-macro;
              leaf traffic-monitoring {
                units "seconds";
                type uint32;
              }
              leaf queue-monitoring {
                units "milliseconds";
                type uint32;
              }
            }
          }
          container interfaces {
            uses apply-group;
            uses apply-macro;
            list interface {
              key "name";
              uses interface-type;
            }
          }
        }
        container collector {
          uses apply-group;
          uses apply-macro;
          container local {
            uses apply-group;
            uses apply-macro;
            container file {
              leaf filename {
                type filename;
              }
              leaf size {
                type string;
              }
              leaf files {
                type uint32;
              }
            }
          }
          list address {
            key "name";
            leaf name {
              type ipaddr;
            }
            uses apply-group;
            uses apply-macro;
            list port {
              key "name";
              leaf name {
                type key-attribute-ulong-type;
              }
              uses apply-group;
              uses apply-macro;
              list transport {
                key "name";
                leaf name {
                  type string;
                }
                uses apply-group;
                uses apply-macro;
                leaf export-profile {
                  type string;
                }
              }
            }
          }
        }
        container traffic-statistics {
          uses apply-group;
          uses apply-macro;
          container file {
            leaf filename {
              type filename;
            }
            leaf size {
              type string;
            }
            leaf files {
              type uint32;
            }
          }
          leaf interval {
            units "seconds";
            type uint32;
          }
        }
        container queue-statistics {
          uses apply-group;
          uses apply-macro;
          container file {
            leaf filename {
              type filename;
            }
            leaf size {
              type string;
            }
            leaf files {
              type uint32;
            }
          }
          leaf interval {
            units "milliseconds";
            type uint32;
          }
        }
        container interfaces {
          uses apply-group;
          uses apply-macro;
          list interface {
            key "name";
            uses interface-type;
          }
        }
        container streaming-servers {
          uses apply-group;
          uses apply-macro;
          list address {
            key "name";
            ordered-by user;
            leaf name {
              type ipaddr;
            }
            uses apply-group;
            uses apply-macro;
            list port {
              key "name";
              leaf name {
                type key-attribute-ulong-type;
              }
              uses apply-group;
              uses apply-macro;
              leaf stream-format {
                type string;
              }
              list stream-type {
                key "name";
                leaf name {
                  type string;
                }
                uses apply-group;
                uses apply-macro;
              }
            }
          }
        }
        list streaming-server {
          key "name";
          ordered-by user;
          leaf name {
            type key-attribute-string-type;
          }
          uses apply-group;
          uses apply-macro;
          leaf remote-address {
            type ipv4addr;
          }
          leaf remote-port {
            type uint16;
          }
          leaf transport {
            type string;
          }
        }
        list export-profile {
          key "name";
          ordered-by user;
          leaf name {
            type key-attribute-string-type;
          }
          uses apply-group;
          uses apply-macro;
          leaf local-address {
            type ipv4addr;
          }
          leaf local-port {
            type uint16;
          }
          leaf dscp {
            type uint8;
          }
          leaf forwarding-class {
            type string;
          }
          leaf loss-priority {
            type string;
          }
          leaf reporting-rate {
            units "seconds";
            type uint32;
          }
          leaf payload-size {
            units "bytes";
            type uint32;
          }
          leaf format {
            type string;
          }
          leaf transport {
            type string;
          }
        }
        list sensor {
          key "name";
          ordered-by user;
          leaf name {
            type key-attribute-string-type;
          }
          uses apply-group;
          uses apply-macro;
          leaf-list server-name {
            ordered-by user;
            type string;
          }
          leaf export-name {
            type string;
          }
          leaf polling-interval {
            units "nanoseconds";
            type uint32;
          }
          leaf resource {
            mandatory true;
            type string;
          }
          leaf resource-filter {
            type string;
          }
          leaf subscription-id {
            type uint64;
          }
          leaf suppress-zeros {
            type empty;
          }
          leaf reporting-rate {
            units "seconds";
            type uint32;
          }
          leaf-list end-of-sync-identifiers {
            ordered-by user;
            type uint32;
          }
          leaf target-defined {
            type empty;
          }
          leaf life-time {
            type string;
          }
        }
        container agent {
          uses apply-group;
          uses apply-macro;
          list service-agents {
            key "name";
            ordered-by user;
            leaf name {
              type string;
            }
            uses apply-group;
            uses apply-macro;
            container inputs {
              uses apply-group;
              uses apply-macro;
              container input-jti-ipfix {
                presence "enable input-jti-ipfix";
                uses apply-group;
                uses apply-macro;
                container parameters {
                  presence "enable parameters";
                  uses apply-group;
                  uses apply-macro;
                  list record-group {
                    key "name";
                    ordered-by user;
                    leaf name {
                      type string;
                    }
                    uses apply-group;
                    uses apply-macro;
                    leaf reporting-interval {
                      type uint32;
                    }
                    leaf-list record {
                      ordered-by user;
                      type string;
                    }
                  }
                }
              }
              container input-ipfix {
                presence "enable input-ipfix";
                uses apply-group;
                uses apply-macro;
                container parameters {
                  presence "enable parameters";
                  uses apply-group;
                  uses apply-macro;
                  leaf tcp-port {
                    type uint16;
                  }
                  leaf maximum-connections {
                    type uint32;
                  }
                  leaf vrf-name {
                    type string;
                  }
                }
              }
              container analytics {
                presence "enable analytics";
                uses apply-group;
                uses apply-macro;
                container parameters {
                  presence "";
                  uses apply-group;
                  uses apply-macro;
                  leaf sample-frequency {
                    units "seconds";
                    type uint32;
                  }
                  leaf sensors {
                    mandatory true;
                    type string;
                  }
                  leaf generate-tags {
                    type empty;
                  }
                }
              }
            }
            list outputs {
              key "name";
              ordered-by user;
              uses output-plugin;
            }
          }
          container traceoptions {
            presence "enable traceoptions";
            uses apply-group;
            uses apply-macro;
            leaf flag {
              type string;
            }
            leaf filename {
              type string;
            }
          }
        }
      }
      container mobile-ip {
        presence "enable mobile-ip";
        uses juniper-protocols-mobile-ipv4;
      }
      container captive-portal-content-delivery {
        uses apply-group;
        uses apply-macro;
        list rule {
          key "name";
          ordered-by user;
          uses cpcd-rule-object-type;
        }
        list rule-set {
          key "name";
          ordered-by user;
          leaf name {
            type key-attribute-string-type;
          }
          uses apply-group;
          uses apply-macro;
          list rule {
            key "name";
            ordered-by user;
            leaf name {
              type string;
            }
            uses apply-group;
            uses apply-macro;
          }
        }
        list profile {
          key "name";
          ordered-by user;
          leaf name {
            type key-attribute-string-type;
          }
          uses apply-group;
          uses apply-macro;
          choice choice-3 {
            leaf dynamic {
              type empty;
            }
            list cpcd-rules {
              key "name";
              ordered-by user;
              leaf name {
                type key-attribute-string-type;
              }
              uses apply-group;
              uses apply-macro;
            }
            list cpcd-rule-sets {
              key "name";
              ordered-by user;
              leaf name {
                type key-attribute-string-type;
              }
              uses apply-group;
              uses apply-macro;
            }
          }
          container ipda-rewrite-options {
            presence "enable ipda-rewrite-options";
            uses apply-group;
            uses apply-macro;
            leaf destination-address {
              type ipaddr;
            }
            leaf destination-port {
              type uint16;
            }
          }
        }
        container traceoptions {
          uses cpcd-trace-options-type;
        }
      }
      container dynamic-flow-capture {
        uses apply-group;
        uses apply-macro;
        leaf g-max-duplicates {
          type uint32;
        }
        leaf g-duplicates-dropped-periodicity {
          type uint32;
        }
        list capture-group {
          key "name";
          ordered-by user;
          uses dfc-group-type;
        }
        container traceoptions {
          presence "enable traceoptions";
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
        }
      }
      container flow-tap {
        uses apply-group;
        uses apply-macro;
        container family {
          uses apply-advanced;
          leaf inet {
            type empty;
          }
          leaf inet6 {
            type empty;
          }
          leaf ccc {
            type empty;
          }
        }
        leaf interface {
          type interface-name;
        }
        leaf tunnel-interface {
          type interface-name;
        }
      }
      container radius-flow-tap {
        uses apply-group;
        uses apply-macro;
        leaf forwarding-class {
          type string;
        }
        leaf source-ipv4-address {
          type ipv4addr;
        }
        leaf multicast-interception {
          type empty;
        }
        container interfaces {
          uses apply-group;
          uses apply-macro;
          list tunnel-interface {
            key "name";
            uses tunnel-interface-type;
          }
        }
        choice ri_or_ls {
          case case_1 {
            leaf routing-instance {
              type string;
            }
          }
          case case_2 {
            list logical-system {
              key "name";
              ordered-by user;
              leaf name {
                type string;
              }
              uses apply-advanced;
              leaf routing-instance {
                type string;
              }
            }
          }
        }
        list policy {
          key "name";
          ordered-by user;
          leaf name {
            type string;
          }
          uses apply-advanced;
          container inet {
            uses apply-advanced;
            list drop-policy {
              key "name";
              ordered-by user;
              uses drop-policy-term;
            }
          }
          container inet6 {
            uses apply-advanced;
            list drop-policy {
              key "name";
              ordered-by user;
              uses drop-policy6-term;
            }
          }
        }
        container snmp {
          uses apply-advanced;
          list notify-targets {
            key "name";
            ordered-by user;
            leaf name {
              type ipaddr;
            }
            uses apply-advanced;
          }
        }
      }
      container flow-monitoring {
        presence "enable flow-monitoring";
        uses apply-group;
        uses apply-macro;
        container version9 {
          uses apply-group;
          uses apply-macro;
          list template {
            key "name";
            ordered-by user;
            uses version9-template;
          }
        }
        container version-ipfix {
          uses apply-group;
          uses apply-macro;
          list template {
            key "name";
            ordered-by user;
            uses version-ipfix-template;
          }
        }
      }
      container rpm {
        presence "enable rpm";
        uses apply-group;
        uses apply-macro;
        container traceoptions {
          uses rmopd-traceoptions;
        }
        container bgp {
          uses apply-group;
          uses apply-macro;
          leaf probe-type {
            type string;
          }
          leaf probe-count {
            type uint32;
          }
          leaf probe-interval {
            type uint32;
          }
          leaf test-interval {
            type uint32;
          }
          leaf destination-port {
            type uint16;
          }
          leaf history-size {
            type uint32;
          }
          leaf moving-average-size {
            type uint32;
          }
          leaf data-size {
            type uint32;
          }
          leaf data-fill {
            type string;
          }
          list logical-system {
            key "name";
            uses bgp-logical-system;
          }
          list routing-instances {
            key "name";
            uses bgp-routing-instances;
          }
        }
        list probe {
          key "name";
          ordered-by user;
          leaf name {
            type key-attribute-string-type;
          }
          uses apply-group;
          uses apply-macro;
          list test {
            key "name";
            ordered-by user;
            leaf name {
              type key-attribute-string-type;
            }
            uses apply-group;
            uses apply-macro;
            leaf probe-type {
              type string;
            }
            container target {
              presence "enable target";
              choice choice-3 {
                leaf address {
                  type ipv4addr;
                }
                leaf inet6-address {
                  type ipv6addr;
                }
                leaf inet6-url {
                  type string;
                }
                leaf url {
                  type string;
                }
              }
            }
            leaf probe-count {
              type uint32;
            }
            leaf probe-interval {
              type uint32;
            }
            leaf test-interval {
              type uint32;
            }
            leaf destination-port {
              type uint16;
            }
            leaf source-address {
              type ipv4addr;
            }
            leaf routing-instance {
              type string;
            }
            leaf history-size {
              type uint32;
            }
            leaf moving-average-size {
              type uint32;
            }
            leaf dscp-code-points {
              type string;
            }
            leaf data-size {
              type uint32;
            }
            leaf data-fill {
              type string;
            }
            container thresholds {
              presence "enable thresholds";
              uses apply-group;
              uses apply-macro;
              leaf successive-loss {
                type uint32;
              }
              leaf total-loss {
                type uint32;
              }
              leaf rtt {
                type uint32;
              }
              leaf jitter-rtt {
                type uint32;
              }
              leaf std-dev-rtt {
                type uint32;
              }
              leaf egress-time {
                type uint32;
              }
              leaf ingress-time {
                type uint32;
              }
              leaf jitter-ingress {
                type uint32;
              }
              leaf jitter-egress {
                type uint32;
              }
              leaf std-dev-ingress {
                type uint32;
              }
              leaf std-dev-egress {
                type uint32;
              }
            }
            leaf-list traps {
              ordered-by user;
              type string;
            }
            leaf destination-interface {
              type interface-name;
            }
            leaf hardware-timestamp {
              type empty;
            }
            leaf one-way-hardware-timestamp {
              type empty;
            }
          }
        }
        container probe-server {
          uses apply-group;
          uses apply-macro;
          container icmp {
            uses apply-group;
            uses apply-macro;
            leaf destination-interface {
              type interface-name;
            }
          }
          container tcp {
            presence "";
            uses apply-group;
            uses apply-macro;
            leaf port {
              type uint16;
            }
            leaf destination-interface {
              type interface-name;
            }
          }
          container udp {
            presence "";
            uses apply-group;
            uses apply-macro;
            leaf port {
              type uint16;
            }
            leaf destination-interface {
              type interface-name;
            }
          }
        }
        leaf probe-limit {
          type uint32;
        }
        container rfc2544-benchmarking {
          presence "enable rfc2544-benchmarking";
          uses apply-group;
          uses apply-macro;
          container apply-advanced {
            uses apply-group;
            uses apply-macro;
          }
          container profiles {
            uses apply-group;
            uses apply-macro;
            container apply-advanced {
              uses apply-group;
              uses apply-macro;
            }
            list test-profile {
              key "name";
              ordered-by user;
              leaf name {
                type key-attribute-string-type;
              }
              uses apply-group;
              uses apply-macro;
              container apply-advanced {
                uses apply-group;
                uses apply-macro;
              }
              leaf test-type {
                type string;
              }
              leaf-list packet-size {
                ordered-by user;
                type uint32;
              }
              leaf bandwidth-kbps {
                type uint32;
              }
              leaf step-percent {
                type uint32;
              }
            }
          }
          container tests {
            presence "enable tests";
            uses apply-group;
            uses apply-macro;
            container apply-advanced {
              uses apply-group;
              uses apply-macro;
            }
            list test-name {
              key "name";
              ordered-by user;
              leaf name {
                type key-attribute-string-type;
              }
              uses apply-group;
              uses apply-macro;
              container apply-advanced {
                uses apply-group;
                uses apply-macro;
              }
              leaf test-profile {
                type string;
              }
              leaf source-mac-address {
                type mac-unicaset;
              }
              leaf destination-mac-address {
                type mac-unicaset;
              }
              leaf ovlan-id {
                type int32;
              }
              leaf ovlan-priority {
                type int32;
              }
              leaf ovlan-cfi {
                type int32;
              }
              leaf outer-tag-protocol-id {
                type string;
              }
              leaf ivlan-id {
                type int32;
              }
              leaf ivlan-priority {
                type int32;
              }
              leaf ivlan-cfi {
                type int32;
              }
              leaf vlan-id {
                type int32;
              }
              leaf vlan-priority {
                type int32;
              }
              leaf vlan-cfi {
                type int32;
              }
              leaf service-type {
                type string;
              }
              leaf in-service {
                type empty;
              }
              leaf ip-swap {
                type empty;
              }
              leaf udp-tcp-port-swap {
                type empty;
              }
              leaf ignore-test-interface-state {
                type empty;
              }
              leaf check-test-interface-mtu {
                type empty;
              }
              leaf disable-signature-check {
                type empty;
              }
              leaf forwarding-class {
                type string;
              }
              leaf packet-loss-priority {
                type string;
              }
              leaf dscp-code-points {
                type string;
              }
              leaf mode {
                type string;
              }
              leaf reflect-mode {
                type string;
              }
              leaf family {
                type string;
              }
              leaf reflect-etype {
                type uint32;
              }
              leaf direction {
                type string;
              }
              leaf timestamp-format {
                type string;
              }
              leaf source-udp-port {
                type uint32;
              }
              leaf destination-udp-port {
                type uint32;
              }
              leaf test-duration {
                type uint32;
              }
              leaf test-iterator-duration {
                type uint32;
              }
              leaf test-finish-wait-duration {
                type uint32;
              }
              leaf transmit-failure-threshold {
                type string;
              }
              leaf receive-failure-threshold {
                type string;
              }
              leaf test-iterator-pass-threshold {
                type string;
              }
              leaf halt-on-prefix-down {
                type empty;
              }
              leaf skip-arp-iteration {
                type empty;
              }
              leaf test-interface {
                type interface-name;
              }
              leaf destination-ipv4-address {
                type ipv4addr;
              }
              leaf source-ipv4-address {
                type ipv4addr;
              }
            }
          }
        }
        container twamp {
          uses apply-group;
          uses apply-macro;
          leaf post-cli-implicit-firewall {
            type empty;
          }
          container client {
            uses apply-group;
            uses apply-macro;
            list control-connection {
              key "name";
              ordered-by user;
              leaf name {
                type key-attribute-string-type;
              }
              uses apply-group;
              uses apply-macro;
              container authentication-mode {
                uses apply-group;
                uses apply-macro;
                leaf none {
                  type empty;
                }
              }
              leaf destination-interface {
                type interface-name;
              }
              leaf persistent-results {
                type empty;
              }
              leaf control-type {
                type string;
              }
              leaf tcp-keepidle {
                units "seconds";
                type uint32;
              }
              leaf tcp-keepintvl {
                units "seconds";
                type uint32;
              }
              leaf tcp-keepcnt {
                type uint32;
              }
              leaf destination-port {
                type uint16;
              }
              leaf history-size {
                type uint16;
              }
              leaf moving-average-size {
                type uint32;
              }
              leaf routing-instance {
                type string;
              }
              leaf source-address {
                type ipv4addr;
              }
              leaf target-address {
                type ipv4addr;
              }
              leaf test-count {
                type uint32;
              }
              leaf test-interval {
                units "seconds";
                type uint16;
              }
              container traps {
                uses apply-group;
                uses apply-macro;
                leaf test-iteration-done {
                  type empty;
                }
                leaf control-connection-closed {
                  type empty;
                }
              }
              list test-session {
                key "name";
                ordered-by user;
                leaf name {
                  type key-attribute-string-type;
                }
                uses apply-group;
                uses apply-macro;
                leaf source-address {
                  type ipaddr;
                }
                leaf target-address {
                  type ipv4addr;
                }
                leaf data-fill-with-zeros {
                  type empty;
                }
                leaf data-size {
                  type uint16;
                }
                leaf dscp-code-points {
                  type string;
                }
                leaf ttl {
                  type uint32;
                }
                leaf probe-count {
                  type uint32;
                }
                leaf probe-interval {
                  units "seconds";
                  type uint32;
                }
                container thresholds {
                  presence "enable thresholds";
                  uses apply-group;
                  uses apply-macro;
                  leaf successive-loss {
                    type uint32;
                  }
                  leaf total-loss {
                    type uint32;
                  }
                  leaf rtt {
                    units "microseconds";
                    type uint32;
                  }
                  leaf max-rtt {
                    units "microseconds";
                    type uint32;
                  }
                  leaf jitter-rtt {
                    units "microseconds";
                    type uint32;
                  }
                  leaf std-dev-rtt {
                    units "microseconds";
                    type uint32;
                  }
                  leaf egress-time {
                    units "microseconds";
                    type uint32;
                  }
                  leaf ingress-time {
                    units "microseconds";
                    type uint32;
                  }
                  leaf jitter-ingress {
                    units "microseconds";
                    type uint32;
                  }
                  leaf jitter-egress {
                    units "microseconds";
                    type uint32;
                  }
                  leaf std-dev-ingress {
                    units "microseconds";
                    type uint32;
                  }
                  leaf std-dev-egress {
                    units "microseconds";
                    type uint32;
                  }
                }
                container traps {
                  uses apply-group;
                  uses apply-macro;
                  leaf probe-failure {
                    type empty;
                  }
                  leaf test-failure {
                    type empty;
                  }
                  leaf test-completion {
                    type empty;
                  }
                  leaf rtt-exceeded {
                    type empty;
                  }
                  leaf max-rtt-exceeded {
                    type empty;
                  }
                  leaf std-dev-exceeded {
                    type empty;
                  }
                  leaf jitter-exceeded {
                    type empty;
                  }
                  leaf ingress-time-exceeded {
                    type empty;
                  }
                  leaf ingress-std-dev-exceeded {
                    type empty;
                  }
                  leaf ingress-jitter-exceeded {
                    type empty;
                  }
                  leaf egress-time-exceeded {
                    type empty;
                  }
                  leaf egress-std-dev-exceeded {
                    type empty;
                  }
                  leaf egress-jitter-exceeded {
                    type empty;
                  }
                }
              }
            }
          }
          container server {
            presence "";
            uses apply-group;
            uses apply-macro;
            list routing-instance-list {
              key "name";
              ordered-by user;
              leaf name {
                type string;
              }
              uses apply-group;
              uses apply-macro;
              leaf port {
                mandatory true;
                type uint32;
              }
            }
            container authentication-mode {
              uses apply-group;
              uses apply-macro;
              leaf none {
                type empty;
              }
              container authenticated {
                presence "enable authenticated";
                leaf control-only {
                  type empty;
                }
              }
              container encrypted {
                presence "enable encrypted";
                leaf control-only {
                  type empty;
                }
              }
            }
            list authentication-key-chain {
              key "name";
              ordered-by user;
              uses twamp-authentication-key-chain;
            }
            leaf inactivity-timeout {
              type uint32;
            }
            leaf maximum-sessions {
              type uint32;
            }
            leaf maximum-sessions-per-connection {
              type uint32;
            }
            leaf maximum-connections {
              type uint32;
            }
            leaf maximum-connections-per-client {
              type uint32;
            }
            leaf port {
              type uint32;
            }
            list client-list {
              key "name";
              ordered-by user;
              leaf name {
                type key-attribute-string-type;
              }
              uses apply-group;
              uses apply-macro;
              leaf authentication-mode {
                type string;
              }
              list address {
                key "name";
                ordered-by user;
                leaf name {
                  type ipv4prefix;
                }
                uses apply-group;
                uses apply-macro;
              }
            }
            container light {
              presence "enable light";
              uses apply-advanced;
              leaf-list port {
                ordered-by user;
                type string;
              }
            }
          }
        }
      }
      container inline-monitoring {
        presence "enable inline-monitoring";
        uses apply-advanced;
        container traceoptions {
          uses apply-advanced;
          leaf no-remote-trace {
            type empty;
          }
          container file {
            leaf filename {
              type string;
            }
            leaf size {
              type string;
            }
            leaf files {
              type string;
            }
            choice world-readable-choice {
              leaf world-readable {
                type empty;
              }
              leaf no-world-readable {
                type empty;
              }
            }
            leaf match {
              type regular-expression;
            }
          }
        }
        list counter-profile {
          key "name";
          ordered-by user;
          leaf name {
            type string;
          }
          uses apply-advanced;
          list counter {
            key "name";
            ordered-by user;
            leaf name {
              type string;
            }
            uses apply-advanced;
            leaf max-value {
              type string;
            }
            leaf min-value {
              type string;
            }
            leaf counter-type {
              type string;
            }
          }
        }
        list feature-profile {
          key "name";
          ordered-by user;
          leaf name {
            type string;
          }
          uses apply-advanced;
          leaf-list features {
            ordered-by user;
            type string;
          }
        }
        list template {
          key "name";
          ordered-by user;
          leaf name {
            type string;
          }
          uses apply-advanced;
          leaf template-refresh-rate {
            type string;
          }
          leaf option-template-refresh-rate {
            type string;
          }
          leaf observation-domain-id {
            type string;
          }
          leaf template-id {
            type string;
          }
          leaf option-template-id {
            type string;
          }
          leaf flow-active-timeout {
            type string;
          }
          leaf flow-inactive-timeout {
            type string;
          }
          leaf template-type {
            type string;
          }
          container flow-monitoring {
            presence "enable flow-monitoring";
            uses apply-advanced;
            leaf sampling-profile {
              type string;
            }
            leaf packet-count {
              type string;
            }
            leaf sampling-rate {
              type string;
            }
            leaf security-enable {
              type empty;
            }
            leaf flow-rate {
              type string;
            }
            leaf burst-size {
              type string;
            }
            leaf flow-limit {
              type string;
            }
            leaf counter-profile {
              type string;
            }
            leaf feature-profile {
              type string;
            }
          }
          list primary-data-record-fields {
            key "name";
            ordered-by user;
            leaf name {
              type string;
            }
          }
        }
        list instance {
          key "name";
          ordered-by user;
          leaf name {
            type string;
          }
          uses apply-advanced;
          leaf template-name {
            type string;
          }
          leaf maximum-clip-length {
            type string;
          }
          leaf controller {
            type string;
          }
          leaf sampling-rate {
            type string;
          }
          list collector {
            key "name";
            ordered-by user;
            leaf name {
              type string;
            }
            uses apply-advanced;
            leaf source-address {
              type ipv4addr;
            }
            leaf destination-address {
              type ipv4addr;
            }
            leaf dscp {
              type string;
            }
            leaf destination-port {
              type string;
            }
            leaf forwarding-class {
              type string;
            }
            leaf sampling-rate {
              type string;
            }
            leaf routing-instance {
              type string;
            }
          }
        }
        leaf observation-cloud-id {
          type string;
        }
        leaf flow-export-timer {
          units "seconds";
          type string;
        }
      }
      container flow-collector {
        presence "";
        uses apply-group;
        uses apply-macro;
        leaf analyzer-address {
          type ipv4addr;
        }
        leaf analyzer-id {
          type string;
        }
        leaf retry {
          type uint32;
        }
        leaf retry-delay {
          type uint32;
        }
        list destinations {
          key "name";
          ordered-by user;
          uses collector-destinations-type;
        }
        list file-specification {
          key "name";
          uses file-specification-type;
        }
        container interface-map {
          presence "";
          uses interface-map-type;
        }
        container transfer-log-archive {
          presence "";
          uses collector-transfer-log-archive-type;
        }
      }
      container logging {
        uses juniper-pic-services-logging-options;
      }
      container application-identification {
        presence "enable application-identification";
        uses apply-group;
        uses apply-macro;
        container download {
          uses apply-group;
          uses apply-macro;
          leaf url {
            type string;
          }
          container automatic {
            presence "";
            uses apply-group;
            uses apply-macro;
            leaf start-time {
              type string;
            }
            leaf interval {
              type uint32;
            }
          }
        }
        container nested-application-settings {
          presence "enable nested-application-settings";
          uses apply-group;
          uses apply-macro;
          leaf no-nested-application {
            type empty;
          }
          leaf no-application-system-cache {
            type empty;
          }
        }
        leaf no-application-identification {
          type empty;
        }
        leaf no-signature-based {
          type empty;
        }
        leaf no-protocol-based {
          type empty;
        }
        leaf no-clear-application-system-cache {
          type empty;
        }
        leaf no-application-system-cache {
          type empty;
        }
        leaf max-sessions {
          type uint32;
        }
        leaf application-system-cache-timeout {
          type uint32;
        }
        leaf min-checked-bytes {
          type uint16;
        }
        leaf max-checked-bytes {
          type uint32;
        }
        leaf max-checked-packets {
          type uint32;
        }
        list application {
          key "name";
          leaf name {
            type key-attribute-string-type;
          }
          uses apply-group;
          uses apply-macro;
          leaf type {
            type string;
          }
          leaf index {
            type uint16;
          }
          list tags {
            key "name";
            ordered-by user;
            leaf name {
              type string;
            }
            uses apply-group;
            uses apply-macro;
            leaf value {
              type string;
            }
          }
          leaf session-timeout {
            type string;
          }
          leaf idle-timeout {
            type string;
          }
          container type-of-service {
            uses apply-group;
            uses apply-macro;
            leaf minimize-delay {
              type empty;
            }
            leaf maximize-throughput {
              type empty;
            }
            leaf maximize-reliability {
              type empty;
            }
            leaf minimize-monetary-cost {
              type empty;
            }
          }
          leaf disable {
            type empty;
          }
          leaf cacheable {
            type empty;
          }
          leaf description {
            type string;
          }
          leaf maximum-transactions {
            type uint16;
          }
          leaf alt-name {
            type string;
          }
          leaf compatibility {
            type string;
          }
          container port-mapping {
            uses apply-group;
            uses apply-macro;
            container icmp {
              uses apply-group;
              uses apply-macro;
              leaf type {
                type uint16;
              }
              leaf code {
                type uint16;
              }
            }
            leaf protocol {
              type uint16;
            }
            container port-range {
              uses apply-group;
              uses apply-macro;
              leaf-list tcp {
                type string;
                ordered-by user;
              }
              leaf-list udp {
                type string;
                ordered-by user;
              }
            }
            leaf disable {
              type empty;
            }
          }
          container icmp-mapping {
            uses apply-group;
            uses apply-macro;
            leaf type {
              type uint16;
            }
            leaf code {
              type uint16;
            }
            leaf order {
              type uint16;
            }
            leaf order-priority {
              type string;
            }
          }
          container ip-protocol-mapping {
            presence "";
            uses apply-group;
            uses apply-macro;
            leaf protocol {
              type uint16;
            }
            leaf order {
              type uint16;
            }
            leaf order-priority {
              type string;
            }
          }
          list address-mapping {
            key "name";
            ordered-by user;
            leaf name {
              type key-attribute-string-type;
            }
            uses apply-group;
            uses apply-macro;
            leaf order {
              type uint16;
            }
            leaf order-priority {
              type string;
            }
            container source {
              uses apply-group;
              uses apply-macro;
              leaf ip {
                type ipprefix;
              }
              container wildcard-address {
                presence "";
                leaf address {
                  type ipaddr;
                }
                leaf wildcard-mask {
                  type ipaddr;
                }
              }
              container port-range {
                uses apply-group;
                uses apply-macro;
                leaf-list tcp {
                  type string;
                  ordered-by user;
                }
                leaf-list udp {
                  type string;
                  ordered-by user;
                }
              }
            }
            container destination {
              uses apply-group;
              uses apply-macro;
              leaf ip {
                type ipprefix;
              }
              container wildcard-address {
                presence "";
                leaf address {
                  type ipaddr;
                }
                leaf wildcard-mask {
                  type ipaddr;
                }
              }
              container port-range {
                uses apply-group;
                uses apply-macro;
                leaf-list tcp {
                  type string;
                  ordered-by user;
                }
                leaf-list udp {
                  type string;
                  ordered-by user;
                }
              }
            }
          }
          list over {
            key "name";
            leaf name {
              type key-attribute-string-type;
            }
            uses apply-group;
            uses apply-macro;
            leaf protocol {
              type string;
            }
            leaf chain-order {
              type empty;
            }
            leaf order-priority {
              type string;
            }
            leaf order {
              type uint16;
            }
            container port-range {
              uses apply-group;
              uses apply-macro;
              leaf-list tcp {
                type string;
                ordered-by user;
              }
              leaf-list udp {
                type string;
                ordered-by user;
              }
            }
            list member {
              key "name";
              leaf name {
                type key-attribute-string-type;
              }
              uses apply-group;
              uses apply-macro;
              leaf context {
                type string;
              }
              leaf pattern {
                type string;
              }
              leaf direction {
                type string;
              }
              leaf check-bytes {
                type uint32;
              }
            }
          }
          container signature {
            presence "";
            uses apply-group;
            uses apply-macro;
            container port-range {
              uses apply-group;
              uses apply-macro;
              leaf-list tcp {
                type string;
                ordered-by user;
              }
              leaf-list udp {
                type string;
                ordered-by user;
              }
            }
            container client-to-server {
              uses apply-group;
              uses apply-macro;
              leaf dfa-pattern {
                type string;
              }
              leaf regex {
                type string;
              }
            }
            container server-to-client {
              uses apply-group;
              uses apply-macro;
              leaf dfa-pattern {
                type string;
              }
              leaf regex {
                type string;
              }
            }
            leaf min-data {
              type uint16;
            }
            leaf order {
              type uint16;
            }
            leaf disable {
              type empty;
            }
          }
        }
        list nested-application {
          key "name";
          leaf name {
            type key-attribute-string-type;
          }
          uses apply-group;
          uses apply-macro;
          leaf type {
            type string;
          }
          leaf index {
            type uint16;
          }
          leaf protocol {
            type string;
          }
          list signature {
            key "name";
            leaf name {
              type key-attribute-string-type;
            }
            uses apply-group;
            uses apply-macro;
            list member {
              key "name";
              leaf name {
                type key-attribute-string-type;
              }
              uses apply-group;
              uses apply-macro;
              leaf context {
                type string;
              }
              leaf pattern {
                type string;
              }
              leaf direction {
                type string;
              }
            }
            leaf chain-order {
              type empty;
            }
            leaf maximum-transactions {
              type uint16;
            }
            leaf order {
              type uint16;
            }
          }
        }
        list application-group {
          key "name";
          leaf name {
            type key-attribute-string-type;
          }
          uses apply-group;
          uses apply-macro;
          leaf index {
            type uint16;
          }
          list application-groups {
            key "name";
            leaf name {
              type key-attribute-string-type;
            }
            uses apply-group;
            uses apply-macro;
          }
          list applications {
            key "name";
            leaf name {
              type key-attribute-string-type;
            }
            uses apply-group;
            uses apply-macro;
          }
          leaf disable {
            type empty;
          }
        }
        list rule {
          key "name";
          ordered-by user;
          leaf name {
            type key-attribute-string-type;
          }
          uses apply-group;
          uses apply-macro;
          leaf application-name {
            type string;
          }
          list address {
            key "name";
            ordered-by user;
            leaf name {
              type string;
            }
            uses apply-group;
            uses apply-macro;
            container source {
              presence "";
              uses apply-group;
              uses apply-macro;
              leaf ip {
                type ipv4prefix;
              }
              container port-range {
                uses apply-group;
                uses apply-macro;
                leaf-list tcp {
                  type string;
                  ordered-by user;
                }
                leaf-list udp {
                  type string;
                  ordered-by user;
                }
              }
            }
            container destination {
              presence "";
              uses apply-group;
              uses apply-macro;
              leaf ip {
                type ipv4prefix;
              }
              container port-range {
                uses apply-group;
                uses apply-macro;
                leaf-list tcp {
                  type string;
                  ordered-by user;
                }
                leaf-list udp {
                  type string;
                  ordered-by user;
                }
              }
            }
            leaf order {
              type uint16;
            }
          }
        }
        list rule-set {
          key "name";
          ordered-by user;
          leaf name {
            type key-attribute-string-type;
          }
          uses apply-group;
          uses apply-macro;
          list rule {
            key "name";
            ordered-by user;
            leaf name {
              type string;
            }
            uses apply-group;
            uses apply-macro;
          }
        }
        list profile {
          key "name";
          ordered-by user;
          leaf name {
            type key-attribute-string-type;
          }
          uses apply-group;
          uses apply-macro;
          list rule-set {
            key "name";
            ordered-by user;
            leaf name {
              type key-attribute-string-type;
            }
            uses apply-group;
            uses apply-macro;
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
      }
      container ip-monitoring {
        uses apply-group;
        uses apply-macro;
        list policy {
          key "name";
          ordered-by user;
          leaf name {
            type key-attribute-string-type;
          }
          uses apply-group;
          uses apply-macro;
          leaf no-preempt {
            type empty;
          }
          container match {
            uses apply-group;
            uses apply-macro;
            leaf-list rpm-probe {
              type string;
              ordered-by user;
            }
          }
          container then {
            uses action-object-type;
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
      }
      container stateful-firewall {
        uses apply-group;
        uses apply-macro;
        list rule {
          key "name";
          ordered-by user;
          uses sfw-rule-object;
        }
        list rule-set {
          key "name";
          ordered-by user;
          leaf name {
            type key-attribute-string-type;
          }
          uses apply-group;
          uses apply-macro;
          list rule {
            key "name";
            ordered-by user;
            leaf name {
              type string;
            }
            uses apply-group;
            uses apply-macro;
          }
        }
      }
      container ip-reassembly {
        uses apply-group;
        uses apply-macro;
        list profile {
          key "name";
          uses ipr-profile-object;
        }
        list rule {
          key "name";
          ordered-by user;
          uses ipr-rule-object;
        }
        list rule-set {
          key "name";
          ordered-by user;
          leaf name {
            type key-attribute-string-type;
          }
          uses apply-group;
          uses apply-macro;
          list rule {
            key "name";
            ordered-by user;
            leaf name {
              type string;
            }
            uses apply-group;
            uses apply-macro;
          }
        }
      }
      container softwire {
        uses apply-group;
        uses apply-macro;
        list ipv6-multicast-interfaces {
          key "name";
          ordered-by user;
          leaf name {
            type string;
          }
          uses apply-group;
          uses apply-macro;
        }
        container softwire-concentrator {
          uses apply-group;
          uses apply-macro;
          list ds-lite {
            key "name";
            ordered-by user;
            uses dslite-object;
          }
          list v6rd {
            key "name";
            ordered-by user;
            uses v6rd-object;
          }
        }
        list rule {
          key "name";
          ordered-by user;
          uses sw-rule-object;
        }
        list rule-set {
          key "name";
          ordered-by user;
          leaf name {
            type key-attribute-string-type;
          }
          uses apply-group;
          uses apply-macro;
          list rule {
            key "name";
            ordered-by user;
            leaf name {
              type string;
            }
            uses apply-group;
            uses apply-macro;
          }
        }
      }
      container aacl {
        uses apply-group;
        uses apply-macro;
        list rule {
          key "name";
          ordered-by user;
          uses aacl-rule-object;
        }
        list rule-set {
          key "name";
          ordered-by user;
          leaf name {
            type key-attribute-string-type;
          }
          uses apply-group;
          uses apply-macro;
          list rule {
            key "name";
            ordered-by user;
            leaf name {
              type string;
            }
            uses apply-group;
            uses apply-macro;
          }
        }
      }
      container ptsp {
        uses apply-group;
        uses apply-macro;
        list rule {
          key "name";
          ordered-by user;
          uses ptsp-rule-object;
        }
        list forward-rule {
          key "name";
          ordered-by user;
          uses ptsp-forward-rule-object;
        }
        list rule-set {
          key "name";
          ordered-by user;
          leaf name {
            type key-attribute-string-type;
          }
          uses apply-group;
          uses apply-macro;
          list rule {
            key "name";
            ordered-by user;
            leaf name {
              type string;
            }
            uses apply-group;
            uses apply-macro;
          }
        }
      }
      container hcm {
        uses apply-group;
        uses apply-macro;
        list url-rule {
          key "name";
          ordered-by user;
          uses hcm-url-rule-object;
        }
        list tag-rule {
          key "name";
          ordered-by user;
          uses hcm-tag-rule-object;
        }
        list url-list {
          key "name";
          ordered-by user;
          uses hcm-url-list-object;
        }
        leaf-list tag-attribute {
          type string;
          ordered-by user;
        }
        list url-rule-set {
          key "name";
          ordered-by user;
          leaf name {
            type key-attribute-string-type;
          }
          uses apply-group;
          uses apply-macro;
          list rule {
            key "name";
            ordered-by user;
            leaf name {
              type string;
            }
            uses apply-group;
            uses apply-macro;
          }
        }
        list tag-rule-set {
          key "name";
          ordered-by user;
          leaf name {
            type key-attribute-string-type;
          }
          uses apply-group;
          uses apply-macro;
          list rule {
            key "name";
            ordered-by user;
            leaf name {
              type string;
            }
            uses apply-group;
            uses apply-macro;
          }
        }
        list profile {
          key "name";
          ordered-by user;
          leaf name {
            type key-attribute-string-type;
          }
          uses apply-group;
          uses apply-macro;
          container tag-rule {
            uses apply-group;
            uses apply-macro;
            leaf tag-rule-name {
              type string;
            }
          }
        }
      }
      container cos {
        uses apply-group;
        uses apply-macro;
        list application-profile {
          key "name";
          ordered-by user;
          uses cos-application-profile-object;
        }
        list rule {
          key "name";
          ordered-by user;
          uses cos-rule-object;
        }
        list rule-set {
          key "name";
          ordered-by user;
          leaf name {
            type key-attribute-string-type;
          }
          uses apply-group;
          uses apply-macro;
          list rule {
            key "name";
            ordered-by user;
            leaf name {
              type string;
            }
            uses apply-group;
            uses apply-macro;
          }
        }
      }
      container pgcp {
        presence "";
        uses apply-group;
        uses apply-macro;
        container traceoptions {
          uses apply-group;
          uses apply-macro;
          container flag {
            presence "enable flag";
            uses apply-group;
            uses apply-macro;
            leaf default {
              type string;
            }
            container h248-stack {
              presence "enable h248-stack";
              uses apply-group;
              uses apply-macro;
              leaf default {
                type string;
              }
              leaf control-association {
                type string;
              }
              leaf media-gateway {
                type string;
              }
              leaf messages {
                type empty;
              }
            }
            container bgf-core {
              presence "enable bgf-core";
              uses apply-group;
              uses apply-macro;
              leaf default {
                type string;
              }
              leaf firewall {
                type string;
              }
              leaf gate-logic {
                type string;
              }
              leaf policy {
                type string;
              }
              leaf pic-broker {
                type string;
              }
              leaf statistics {
                type string;
              }
              leaf common {
                type string;
              }
            }
            container sbc-utils {
              presence "enable sbc-utils";
              uses apply-group;
              uses apply-macro;
              leaf default {
                type string;
              }
              leaf common {
                type string;
              }
              leaf configuration {
                type string;
              }
              leaf device-monitor {
                type string;
              }
              leaf ipc {
                type string;
              }
              leaf memory-management {
                type string;
              }
              leaf messaging {
                type string;
              }
              leaf user-interface {
                type string;
              }
            }
          }
          container file {
            leaf filename {
              type string;
            }
            leaf size {
              type string;
            }
            leaf files {
              type uint32;
            }
            leaf world-readable {
              type empty;
            }
            leaf no-world-readable {
              type empty;
            }
            leaf match {
              type regular-expression;
            }
          }
        }
        list virtual-interface {
          key "name";
          ordered-by user;
          uses pgcp-virtual-interface-object;
        }
        list gateway {
          key "name";
          ordered-by user;
          uses pgcp-gateway-object;
        }
        list rule {
          key "name";
          ordered-by user;
          uses pgcp-rule-object;
        }
        list rule-set {
          key "name";
          ordered-by user;
          leaf name {
            type key-attribute-string-type;
          }
          uses apply-group;
          uses apply-macro;
          list rule {
            key "name";
            ordered-by user;
            leaf name {
              type string;
            }
            uses apply-group;
            uses apply-macro;
          }
        }
        container session-mirroring {
          presence "enable session-mirroring";
          uses pgcp-session-mirroring-object;
        }
        leaf notification-rate-limit {
          type int32;
        }
      }
      container border-signaling-gateway {
        uses apply-group;
        uses apply-macro;
        list gateway {
          key "name";
          ordered-by user;
          uses gateway-type;
        }
      }
      container ids {
        uses apply-group;
        uses apply-macro;
        list rule {
          key "name";
          ordered-by user;
          uses ids-rule-object;
        }
        list rule-set {
          key "name";
          ordered-by user;
          leaf name {
            type key-attribute-string-type;
          }
          uses apply-group;
          uses apply-macro;
          list rule {
            key "name";
            ordered-by user;
            leaf name {
              type string;
            }
            uses apply-group;
            uses apply-macro;
          }
        }
      }
      container nat {
        uses apply-group;
        uses apply-macro;
        list pool {
          key "name";
          ordered-by user;
          uses nat-pool-object;
        }
        list ipv6-multicast-interfaces {
          key "name";
          ordered-by user;
          leaf name {
            type string;
          }
          uses apply-group;
          uses apply-macro;
          leaf disable {
            type empty;
          }
        }
        leaf allow-overlapping-nat-pools {
          type empty;
        }
        list rule {
          key "name";
          ordered-by user;
          uses nat-rule-object;
        }
        list port-forwarding {
          key "name";
          ordered-by user;
          uses pf-mapping;
        }
        list rule-set {
          key "name";
          ordered-by user;
          leaf name {
            type key-attribute-string-type;
          }
          uses apply-group;
          uses apply-macro;
          list rule {
            key "name";
            ordered-by user;
            leaf name {
              type string;
            }
            uses apply-group;
            uses apply-macro;
          }
        }
        container source {
          uses ssg-source-nat-object;
        }
      }
      container l2tp {
        presence "enable l2tp";
        uses apply-group;
        uses apply-macro;
        list tunnel-group {
          key "name";
          ordered-by user;
          uses l2tp-tunnel-group-object;
        }
        container ip-reassembly {
          uses apply-group;
          uses apply-macro;
          leaf service-set {
            type string;
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          leaf level {
            type string;
          }
          list flag {
            key "name";
            ordered-by user;
            leaf name {
              type string;
            }
          }
          leaf debug-level {
            type string;
          }
          container filter {
            presence "enable filter";
            uses apply-group;
            uses apply-macro;
            list protocol {
              key "name";
              ordered-by user;
              leaf name {
                type string;
              }
            }
            leaf user-name {
              type string;
            }
          }
          list interfaces {
            key "name";
            ordered-by user;
            uses l2tp-interface-traceoptions;
          }
        }
        leaf weighted-load-balancing {
          type empty;
        }
        leaf destination-equal-load-balancing {
          type empty;
        }
        leaf drain {
          type empty;
        }
        leaf failover-within-preference {
          type empty;
        }
        leaf fail-over-within-preference {
          type empty;
        }
        leaf disable-calling-number-avp {
          type empty;
        }
        leaf disable-failover-protocol {
          type empty;
        }
        leaf destruct-timeout {
          type uint16;
        }
        leaf tunnel-switch-profile {
          type string;
        }
        container destination {
          presence "enable destination";
          uses l2tp-destination-object;
        }
        leaf maximum-sessions {
          type uint32;
        }
        container tunnel {
          uses apply-group;
          uses apply-macro;
          list name {
            key "name";
            ordered-by user;
            leaf name {
              type key-attribute-string-type;
            }
            list address {
              key "name";
              ordered-by user;
              leaf name {
                type ipv4addr;
              }
              list routing-instance {
                key "name";
                ordered-by user;
                leaf name {
                  type string;
                }
                leaf drain {
                  type empty;
                }
              }
              leaf drain {
                type empty;
              }
            }
            leaf drain {
              type empty;
            }
          }
          leaf assignment-id-format {
            type string;
          }
          leaf retransmission-count-established {
            type uint16;
          }
          leaf retransmission-count-not-established {
            type uint16;
          }
          leaf nas-port-method {
            type string;
          }
          leaf minimum-retransmission-timeout {
            type string;
          }
          leaf idle-timeout {
            type uint32;
          }
          leaf rx-window-size {
            type uint16;
          }
          container tx-address-change {
            presence "enable tx-address-change";
            uses apply-group;
            uses apply-macro;
            leaf accept {
              type empty;
            }
            leaf ignore {
              type empty;
            }
            leaf ignore-ip-address {
              type empty;
            }
            leaf ignore-udp-port {
              type empty;
            }
            leaf reject {
              type empty;
            }
            leaf reject-ip-address {
              type empty;
            }
            leaf reject-udp-port {
              type empty;
            }
          }
          leaf maximum-sessions {
            type uint32;
          }
          leaf failover-resync {
            type string;
          }
        }
        list session-limit-group {
          key "name";
          ordered-by user;
          leaf name {
            type key-attribute-string-type;
          }
          uses apply-group;
          uses apply-macro;
          leaf maximum-sessions {
            type uint32;
            mandatory true;
          }
        }
      }
      container adaptive-services-pics {
        uses apply-group;
        uses apply-macro;
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
      }
      list service-set {
        key "name";
        ordered-by user;
        leaf name {
          type key-attribute-string-type;
        }
        uses apply-group;
        uses apply-macro;
        container syslog {
          uses service-set-syslog-object;
        }
        leaf max-flows {
          type string;
        }
        leaf hosted-service-identifier {
          type int32;
        }
        leaf max-session-setup-rate {
          type string;
        }
        container max-drop-flows {
          uses apply-group;
          uses apply-macro;
          leaf ingress {
            type int32;
          }
          leaf egress {
            type int32;
          }
        }
        container snmp-trap-thresholds {
          presence "enable snmp-trap-thresholds";
          uses apply-group;
          uses apply-macro;
          container flow {
            presence "";
            leaf low {
              mandatory true;
              units "percent";
              type uint16;
            }
            leaf high {
              mandatory true;
              units "percent";
              type uint16;
            }
          }
          container nat-address-port {
            presence "";
            leaf low {
              mandatory true;
              units "percent";
              type uint16;
            }
            leaf high {
              mandatory true;
              units "percent";
              type uint16;
            }
          }
          container session {
            presence "";
            leaf low {
              mandatory true;
              units "percent";
              type uint16;
            }
            leaf high {
              mandatory true;
              units "percent";
              type uint16;
            }
          }
        }
        leaf tcp-mss {
          type uint16;
        }
        container cos-options {
          presence "enable cos-options";
          uses apply-group;
          uses apply-macro;
          leaf match-rules-on-reverse-flow {
            type empty;
          }
        }
        container softwire-options {
          presence "enable softwire-options";
          uses apply-group;
          uses apply-macro;
          leaf dslite-ipv6-prefix-length {
            type string;
          }
        }
        container nat-options {
          uses apply-group;
          uses apply-macro;
          container stateful-nat64 {
            uses apply-group;
            uses apply-macro;
            leaf clear-dont-fragment-bit {
              type empty;
            }
            leaf ipv6-mtu {
              type uint16;
            }
            leaf disable-h323-ras {
              type empty;
            }
          }
          container nptv6 {
            uses apply-group;
            uses apply-macro;
            leaf icmpv6-error-messages {
              type empty;
            }
          }
          leaf land-attack-check {
            type string;
          }
          leaf max-sessions-per-subscriber {
            type uint16;
          }
          leaf snmp-value-match-msmic {
            type empty;
          }
        }
        container service-set-options {
          presence "enable service-set-options";
          uses apply-group;
          uses apply-macro;
          container undocumented {
            leaf disable-session-open-syslog {
              type empty;
            }
          }
          leaf tcp-non-syn {
            type string;
          }
          leaf tcp-fast-open {
            type string;
          }
          leaf bypass-traffic-on-pic-failure {
            type empty;
          }
          leaf bypass-traffic-on-exceeding-flow-limits {
            type empty;
          }
          leaf enable-asymmetric-traffic-processing {
            type empty;
          }
          leaf subscriber-awareness {
            type empty;
          }
          container header-integrity-check {
            uses apply-group;
            uses apply-macro;
            leaf enable-all {
              type empty;
            }
          }
          leaf enable-change-on-ams-redistribution {
            type empty;
          }
          leaf routing-engine-services {
            type empty;
          }
          leaf inactivity-non-tcp-timeout {
            units "seconds";
            type uint32;
          }
          leaf session-timeout {
            units "seconds";
            type uint32;
          }
          container session-limit {
            presence "enable session-limit";
            uses apply-group;
            uses apply-macro;
            leaf maximum {
              type string;
            }
          }
          container tcp-session {
            presence "enable tcp-session";
            uses apply-group;
            uses apply-macro;
            leaf tcp-mss {
              type uint16;
            }
            leaf tcp-tickles {
              type uint8;
            }
            leaf open-timeout {
              units "seconds";
              type uint32;
            }
            leaf inactivity-tcp-timeout {
              units "seconds";
              type uint32;
            }
            leaf inactivity-asymm-tcp-timeout {
              units "seconds";
              type uint32;
            }
            container ignore-errors {
              presence "enable ignore-errors";
              leaf tcp {
                type empty;
              }
            }
            leaf close-timeout {
              units "seconds";
              type uint32;
            }
            leaf tcp-non-syn {
              type string;
            }
            leaf tcp-fast-open {
              type string;
            }
          }
        }
        container replicate-services {
          uses apply-group;
          uses apply-macro;
          leaf replication-threshold {
            type uint32;
          }
          leaf disable-replication-capability {
            type empty;
          }
        }
        container allow-multicast {
          presence "enable allow-multicast";
          uses apply-group;
          uses apply-macro;
        }
        choice choice-13 {
          list softwire-rules {
            key "name";
            ordered-by user;
            leaf name {
              type key-attribute-string-type;
            }
            uses apply-group;
            uses apply-macro;
          }
          list softwire-rule-sets {
            key "name";
            ordered-by user;
            leaf name {
              type key-attribute-string-type;
            }
            uses apply-group;
            uses apply-macro;
          }
        }
        list softwires-rule-set {
          key "name";
          ordered-by user;
          leaf name {
            type key-attribute-string-type;
          }
          uses apply-group;
          uses apply-macro;
        }
        choice choice-14 {
          list stateful-firewall-rules {
            key "name";
            ordered-by user;
            leaf name {
              type key-attribute-string-type;
            }
            uses apply-group;
            uses apply-macro;
          }
          list stateful-firewall-rule-sets {
            key "name";
            ordered-by user;
            leaf name {
              type key-attribute-string-type;
            }
            uses apply-group;
            uses apply-macro;
          }
        }
        list ids-option {
          key "name";
          ordered-by user;
          leaf name {
            type key-attribute-string-type;
          }
          uses apply-group;
          uses apply-macro;
        }
        choice choice-pcp-rules {
          list pcp-rules {
            key "name";
            ordered-by user;
            leaf name {
              type key-attribute-string-type;
            }
            uses apply-group;
            uses apply-macro;
          }
          list pcp-rule-sets {
            key "name";
            ordered-by user;
            leaf name {
              type key-attribute-string-type;
            }
            uses apply-group;
            uses apply-macro;
          }
        }
        leaf appid-profile {
          type string;
        }
        choice choice-15 {
          list nat-rules {
            key "name";
            ordered-by user;
            leaf name {
              type key-attribute-string-type;
            }
            uses apply-group;
            uses apply-macro;
          }
          list nat-rule-sets {
            key "name";
            ordered-by user;
            leaf name {
              type key-attribute-string-type;
            }
            uses apply-group;
            uses apply-macro;
          }
        }
        list ip-reassembly-rules {
          key "name";
          ordered-by user;
          leaf name {
            type key-attribute-string-type;
          }
          uses apply-group;
          uses apply-macro;
        }
        choice choice-16 {
          list ids-rules {
            key "name";
            ordered-by user;
            leaf name {
              type key-attribute-string-type;
            }
            uses apply-group;
            uses apply-macro;
          }
          list ids-rule-sets {
            key "name";
            ordered-by user;
            leaf name {
              type key-attribute-string-type;
            }
            uses apply-group;
            uses apply-macro;
          }
        }
        choice choice-17 {
          list cos-rules {
            key "name";
            ordered-by user;
            leaf name {
              type key-attribute-string-type;
            }
            uses apply-group;
            uses apply-macro;
          }
          list cos-rule-sets {
            key "name";
            ordered-by user;
            leaf name {
              type key-attribute-string-type;
            }
            uses apply-group;
            uses apply-macro;
          }
        }
        choice choice-18 {
          list aacl-rules {
            key "name";
            ordered-by user;
            leaf name {
              type key-attribute-string-type;
            }
            uses apply-group;
            uses apply-macro;
          }
          list aacl-rule-sets {
            key "name";
            ordered-by user;
            leaf name {
              type key-attribute-string-type;
            }
            uses apply-group;
            uses apply-macro;
          }
        }
        list aacl-dyn-rules {
          key "name";
          ordered-by user;
          leaf name {
            type key-attribute-string-type;
          }
          uses apply-group;
          uses apply-macro;
        }
        choice choice-19 {
          list ptsp-rules {
            key "name";
            ordered-by user;
            leaf name {
              type key-attribute-string-type;
            }
            uses apply-group;
            uses apply-macro;
          }
          list ptsp-rule-sets {
            key "name";
            ordered-by user;
            leaf name {
              type key-attribute-string-type;
            }
            uses apply-group;
            uses apply-macro;
          }
        }
        choice choice-20 {
          list pgcp-rules {
            key "name";
            ordered-by user;
            leaf name {
              type key-attribute-string-type;
            }
            uses apply-group;
            uses apply-macro;
          }
          list pgcp-rule-sets {
            key "name";
            ordered-by user;
            leaf name {
              type key-attribute-string-type;
            }
            uses apply-group;
            uses apply-macro;
          }
        }
        container jflow-rules {
          presence "enable jflow-rules";
          uses apply-group;
          uses apply-macro;
          container sampling {
            presence "enable sampling";
            uses apply-group;
            uses apply-macro;
            leaf instance {
              type string;
            }
          }
        }
        leaf application-identification-profile {
          type string;
        }
        leaf pcef-profile {
          type string;
        }
        leaf lrf-profile {
          type string;
        }
        leaf hcm-profile {
          type string;
        }
        leaf web-filter-profile {
          type string;
        }
        choice choice-hcm-url-rules {
          list hcm-url-rules {
            key "name";
            ordered-by user;
            leaf name {
              type key-attribute-string-type;
            }
            uses apply-group;
            uses apply-macro;
          }
          list hcm-url-rule-sets {
            key "name";
            ordered-by user;
            leaf name {
              type key-attribute-string-type;
            }
            uses apply-group;
            uses apply-macro;
          }
        }
        choice choice-tag-rules {
          list tag-rules {
            key "name";
            ordered-by user;
            leaf name {
              type key-attribute-string-type;
            }
            uses apply-group;
            uses apply-macro;
          }
          list tag-rule-sets {
            key "name";
            ordered-by user;
            leaf name {
              type key-attribute-string-type;
            }
            uses apply-group;
            uses apply-macro;
          }
        }
        leaf idp-profile {
          type string;
        }
        leaf captive-portal-content-delivery-profile {
          type string;
        }
        container policy-decision-statistics-profile {
          uses apply-group;
          uses apply-macro;
          leaf profile-name {
            type string;
          }
        }
        choice choice-25 {
          container interface-service {
            presence "";
            uses apply-group;
            uses apply-macro;
            leaf service-interface {
              type interface-unit;
            }
            container load-balancing-options {
              uses apply-group;
              uses apply-macro;
              container hash-keys {
                presence "enable hash-keys";
                uses apply-group;
                uses apply-macro;
                leaf resource-triggered {
                  type empty;
                }
                leaf-list ingress-key {
                  ordered-by user;
                  type string;
                }
                leaf-list egress-key {
                  ordered-by user;
                  type string;
                }
              }
            }
          }
          container sampling-service {
            presence "";
            uses apply-group;
            uses apply-macro;
            leaf service-interface {
              type interface-device;
            }
          }
          container next-hop-service {
            uses apply-group;
            uses apply-macro;
            leaf inside-service-interface {
              type interface-unit;
            }
            leaf outside-service-interface {
              type interface-unit;
            }
            leaf outside-service-interface-type {
              type string;
            }
            leaf service-interface-pool {
              type string;
            }
          }
        }
        list extension-service {
          key "name";
          ordered-by user;
          leaf name {
            type key-attribute-string-type;
          }
          uses apply-group;
          uses apply-macro;
        }
        container service-order {
          presence "";
          uses apply-group;
          uses apply-macro;
          leaf-list forward-flow {
            type string;
            ordered-by user;
          }
          leaf-list reverse-flow {
            type string;
            ordered-by user;
          }
        }
        container jflow-log {
          uses apply-group;
          uses apply-macro;
          leaf template-profile {
            type string;
          }
        }
        leaf subscriber-profile {
          type string;
        }
        container ipsec-vpn-options {
          presence "";
          uses service-set-ipsec-vpn-options-object;
        }
        choice choice-ipsec-vpn-rules {
          list ipsec-vpn-rules {
            key "name";
            ordered-by user;
            leaf name {
              type key-attribute-string-type;
            }
            uses apply-group;
            uses apply-macro;
          }
          list ipsec-vpn-rule-sets {
            key "name";
            ordered-by user;
            leaf name {
              type key-attribute-string-type;
            }
            uses apply-group;
            uses apply-macro;
          }
        }
        leaf ipsec-group-vpn {
          type string;
        }
        leaf redundancy-set-id {
          type uint32;
        }
      }
      container ipsec-vpn {
        uses apply-group;
        uses apply-macro;
        list rule {
          key "name";
          ordered-by user;
          uses ipsec-vpn-rule-object;
        }
        list rule-set {
          key "name";
          ordered-by user;
          leaf name {
            type key-attribute-string-type;
          }
          uses apply-group;
          uses apply-macro;
          list rule {
            key "name";
            ordered-by user;
            leaf name {
              type string;
            }
            uses apply-group;
            uses apply-macro;
          }
        }
        container ipsec {
          uses services-ipsec;
        }
        container ike {
          uses services-ike;
        }
        container traceoptions {
          uses ipsec-services-traceoptions;
        }
        leaf no-ipsec-tunnel-in-traceroute {
          type empty;
        }
        leaf establish-tunnels {
          type string;
        }
        leaf clear-ike-sas-on-pic-restart {
          type empty;
        }
        leaf clear-ipsec-sas-on-pic-restart {
          type empty;
        }
      }
      container service-interface-pools {
        uses apply-group;
        uses apply-macro;
        list pool {
          key "name";
          ordered-by user;
          uses service-interface-pool-object;
        }
      }
      container hosted-services {
        uses apply-group;
        uses apply-macro;
        list client-profile {
          key "name";
          ordered-by user;
          leaf name {
            type key-attribute-string-type;
          }
          uses apply-group;
          uses apply-macro;
          leaf transport-type {
            type string;
          }
          leaf client-address {
            type ipv4addr;
          }
          leaf hosted-service-identifier {
            type int32;
          }
        }
        list server-profile {
          key "name";
          ordered-by user;
          leaf name {
            type key-attribute-string-type;
          }
          uses apply-group;
          uses apply-macro;
          leaf transport-type {
            type string;
          }
          leaf server-address {
            type ipv4addr;
          }
          leaf client-address {
            type ipv4addr;
          }
          leaf hosted-service-identifier {
            type int32;
          }
        }
      }
      container service-device-pools {
        uses apply-group;
        uses apply-macro;
        list pool {
          key "name";
          ordered-by user;
          uses service-device-pool-object;
        }
      }
      container pcef {
        presence "enable pcef";
        uses apply-group;
        uses apply-macro;
        container profile {
          uses apply-group;
          uses apply-macro;
          leaf profile-name {
            type string;
          }
        }
      }
      container convergence-services {
        uses apply-group;
        uses apply-macro;
        container station-template {
          uses apply-group;
          uses apply-macro;
          list sip-template {
            key "name";
            ordered-by user;
            leaf name {
              type string;
            }
            uses apply-group;
            uses apply-macro;
            leaf dtmf-method {
              type string;
            }
            container caller-id-transmit {
              presence "enable caller-id-transmit";
              uses apply-group;
              uses apply-macro;
              choice choice-3 {
                leaf disable {
                  type empty;
                }
              }
            }
            container extension-inherit {
              presence "enable extension-inherit";
              uses apply-group;
              uses apply-macro;
              leaf from-extension {
                type string;
              }
              leaf to-extension {
                type string;
              }
            }
            leaf class-of-restriction {
              type string;
            }
            leaf-list codec {
              ordered-by user;
              type string;
            }
          }
          list analog-template {
            key "name";
            ordered-by user;
            leaf name {
              type string;
            }
            uses apply-group;
            uses apply-macro;
            container caller-id-transmit {
              presence "enable caller-id-transmit";
              uses apply-group;
              uses apply-macro;
              choice choice-3 {
                leaf disable {
                  type empty;
                }
              }
            }
            container voice-activity-detection {
              presence "enable voice-activity-detection";
              uses apply-group;
              uses apply-macro;
              choice choice-3 {
                leaf disable {
                  type empty;
                }
              }
            }
            container comfort-noise-generation {
              presence "enable comfort-noise-generation";
              uses apply-group;
              uses apply-macro;
              choice choice-3 {
                leaf disable {
                  type empty;
                }
              }
            }
            container echo-cancellation {
              presence "enable echo-cancellation";
              uses apply-group;
              uses apply-macro;
              choice choice-3 {
                leaf disable {
                  type empty;
                }
              }
              leaf tail-length {
                type uint32;
              }
            }
            container digital-gain {
              presence "enable digital-gain";
              uses apply-group;
              uses apply-macro;
              leaf tx-gain {
                type int32;
              }
              leaf rx-gain {
                type int32;
              }
            }
            container analog-gain {
              presence "enable analog-gain";
              uses apply-group;
              uses apply-macro;
              leaf tx-gain {
                type int32;
              }
              leaf rx-gain {
                type int32;
              }
            }
            container disconnect-supervision {
              presence "enable disconnect-supervision";
              uses apply-group;
              uses apply-macro;
              container power-denial {
                presence "enable power-denial";
                uses apply-group;
                uses apply-macro;
                choice choice-3 {
                  leaf disable {
                    type empty;
                  }
                }
                leaf denial-timeout {
                  type uint32;
                }
              }
              container battery-reversal {
                presence "enable battery-reversal";
                uses apply-group;
                uses apply-macro;
                choice choice-3 {
                  leaf disable {
                    type empty;
                  }
                }
              }
            }
            leaf class-of-restriction {
              type string;
            }
          }
        }
        container trunk-template {
          uses apply-group;
          uses apply-macro;
          list analog-template {
            key "name";
            ordered-by user;
            leaf name {
              type string;
            }
            uses apply-group;
            uses apply-macro;
            container caller-id-transmit {
              presence "enable caller-id-transmit";
              uses apply-group;
              uses apply-macro;
              choice choice-3 {
                leaf disable {
                  type empty;
                }
              }
            }
            container voice-activity-detection {
              presence "enable voice-activity-detection";
              uses apply-group;
              uses apply-macro;
              choice choice-3 {
                leaf disable {
                  type empty;
                }
              }
            }
            container comfort-noise-generation {
              presence "enable comfort-noise-generation";
              uses apply-group;
              uses apply-macro;
              choice choice-3 {
                leaf disable {
                  type empty;
                }
              }
            }
            container echo-cancellation {
              presence "enable echo-cancellation";
              uses apply-group;
              uses apply-macro;
              choice choice-3 {
                leaf disable {
                  type empty;
                }
              }
              leaf tail-length {
                type uint32;
              }
            }
            container digital-gain {
              presence "enable digital-gain";
              uses apply-group;
              uses apply-macro;
              leaf tx-gain {
                type int32;
              }
              leaf rx-gain {
                type int32;
              }
            }
            container analog-gain {
              presence "enable analog-gain";
              uses apply-group;
              uses apply-macro;
              leaf tx-gain {
                type int32;
              }
              leaf rx-gain {
                type int32;
              }
            }
            container disconnect-supervision {
              presence "enable disconnect-supervision";
              uses apply-group;
              uses apply-macro;
              container power-denial {
                presence "enable power-denial";
                uses apply-group;
                uses apply-macro;
                choice choice-3 {
                  leaf disable {
                    type empty;
                  }
                }
                leaf denial-timeout {
                  type uint32;
                }
              }
              container battery-reversal {
                presence "enable battery-reversal";
                uses apply-group;
                uses apply-macro;
                choice choice-3 {
                  leaf disable {
                    type empty;
                  }
                }
              }
            }
            container answer-supervision {
              presence "enable answer-supervision";
              uses apply-group;
              uses apply-macro;
              container battery-reversal {
                presence "enable battery-reversal";
                uses apply-group;
                uses apply-macro;
                choice choice-3 {
                  leaf disable {
                    type empty;
                  }
                }
              }
            }
            leaf class-of-restriction {
              type string;
            }
          }
        }
        list station {
          key "name";
          ordered-by user;
          leaf name {
            type string;
          }
          uses apply-group;
          uses apply-macro;
          leaf extension {
            type string;
          }
          leaf class-of-restriction {
            type string;
          }
          leaf caller-id {
            type string;
          }
          leaf direct-inward-dialing {
            type string;
          }
          container direct-inward-line {
            presence "";
            uses apply-group;
            uses apply-macro;
            leaf trunk-group {
              type string;
            }
          }
          leaf auth-id {
            type string;
          }
          leaf auth-password {
            type unreadable;
          }
          container station-type {
            presence "enable station-type";
            uses apply-group;
            uses apply-macro;
            choice choice-3 {
              container sip {
                presence "enable sip";
                uses apply-group;
                uses apply-macro;
                leaf template {
                  type string;
                }
              }
              container analog {
                presence "";
                uses apply-group;
                uses apply-macro;
                leaf template {
                  type string;
                }
                leaf tdm-interface {
                  type string;
                }
                leaf time-slot {
                  type uint32;
                }
              }
            }
          }
        }
        list station-group {
          key "name";
          ordered-by user;
          leaf name {
            type string;
          }
          uses apply-group;
          uses apply-macro;
          leaf description {
            type string;
          }
          leaf-list station {
            type string;
            ordered-by user;
          }
        }
        list peer-call-server {
          key "name";
          ordered-by user;
          leaf name {
            type string;
          }
          uses apply-group;
          uses apply-macro;
          leaf description {
            type string;
          }
          container address {
            presence "enable address";
            uses apply-group;
            uses apply-macro;
            leaf fqdn {
              type string;
            }
            leaf ipv4-addr {
              type ipv4addr;
            }
          }
          container registrar-address {
            presence "enable registrar-address";
            uses apply-group;
            uses apply-macro;
            leaf fqdn {
              type string;
            }
            leaf ipv4-addr {
              type ipv4addr;
            }
          }
          container sip-registration {
            presence "enable sip-registration";
            uses apply-group;
            uses apply-macro;
            choice choice-3 {
              leaf disable {
                type empty;
              }
            }
          }
          leaf source-interface {
            type interface-name;
          }
          container protocol {
            presence "enable protocol";
            uses apply-group;
            uses apply-macro;
            container sip {
              presence "enable sip";
              uses apply-group;
              uses apply-macro;
              leaf port {
                type uint32;
              }
              leaf transport {
                type string;
              }
            }
          }
          leaf-list codec {
            ordered-by user;
            type string;
          }
          leaf dtmf-method {
            type string;
          }
          leaf auth-id {
            type string;
          }
          leaf auth-password {
            type unreadable;
          }
          container from-domain {
            uses apply-group;
            uses apply-macro;
            choice choice-3 {
              leaf ip-address {
                type ipaddr;
              }
              leaf fqdn {
                type string;
              }
            }
          }
        }
        container profiles {
          presence "enable profiles";
          uses apply-group;
          uses apply-macro;
          list availability-check-profile {
            key "name";
            ordered-by user;
            leaf name {
              type string;
            }
            uses apply-group;
            uses apply-macro;
            container keepalive-interval {
              uses apply-group;
              uses apply-macro;
              leaf available-server {
                type uint32;
              }
              leaf unavailable-server {
                type uint32;
              }
            }
            leaf transaction-timeout {
              type uint32;
            }
          }
        }
        list media-gateway {
          key "name";
          ordered-by user;
          leaf name {
            type string;
          }
          uses apply-group;
          uses apply-macro;
          leaf peer-call-server {
            type string;
          }
          leaf dial-plan {
            type string;
          }
          container protocol {
            presence "enable protocol";
            uses apply-group;
            uses apply-macro;
            container sip {
              presence "enable sip";
              uses apply-group;
              uses apply-macro;
              leaf port {
                type uint32;
              }
              leaf transport {
                type string;
              }
            }
          }
          container service-point {
            presence "enable service-point";
            uses apply-group;
            uses apply-macro;
            leaf zone {
              type string;
            }
          }
        }
        list survivable-call-service {
          key "name";
          ordered-by user;
          leaf name {
            type string;
          }
          uses apply-group;
          uses apply-macro;
          leaf peer-call-server {
            type string;
          }
          leaf dial-plan {
            type string;
          }
          container protocol {
            presence "enable protocol";
            uses apply-group;
            uses apply-macro;
            container sip {
              presence "enable sip";
              uses apply-group;
              uses apply-macro;
              leaf port {
                type uint32;
              }
              leaf transport {
                type string;
              }
            }
          }
          leaf registration-expiry-timeout {
            type uint32;
          }
          leaf sip-timeout {
            type uint32;
          }
          leaf monitor-timeout {
            type uint32;
          }
          leaf heartbeat-normal-interval {
            type uint32;
          }
          leaf heartbeat-survivable-interval {
            type uint32;
          }
          container response-threshold {
            presence "enable response-threshold";
            uses apply-group;
            uses apply-macro;
            leaf minimum {
              type uint32;
            }
          }
          container service-point {
            presence "enable service-point";
            uses apply-group;
            uses apply-macro;
            leaf zone {
              type string;
            }
          }
        }
        list dial-plan {
          key "name";
          ordered-by user;
          leaf name {
            type string;
          }
          uses apply-group;
          uses apply-macro;
          list route-pattern {
            key "name";
            ordered-by user;
            leaf name {
              type string;
            }
            uses apply-group;
            uses apply-macro;
            container call-type {
              presence "enable call-type";
              uses apply-group;
              uses apply-macro;
              choice choice-3 {
                leaf custom-call {
                  type empty;
                }
                leaf emergency-call {
                  type empty;
                }
                leaf intra-branch-call {
                  type empty;
                }
                leaf inter-branch-call {
                  type empty;
                }
                leaf local-call {
                  type empty;
                }
                leaf long-distance-call {
                  type empty;
                }
                leaf international-call {
                  type empty;
                }
                leaf trunk-call {
                  type empty;
                }
              }
            }
            list trunk-group {
              key "name";
              ordered-by user;
              leaf name {
                type string;
              }
              uses apply-group;
              uses apply-macro;
              leaf preference {
                type uint32;
              }
              leaf digit-transform {
                type string;
              }
            }
          }
          list route-policy {
            key "name";
            ordered-by user;
            uses rtmd-dialplan-policy;
          }
        }
        list trunk {
          key "name";
          ordered-by user;
          leaf name {
            type string;
          }
          uses apply-group;
          uses apply-macro;
          leaf-list direct-inward-dialing {
            type string;
            ordered-by user;
          }
          container trunk-type {
            presence "enable trunk-type";
            uses apply-group;
            uses apply-macro;
            choice choice-3 {
              container fxo {
                presence "";
                uses apply-group;
                uses apply-macro;
                leaf template {
                  type string;
                }
                leaf tdm-interface {
                  type string;
                }
                container disconnect-supervision {
                  presence "enable disconnect-supervision";
                  uses apply-group;
                  uses apply-macro;
                  container battery-reversal {
                    presence "enable battery-reversal";
                    uses apply-group;
                    uses apply-macro;
                    choice choice-3 {
                      leaf disable {
                        type empty;
                      }
                    }
                  }
                  container power-denial {
                    presence "enable power-denial";
                    uses apply-group;
                    uses apply-macro;
                    choice choice-3 {
                      leaf disable {
                        type empty;
                      }
                    }
                    leaf denial-timeout {
                      type uint32;
                    }
                  }
                }
                container answer-supervision {
                  presence "enable answer-supervision";
                  uses apply-group;
                  uses apply-macro;
                  container battery-reversal {
                    presence "enable battery-reversal";
                    uses apply-group;
                    uses apply-macro;
                    choice choice-3 {
                      leaf disable {
                        type empty;
                      }
                    }
                  }
                }
              }
              container fxs {
                presence "";
                uses apply-group;
                uses apply-macro;
                leaf template {
                  type string;
                }
                leaf tdm-interface {
                  type string;
                }
                container disconnect-supervision {
                  presence "enable disconnect-supervision";
                  uses apply-group;
                  uses apply-macro;
                  container power-denial {
                    presence "enable power-denial";
                    uses apply-group;
                    uses apply-macro;
                    choice choice-3 {
                      leaf disable {
                        type empty;
                      }
                    }
                    leaf denial-timeout {
                      type uint32;
                    }
                  }
                  container battery-reversal {
                    presence "enable battery-reversal";
                    uses apply-group;
                    uses apply-macro;
                    choice choice-3 {
                      leaf disable {
                        type empty;
                      }
                    }
                  }
                }
              }
              container t1 {
                presence "";
                uses apply-group;
                uses apply-macro;
                leaf template {
                  type string;
                }
                leaf tdm-interface {
                  type string;
                }
                container cas-group {
                  presence "";
                  uses apply-group;
                  uses apply-macro;
                  leaf time-slots {
                    type string;
                  }
                  leaf signaling {
                    type string;
                  }
                }
                container pri-group {
                  presence "";
                  uses apply-group;
                  uses apply-macro;
                  leaf network-type {
                    type string;
                  }
                  leaf time-slots {
                    type string;
                  }
                }
              }
              container e1 {
                presence "";
                uses apply-group;
                uses apply-macro;
                leaf tdm-interface {
                  type string;
                }
                container pri-group {
                  presence "";
                  uses apply-group;
                  uses apply-macro;
                  leaf network-type {
                    type string;
                  }
                  leaf time-slots {
                    type string;
                  }
                }
              }
              container sip {
                presence "enable sip";
                uses apply-group;
                uses apply-macro;
                container peer-proxy-server {
                  presence "enable peer-proxy-server";
                  uses apply-group;
                  uses apply-macro;
                  leaf description {
                    type string;
                  }
                  leaf availability-check-profile {
                    type string;
                  }
                  container address {
                    presence "enable address";
                    uses apply-group;
                    uses apply-macro;
                    leaf fqdn {
                      type string;
                    }
                    leaf ipv4-addr {
                      type ipv4addr;
                    }
                  }
                  container from-domain {
                    uses apply-group;
                    uses apply-macro;
                    choice choice-3 {
                      leaf ip-address {
                        type ipaddr;
                      }
                      leaf fqdn {
                        type string;
                      }
                    }
                  }
                  container registrar-address {
                    presence "enable registrar-address";
                    uses apply-group;
                    uses apply-macro;
                    leaf fqdn {
                      type string;
                    }
                    leaf ipv4-addr {
                      type ipv4addr;
                    }
                  }
                  container sip-registration {
                    presence "enable sip-registration";
                    uses apply-group;
                    uses apply-macro;
                    choice choice-3 {
                      leaf disable {
                        type empty;
                      }
                    }
                  }
                  leaf port {
                    type uint32;
                  }
                  leaf transport {
                    type string;
                  }
                  leaf max-concurrent-calls {
                    type uint32;
                  }
                  leaf source-interface {
                    type interface-name;
                  }
                  leaf-list codec {
                    ordered-by user;
                    type string;
                  }
                  leaf dtmf-method {
                    type string;
                  }
                  leaf auth-id {
                    type string;
                  }
                  leaf auth-password {
                    type unreadable;
                  }
                }
              }
            }
          }
        }
        list trunk-group {
          key "name";
          ordered-by user;
          leaf name {
            type string;
          }
          uses apply-group;
          uses apply-macro;
          leaf description {
            type string;
          }
          leaf-list trunk {
            type string;
            ordered-by user;
          }
        }
        container digit-manipulation {
          presence "enable digit-manipulation";
          uses apply-group;
          uses apply-macro;
          list digit-transform {
            key "name";
            ordered-by user;
            leaf name {
              type string;
            }
            uses apply-group;
            uses apply-macro;
            leaf regular-expression {
              type string;
            }
          }
        }
        list class-of-restriction {
          key "name";
          ordered-by user;
          leaf name {
            type string;
          }
          uses apply-group;
          uses apply-macro;
          list policy {
            key "name";
            ordered-by user;
            leaf name {
              type string;
            }
            uses apply-group;
            uses apply-macro;
            container call-type {
              presence "enable call-type";
              uses apply-group;
              uses apply-macro;
              choice choice-3 {
                leaf custom-call {
                  type empty;
                }
                leaf any-call {
                  type empty;
                }
                leaf inter-branch-call {
                  type empty;
                }
                leaf local-call {
                  type empty;
                }
                leaf long-distance-call {
                  type empty;
                }
                leaf international-call {
                  type empty;
                }
              }
            }
            leaf permission {
              type string;
            }
          }
        }
        container features {
          presence "enable features";
          uses apply-group;
          uses apply-macro;
          list ring-group {
            key "name";
            ordered-by user;
            leaf name {
              type string;
            }
            uses apply-group;
            uses apply-macro;
            leaf extension {
              type string;
            }
            leaf direct-inward-dialing {
              type string;
            }
            leaf ring-timeout {
              type uint32;
            }
            leaf station-group {
              type string;
            }
          }
          list hunt-group {
            key "name";
            ordered-by user;
            leaf name {
              type string;
            }
            uses apply-group;
            uses apply-macro;
            leaf extension {
              type string;
            }
            leaf direct-inward-dialing {
              type string;
            }
            leaf ring-timeout {
              type uint32;
            }
            leaf station-group {
              type string;
            }
          }
          list pickup-group {
            key "name";
            ordered-by user;
            leaf name {
              type string;
            }
            uses apply-group;
            uses apply-macro;
            leaf station-group {
              type string;
            }
          }
          container call-park {
            presence "";
            uses apply-group;
            uses apply-macro;
            leaf extension {
              type string;
            }
            leaf number-of-slots {
              type uint32;
            }
          }
          container auto-attendant {
            presence "enable auto-attendant";
            uses apply-group;
            uses apply-macro;
            container live-attendant {
              presence "";
              uses apply-group;
              uses apply-macro;
              leaf extension {
                type string;
              }
              container hours {
                presence "enable hours";
                uses apply-group;
                uses apply-macro;
                leaf start-time {
                  type time;
                }
                leaf end-time {
                  type time;
                }
              }
            }
            leaf ring-count {
              type uint32;
            }
          }
          container voicemail {
            presence "";
            uses apply-group;
            uses apply-macro;
            leaf extension {
              type string;
            }
            leaf remote-access-number {
              type string;
            }
          }
          container music-on-hold {
            presence "enable music-on-hold";
            uses apply-group;
            uses apply-macro;
            leaf directory {
              type string;
            }
            leaf format {
              type string;
            }
            container order {
              presence "enable order";
              uses apply-group;
              uses apply-macro;
              choice choice-3 {
                leaf alphabetical {
                  type empty;
                }
                leaf random {
                  type empty;
                }
              }
            }
          }
          container guest {
            presence "enable guest";
            uses apply-group;
            uses apply-macro;
            leaf class-of-restriction {
              type string;
            }
            container auto-register {
              presence "enable auto-register";
              uses apply-group;
              uses apply-macro;
              choice choice-3 {
                leaf disable {
                  type empty;
                }
              }
            }
          }
          container accounting {
            presence "enable accounting";
            uses apply-group;
            uses apply-macro;
            list profile {
              key "name";
              ordered-by user;
              leaf name {
                type string;
              }
              uses apply-group;
              uses apply-macro;
              leaf description {
                type string;
              }
              leaf report-unanswered-call {
                type empty;
              }
              leaf use-compact-cdr {
                type empty;
              }
              leaf operational-state {
                type string;
              }
              container formats {
                presence "enable formats";
                uses apply-group;
                uses apply-macro;
                list comma-separated-value {
                  key "name";
                  ordered-by user;
                  leaf name {
                    type string;
                  }
                  uses apply-group;
                  uses apply-macro;
                  leaf description {
                    type string;
                  }
                  leaf batch-size {
                    type uint32;
                  }
                  leaf purge-time-interval {
                    type uint32;
                  }
                }
              }
              container transport {
                presence "enable transport";
                uses apply-group;
                uses apply-macro;
                container ftp {
                  presence "enable ftp";
                  uses apply-group;
                  uses apply-macro;
                  list server {
                    key "name";
                    ordered-by user;
                    leaf name {
                      type string;
                    }
                    uses apply-group;
                    uses apply-macro;
                    leaf description {
                      type string;
                    }
                    container address {
                      presence "enable address";
                      uses apply-group;
                      uses apply-macro;
                      leaf fqdn {
                        type string;
                      }
                      leaf ipv4-addr {
                        type ipv4addr;
                      }
                    }
                    leaf auth-id {
                      type string;
                    }
                    leaf auth-password {
                      type unreadable;
                    }
                    leaf path-name {
                      type string;
                    }
                    leaf format {
                      type string;
                    }
                  }
                }
              }
            }
          }
        }
        container preferences {
          presence "enable preferences";
          uses apply-group;
          uses apply-macro;
          container sip {
            presence "enable sip";
            uses apply-group;
            uses apply-macro;
            leaf registration-expiry-timeout {
              type uint32;
            }
            container session-timers {
              presence "enable session-timers";
              uses apply-group;
              uses apply-macro;
              leaf minimum-expiry-interval {
                type uint32;
              }
              leaf session-expiry-interval {
                type uint32;
              }
            }
          }
          container media-processing-unit {
            presence "enable media-processing-unit";
            uses apply-group;
            uses apply-macro;
            container jitter-buffer {
              presence "enable jitter-buffer";
              uses apply-group;
              uses apply-macro;
              container adaptive-jitter {
                presence "enable adaptive-jitter";
                uses apply-group;
                uses apply-macro;
                choice choice-3 {
                  leaf disable {
                    type empty;
                  }
                }
              }
              container fixed-jitter {
                presence "enable fixed-jitter";
                uses apply-group;
                uses apply-macro;
                choice choice-3 {
                  leaf disable {
                    type empty;
                  }
                }
                leaf fixed-jitter-time {
                  type uint32;
                }
              }
            }
            container codec-packetization-interval {
              presence "enable codec-packetization-interval";
              uses apply-group;
              uses apply-macro;
              leaf G711 {
                type uint32;
              }
              leaf G729 {
                type uint32;
              }
            }
            leaf companding {
              type string;
            }
          }
        }
        list media-policy {
          key "name";
          ordered-by user;
          uses rtmd-mediapolicy;
        }
      }
      container unified-access-control {
        uses apply-group;
        uses apply-macro;
        list infranet-controller {
          key "name";
          ordered-by user;
          leaf name {
            type key-attribute-string-type;
          }
          uses apply-group;
          uses apply-macro;
          leaf address {
            type ipv4addr;
          }
          leaf port {
            type uint32;
          }
          leaf interface {
            type interface-name;
          }
          leaf password {
            type string;
          }
          leaf-list ca-profile {
            type string;
            ordered-by user;
          }
          leaf server-certificate-subject {
            type string;
          }
        }
        leaf timeout {
          type uint32;
        }
        leaf interval {
          type uint32;
        }
        leaf timeout-action {
          type string;
        }
        leaf test-only-mode {
          type empty;
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
        list captive-portal {
          key "name";
          ordered-by user;
          leaf name {
            type key-attribute-string-type;
          }
          uses apply-group;
          uses apply-macro;
          leaf redirect-traffic {
            type string;
          }
          leaf redirect-url {
            type string;
          }
        }
      }
      container monitoring {
        container rpm {
          list owner {
            key "name";
            leaf name {
              type string;
            }
            list test {
              key "name";
              leaf name {
                type string;
              }
              leaf probe-type {
                type string;
              }
              leaf source-address {
                type string;
              }
              leaf probe-count {
                type uint32;
              }
              leaf test-interval {
                type uint32;
              }
              leaf history-size {
                type uint32;
              }
              leaf data-size {
                type uint32;
              }
              container thresholds {
                uses apply-advanced;
                container egress-time {
                  presence "enable egress-time";
                  leaf limit-value {
                    units "microseconds";
                    type string;
                  }
                  leaf average {
                    type empty;
                  }
                }
                container ingress-time {
                  presence "enable ingress-time";
                  leaf limit-value {
                    units "microseconds";
                    type string;
                  }
                  leaf average {
                    type empty;
                  }
                }
                container jitter-egress {
                  presence "enable jitter-egress";
                  leaf limit-value {
                    units "microseconds";
                    type string;
                  }
                  leaf average {
                    type empty;
                  }
                }
                container jitter-ingress {
                  presence "enable jitter-ingress";
                  leaf limit-value {
                    units "microseconds";
                    type string;
                  }
                  leaf average {
                    type empty;
                  }
                }
                container jitter-rtt {
                  presence "enable jitter-rtt";
                  leaf limit-value {
                    units "microseconds";
                    type string;
                  }
                  leaf average {
                    type empty;
                  }
                }
                container rtt {
                  presence "enable rtt";
                  leaf limit-value {
                    units "microseconds";
                    type string;
                  }
                  leaf average {
                    type empty;
                  }
                }
                leaf successive-loss {
                  type string;
                }
                leaf total-loss {
                  type string;
                }
              }
              leaf-list traps {
                ordered-by user;
                type string;
              }
            }
          }
        }
        container twamp {
          container server {
            presence "enable server";
            container light {
              presence "enable light";
              uses apply-advanced;
              leaf-list port {
                ordered-by user;
                type string;
              }
              leaf offload-type {
                type string;
              }
              container stateful-sequence {
                presence "enable stateful-sequence";
                uses apply-advanced;
                leaf cache-size {
                  type string;
                }
              }
            }
          }
        }
      }
    }
    container vmhost {
      uses apply-group;
      uses apply-macro;
      leaf no-auto-recovery {
        type empty;
      }
      container management-if {
        presence "enable management-if";
        uses apply-group;
        uses apply-macro;
        leaf link-mode {
          type string;
        }
        leaf speed {
          type string;
        }
        leaf disable {
          type empty;
        }
      }
      container resize {
        uses apply-group;
        uses apply-macro;
        container vjunos {
          presence "";
          uses apply-group;
          uses apply-macro;
          leaf compact {
            mandatory true;
            type empty;
          }
        }
      }
      list interfaces {
        key "name";
        ordered-by user;
        leaf name {
          type string;
        }
        uses apply-group;
        uses apply-macro;
        container family {
          uses apply-group;
          uses apply-macro;
          container inet {
            presence "";
            uses apply-group;
            uses apply-macro;
            list address {
              key "name";
              ordered-by user;
              leaf name {
                type ipv4prefix;
              }
              uses apply-group;
              uses apply-macro;
              leaf master-only {
                type empty;
              }
            }
            leaf gateway {
              mandatory true;
              type ipv4addr;
            }
          }
          container inet6 {
            presence "";
            uses apply-group;
            uses apply-macro;
            list address {
              key "name";
              ordered-by user;
              leaf name {
                type ipv6prefix;
              }
              uses apply-group;
              uses apply-macro;
              leaf master-only {
                type empty;
              }
            }
            leaf gateway {
              mandatory true;
              type ipv6addr;
            }
          }
        }
      }
      container syslog {
        presence "enable syslog";
        uses apply-group;
        uses apply-macro;
        list file {
          key "name";
          ordered-by user;
          leaf name {
            type key-attribute-string-type;
          }
          uses apply-group;
          uses apply-macro;
          list vmhost-syslog-object {
            key "facility level";
            leaf facility {
              type string;
            }
            leaf level {
              type string;
            }
          }
        }
        list host {
          key "name";
          ordered-by user;
          leaf name {
            type string;
          }
          uses apply-group;
          uses apply-macro;
          list vmhost-syslog-object {
            key "facility level";
            leaf facility {
              type string;
            }
            leaf level {
              type string;
            }
          }
          leaf transport {
            type string;
          }
        }
      }
      container services {
        presence "enable services";
        uses apply-group;
        uses apply-macro;
        container ssh {
          presence "enable ssh";
          uses apply-group;
          uses apply-macro;
          leaf root-login {
            type string;
          }
        }
      }
    }
    container applications {
      uses apply-group;
      uses apply-macro;
      list application {
        key "name";
        ordered-by user;
        uses application-object;
      }
      list application-set {
        key "name";
        ordered-by user;
        uses application-set-object;
      }
    }
    container diameter {
      presence "";
      uses apply-group;
      uses apply-macro;
      container origin {
        presence "";
        uses apply-group;
        uses apply-macro;
        leaf realm {
          mandatory true;
          type string;
        }
        leaf host {
          mandatory true;
          type string;
        }
      }
      list network-element {
        key "name";
        ordered-by user;
        leaf name {
          type key-attribute-string-type;
        }
        uses apply-group;
        uses apply-macro;
        container dne-origin {
          presence "";
          uses apply-group;
          uses apply-macro;
          leaf realm {
            mandatory true;
            type string;
          }
          leaf host {
            type string;
          }
        }
        leaf-list function {
          ordered-by user;
          type string;
        }
        list peer {
          key "name";
          ordered-by user;
          leaf name {
            type key-attribute-string-type;
          }
          uses apply-group;
          uses apply-macro;
          leaf priority {
            mandatory true;
            type uint32;
          }
        }
        container forwarding {
          presence "";
          uses apply-group;
          uses apply-macro;
          list route {
            key "name";
            ordered-by user;
            leaf name {
              type key-attribute-string-type;
            }
            uses apply-group;
            uses apply-macro;
            container function {
              choice choice-jsrc {
                leaf jsrc {
                  type empty;
                }
                leaf packet-triggered-subscribers {
                  type empty;
                }
                leaf gx-plus {
                  type empty;
                }
                leaf sd-3gpp {
                  type empty;
                }
                leaf nasreq {
                  type empty;
                }
                leaf pcrf {
                  type empty;
                }
                leaf ocs {
                  type empty;
                }
              }
              leaf partition {
                type string;
              }
            }
            container destination {
              presence "";
              leaf realm {
                mandatory true;
                type string;
              }
              leaf host {
                type string;
              }
            }
            leaf metric {
              mandatory true;
              type uint32;
            }
          }
        }
      }
      list transport {
        key "name";
        ordered-by user;
        leaf name {
          type key-attribute-string-type;
        }
        uses apply-group;
        uses apply-macro;
        leaf address {
          mandatory true;
          type ipaddr;
        }
        choice choice-logical-system {
          container logical-system {
            presence "";
            leaf logical-system-name {
              type string;
              mandatory true;
            }
            leaf routing-instance {
              type string;
            }
          }
          leaf routing-instance {
            type string;
          }
        }
      }
      list peer {
        key "name";
        ordered-by user;
        leaf name {
          type key-attribute-string-type;
        }
        uses apply-group;
        uses apply-macro;
        leaf address {
          mandatory true;
          type ipaddr;
        }
        leaf send-origin-state-id {
          type empty;
        }
        choice choice-logical-system {
          container logical-system {
            presence "";
            leaf logical-system-name {
              type string;
              mandatory true;
            }
            leaf routing-instance {
              type string;
            }
          }
          leaf routing-instance {
            type string;
          }
        }
        container connect-actively {
          presence "enable connect-actively";
          uses apply-group;
          uses apply-macro;
          leaf transport {
            type string;
          }
          leaf port {
            type uint16;
          }
        }
        container peer-origin {
          presence "";
          uses apply-group;
          uses apply-macro;
          leaf realm {
            mandatory true;
            type string;
          }
          leaf host {
            mandatory true;
            type string;
          }
        }
      }
    }
    container bridge-domains {
      uses apply-group;
      uses apply-macro;
      list domain {
        key "name";
        uses juniper-bridge-domains;
      }
    }
    container fabric {
      uses apply-group;
      uses apply-macro;
      container routing-instances {
        uses apply-group;
        uses apply-macro;
        list instance {
          key "name";
          uses juniper-fabric-routing-instance;
        }
      }
      container routing-options {
        uses juniper-fabric-routing-options;
      }
      container protocols {
        uses apply-group;
        uses apply-macro;
        container bgp {
          uses juniper-protocols-bgp;
        }
      }
      container resources {
        list node-group {
          key "name";
          leaf name {
            type string;
          }
          leaf network-domain {
            type empty;
          }
          list node-device {
            key "name";
            leaf name {
              type string;
            }
          }
        }
      }
      container aliases {
        list node-device {
          key "name";
          leaf name {
            type string;
          }
          leaf item-alias {
            type string;
          }
        }
        list interconnect-device {
          key "name";
          leaf name {
            type string;
          }
          leaf item-alias {
            type string;
          }
        }
        list director-device {
          key "name";
          leaf name {
            type string;
          }
          leaf item-alias {
            type string;
          }
        }
      }
      container administration {
        leaf traceoptions {
          type string;
        }
        leaf ais {
          type string;
        }
      }
    }
    container switch-options {
      uses juniper-def-rtb-switch-options;
    }
    container access-profile {
      leaf access-profile-name {
        type string;
      }
    }
    container unified-edge {
      uses apply-group;
      uses apply-macro;
      container cos-cac {
        uses juniper-unified-edge-cos-options;
      }
      list local-policies {
        key "name";
        ordered-by user;
        leaf name {
          type string;
        }
        uses apply-group;
        uses apply-macro;
        leaf description {
          type string;
        }
        leaf resource-threshold-profile {
          type string;
        }
        leaf classifier-profile {
          type string;
        }
        leaf cos-policy-profile {
          type string;
        }
        leaf roamer-classifier-profile {
          type string;
        }
        leaf roamer-cos-policy-profile {
          type string;
        }
        leaf visitor-classifier-profile {
          type string;
        }
        leaf visitor-cos-policy-profile {
          type string;
        }
        leaf traffic-class-qci-mapping-profile {
          type string;
        }
        leaf ul-bandwidth-pool {
          type string;
        }
        leaf dl-bandwidth-pool {
          type string;
        }
      }
      container aaa {
        uses apply-group;
        uses apply-macro;
        container traceoptions {
          uses aaa-traceoptions;
        }
        list mobile-profiles {
          key "name";
          ordered-by user;
          uses aaa-profile;
        }
      }
      container diameter-profiles {
        uses mobile-diameter-profiles;
      }
      container gateways {
        uses apply-group;
        uses apply-macro;
        list ggsn-pgw {
          key "name";
          ordered-by user;
          leaf name {
            type key-attribute-string-type;
          }
          uses apply-group;
          uses apply-macro;
          leaf service-mode {
            type string;
          }
          leaf maximum-bearers {
            type uint32;
          }
          leaf session-timeout-check-interval {
            units "in minutes";
            type uint32;
          }
          leaf redirect-timeout {
            units "in seconds";
            type uint32;
          }
          leaf local-policy-profile {
            type string;
          }
          leaf anchor-pfe-guaranteed-bandwidth {
            units "giga-bits per second";
            type uint32;
          }
          leaf anchor-pfe-maximum-bearers {
            units "in thousands";
            type uint32;
          }
          leaf anchor-pfe-default-bearers-percentage {
            units "percentage of maximum apfe bearers";
            type uint32;
          }
          leaf anchor-pfe-ipv4-nbm-prefixes {
            units "number of prefixes in multiples of 1K";
            type uint32;
          }
          leaf anchor-pfe-ipv6-nbm-prefixes {
            units "number of prefixes in multiples of 1K";
            type uint32;
          }
          container preemption {
            presence "enable preemption";
            uses apply-group;
            uses apply-macro;
            leaf enable {
              type empty;
            }
            leaf gtpv1-pvi-disable {
              type empty;
            }
            leaf gtpv1-pci-disable {
              type empty;
            }
          }
          container gtp {
            uses mobile-gateway-config-gtp;
          }
          container home-plmn {
            uses apply-group;
            uses apply-macro;
            list mcc {
              key "mcc mnc";
              ordered-by user;
              leaf mcc {
                type key-attribute-string-type;
              }
              leaf mnc {
                type key-attribute-string-type;
              }
              uses apply-group;
              uses apply-macro;
            }
          }
          container traceoptions {
            uses mobile-smd-traceoptions;
          }
          container call-rate-statistics {
            presence "enable call-rate-statistics";
            uses apply-group;
            uses apply-macro;
            leaf interval {
              units "minutes";
              type uint32;
            }
            leaf history {
              type uint32;
            }
          }
          list service-selection-profiles {
            key "name";
            ordered-by user;
            leaf name {
              type key-attribute-string-type;
            }
            uses apply-group;
            uses apply-macro;
            list term {
              key "name";
              ordered-by user;
              leaf name {
                type key-attribute-string-type;
              }
              uses apply-group;
              uses apply-macro;
              container from {
                uses apply-group;
                uses apply-macro;
                leaf imsi {
                  type string;
                }
                leaf msisdn {
                  type string;
                }
                leaf imei {
                  type string;
                }
                leaf anonymous-user {
                  type empty;
                }
                leaf domain-name {
                  type string;
                }
                leaf roaming-status {
                  type string;
                }
                container plmn {
                  uses apply-group;
                  uses apply-macro;
                  list mcc {
                    key "mcc mnc";
                    ordered-by user;
                    leaf mcc {
                      type key-attribute-string-type;
                    }
                    leaf mnc {
                      type key-attribute-string-type;
                    }
                    uses apply-group;
                    uses apply-macro;
                  }
                  leaf except {
                    type empty;
                  }
                }
                leaf charging-characteristics {
                  type uint32;
                }
                leaf maximum-bearers {
                  type uint32;
                }
                leaf peer {
                  type ipaddr;
                }
                leaf peer-routing-instance {
                  type string;
                }
                leaf pdn-type {
                  type string;
                }
                leaf rat-type {
                  type string;
                }
              }
              container then {
                uses apply-group;
                uses apply-macro;
                list redirect-peer {
                  key "name";
                  ordered-by user;
                  leaf name {
                    type ipaddr;
                  }
                }
                leaf accept {
                  type empty;
                }
                leaf reject {
                  type empty;
                }
                leaf apn-name {
                  type string;
                }
                leaf pcef-profile {
                  type string;
                }
                leaf charging-profile {
                  type string;
                }
              }
            }
          }
          container apn-services {
            uses ggsn-pgw-apn-services;
          }
          container system {
            presence "";
            uses unified-edge-ggsn-pgw-system;
          }
          container diameter {
            uses unified-edge-gateway-diameter;
          }
          container charging {
            presence "enable charging";
            uses apply-group;
            uses apply-macro;
            container traceoptions {
              uses charging-traceoptions;
            }
            container cdr-profiles {
              uses apply-group;
              uses apply-macro;
              list cdr-profile {
                key "name";
                uses juniper-cdr-profiles;
              }
            }
            container trigger-profiles {
              uses apply-group;
              uses apply-macro;
              list trigger-profile {
                key "name";
                ordered-by user;
                uses juniper-trigger-profiles;
              }
            }
            container transport-profiles {
              uses apply-group;
              uses apply-macro;
              list transport-profile {
                key "name";
                uses juniper-transport-profiles;
              }
            }
            container local-persistent-storage-options {
              uses juniper-charged-configuraton;
            }
            container charging-profiles {
              uses apply-group;
              uses apply-macro;
              list charging-profile {
                key "name";
                uses juniper-charging-profiles;
              }
            }
            container gtpp {
              uses apply-group;
              uses apply-macro;
              container source-interface {
                presence "";
                leaf interface-name {
                  type interface-name;
                }
                leaf ipv4-address {
                  type ipv4addr;
                }
              }
              leaf destination-port {
                type uint32;
              }
              leaf n3-requests {
                type uint16;
              }
              leaf transport-protocol {
                type string;
              }
              leaf version {
                type string;
              }
              leaf echo-interval {
                units "seconds";
                type uint32;
              }
              leaf no-path-management {
                type empty;
              }
              leaf t3-response {
                units "seconds";
                type uint16;
              }
              leaf header-type {
                type string;
              }
              leaf pending-queue-size {
                type uint32;
              }
              leaf down-detect-time {
                units "seconds";
                type uint32;
              }
              leaf reconnect-time {
                units "seconds";
                type uint32;
              }
              list peer {
                key "name";
                uses gtpp-peer;
              }
            }
            container diameter-avp-profiles {
              uses apply-group;
              uses apply-macro;
              list diameter-avpp {
                key "name";
                uses juniper-diameter-avp-profiles;
              }
            }
          }
          container ip-reassembly-profile {
            uses apply-group;
            uses apply-macro;
            leaf profile-name {
              type string;
            }
          }
          container ipv6-router-advertisement {
            presence "enable ipv6-router-advertisement";
            uses mobile-gateways-ipv6-router-advertisement;
          }
          container software-datapath {
            presence "enable software-datapath";
            uses apply-group;
            uses apply-macro;
            container traceoptions {
              uses software-datapath-traceoptions;
            }
          }
          container inline-services {
            uses apply-group;
            uses apply-macro;
            container ip-reassembly {
              presence "enable ip-reassembly";
              uses apply-group;
              uses apply-macro;
              container service-set {
                uses apply-group;
                uses apply-macro;
                leaf service-set-name {
                  type string;
                }
              }
            }
          }
        }
        list sgw {
          key "name";
          ordered-by user;
          leaf name {
            type key-attribute-string-type;
          }
          uses apply-group;
          uses apply-macro;
          leaf service-mode {
            type string;
          }
          leaf maximum-bearers {
            type uint32;
          }
          leaf local-policy-profile {
            type string;
          }
          leaf anchor-pfe-guaranteed-bandwidth {
            units "giga-bits per second";
            type uint32;
          }
          leaf anchor-pfe-maximum-bearers {
            units "in thousands";
            type uint32;
          }
          leaf anchor-pfe-default-bearers-percentage {
            units "percentage of maximum apfe bearers";
            type uint32;
          }
          container preemption {
            presence "enable preemption";
            uses apply-group;
            uses apply-macro;
            leaf enable {
              type empty;
            }
          }
          leaf remote-delete-on-peer-fail {
            type empty;
          }
          container gtp {
            uses sgw-config-gtp;
          }
          container home-plmn {
            uses apply-group;
            uses apply-macro;
            list mcc {
              key "mcc mnc";
              ordered-by user;
              leaf mcc {
                type key-attribute-string-type;
              }
              leaf mnc {
                type key-attribute-string-type;
              }
              uses apply-group;
              uses apply-macro;
            }
          }
          container traceoptions {
            uses mobile-smd-traceoptions;
          }
          container call-rate-statistics {
            presence "enable call-rate-statistics";
            uses apply-group;
            uses apply-macro;
            leaf interval {
              units "minutes";
              type uint32;
            }
            leaf history {
              type uint32;
            }
          }
          container system {
            presence "";
            uses unified-edge-sgw-system;
          }
          container charging {
            presence "enable charging";
            uses apply-group;
            uses apply-macro;
            container traceoptions {
              uses charging-traceoptions;
            }
            container cdr-profiles {
              uses apply-group;
              uses apply-macro;
              list cdr-profile {
                key "name";
                uses juniper-cdr-profiles;
              }
            }
            container trigger-profiles {
              uses apply-group;
              uses apply-macro;
              list trigger-profile {
                key "name";
                ordered-by user;
                uses juniper-trigger-profiles;
              }
            }
            container transport-profiles {
              uses apply-group;
              uses apply-macro;
              list transport-profile {
                key "name";
                uses juniper-transport-profiles;
              }
            }
            container local-persistent-storage-options {
              uses juniper-charged-configuraton;
            }
            container charging-profiles {
              uses apply-group;
              uses apply-macro;
              list charging-profile {
                key "name";
                uses juniper-charging-profiles;
              }
            }
            container gtpp {
              uses apply-group;
              uses apply-macro;
              container source-interface {
                presence "";
                leaf interface-name {
                  type interface-name;
                }
                leaf ipv4-address {
                  type ipv4addr;
                }
              }
              leaf destination-port {
                type uint32;
              }
              leaf n3-requests {
                type uint16;
              }
              leaf transport-protocol {
                type string;
              }
              leaf version {
                type string;
              }
              leaf echo-interval {
                units "seconds";
                type uint32;
              }
              leaf no-path-management {
                type empty;
              }
              leaf t3-response {
                units "seconds";
                type uint16;
              }
              leaf header-type {
                type string;
              }
              leaf pending-queue-size {
                type uint32;
              }
              leaf down-detect-time {
                units "seconds";
                type uint32;
              }
              leaf reconnect-time {
                units "seconds";
                type uint32;
              }
              list peer {
                key "name";
                uses gtpp-peer;
              }
            }
            container global-profile {
              uses apply-group;
              uses apply-macro;
              leaf default-profile {
                type string;
              }
              leaf home-profile {
                type string;
              }
              leaf roamer-profile {
                type string;
              }
              leaf visitor-profile {
                type string;
              }
              leaf-list profile-selection-order {
                ordered-by user;
                type string;
              }
            }
          }
          container ip-reassembly-profile {
            uses apply-group;
            uses apply-macro;
            leaf profile-name {
              type string;
            }
          }
          container idle-mode-buffering {
            uses sgw-idle-mode-buffering;
          }
          container software-datapath {
            presence "enable software-datapath";
            uses apply-group;
            uses apply-macro;
            container traceoptions {
              uses software-datapath-traceoptions;
            }
          }
          container inline-services {
            uses apply-group;
            uses apply-macro;
            container ip-reassembly {
              presence "enable ip-reassembly";
              uses apply-group;
              uses apply-macro;
              container service-set {
                uses apply-group;
                uses apply-macro;
                leaf service-set-name {
                  type string;
                }
              }
            }
          }
        }
      }
      container mobile-options {
        uses unified-edge-mobile-options;
      }
      container pcef {
        uses unified-edge-pcef;
      }
      container resource-management {
        uses apply-group;
        uses apply-macro;
        container server {
          uses apply-group;
          uses apply-macro;
          container traceoptions {
            uses rmpsd-traceoptions-type;
          }
        }
        container client {
          uses apply-group;
          uses apply-macro;
          container traceoptions {
            uses rmps-clnt-traceoptions-type;
          }
        }
      }
    }
    container jsrc {
      uses jsrc-partition-definition;
    }
    container jsrc-partition {
      leaf jsrc-partition-name {
        type string;
      }
    }
    container ethernet-switching-options {
      uses juniper-ethernet-options;
    }
    container virtual-chassis {
      uses apply-group;
      uses apply-macro;
      container auto-sw-update {
        presence "enable auto-sw-update";
        uses apply-group;
        uses apply-macro;
        leaf package-name {
          type string;
        }
        container ex-4200 {
          presence "enable ex-4200";
          uses apply-group;
          uses apply-macro;
          leaf package-name {
            type string;
          }
        }
        container ex-4500 {
          presence "enable ex-4500";
          uses apply-group;
          uses apply-macro;
          leaf package-name {
            type string;
          }
        }
        container ex-4300 {
          presence "enable ex-4300";
          uses apply-group;
          uses apply-macro;
          leaf package-name {
            type string;
          }
        }
        container ex-4600 {
          presence "enable ex-4600";
          uses apply-group;
          uses apply-macro;
          leaf package-name {
            type string;
          }
        }
        container qfx-3 {
          presence "enable qfx-3";
          uses apply-group;
          uses apply-macro;
          leaf package-name {
            type string;
          }
        }
        container qfx-5 {
          presence "enable qfx-5";
          uses apply-group;
          uses apply-macro;
          leaf package-name {
            type string;
          }
        }
      }
      choice choice-preprovisioned {
        leaf preprovisioned {
          type empty;
        }
        leaf auto-provisioned {
          type empty;
        }
      }
      leaf id {
        type isosysid;
      }
      container graceful-restart {
        uses apply-group;
        uses apply-macro;
        leaf disable {
          type empty;
        }
      }
      leaf no-split-detection {
        type empty;
      }
      container traceoptions {
        uses juniper-virtual-chassis-traceoptions;
      }
      leaf heartbeat-timeout {
        units "seconds";
        type uint32;
      }
      leaf heartbeat-address {
        type ipaddr;
      }
      leaf heartbeat-tos {
        type uint32;
      }
      leaf locality-bias {
        type empty;
      }
      list member {
        key "name";
        ordered-by user;
        leaf name {
          type key-attribute-long-type;
        }
        uses apply-group;
        uses apply-macro;
        leaf mastership-priority {
          type int32;
        }
        leaf role {
          type string;
        }
        leaf serial-number {
          type string;
        }
        leaf no-management-vlan {
          type empty;
        }
        leaf location {
          type string;
        }
      }
      container mac-persistence-timer {
        uses apply-group;
        uses apply-macro;
        leaf timer {
          units "minutes";
          type uint32;
        }
        leaf disable {
          type empty;
        }
      }
      container fast-failover {
        uses apply-group;
        uses apply-macro;
        leaf ge {
          type empty;
        }
        leaf xe {
          type empty;
        }
        leaf et {
          type empty;
        }
        container vcp {
          uses apply-group;
          uses apply-macro;
          leaf disable {
            type empty;
          }
        }
      }
      container vc-port {
        presence "enable vc-port";
        uses apply-group;
        uses apply-macro;
        leaf lag-hash {
          type string;
        }
      }
      leaf vcp-no-hold-time {
        type empty;
      }
    }
    container vlans {
      uses apply-group;
      uses apply-macro;
      container traceoptions {
        uses apply-group;
        uses apply-macro;
        list flag {
          key "name";
          leaf name {
            type string;
          }
          leaf disable {
            type empty;
          }
        }
      }
      list vlan {
        key "name";
        uses vlan-type;
      }
    }
    container dialer {
      presence "enable dialer";
      uses apply-group;
      uses apply-macro;
    }
    container schedulers {
      uses apply-group;
      uses apply-macro;
      list scheduler {
        key "name";
        ordered-by user;
        uses scheduler-object-type;
      }
    }
    container smtp {
      uses apply-group;
      uses apply-macro;
      container primary-server {
        presence "";
        uses apply-group;
        uses apply-macro;
        leaf address {
          type ipv4addr;
        }
        choice choice-5 {
          list login {
            key "name";
            ordered-by user;
            uses login-object;
          }
        }
      }
      container secondary-server {
        presence "";
        uses apply-group;
        uses apply-macro;
        leaf address {
          type ipv4addr;
        }
        choice choice-5 {
          list login {
            key "name";
            ordered-by user;
            uses login-object;
          }
        }
      }
      container traceoptions {
        uses apply-group;
        uses apply-macro;
        list flag {
          key "name";
          ordered-by user;
          leaf name {
            type string;
          }
        }
      }
    }
    container poe {
      uses apply-group;
      uses apply-macro;
      leaf management {
        type string;
      }
      leaf guard-band {
        type uint32;
      }
      container notification-control {
        uses apply-group;
        uses apply-macro;
        list fpc {
          key "name";
          ordered-by user;
          leaf name {
            type string;
          }
          uses apply-group;
          uses apply-macro;
          leaf disable {
            type empty;
          }
        }
      }
      list interface {
        key "name";
        ordered-by user;
        leaf name {
          type string;
        }
        uses apply-group;
        uses apply-macro;
        leaf disable {
          type empty;
        }
        leaf priority {
          type string;
        }
        leaf maximum-power {
          type unsigned-float;
        }
        container telemetries {
          presence "enable telemetries";
          uses apply-group;
          uses apply-macro;
          leaf disable {
            type empty;
          }
          leaf interval {
            type uint32;
          }
          leaf duration {
            type uint32;
          }
        }
      }
      list fpc {
        key "name";
        ordered-by user;
        leaf name {
          type uint32;
        }
        uses apply-group;
        uses apply-macro;
        leaf maximum-power {
          type uint32;
        }
        leaf priority {
          type string;
        }
      }
    }
    container wlan {
      presence "enable wlan";
      uses apply-group;
      uses apply-macro;
      container admin-authentication {
        uses apply-group;
        uses apply-macro;
        leaf encrypted-password {
          type unreadable;
        }
      }
      list access-point {
        key "name";
        ordered-by user;
        leaf name {
          type string;
        }
        uses apply-group;
        uses apply-macro;
        leaf description {
          type string;
        }
        leaf mac-address {
          type mac-unicaset;
        }
        leaf location {
          type string;
        }
        choice choice-9 {
          container external {
            uses apply-group;
            uses apply-macro;
            container system {
              uses apply-group;
              uses apply-macro;
              container ports {
                uses apply-group;
                uses apply-macro;
                container ethernet {
                  presence "";
                  uses apply-group;
                  uses apply-macro;
                  leaf management-vlan {
                    type int32;
                  }
                  leaf untagged-vlan {
                    type int32;
                  }
                  choice choice-7 {
                    container static {
                      presence "";
                      uses apply-group;
                      uses apply-macro;
                      leaf address {
                        type ipv4prefix;
                      }
                      leaf default-gateway {
                        type ipaddr;
                      }
                    }
                  }
                  leaf-list name-server {
                    type ipaddr;
                    ordered-by user;
                  }
                }
              }
              container console {
                uses apply-group;
                uses apply-macro;
                leaf baud-rate {
                  type int32;
                }
              }
              container services {
                uses apply-group;
                uses apply-macro;
                leaf ssh {
                  type empty;
                }
              }
            }
            container dot1x-supplicant {
              uses apply-group;
              uses apply-macro;
              leaf username {
                type string;
              }
              leaf password {
                type string;
              }
            }
          }
        }
        container access-point-options {
          uses ap-options-type;
        }
        list radio {
          key "name";
          ordered-by user;
          leaf name {
            type string;
          }
          uses apply-group;
          uses apply-macro;
          container radio-options {
            uses apply-group;
            uses apply-macro;
            leaf radio-off {
              type empty;
            }
            leaf disable-dot11d {
              type empty;
            }
            leaf mode {
              type string;
            }
            container channel {
              uses apply-group;
              uses apply-macro;
              leaf number {
                type string;
              }
              leaf bandwidth {
                type int32;
              }
              leaf primary {
                type string;
              }
            }
            leaf space-time-block-coding {
              type empty;
            }
            leaf protection {
              type string;
            }
            leaf beacon-interval {
              type int32;
            }
            leaf dtim-period {
              type int32;
            }
            leaf rts-threshold {
              type int32;
            }
            leaf no-short-guard-interval {
              type empty;
            }
            leaf fragmentation-threshold {
              type int32;
            }
            leaf maximum-stations {
              type int32;
            }
            leaf transmit-power {
              type int32;
            }
            leaf fixed-multicast-rate {
              type string;
            }
            container transmit-rate-sets {
              uses transmit-rate-sets;
            }
            container broadcast-multicast-rate-limit {
              uses broadcast-multicast-rate-limit;
            }
          }
          leaf station-isolation {
            type empty;
          }
          list virtual-access-point {
            key "name";
            ordered-by user;
            uses vap-type;
          }
          container quality-of-service {
            uses qos-parameter-type;
          }
        }
      }
    }
  }

  grouping aaa-profile {
    leaf name {
      type key-attribute-string-type;
    }
    uses apply-group;
    uses apply-macro;
    container radius {
      uses aaa-profile-radius;
    }
  }

  grouping aaa-profile-radius {
    uses apply-group;
    uses apply-macro;
    container authentication {
      uses apply-group;
      uses apply-macro;
      leaf network-element {
        type string;
      }
    }
    container accounting {
      uses apply-group;
      uses apply-macro;
      leaf network-element {
        type string;
      }
      leaf network-element-group {
        type string;
      }
      leaf send-accounting-on {
        type empty;
      }
      container trigger {
        uses apply-group;
        uses apply-macro;
        leaf no-rat-change {
          type empty;
        }
        leaf no-sgw-change {
          type empty;
        }
        leaf no-qos-change {
          type empty;
        }
        leaf no-plmn-change {
          type empty;
        }
        leaf no-user-location-information-change {
          type empty;
        }
        leaf no-ms-timezone-change {
          type empty;
        }
        leaf no-deferred-ipv4-address-update {
          type empty;
        }
        leaf interim-interval {
          units "minutes";
          type uint32;
        }
      }
    }
    container options {
      uses apply-group;
      uses apply-macro;
      leaf nas-identifier-prefix {
        type string;
      }
      leaf nas-ip-address {
        type ipv4addr;
      }
      leaf nas-port-type {
        type string;
      }
    }
    container attributes {
      uses apply-group;
      uses apply-macro;
      container ignore {
        uses apply-group;
        uses apply-macro;
        leaf output-filter {
          type empty;
        }
        leaf input-filter {
          type empty;
        }
        leaf framed-ip-netmask {
          type empty;
        }
      }
      container exclude {
        uses apply-group;
        uses apply-macro;
        leaf-list accounting-authentic {
          ordered-by user;
          type string;
        }
        leaf-list accounting-delay-time {
          ordered-by user;
          type string;
        }
        leaf-list accounting-terminate-cause {
          ordered-by user;
          type string;
        }
        leaf-list called-station-id {
          ordered-by user;
          type string;
        }
        leaf-list calling-station-id {
          ordered-by user;
          type string;
        }
        leaf-list event-time-stamp {
          ordered-by user;
          type string;
        }
        leaf-list input-gigapackets {
          ordered-by user;
          type string;
        }
        leaf-list input-gigawords {
          ordered-by user;
          type string;
        }
        leaf-list nas-identifier {
          ordered-by user;
          type string;
        }
        leaf-list nas-ip-address {
          ordered-by user;
          type string;
        }
        leaf-list nas-port-type {
          ordered-by user;
          type string;
        }
        leaf-list input-packets {
          ordered-by user;
          type string;
        }
        leaf-list output-packets {
          ordered-by user;
          type string;
        }
        leaf-list output-gigapackets {
          ordered-by user;
          type string;
        }
        leaf-list output-gigawords {
          ordered-by user;
          type string;
        }
        leaf-list sgsn-mcc-mnc {
          ordered-by user;
          type string;
        }
        leaf-list imeisv {
          ordered-by user;
          type string;
        }
        leaf-list imsi {
          ordered-by user;
          type string;
        }
        leaf-list imsi-mcc-mnc {
          ordered-by user;
          type string;
        }
        leaf-list user-location-info {
          ordered-by user;
          type string;
        }
        leaf-list gprs-negotiated-qos {
          ordered-by user;
          type string;
        }
        leaf-list ggsn-address {
          ordered-by user;
          type string;
        }
        leaf-list nsapi {
          ordered-by user;
          type string;
        }
        leaf-list selection-mode {
          ordered-by user;
          type string;
        }
        leaf-list charging-id {
          ordered-by user;
          type string;
        }
        leaf-list all-3gpp {
          ordered-by user;
          type string;
        }
      }
    }
  }

  grouping aaa-traceoptions {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
    }
    leaf level {
      type string;
    }
    list flag {
      key "name";
      ordered-by user;
      leaf name {
        type string;
      }
    }
    list protocol {
      key "name";
      ordered-by user;
      leaf name {
        type string;
      }
    }
  }

  grouping aacl-rule-object {
    leaf name {
      type key-attribute-string-type;
    }
    uses apply-group;
    uses apply-macro;
    leaf match-direction {
      type string;
    }
    list term {
      key "name";
      ordered-by user;
      leaf name {
        type key-attribute-string-type;
      }
      uses apply-group;
      uses apply-macro;
      container from {
        presence "enable from";
        uses aacl-match-object;
      }
      container then {
        uses apply-group;
        uses apply-macro;
        leaf forwarding-class {
          type string;
        }
        leaf count {
          type string;
        }
        leaf police {
          type string;
        }
        choice choice-9 {
          leaf accept {
            type empty;
          }
          leaf discard {
            type empty;
          }
        }
      }
    }
  }

  grouping aacl-match-object {
    uses apply-group;
    uses apply-macro;
    list source-address {
      key "name";
      ordered-by user;
      uses sfw-addr-object;
    }
    list destination-address {
      key "name";
      ordered-by user;
      uses sfw-addr-object;
    }
    list source-address-range {
      key "low high";
      ordered-by user;
      leaf low {
        type ipaddr;
      }
      leaf high {
        type ipaddr;
      }
      leaf except {
        type empty;
      }
    }
    list source-prefix-list {
      key "name";
      ordered-by user;
      leaf name {
        type string;
      }
      leaf except {
        type empty;
      }
    }
    list destination-address-range {
      key "low high";
      ordered-by user;
      leaf low {
        type ipaddr;
      }
      leaf high {
        type ipaddr;
      }
      leaf except {
        type empty;
      }
    }
    list destination-prefix-list {
      key "name";
      ordered-by user;
      leaf name {
        type string;
      }
      leaf except {
        type empty;
      }
    }
    choice choice-15 {
      leaf application-group-any {
        type empty;
      }
      leaf-list applications {
        type string;
        ordered-by user;
      }
      leaf-list application-groups {
        type string;
        ordered-by user;
      }
    }
  }

  grouping action-object-type {
    uses apply-group;
    uses apply-macro;
    container preferred-route {
      uses apply-group;
      uses apply-macro;
      leaf withdraw {
        type empty;
      }
      list routing-instances {
        key "name";
        ordered-by user;
        leaf name {
          mandatory true;
          type string;
        }
        uses apply-group;
        uses apply-macro;
        list route {
          key "name";
          ordered-by user;
          leaf name {
            mandatory true;
            type ipprefix;
          }
          uses apply-group;
          uses apply-macro;
          choice choice-next-hop {
            leaf-list next-hop {
              type ipaddr-or-interface;
              ordered-by user;
            }
            leaf discard {
              type empty;
            }
          }
          leaf direct-next-hop {
            type empty;
          }
          leaf preferred-metric {
            type uint32;
          }
        }
      }
      list route {
        key "name";
        ordered-by user;
        leaf name {
          mandatory true;
          type ipprefix;
        }
        uses apply-group;
        uses apply-macro;
        choice choice-next-hop {
          leaf-list next-hop {
            type ipaddr-or-interface;
            ordered-by user;
          }
          leaf discard {
            type empty;
          }
        }
        leaf direct-next-hop {
          type empty;
        }
        leaf preferred-metric {
          type uint32;
        }
      }
    }
    list interface {
      key "name";
      ordered-by user;
      leaf name {
        mandatory true;
        type interface-wildcard;
      }
      uses apply-group;
      uses apply-macro;
      choice choice-enable {
        leaf enable {
          type empty;
        }
        leaf disable {
          type empty;
        }
      }
    }
  }

  grouping advisory-options-type {
    uses apply-group;
    uses apply-macro;
    leaf upstream-rate {
      type string;
      units "bits per second";
    }
    leaf downstream-rate {
      type string;
      units "bits per second";
    }
  }

  grouping anti-spam-feature {
    uses apply-group;
    uses apply-macro;
    leaf address-whitelist {
      type string;
    }
    leaf address-blacklist {
      type string;
    }
    container traceoptions {
      uses anti-spam-traceoptions;
    }
    container sbl {
      presence "enable sbl";
      uses sbl-type;
    }
  }

  grouping anti-spam-traceoptions {
    uses apply-group;
    uses apply-macro;
    list flag {
      key "name";
      ordered-by user;
      leaf name {
        type string;
      }
    }
  }

  grouping anti-virus-feature {
    uses apply-group;
    uses apply-macro;
    container mime-whitelist {
      presence "enable mime-whitelist";
      uses apply-group;
      uses apply-macro;
      leaf list {
        type string;
      }
      leaf exception {
        type string;
      }
    }
    leaf url-whitelist {
      type string;
    }
    leaf type {
      type string;
    }
    container traceoptions {
      uses anti-virus-traceoptions;
    }
    container kaspersky-lab-engine {
      uses apply-group;
      uses apply-macro;
      container pattern-update {
        presence "enable pattern-update";
        uses anti-virus-pattern-update;
      }
      list profile {
        key "name";
        ordered-by user;
        leaf name {
          type key-attribute-string-type;
        }
        uses apply-group;
        uses apply-macro;
        container fallback-options {
          presence "enable fallback-options";
          uses anti-virus-fallback-settings;
        }
        container scan-options {
          presence "enable scan-options";
          uses anti-virus-scan-options;
        }
        container trickling {
          presence "";
          uses anti-virus-trickling;
        }
        container notification-options {
          presence "enable notification-options";
          uses anti-virus-notification-options;
        }
      }
    }
    container juniper-express-engine {
      uses apply-group;
      uses apply-macro;
      container pattern-update {
        presence "enable pattern-update";
        uses anti-virus-pattern-update;
      }
      list profile {
        key "name";
        ordered-by user;
        leaf name {
          type key-attribute-string-type;
        }
        uses apply-group;
        uses apply-macro;
        container fallback-options {
          presence "enable fallback-options";
          uses juniper-express-fallback-settings;
        }
        container scan-options {
          presence "enable scan-options";
          uses juniper-express-scan-options;
        }
        container trickling {
          presence "";
          uses anti-virus-trickling;
        }
        container notification-options {
          presence "enable notification-options";
          uses anti-virus-notification-options;
        }
      }
    }
    container sophos-engine {
      uses apply-group;
      uses apply-macro;
      leaf sxl-timeout {
        units "seconds";
        type uint32;
      }
      leaf sxl-retry {
        type uint32;
      }
      container pattern-update {
        presence "enable pattern-update";
        uses anti-virus-pattern-update;
      }
      list profile {
        key "name";
        ordered-by user;
        leaf name {
          type key-attribute-string-type;
        }
        uses apply-group;
        uses apply-macro;
        container fallback-options {
          presence "enable fallback-options";
          uses sophos-fallback-settings;
        }
        container scan-options {
          presence "enable scan-options";
          uses sophos-scan-options;
        }
        container trickling {
          presence "";
          uses anti-virus-trickling;
        }
        container notification-options {
          presence "enable notification-options";
          uses anti-virus-notification-options;
        }
      }
    }
  }

  grouping anti-virus-fallback-settings {
    uses apply-group;
    uses apply-macro;
    leaf default {
      type string;
    }
    leaf corrupt-file {
      type string;
    }
    leaf password-file {
      type string;
    }
    leaf decompress-layer {
      type string;
    }
    leaf content-size {
      type string;
    }
    leaf engine-not-ready {
      type string;
    }
    leaf timeout {
      type string;
    }
    leaf out-of-resources {
      type string;
    }
    leaf too-many-requests {
      type string;
    }
  }

  grouping anti-virus-notification-options {
    uses apply-group;
    uses apply-macro;
    container virus-detection {
      presence "enable virus-detection";
      uses apply-group;
      uses apply-macro;
      leaf type {
        type string;
      }
      leaf notify-mail-sender {
        type empty;
      }
      leaf no-notify-mail-sender {
        type empty;
      }
      leaf custom-message {
        type string;
      }
      leaf custom-message-subject {
        type string;
      }
    }
    container fallback-block {
      presence "enable fallback-block";
      uses apply-group;
      uses apply-macro;
      leaf type {
        type string;
      }
      leaf notify-mail-sender {
        type empty;
      }
      leaf no-notify-mail-sender {
        type empty;
      }
      leaf custom-message {
        type string;
      }
      leaf custom-message-subject {
        type string;
      }
    }
    container fallback-non-block {
      presence "enable fallback-non-block";
      uses apply-group;
      uses apply-macro;
      leaf notify-mail-recipient {
        type empty;
      }
      leaf no-notify-mail-recipient {
        type empty;
      }
      leaf custom-message {
        type string;
      }
      leaf custom-message-subject {
        type string;
      }
    }
  }

  grouping anti-virus-pattern-update {
    uses apply-group;
    uses apply-macro;
    container email-notify {
      presence "enable email-notify";
      uses apply-group;
      uses apply-macro;
      leaf admin-email {
        type string;
      }
      leaf custom-message {
        type string;
      }
      leaf custom-message-subject {
        type string;
      }
    }
    leaf url {
      type string;
    }
    leaf interval {
      type uint32;
    }
    leaf no-autoupdate {
      type empty;
    }
  }

  grouping anti-virus-scan-options {
    uses apply-group;
    uses apply-macro;
    leaf intelligent-prescreening {
      type empty;
    }
    leaf no-intelligent-prescreening {
      type empty;
    }
    leaf scan-mode {
      type string;
    }
    leaf scan-extension {
      type string;
    }
    leaf content-size-limit {
      type string;
    }
    leaf timeout {
      type uint32;
    }
    leaf decompress-layer-limit {
      type uint32;
    }
  }

  grouping anti-virus-traceoptions {
    uses apply-group;
    uses apply-macro;
    list flag {
      key "name";
      ordered-by user;
      leaf name {
        type string;
      }
    }
  }

  grouping anti-virus-trickling {
    uses apply-group;
    uses apply-macro;
    leaf timeout {
      type uint32;
    }
  }

  grouping aggregate-load-balance {
    uses apply-group;
    uses apply-macro;
    choice choice-per-packet {
      leaf per-packet {
        type empty;
      }
      leaf no-adaptive {
        type empty;
      }
      container adaptive {
        presence "";
        uses apply-group;
        uses apply-macro;
        leaf tolerance {
          units "percent";
          type uint32;
        }
        leaf pps {
          type empty;
        }
        leaf scan-interval {
          type uint32;
        }
      }
    }
  }

  grouping any-filter {
    leaf name {
      type string;
    }
    uses apply-group;
    uses apply-macro;
    leaf interface-specific {
      type empty;
    }
    leaf interface-shared {
      type empty;
    }
    list term {
      key "name";
      ordered-by user;
      leaf name {
        type string;
      }
      uses apply-group;
      uses apply-macro;
      container from {
        uses apply-group;
        uses apply-macro;
        list interface {
          key "name";
          ordered-by user;
          uses match-interface-object-oam;
        }
        list interface-set {
          key "name";
          ordered-by user;
          uses match-interface-set-object;
        }
        choice choice-7 {
          leaf-list packet-length {
            type string;
            ordered-by user;
          }
          leaf-list packet-length-except {
            type string;
            ordered-by user;
          }
        }
        choice choice-8 {
          leaf-list forwarding-class {
            type string;
            ordered-by user;
          }
          leaf-list forwarding-class-except {
            type string;
            ordered-by user;
          }
        }
        choice choice-9 {
          leaf-list loss-priority {
            ordered-by user;
            type string;
          }
          leaf-list loss-priority-except {
            ordered-by user;
            type string;
          }
        }
      }
      container then {
        uses apply-group;
        uses apply-macro;
        choice choice-3 {
          leaf policer {
            type string;
          }
          container three-color-policer {
            uses apply-group;
            uses apply-macro;
            choice choice-3 {
              leaf single-rate {
                type string;
              }
              leaf two-rate {
                type string;
              }
            }
          }
          leaf hierarchical-policer {
            type string;
          }
        }
        choice choice-clear-policy-map {
          leaf clear-policy-map {
            type empty;
          }
          leaf policy-map {
            type string;
          }
        }
        leaf count {
          type string;
        }
        leaf service-accounting {
          type empty;
        }
        leaf service-accounting-deferred {
          type empty;
        }
        leaf service-filter-hit {
          type empty;
        }
        leaf force-premium {
          type empty;
        }
        leaf loss-priority {
          type string;
        }
        leaf port-mirror-instance {
          type string;
        }
        leaf port-mirror {
          type empty;
        }
        leaf inline-monitoring-instance {
          type string;
        }
        leaf forwarding-class {
          type string;
        }
        choice choice-10 {
          leaf accept {
            type empty;
          }
          leaf discard {
            type empty;
          }
          leaf next {
            type string;
          }
        }
      }
    }
  }

  grouping appfw-rule-type {
    leaf name {
      type key-attribute-string-type;
    }
    uses apply-group;
    uses apply-macro;
    container match {
      presence "enable match";
      uses apply-group;
      uses apply-macro;
      leaf-list dynamic-application {
        ordered-by user;
        type string;
      }
      leaf-list dynamic-application-group {
        ordered-by user;
        type string;
      }
      leaf ssl-encryption {
        type string;
      }
    }
    container then {
      presence "enable then";
      uses apply-group;
      uses apply-macro;
      choice choice-permit {
        leaf permit {
          type empty;
        }
        container deny {
          presence "enable deny";
          uses apply-group;
          uses apply-macro;
          leaf block-message {
            type empty;
          }
        }
        container reject {
          presence "enable reject";
          uses apply-group;
          uses apply-macro;
          leaf block-message {
            type empty;
          }
        }
      }
    }
  }

  grouping ap-options-type {
    uses apply-group;
    uses apply-macro;
    container country {
      presence "enable country";
      uses country;
    }
    container station-mac-filter {
      uses station-mac-filter;
    }
  }

  grouping application-ddos-type {
    leaf name {
      type string;
    }
    uses apply-group;
    uses apply-macro;
    leaf service {
      type string;
    }
    leaf connection-rate-threshold {
      type uint32;
    }
    list context {
      key "name";
      ordered-by user;
      leaf name {
        type string;
      }
      uses apply-group;
      uses apply-macro;
      leaf hit-rate-threshold {
        type uint32;
      }
      leaf value-hit-rate-threshold {
        type uint32;
      }
      leaf max-context-values {
        type uint32;
      }
      leaf time-binding-count {
        type uint32;
      }
      leaf time-binding-period {
        type uint32;
      }
      leaf-list exclude-context-values {
        type string;
        ordered-by user;
      }
    }
  }

  grouping application-object {
    leaf name {
      type key-attribute-string-type;
    }
    uses apply-group;
    uses apply-macro;
    leaf application-protocol {
      type string;
    }
    leaf protocol {
      type string;
    }
    leaf source-port {
      type string;
    }
    leaf destination-port {
      type string;
    }
    leaf ether-type {
      type string;
    }
    leaf snmp-command {
      type string;
    }
    leaf icmp-type {
      type string;
    }
    leaf icmp6-type {
      type string;
    }
    leaf icmp-code {
      type string;
    }
    leaf icmp6-code {
      type string;
    }
    leaf ttl-threshold {
      type uint8;
    }
    leaf rpc-program-number {
      type string;
    }
    leaf uuid {
      type string;
    }
    leaf inactivity-timeout {
      type string;
    }
    leaf gate-timeout {
      units "seconds";
      type uint32;
    }
    leaf child-inactivity-timeout {
      units "seconds";
      type uint32;
    }
    leaf learn-sip-register {
      type empty;
    }
    leaf sip-call-hold-timeout {
      type uint32;
    }
    choice choice-33 {
      leaf do-not-translate-AAAA-query-to-A-query {
        type empty;
      }
      leaf do-not-translate-A-query-to-AAAA-query {
        type empty;
      }
    }
    list term {
      key "name";
      ordered-by user;
      uses term-object;
    }
    leaf description {
      type string;
    }
  }

  grouping application-set-object {
    leaf name {
      type key-attribute-string-type;
    }
    uses apply-group;
    uses apply-macro;
    leaf description {
      type string;
    }
    list application {
      key "name";
      ordered-by user;
      leaf name {
        type key-attribute-string-type;
      }
      uses apply-group;
      uses apply-macro;
    }
    list application-set {
      key "name";
      ordered-by user;
      leaf name {
        type key-attribute-string-type;
      }
      uses apply-group;
      uses apply-macro;
    }
  }

  grouping aps-type {
    uses apply-group;
    uses apply-macro;
    choice choice-3 {
      leaf working-circuit {
        type string;
      }
      leaf protect-circuit {
        type string;
      }
    }
    leaf annex-b {
      type empty;
    }
    leaf wait-to-restore-time {
      type uint32;
    }
    leaf preserve-interface {
      type empty;
    }
    leaf neighbor {
      type ipv4addr;
    }
    leaf paired-group {
      type string;
    }
    container authentication-key {
      presence "";
      leaf auth_key {
        type unreadable;
      }
    }
    leaf switching-mode {
      type string;
    }
    leaf advertise-interval {
      type uint32;
    }
    leaf hold-time {
      type uint32;
    }
    leaf revert-time {
      type uint32;
    }
    leaf break-before-make {
      type empty;
    }
    leaf no-break-before-make {
      type empty;
    }
    choice choice-28 {
      leaf request {
        type string;
      }
      leaf force {
        type string;
      }
      leaf lockout {
        type empty;
      }
    }
  }

  grouping auto-configure-vlan-type {
    uses apply-group;
    uses apply-macro;
    container stacked-vlan-ranges {
      presence "enable stacked-vlan-ranges";
      uses apply-group;
      uses apply-macro;
      list dynamic-profile {
        key "name";
        ordered-by user;
        leaf name {
          type string;
        }
        uses apply-group;
        uses apply-macro;
        leaf-list accept {
          ordered-by user;
          type string;
        }
        list ranges {
          key "name";
          ordered-by user;
          leaf name {
            type string;
          }
          uses apply-group;
          uses apply-macro;
        }
        container access-profile {
          leaf ap-name {
            type string;
          }
        }
      }
      container override {
        presence "enable override";
        uses apply-group;
        uses apply-macro;
        list outer-tag {
          key "name";
          ordered-by user;
          leaf name {
            mandatory true;
            type key-attribute-ulong-type;
          }
          uses apply-group;
          uses apply-macro;
          leaf inner-tag {
            mandatory true;
            type uint32;
          }
          leaf dynamic-profile {
            type string;
            mandatory true;
          }
        }
      }
      container authentication {
        uses auto-configure-authentication-type;
      }
      container access-profile {
        leaf access-profile-name {
          type string;
        }
      }
    }
    container vlan-ranges {
      presence "enable vlan-ranges";
      uses apply-group;
      uses apply-macro;
      list dynamic-profile {
        key "name";
        ordered-by user;
        leaf name {
          type string;
        }
        uses apply-group;
        uses apply-macro;
        choice choice-accept {
          leaf-list accept {
            ordered-by user;
            type string;
          }
          leaf-list accept-out-of-band {
            ordered-by user;
            type string;
          }
        }
        list ranges {
          key "name";
          ordered-by user;
          leaf name {
            type string;
          }
          uses apply-group;
          uses apply-macro;
        }
        container access-profile {
          leaf ap-name {
            type string;
          }
        }
      }
      container override {
        presence "enable override";
        uses apply-group;
        uses apply-macro;
        list tag {
          key "name";
          ordered-by user;
          leaf name {
            mandatory true;
            type key-attribute-ulong-type;
          }
          uses apply-group;
          uses apply-macro;
          leaf dynamic-profile {
            type string;
            mandatory true;
          }
        }
      }
      container authentication {
        uses auto-configure-authentication-type;
      }
      container access-profile {
        leaf access-profile-name {
          type string;
        }
      }
    }
    container agent-circuit-identifier {
      presence "";
      uses apply-group;
      uses apply-macro;
      leaf dynamic-profile {
        mandatory true;
        type string;
      }
    }
    container line-identity {
      presence "";
      uses apply-group;
      uses apply-macro;
      container includes {
        presence "enable includes";
        uses apply-group;
        uses apply-macro;
        leaf circuit-id {
          type empty;
        }
        leaf remote-id {
          type empty;
        }
        container accept-no-ids {
          presence "enable accept-no-ids";
          uses apply-group;
          uses apply-macro;
        }
      }
      leaf dynamic-profile {
        mandatory true;
        type string;
      }
    }
    leaf remove-when-no-subscribers {
      type empty;
    }
  }

  grouping auto-configure-authentication-type {
    uses apply-group;
    uses apply-macro;
    leaf password {
      type string;
    }
    container username-include {
      uses apply-group;
      uses apply-macro;
      leaf delimiter {
        type string;
      }
      leaf domain-name {
        type string;
      }
      leaf user-prefix {
        type string;
      }
      leaf mac-address {
        type empty;
      }
      container option-82 {
        presence "enable option-82";
        leaf circuit-id {
          type empty;
        }
        leaf remote-id {
          type empty;
        }
      }
      leaf circuit-type {
        type empty;
      }
      leaf radius-realm {
        type string;
      }
      leaf interface-name {
        type empty;
      }
      leaf vlan-tags {
        type empty;
      }
    }
  }

  grouping bgp-logical-system {
    leaf name {
      type string;
    }
    uses apply-group;
    uses apply-macro;
    list routing-instances {
      key "name";
      uses bgp-routing-instances;
    }
  }

  grouping bgp-routing-instances {
    leaf name {
      type string;
    }
    uses apply-group;
    uses apply-macro;
  }

  grouping bridge-filter {
    leaf name {
      type string;
    }
    uses apply-group;
    uses apply-macro;
    leaf-list accounting-profile {
      type string;
      ordered-by user;
    }
    leaf interface-specific {
      type empty;
    }
    leaf physical-interface-filter {
      type empty;
    }
    leaf instance-shared {
      type empty;
    }
    list term {
      key "name";
      ordered-by user;
      leaf name {
        type string;
      }
      uses apply-group;
      uses apply-macro;
      leaf filter {
        type string;
      }
      container from {
        uses apply-group;
        uses apply-macro;
        container apply-flags {
          container omit {
            presence "true";
          }
        }
        choice choice-3 {
          leaf-list interface-group {
            type string;
            ordered-by user;
          }
          leaf-list interface-group-except {
            type string;
            ordered-by user;
          }
        }
        choice choice-4 {
          leaf-list ether-type {
            ordered-by user;
            type string;
          }
          leaf-list ether-type-except {
            ordered-by user;
            type string;
          }
        }
        choice choice-5 {
          leaf-list vlan-ether-type {
            ordered-by user;
            type string;
          }
          leaf-list vlan-ether-type-except {
            ordered-by user;
            type string;
          }
        }
        list destination-mac-address {
          key "name";
          ordered-by user;
          uses firewall-mac-addr-object;
        }
        list source-mac-address {
          key "name";
          ordered-by user;
          uses firewall-mac-addr-object;
        }
        choice choice-10 {
          leaf-list forwarding-class {
            type string;
            ordered-by user;
          }
          leaf-list forwarding-class-except {
            type string;
            ordered-by user;
          }
        }
        choice choice-11 {
          leaf-list loss-priority {
            ordered-by user;
            type string;
          }
          leaf-list loss-priority-except {
            ordered-by user;
            type string;
          }
        }
        choice choice-12 {
          leaf-list learn-vlan-id {
            type string;
            ordered-by user;
          }
          leaf-list learn-vlan-id-except {
            type string;
            ordered-by user;
          }
        }
        choice choice-13 {
          leaf-list learn-vlan-1p-priority {
            type uint32;
            ordered-by user;
          }
          leaf-list learn-vlan-1p-priority-except {
            type uint32;
            ordered-by user;
          }
        }
        choice choice-14 {
          leaf-list user-vlan-id {
            type string;
            ordered-by user;
          }
          leaf-list user-vlan-id-except {
            type string;
            ordered-by user;
          }
        }
        choice choice-15 {
          leaf-list user-vlan-1p-priority {
            type uint32;
            ordered-by user;
          }
          leaf-list user-vlan-1p-priority-except {
            type uint32;
            ordered-by user;
          }
        }
        choice choice-16 {
          leaf-list learn-vlan-dei {
            type uint32;
            ordered-by user;
          }
          leaf-list learn-vlan-dei-except {
            type uint32;
            ordered-by user;
          }
        }
        choice choice-17 {
          leaf-list traffic-type {
            ordered-by user;
            type string;
          }
          leaf-list traffic-type-except {
            ordered-by user;
            type string;
          }
        }
        list ip-source-address {
          key "name";
          ordered-by user;
          uses firewall-addr-object;
        }
        list ip-destination-address {
          key "name";
          ordered-by user;
          uses firewall-addr-object;
        }
        list ip-address {
          key "name";
          ordered-by user;
          uses firewall-addr-object;
        }
        choice choice-24 {
          leaf-list ip-protocol {
            ordered-by user;
            type string;
          }
          leaf-list ip-protocol-except {
            ordered-by user;
            type string;
          }
        }
        choice choice-25 {
          leaf-list dscp {
            ordered-by user;
            type string;
          }
          leaf-list dscp-except {
            ordered-by user;
            type string;
          }
        }
        choice choice-26 {
          leaf-list ip-precedence {
            ordered-by user;
            type string;
          }
          leaf-list ip-precedence-except {
            ordered-by user;
            type string;
          }
        }
        choice choice-27 {
          leaf-list source-port {
            ordered-by user;
            type string;
          }
          leaf-list source-port-except {
            ordered-by user;
            type string;
          }
        }
        choice choice-28 {
          leaf-list destination-port {
            ordered-by user;
            type string;
          }
          leaf-list destination-port-except {
            ordered-by user;
            type string;
          }
        }
        choice choice-29 {
          leaf-list port {
            ordered-by user;
            type string;
          }
          leaf-list port-except {
            ordered-by user;
            type string;
          }
        }
        leaf tcp-flags {
          type string;
        }
        choice choice-32 {
          leaf-list icmp-type {
            ordered-by user;
            type string;
          }
          leaf-list icmp-type-except {
            ordered-by user;
            type string;
          }
        }
        choice choice-33 {
          leaf-list icmp-code {
            ordered-by user;
            type string;
          }
          leaf-list icmp-code-except {
            ordered-by user;
            type string;
          }
        }
        choice choice-34;
        choice choice-35;
        list interface {
          key "name";
          ordered-by user;
          uses match-interface-object;
        }
        list interface-set {
          key "name";
          ordered-by user;
          uses match-interface-set-object;
        }
        list source-prefix-list {
          key "name";
          ordered-by user;
          uses firewall-prefix-list;
        }
        list destination-prefix-list {
          key "name";
          ordered-by user;
          uses firewall-prefix-list;
        }
        list prefix-list {
          key "name";
          ordered-by user;
          uses firewall-prefix-list;
        }
        choice choice-46 {
          leaf-list isid {
            type string;
            ordered-by user;
          }
          leaf-list isid-except {
            type string;
            ordered-by user;
          }
        }
        choice choice-47 {
          leaf-list isid-priority-code-point {
            type uint32;
            ordered-by user;
          }
          leaf-list isid-priority-code-point-except {
            type uint32;
            ordered-by user;
          }
        }
        choice choice-48 {
          leaf-list isid-dei {
            type uint32;
            ordered-by user;
          }
          leaf-list isid-dei-except {
            type uint32;
            ordered-by user;
          }
        }
      }
      container then {
        uses apply-group;
        uses apply-macro;
        choice choice-3 {
          leaf policer {
            type string;
          }
          container three-color-policer {
            uses apply-group;
            uses apply-macro;
            choice choice-3 {
              leaf single-rate {
                type string;
              }
              leaf two-rate {
                type string;
              }
            }
          }
          leaf hierarchical-policer {
            type string;
          }
        }
        choice choice-clear-policy-map {
          leaf clear-policy-map {
            type empty;
          }
          leaf policy-map {
            type string;
          }
        }
        leaf count {
          type string;
        }
        leaf loss-priority {
          type string;
        }
        leaf forwarding-class {
          type string;
        }
        choice choice-10 {
          leaf accept {
            type empty;
          }
          leaf discard {
            type empty;
          }
          leaf next {
            type string;
          }
        }
        leaf port-mirror-instance {
          type string;
        }
        leaf port-mirror {
          type empty;
        }
        leaf inline-monitoring-instance {
          type string;
        }
        leaf next-hop-group {
          type string;
        }
        leaf sample {
          type empty;
        }
        leaf log {
          type empty;
        }
        leaf syslog {
          type empty;
        }
        container forwarding-policy {
          uses apply-group;
          uses apply-macro;
          leaf uplink-select {
            type string;
          }
        }
      }
    }
  }

  grouping broadcast-multicast-rate-limit {
    uses apply-group;
    uses apply-macro;
    leaf rate-limit {
      type int32;
    }
    leaf rate-limit-bursts {
      type int32;
    }
  }

  grouping category-list-type {
    leaf name {
      type key-attribute-string-type;
    }
    uses apply-group;
    uses apply-macro;
    leaf-list value {
      type string;
      ordered-by user;
    }
  }

  grouping ccc-filter {
    leaf name {
      type string;
    }
    uses apply-group;
    uses apply-macro;
    leaf-list accounting-profile {
      type string;
      ordered-by user;
    }
    leaf interface-specific {
      type empty;
    }
    leaf physical-interface-filter {
      type empty;
    }
    list term {
      key "name";
      ordered-by user;
      leaf name {
        type string;
      }
      uses apply-group;
      uses apply-macro;
      leaf filter {
        type string;
      }
      container from {
        uses apply-group;
        uses apply-macro;
        choice choice-3 {
          leaf-list interface-group {
            type string;
            ordered-by user;
          }
          leaf-list interface-group-except {
            type string;
            ordered-by user;
          }
        }
        choice choice-4 {
          leaf-list forwarding-class {
            type string;
            ordered-by user;
          }
          leaf-list forwarding-class-except {
            type string;
            ordered-by user;
          }
        }
        choice choice-5 {
          leaf-list loss-priority {
            ordered-by user;
            type string;
          }
          leaf-list loss-priority-except {
            ordered-by user;
            type string;
          }
        }
        choice choice-6 {
          leaf-list learn-vlan-1p-priority {
            type uint32;
            ordered-by user;
          }
          leaf-list learn-vlan-1p-priority-except {
            type uint32;
            ordered-by user;
          }
        }
        choice choice-7 {
          leaf-list user-vlan-1p-priority {
            type uint32;
            ordered-by user;
          }
          leaf-list user-vlan-1p-priority-except {
            type uint32;
            ordered-by user;
          }
        }
        list destination-mac-address {
          key "name";
          ordered-by user;
          uses firewall-mac-addr-object;
        }
        leaf is-host-packet {
          type empty;
        }
        list source-mac-address {
          key "name";
          ordered-by user;
          uses firewall-mac-addr-object;
        }
        list ip-source-address {
          key "name";
          ordered-by user;
          uses firewall-addr-object;
        }
        list ip-destination-address {
          key "name";
          ordered-by user;
          uses firewall-addr-object;
        }
        choice dscp_choice {
          case case_1 {
            leaf-list dscp {
              ordered-by user;
              type string;
            }
          }
          case case_2 {
            leaf-list dscp-except {
              ordered-by user;
              type string;
            }
          }
        }
        choice ip-precedence_choice {
          case case_1 {
            leaf-list ip-precedence {
              ordered-by user;
              type string;
            }
          }
          case case_2 {
            leaf-list ip-precedence-except {
              ordered-by user;
              type string;
            }
          }
        }
        choice ip-protocol_choice {
          case case_1 {
            leaf-list ip-protocol {
              ordered-by user;
              type string;
            }
          }
          case case_2 {
            leaf-list ip-protocol-except {
              ordered-by user;
              type string;
            }
          }
        }
        choice icmp-type_choice {
          case case_1 {
            leaf-list icmp-type {
              ordered-by user;
              type string;
            }
          }
          case case_2 {
            leaf-list icmp-type-except {
              ordered-by user;
              type string;
            }
          }
        }
        choice icmp-code_choice {
          case case_1 {
            leaf-list icmp-code {
              ordered-by user;
              type string;
            }
          }
          case case_2 {
            leaf-list icmp-code-except {
              ordered-by user;
              type string;
            }
          }
        }
        choice source-port_choice {
          case case_1 {
            leaf-list source-port {
              ordered-by user;
              type string;
            }
          }
          case case_2 {
            leaf-list source-port-except {
              ordered-by user;
              type string;
            }
          }
        }
        choice destination-port_choice {
          case case_1 {
            leaf-list destination-port {
              ordered-by user;
              type string;
            }
          }
          case case_2 {
            leaf-list destination-port-except {
              ordered-by user;
              type string;
            }
          }
        }
        choice policy-map_choice {
          case case_1 {
            leaf-list policy-map {
              ordered-by user;
              type string;
            }
          }
          case case_2 {
            leaf-list policy-map-except {
              ordered-by user;
              type string;
            }
          }
        }
        choice flex-mask_choice {
          case case_1 {
            container flexible-match-mask {
              presence "enable flexible-match-mask";
              uses match-L2-flexible-mask;
            }
          }
        }
        choice flex-range_choice {
          case case_1 {
            container flexible-match-range {
              presence "enable flexible-match-range";
              uses match-L2-flexible-range;
            }
          }
        }
        choice user-vlan-id_choice {
          case case_2 {
            leaf-list user-vlan-id-except {
              ordered-by user;
              type string;
            }
          }
        }
      }
      container then {
        uses apply-group;
        uses apply-macro;
        choice choice-3 {
          leaf policer {
            type string;
          }
          container three-color-policer {
            uses apply-group;
            uses apply-macro;
            choice choice-3 {
              leaf single-rate {
                type string;
              }
              leaf two-rate {
                type string;
              }
            }
          }
          leaf hierarchical-policer {
            type string;
          }
        }
        choice choice-clear-policy-map {
          leaf clear-policy-map {
            type empty;
          }
          leaf policy-map {
            type string;
          }
        }
        leaf count {
          type string;
        }
        leaf loss-priority {
          type string;
        }
        leaf forwarding-class {
          type string;
        }
        leaf port-mirror-instance {
          type string;
        }
        leaf next-hop-group {
          type string;
        }
        leaf port-mirror {
          type empty;
        }
        leaf inline-monitoring-instance {
          type string;
        }
        leaf packet-mode {
          type empty;
        }
        leaf force-premium {
          type empty;
        }
        leaf log {
          type empty;
        }
        leaf syslog {
          type empty;
        }
        choice choice-18 {
          container encapsulate {
            presence "enable encapsulate";
            leaf tunnel-end-point {
              type string;
            }
          }
          leaf accept {
            type empty;
          }
          leaf discard {
            type empty;
          }
          leaf next {
            type string;
          }
        }
      }
    }
  }

  grouping certificate-object {
    leaf name {
      type string;
    }
    uses apply-group;
    uses apply-macro;
    leaf certificate {
      type string;
    }
  }

  grouping charging-traceoptions {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
    }
    leaf level {
      type string;
    }
    list flag {
      key "name";
      ordered-by user;
      leaf name {
        type string;
      }
    }
  }

  grouping chassis-pw-type {
    uses apply-group;
    uses apply-macro;
    leaf device-count {
      type string;
    }
  }

  grouping chassis-type {
    uses apply-group;
    uses apply-macro;
    container undocumented {
      leaf dump-on-panic {
        type empty;
      }
      leaf no-reset-on-timeout {
        type empty;
      }
      leaf no-service-pic-restart-on-failover {
        type empty;
      }
    }
    container copy-tos-to-outer {
      uses apply-group;
      uses apply-macro;
      container service-type {
        uses apply-group;
        uses apply-macro;
        leaf gre {
          type empty;
        }
        leaf mt {
          type empty;
        }
      }
    }
    container nssu {
      presence "enable nssu";
      uses apply-group;
      uses apply-macro;
      list upgrade-group {
        key "name";
        ordered-by user;
        leaf name {
          type key-attribute-string-type;
        }
        uses apply-group;
        uses apply-macro;
        leaf-list fpcs {
          type uint32;
        }
      }
      leaf rcp-count {
        type string;
      }
      leaf lc-reboot-delay {
        type string;
      }
    }
    leaf no-power-budget {
      type empty;
    }
    container psu {
      uses apply-group;
      uses apply-macro;
      container redundancy {
        uses apply-group;
        uses apply-macro;
        leaf n-plus-n {
          type empty;
        }
      }
    }
    leaf fpc-resync {
      type empty;
    }
    leaf craft-lockout {
      type empty;
    }
    container config-button {
      leaf no-rescue {
        type empty;
      }
      leaf no-clear {
        type empty;
      }
    }
    leaf routing-engine-power-off-button-disable {
      type empty;
    }
    leaf source-route {
      type empty;
    }
    leaf no-source-route {
      type empty;
    }
    leaf packet-scheduling {
      type empty;
    }
    leaf no-packet-scheduling {
      type empty;
    }
    leaf route-memory-enhanced {
      type empty;
    }
    leaf vpn-label-memory-enhanced {
      type empty;
    }
    leaf policer-drop-probability-low {
      type empty;
    }
    leaf enhanced-policer {
      type empty;
    }
    leaf effective-shaping-rate {
      type empty;
    }
    container memory-enhanced {
      presence "enable memory-enhanced";
      uses apply-group;
      uses apply-macro;
      leaf route {
        type empty;
      }
      leaf filter {
        type empty;
      }
      leaf vpn-label {
        type empty;
      }
    }
    leaf vrf-mtu-check {
      type empty;
    }
    leaf maximum-ecmp {
      type int32;
    }
    container redundancy {
      uses chassis-redundancy-type;
    }
    container routing-engine {
      uses chassis-routing-engine-type;
    }
    container aggregated-devices {
      uses chassis-agg-dev-type;
    }
    list disk-partition {
      key "name";
      ordered-by user;
      leaf name {
        type string;
      }
      uses apply-advanced;
      list level {
        key "name";
        ordered-by user;
        leaf name {
          type string;
        }
        uses apply-advanced;
        container free-space {
          leaf thres-free {
            type string;
          }
          choice thres-metric {
            case case_1 {
              leaf percent {
                type empty;
              }
            }
            case case_2 {
              leaf mb {
                type empty;
              }
            }
          }
        }
      }
    }
    container container-devices {
      uses chassisd-agg-container-type;
    }
    container pseudowire-service {
      presence "enable pseudowire-service";
      uses chassis-pw-type;
    }
    container provider-instance-devices {
      uses chassisd-provider-instance-type;
    }
    container redundancy-group {
      uses chassisd-redundancy-group-type;
    }
    list fpc {
      key "name";
      uses chassis-fpc-type;
    }
    leaf disable-power-management {
      type empty;
    }
    container fpc-feb-connectivity {
      uses apply-group;
      uses apply-macro;
      list fpc {
        key "name";
        leaf name {
          type string;
        }
        uses apply-group;
        uses apply-macro;
        container feb {
          choice choice-3 {
            leaf none {
              type empty;
            }
            leaf feb-slot {
              type string;
            }
          }
        }
      }
    }
    container ioc-npc-connectivity {
      uses apply-group;
      uses apply-macro;
      list ioc {
        key "name";
        leaf name {
          type string;
        }
        uses apply-group;
        uses apply-macro;
        container npc {
          choice choice-3 {
            leaf none {
              type empty;
            }
            leaf npc-slot {
              type uint32;
            }
          }
        }
      }
    }
    container pem {
      uses chassis-pem-type;
    }
    container sib {
      uses chassis-sib-type;
    }
    list sfm {
      key "name";
      uses chassis-sfm-type;
    }
    container feb {
      uses chassis-feb-type;
    }
    container afeb {
      uses chassis-feb-type;
    }
    container tfeb {
      uses chassis-feb-type;
    }
    container alarm {
      uses chassis-alarm-type;
    }
    leaf ppp-subscriber-services {
      type string;
    }
    leaf ambient-temperature {
      type string;
    }
    leaf fabric-header-crc-enable {
      type empty;
    }
    leaf network-services {
      type string;
    }
    leaf limited-ifl-scaling {
      type empty;
    }
    container usb {
      presence "";
      uses apply-group;
      uses apply-macro;
      container storage {
        uses apply-group;
        uses apply-macro;
        leaf disable {
          type empty;
        }
      }
    }
    list node {
      key "name";
      leaf name {
        type string;
      }
      uses apply-group;
      uses apply-macro;
      list fpc {
        key "name";
        uses chassis-fpc-type;
      }
    }
    list lcc {
      key "name";
      leaf name {
        type string;
      }
      uses apply-group;
      uses apply-macro;
      list fpc {
        key "name";
        uses chassis-fpc-type;
      }
      container spmb {
        uses apply-group;
        uses apply-macro;
      }
      choice choice-7 {
        leaf online-expected {
          type empty;
        }
        leaf offline {
          type empty;
        }
      }
    }
    container fabric {
      uses apply-group;
      uses apply-macro;
      container undocumented {
        container error-thresholds {
          leaf plane-error-on-cell-drops {
            type empty;
          }
          leaf hsl2-crc-error-rate-threshold {
            type uint32;
          }
          leaf hsl2-crc-error-aggregate-threshold {
            type uint32;
          }
          leaf optical-crc-error-rate-threshold {
            type uint32;
          }
          leaf optical-crc-error-aggregate-threshold {
            type uint32;
          }
          leaf vcsel-low-power-threshold {
            type uint32;
          }
          leaf optical-transmit-squelch-disable {
            type empty;
          }
          leaf optical-receive-squelch-disable {
            type empty;
          }
          leaf optical-crc-rate-cons-polls {
            type uint32;
          }
          leaf optical-crc-autoheal-attempt {
            type empty;
          }
          leaf optical-crc-autoheal-period {
            type uint32;
          }
          leaf optical-crc-autoheal-exceed-threshold-enable {
            type empty;
          }
        }
      }
      leaf upgrade-mode {
        type empty;
      }
      container redundancy-mode {
        uses apply-group;
        uses apply-macro;
        choice choice-redundant {
          leaf redundant {
            type empty;
          }
          leaf increased-bandwidth {
            type empty;
          }
        }
      }
    }
    list member {
      key "name";
      leaf name {
        type key-attribute-ulong-type;
      }
      uses apply-group;
      uses apply-macro;
      container fabric {
        uses chassis-fabric-type;
      }
      list fpc {
        key "name";
        uses chassis-fpc-type;
      }
    }
    container synchronization {
      uses apply-group;
      uses apply-macro;
      leaf switchover-mode {
        type string;
      }
      leaf switching-mode {
        type string;
      }
      leaf network-option {
        type string;
      }
      leaf selection-mode {
        type string;
      }
      leaf clock-mode {
        type string;
      }
      leaf quality-mode-enable {
        type empty;
      }
      leaf max-transmit-quality-level {
        type string;
      }
      leaf global-wait-to-restore {
        units "min";
        type uint32;
      }
      list port {
        key "name";
        leaf name {
          type string;
        }
        uses apply-group;
        uses apply-macro;
        container client {
          presence "enable client";
          uses apply-group;
          uses apply-macro;
          container time-of-day-format {
            uses apply-group;
            uses apply-macro;
            leaf ascii {
              type string;
            }
          }
          leaf cable-length-compensation {
            type uint32;
          }
          leaf antenna-voltage {
            type string;
          }
          leaf constellation {
            type string;
          }
          leaf anti-jamming {
            type empty;
          }
        }
        container server {
          presence "enable server";
          uses apply-group;
          uses apply-macro;
          container time-of-day-format {
            uses apply-group;
            uses apply-macro;
            leaf ascii {
              type string;
            }
          }
        }
      }
      list interfaces {
        key "name";
        leaf name {
          type string;
        }
        uses apply-group;
        uses apply-macro;
        leaf signal-type {
          type string;
        }
        leaf pulse-per-second-enable {
          type empty;
        }
        container e1-options {
          uses apply-group;
          uses apply-macro;
          leaf line-encoding {
            type string;
          }
          leaf framing {
            type string;
          }
          leaf sabit {
            type uint32;
          }
        }
        container t1-options {
          uses apply-group;
          uses apply-macro;
          leaf line-encoding {
            type string;
          }
          leaf framing {
            type string;
          }
        }
      }
      container output {
        uses apply-group;
        uses apply-macro;
        list interfaces {
          key "name";
          leaf name {
            type string;
          }
          uses apply-group;
          uses apply-macro;
          leaf wander-filter-disable {
            type empty;
          }
          leaf holdover-mode-disable {
            type empty;
          }
          leaf source-mode {
            type string;
          }
          leaf tx-dnu-to-line-source-enable {
            type empty;
          }
          leaf minimum-quality {
            type string;
          }
        }
      }
      container source {
        uses apply-group;
        uses apply-macro;
        container external-a {
          presence "enable external-a";
          uses apply-group;
          uses apply-macro;
          leaf priority {
            type uint32;
          }
          leaf request {
            type string;
          }
          leaf quality-level {
            type string;
          }
        }
        container external-b {
          presence "enable external-b";
          uses apply-group;
          uses apply-macro;
          leaf priority {
            type uint32;
          }
          leaf request {
            type string;
          }
          leaf quality-level {
            type string;
          }
        }
        container gps {
          presence "enable gps";
          uses apply-group;
          uses apply-macro;
          leaf priority {
            type uint32;
          }
          leaf request {
            type string;
          }
          leaf no-ssm-support {
            type empty;
          }
          leaf quality-level {
            type string;
          }
        }
        container gps-0 {
          presence "enable gps-0";
          uses apply-group;
          uses apply-macro;
          leaf priority {
            type uint32;
          }
          leaf request {
            type string;
          }
          leaf wait-to-restore {
            units "min";
            type uint32;
          }
          leaf quality-level {
            type string;
          }
        }
        container gps-1 {
          presence "enable gps-1";
          uses apply-group;
          uses apply-macro;
          leaf priority {
            type uint32;
          }
          leaf request {
            type string;
          }
          leaf wait-to-restore {
            units "min";
            type uint32;
          }
          leaf quality-level {
            type string;
          }
        }
        container bits {
          presence "enable bits";
          uses apply-group;
          uses apply-macro;
          leaf priority {
            type uint32;
          }
          leaf request {
            type string;
          }
          leaf no-ssm-support {
            type empty;
          }
          leaf quality-level {
            type string;
          }
        }
        container bits-a {
          presence "enable bits-a";
          uses apply-group;
          uses apply-macro;
          leaf priority {
            type uint32;
          }
          leaf request {
            type string;
          }
          leaf wait-to-restore {
            units "min";
            type uint32;
          }
          leaf quality-level {
            type string;
          }
        }
        container bits-b {
          presence "enable bits-b";
          uses apply-group;
          uses apply-macro;
          leaf priority {
            type uint32;
          }
          leaf request {
            type string;
          }
          leaf wait-to-restore {
            units "min";
            type uint32;
          }
          leaf quality-level {
            type string;
          }
        }
        list interfaces {
          key "name";
          leaf name {
            type interface-device;
          }
          uses apply-group;
          uses apply-macro;
          leaf priority {
            type uint32;
          }
          leaf request {
            type string;
          }
          leaf wait-to-restore {
            type uint32;
          }
          leaf no-ssm-support {
            type empty;
          }
          leaf hold-off-time {
            units "milliseconds";
            type uint32;
          }
          leaf aggregated-ether {
            type string;
          }
          leaf quality-level {
            type string;
          }
        }
      }
      container esmc-transmit {
        uses apply-group;
        uses apply-macro;
        list interfaces {
          key "name";
          ordered-by user;
          leaf name {
            type string;
          }
          uses apply-group;
          uses apply-macro;
        }
      }
      container hold-interval {
        uses apply-group;
        uses apply-macro;
        leaf switchover {
          type uint32;
        }
        leaf configuration-change {
          type uint32;
        }
        leaf restart {
          type uint32;
        }
      }
      leaf validation-interval {
        type uint32;
      }
      leaf slave-free-run {
        type empty;
      }
      leaf y-cable-line-termination {
        type empty;
      }
      leaf transmitter-enable {
        type empty;
      }
      leaf signal-type {
        type string;
      }
      leaf primary {
        type string;
      }
      leaf secondary {
        type string;
      }
    }
    container forwarding-options {
      uses apply-group;
      uses apply-macro;
      choice choice-l2-profile-one {
        container l2-profile-one {
          presence "enable l2-profile-one";
          uses apply-group;
          uses apply-macro;
          leaf num-65-127-prefix {
            type int32;
          }
        }
        container l2-profile-two {
          presence "enable l2-profile-two";
          uses apply-group;
          uses apply-macro;
          leaf num-65-127-prefix {
            type int32;
          }
        }
        container l2-profile-three {
          presence "enable l2-profile-three";
          uses apply-group;
          uses apply-macro;
          leaf num-65-127-prefix {
            type int32;
          }
        }
        container l3-profile {
          presence "enable l3-profile";
          uses apply-group;
          uses apply-macro;
          leaf num-65-127-prefix {
            type int32;
          }
        }
        container lpm-profile {
          presence "enable lpm-profile";
          uses apply-group;
          uses apply-macro;
          leaf prefix-65-127-disable {
            type empty;
          }
        }
      }
    }
    container lcd-menu {
      uses apply-group;
      uses apply-macro;
      list fpc {
        key "name";
        ordered-by user;
        leaf name {
          type string;
        }
        uses apply-group;
        uses apply-macro;
        list menu-item {
          key "name";
          ordered-by user;
          leaf name {
            type string;
          }
          leaf disable {
            type empty;
          }
        }
      }
      list menu-item {
        key "name";
        ordered-by user;
        leaf name {
          type string;
        }
        leaf disable {
          type empty;
        }
      }
    }
    leaf fru-poweron-sequence {
      type string;
    }
    leaf auto-image-upgrade {
      type empty;
    }
    list tor {
      key "name";
      ordered-by user;
      leaf name {
        type string;
      }
      uses apply-group;
      uses apply-macro;
      list tor-member {
        key "name";
        leaf name {
          type string;
        }
        uses apply-group;
        uses apply-macro;
      }
    }
    list vdcf {
      key "name";
      ordered-by user;
      leaf name {
        type string;
      }
      uses apply-group;
      uses apply-macro;
      list re-group {
        key "name";
        ordered-by user;
        leaf name {
          type string;
        }
        uses apply-group;
        uses apply-macro;
      }
      container resources {
        uses apply-group;
        uses apply-macro;
        list routing-engine-resource {
          key "name";
          ordered-by user;
          leaf name {
            type string;
          }
          uses apply-group;
          uses apply-macro;
        }
        list tor {
          key "name";
          ordered-by user;
          leaf name {
            type string;
          }
          uses apply-group;
          uses apply-macro;
        }
      }
      list network-domain {
        key "name";
        ordered-by user;
        leaf name {
          type string;
        }
        uses apply-group;
        uses apply-macro;
        list re-group {
          key "name";
          ordered-by user;
          leaf name {
            type string;
          }
          uses apply-group;
          uses apply-macro;
        }
        list tor {
          key "name";
          leaf name {
            type string;
          }
          uses apply-group;
          uses apply-macro;
        }
      }
    }
    container satellite-management {
      presence "enable satellite-management";
      uses apply-group;
      uses apply-macro;
      container designated-event-forwarding {
        presence "enable designated-event-forwarding";
        uses apply-group;
        uses apply-macro;
      }
      container traceoptions {
        uses apply-group;
        uses apply-macro;
        leaf no-remote-trace {
          type empty;
        }
        container file {
          leaf filename {
            type string;
          }
          leaf size {
            type string;
          }
          leaf files {
            type uint32;
          }
          leaf world-readable {
            type empty;
          }
          leaf no-world-readable {
            type empty;
          }
          leaf match {
            type regular-expression;
          }
        }
        list flag {
          key "name";
          ordered-by user;
          leaf name {
            type string;
          }
          leaf disable {
            type empty;
          }
        }
      }
      leaf cluster-policy {
        type string;
      }
      list cluster {
        key "name";
        leaf name {
          type key-attribute-string-type;
        }
        uses apply-group;
        uses apply-macro;
        leaf cluster-id {
          mandatory true;
          type uint32;
        }
        leaf-list cascade-ports {
          type interface-device;
        }
        leaf cluster-policy {
          type string;
        }
        list fpc {
          key "name";
          leaf name {
            type key-attribute-ulong-type;
          }
          uses apply-group;
          uses apply-macro;
          leaf alias {
            type string;
          }
          leaf description {
            type string;
          }
          leaf member-id {
            mandatory true;
            type uint32;
          }
          leaf system-id {
            mandatory true;
            type mac-addr;
          }
          leaf cluster-policy {
            type string;
          }
        }
      }
      list fpc {
        key "name";
        leaf name {
          type key-attribute-ulong-type;
        }
        uses apply-group;
        uses apply-macro;
        leaf serial-number {
          type string;
        }
        leaf system-id {
          type mac-addr;
        }
        leaf target-mode {
          type empty;
        }
        leaf alias {
          type string;
        }
        leaf description {
          type string;
        }
        container management-address {
          presence "";
          uses apply-group;
          uses apply-macro;
          leaf address {
            mandatory true;
            type ipv4prefix;
          }
          leaf gateway {
            mandatory true;
            type ipv4addr;
          }
        }
        leaf-list cascade-ports {
          type interface-device;
        }
        leaf extended-ports-template {
          type string;
        }
        container uplink-failure-detection {
          presence "enable uplink-failure-detection";
          uses apply-group;
          uses apply-macro;
          leaf candidate-uplink-policy {
            type string;
          }
        }
        leaf environment-monitoring-policy {
          type string;
        }
        container forwarding-policy {
          presence "";
          uses apply-group;
          uses apply-macro;
          leaf forwarding-policy-alias {
            type string;
            mandatory true;
          }
        }
      }
      leaf extended-ports-policy {
        type string;
      }
      container uplink-failure-detection {
        presence "enable uplink-failure-detection";
        uses apply-group;
        uses apply-macro;
        leaf candidate-uplink-policy {
          type string;
        }
      }
      container psu {
        uses apply-group;
        uses apply-macro;
        container redundancy {
          uses apply-group;
          uses apply-macro;
          leaf n-plus-n {
            type empty;
          }
        }
      }
      container environment-monitoring-policy {
        presence "enable environment-monitoring-policy";
        uses apply-group;
        uses apply-macro;
        leaf policy-name {
          type string;
        }
      }
      container forwarding-policy {
        presence "";
        uses apply-group;
        uses apply-macro;
        leaf forwarding-policy-alias {
          type string;
          mandatory true;
        }
      }
      container redundancy-groups {
        presence "";
        uses apply-group;
        uses apply-macro;
        leaf chassis-id {
          mandatory true;
          type uint32;
        }
        list rg-group {
          key "name";
          ordered-by user;
          uses redundancy-group-type;
        }
      }
      container upgrade-groups {
        uses apply-group;
        uses apply-macro;
        list upgrade-group {
          key "name";
          uses upgrade-group-type;
        }
      }
      container auto-satellite-conversion {
        presence "";
        uses apply-group;
        uses apply-macro;
        leaf-list satellite {
          ordered-by user;
          type string;
        }
      }
      container single-home {
        presence "";
        uses apply-group;
        uses apply-macro;
        leaf-list satellite {
          ordered-by user;
          type string;
        }
      }
      leaf aging-timer {
        units "minutes";
        type uint32;
      }
      leaf block-console-access {
        type empty;
      }
      container firewall {
        uses apply-group;
        uses apply-macro;
        container family {
          uses apply-group;
          uses apply-macro;
          container bridge {
            uses apply-group;
            uses apply-macro;
            list filter {
              key "name";
              ordered-by user;
              uses satellite-bridge-filter;
            }
          }
          container ethernet-switching {
            uses apply-group;
            uses apply-macro;
            list filter {
              key "name";
              ordered-by user;
              uses satellite-bridge-filter;
            }
          }
        }
      }
    }
    container system-domains {
      presence "";
      uses apply-group;
      uses apply-macro;
      leaf root-domain-id {
        type uint32;
      }
      list protected-system-domains {
        key "name";
        uses juniper-protected-system-domain;
      }
      container traceoptions {
        uses juniper-protected-system-domain-traceoptions;
      }
    }
    container cluster {
      presence "";
      uses apply-group;
      uses apply-macro;
      container traceoptions {
        uses apply-group;
        uses apply-macro;
        leaf no-remote-trace {
          type empty;
        }
        container file {
          leaf filename {
            type string;
          }
          leaf size {
            type string;
          }
          leaf files {
            type uint32;
          }
          leaf world-readable {
            type empty;
          }
          leaf no-world-readable {
            type empty;
          }
          leaf match {
            type regular-expression;
          }
        }
        list flag {
          key "name";
          ordered-by user;
          leaf name {
            type string;
          }
        }
        leaf level {
          type string;
        }
      }
      leaf control-link-recovery {
        type empty;
      }
      leaf reth-count {
        type uint16;
      }
      list control-ports {
        key "fpc port";
        ordered-by user;
        leaf fpc {
          type string;
        }
        leaf port {
          type string;
        }
      }
      leaf heartbeat-interval {
        type uint32;
      }
      leaf heartbeat-threshold {
        type uint32;
      }
      list redundancy-group {
        key "name";
        ordered-by user;
        leaf name {
          type string;
        }
        uses apply-group;
        uses apply-macro;
        list node {
          key "name";
          ordered-by user;
          leaf name {
            type string;
          }
          leaf priority {
            type uint8;
          }
        }
        leaf preempt {
          type empty;
        }
        leaf gratuitous-arp-count {
          type uint8;
        }
        leaf hold-down-interval {
          type uint16;
        }
        list interface-monitor {
          key "name";
          ordered-by user;
          leaf name {
            type interface-device;
          }
          leaf weight {
            type uint16;
          }
        }
        container ip-monitoring {
          uses apply-group;
          uses apply-macro;
          leaf global-weight {
            type uint16;
          }
          leaf global-threshold {
            type uint16;
          }
          leaf retry-interval {
            type uint16;
          }
          leaf retry-count {
            type uint16;
          }
          container family {
            uses apply-group;
            uses apply-macro;
            container inet {
              uses apply-group;
              uses apply-macro;
              list address {
                key "name";
                uses ip-monitoring-address-type;
              }
            }
          }
        }
      }
      container configuration-synchronize {
        presence "";
        uses apply-group;
        uses apply-macro;
        leaf no-secondary-bootup-auto {
          mandatory true;
          type empty;
        }
      }
      leaf use-actual-mac-on-physical-interfaces {
        type empty;
      }
      leaf use-active-child-mac-on-reth {
        type empty;
      }
    }
    list node-group {
      key "name";
      leaf name {
        type key-attribute-string-type;
      }
      container aggregated-devices {
        uses chassis-agg-dev-type;
      }
    }
    container high-availability {
      presence "enable high-availability";
      uses apply-advanced;
      leaf software-upgrade {
        type empty;
      }
      leaf hardware-upgrade {
        type empty;
      }
      container local-id {
        uses apply-advanced;
        leaf id {
          type string;
        }
        leaf local-ip {
          type ipaddr;
        }
        container local-forwarding-ip {
          uses apply-advanced;
          leaf loopback-address {
            type ipaddr;
          }
        }
      }
      list peer-id {
        key "name";
        ordered-by user;
        leaf name {
          type string;
        }
        uses apply-advanced;
        leaf desc {
          type string;
        }
        leaf peer-ip {
          type ipaddr;
        }
        leaf interface {
          type string;
        }
        leaf routing-instance {
          type string;
        }
        leaf vpn-profile {
          type string;
        }
        container peer-forwarding-ip {
          uses apply-advanced;
          leaf loopback-address {
            type ipaddr;
          }
          leaf interface {
            type string;
          }
          container liveness-detection {
            presence "enable liveness-detection";
            uses apply-advanced;
            leaf version {
              type string;
            }
            leaf minimum-interval {
              units "milliseconds";
              type string;
            }
            leaf minimum-transmit-interval {
              status deprecated;
              units "milliseconds";
              type string;
            }
            leaf minimum-receive-interval {
              units "milliseconds";
              type string;
            }
            leaf multiplier {
              type string;
            }
            choice adaptation-choice {
              case case_1 {
                leaf no-adaptation {
                  type empty;
                }
              }
            }
            container transmit-interval {
              uses apply-advanced;
              leaf minimum-interval {
                units "milliseconds";
                type string;
              }
              leaf threshold {
                units "milliseconds";
                type string;
              }
            }
            container detection-time {
              uses apply-advanced;
              leaf threshold {
                units "milliseconds";
                type string;
              }
            }
          }
        }
        container liveness-detection {
          presence "enable liveness-detection";
          uses apply-advanced;
          leaf version {
            type string;
          }
          leaf minimum-interval {
            units "milliseconds";
            type string;
          }
          leaf minimum-transmit-interval {
            status deprecated;
            units "milliseconds";
            type string;
          }
          leaf minimum-receive-interval {
            units "milliseconds";
            type string;
          }
          leaf multiplier {
            type string;
          }
          choice adaptation-choice {
            case case_1 {
              leaf no-adaptation {
                type empty;
              }
            }
          }
          container transmit-interval {
            uses apply-advanced;
            leaf minimum-interval {
              units "milliseconds";
              type string;
            }
            leaf threshold {
              units "milliseconds";
              type string;
            }
          }
          container detection-time {
            uses apply-advanced;
            leaf threshold {
              units "milliseconds";
              type string;
            }
          }
        }
      }
      container traceoptions {
        uses apply-advanced;
        leaf no-remote-trace {
          type empty;
        }
        container file {
          leaf filename {
            type string;
          }
          leaf size {
            type string;
          }
          leaf files {
            type string;
          }
          choice world-readable-choice {
            leaf world-readable {
              type empty;
            }
            leaf no-world-readable {
              type empty;
            }
          }
          leaf match {
            type regular-expression;
          }
        }
        list flag {
          key "name";
          ordered-by user;
          leaf name {
            type string;
          }
        }
        leaf level {
          type string;
        }
      }
      list services-redundancy-group {
        key "name";
        ordered-by user;
        leaf name {
          type string;
        }
        uses apply-advanced;
        list shutdown-on-failure {
          key "name";
          ordered-by user;
          leaf name {
            type string;
          }
          uses apply-advanced;
        }
        leaf deployment-type {
          type string;
        }
        container peer-id {
          presence "enable peer-id";
          uses apply-advanced;
          leaf id {
            type string;
          }
        }
        container activeness-probe {
          uses apply-advanced;
          container dest-ip {
            uses apply-advanced;
            leaf ip-address {
              type ipaddr;
            }
            leaf src-ip {
              type ipaddr;
            }
            leaf routing-instance {
              type string;
            }
          }
          leaf minimum-interval {
            type string;
          }
          leaf multiplier {
            type string;
          }
          container bfd-liveliness {
            uses apply-advanced;
            leaf source-ip {
              type ipaddr;
            }
            leaf destination-ip {
              type ipaddr;
            }
            leaf interface {
              type string;
            }
            leaf routing-instance {
              type string;
            }
            leaf minimum-interval {
              units "milliseconds";
              type string;
            }
            leaf multiplier {
              type string;
            }
          }
        }
        list virtual-ip {
          key "name";
          ordered-by user;
          leaf name {
            type string;
          }
          uses apply-advanced;
          leaf ip {
            type ipprefix-mandatory;
          }
          leaf interface {
            type string;
          }
          leaf use-virtual-mac {
            type empty;
          }
        }
        container monitor {
          uses apply-advanced;
          list ip {
            key "name";
            ordered-by user;
            leaf name {
              type ipaddr;
            }
            uses apply-advanced;
            leaf routing-instance {
              type string;
            }
          }
          list bfd-liveliness {
            key "name";
            ordered-by user;
            leaf name {
              type ipaddr;
            }
            uses apply-advanced;
            leaf src-ip {
              type ipaddr;
            }
            leaf routing-instance {
              type string;
            }
            leaf session-type {
              type string;
            }
            leaf interface {
              type string;
            }
          }
          list interface {
            key "name";
            ordered-by user;
            leaf name {
              type string;
            }
            uses apply-advanced;
          }
          list monitor-object {
            key "name";
            ordered-by user;
            leaf name {
              type string;
            }
            uses apply-advanced;
            leaf object-threshold {
              type string;
            }
            container ip {
              presence "enable ip";
              uses apply-advanced;
              leaf threshold {
                type string;
              }
              list destination-ip {
                key "name";
                ordered-by user;
                leaf name {
                  type ipaddr;
                }
                uses apply-advanced;
                leaf routing-instance {
                  type string;
                }
                leaf weight {
                  type string;
                }
              }
            }
            container bfd-liveliness {
              presence "enable bfd-liveliness";
              uses apply-advanced;
              leaf threshold {
                type string;
              }
              list destination-ip {
                key "name";
                ordered-by user;
                leaf name {
                  type ipaddr;
                }
                uses apply-advanced;
                leaf src-ip {
                  type ipaddr;
                }
                leaf routing-instance {
                  type string;
                }
                leaf session-type {
                  type string;
                }
                leaf interface {
                  type string;
                }
                leaf weight {
                  type string;
                }
              }
            }
            container interface {
              presence "enable interface";
              uses apply-advanced;
              leaf threshold {
                type string;
              }
              list interface-name {
                key "name";
                ordered-by user;
                leaf name {
                  type string;
                }
                uses apply-advanced;
                leaf weight {
                  type string;
                }
              }
            }
          }
          leaf srg-threshold {
            type string;
          }
        }
        container active-signal-route {
          uses apply-advanced;
          leaf ip-address {
            type ipv4addr;
          }
          leaf routing-instance {
            type string;
          }
        }
        container backup-signal-route {
          uses apply-advanced;
          leaf ip-address {
            type ipv4addr;
          }
          leaf routing-instance {
            type string;
          }
        }
        container install-on-failure-route {
          uses apply-advanced;
          leaf ip-address {
            type ipv4addr;
          }
          leaf routing-instance {
            type string;
          }
        }
        list prefix-list {
          key "name";
          ordered-by user;
          leaf name {
            type string;
          }
          uses apply-advanced;
          leaf routing-instance {
            type string;
          }
        }
        list managed-services {
          key "name";
          leaf name {
            type string;
          }
        }
        leaf preemption {
          type empty;
        }
        leaf process-packet-on-backup {
          type empty;
        }
        leaf activeness-priority {
          type string;
        }
      }
    }
  }

  grouping chassis-fabric-type {
    uses apply-group;
    uses apply-macro;
    leaf upgrade-mode {
      type string;
    }
    container blackhole {
      presence "enable blackhole";
      uses apply-group;
      uses apply-macro;
    }
    container link-autoheal {
      presence "enable link-autoheal";
      uses apply-group;
      uses apply-macro;
    }
    container degraded {
      presence "enable degraded";
      uses apply-group;
      uses apply-macro;
      leaf action-fpc-restart-disable {
        type empty;
      }
      leaf degraded-fpc-bad-plane-threshold {
        type uint32;
      }
      leaf degraded-fabric-detection-enable {
        type empty;
      }
      leaf fpc-restart {
        type empty;
      }
      leaf auto-recovery-disable {
        type empty;
      }
      leaf fpc-offline-on-blackholing {
        type empty;
      }
    }
    container redundancy-mode {
      uses apply-group;
      uses apply-macro;
      choice choice-redundant {
        leaf redundant {
          type empty;
        }
        leaf increased-bandwidth {
          type empty;
        }
      }
    }
    leaf disable-grant-bypass {
      type empty;
    }
  }

  grouping chassis-agg-dev-type {
    uses apply-group;
    uses apply-macro;
    leaf ae-20 {
      type empty;
    }
    container ethernet {
      uses chassisd-agg-enet-type;
    }
    container sonet {
      uses chassisd-agg-pos-type;
    }
    leaf maximum-links {
      type int32;
    }
  }

  grouping chassis-alarm-type {
    uses apply-group;
    uses apply-macro;
    container management-ethernet {
      uses chassis-alarm-ethernet-type;
    }
    container sonet {
      uses chassis-alarm-sonet-type;
    }
    container t3 {
      uses chassis-alarm-ds3-type;
    }
    container ds1 {
      uses chassis-alarm-ds1-type;
    }
    container ethernet {
      uses chassis-alarm-ethernet-type;
    }
    container integrated-services {
      uses chassis-alarm-integrated-services-type;
    }
    container services {
      uses chassis-alarm-services-type;
    }
    container serial {
      uses chassis-alarm-serial-type;
    }
    container undocumented {
      container redundancy {
        leaf backup-re-master {
          type string;
        }
      }
    }
  }

  grouping chassis-alarm-ds1-type {
    uses apply-group;
    uses apply-macro;
    leaf ais {
      type string;
    }
    leaf ylw {
      type string;
    }
  }

  grouping chassis-alarm-ds3-type {
    uses apply-group;
    uses apply-macro;
    leaf ais {
      type string;
    }
    leaf exz {
      type string;
    }
    leaf ferf {
      type string;
    }
    leaf idle {
      type string;
    }
    leaf lcv {
      type string;
    }
    leaf lof {
      type string;
    }
    leaf los {
      type string;
    }
    leaf pll {
      type string;
    }
    leaf ylw {
      type string;
    }
  }

  grouping chassis-alarm-ethernet-type {
    uses apply-group;
    uses apply-macro;
    leaf link-down {
      type string;
    }
  }

  grouping chassis-alarm-integrated-services-type {
    uses apply-group;
    uses apply-macro;
    leaf failure {
      type string;
    }
  }

  grouping chassis-alarm-serial-type {
    uses apply-group;
    uses apply-macro;
    leaf loss-of-rx-clock {
      type string;
    }
    leaf loss-of-tx-clock {
      type string;
    }
    leaf dcd-absent {
      type string;
    }
    leaf cts-absent {
      type string;
    }
    leaf dsr-absent {
      type string;
    }
    leaf tm-absent {
      type string;
    }
  }

  grouping chassis-alarm-services-type {
    uses apply-group;
    uses apply-macro;
    leaf pic-reset {
      type string;
    }
    leaf pic-hold-reset {
      type string;
    }
    leaf linkdown {
      type string;
    }
    leaf rx-errors {
      type string;
    }
    leaf tx-errors {
      type string;
    }
    leaf sw-down {
      type string;
    }
    leaf hw-down {
      type string;
    }
  }

  grouping chassis-alarm-sonet-type {
    uses apply-group;
    uses apply-macro;
    leaf lol {
      type string;
    }
    leaf pll {
      type string;
    }
    leaf lof {
      type string;
    }
    leaf los {
      type string;
    }
    leaf ais-l {
      type string;
    }
    leaf ais-p {
      type string;
    }
    leaf lop-p {
      type string;
    }
    leaf ber-sd {
      type string;
    }
    leaf ber-sf {
      type string;
    }
    leaf rfi-l {
      type string;
    }
    leaf rfi-p {
      type string;
    }
    leaf uneq-p {
      type string;
    }
    leaf locd {
      type string;
    }
    leaf plm-p {
      type string;
    }
  }

  grouping chassis-feb-type {
    uses apply-group;
    uses apply-macro;
    list slot {
      key "name";
      ordered-by user;
      leaf name {
        type string;
      }
      uses apply-group;
      uses apply-macro;
      leaf power {
        type string;
      }
      leaf port-mirror-instance {
        type string;
      }
      leaf sampling-instance {
        type string;
      }
      leaf ucode-imem-remap {
        type empty;
      }
      container inline-services {
        uses apply-group;
        uses apply-macro;
        leaf report-zero-oif-gw-on-discard {
          type empty;
        }
        leaf flex-flow-sizing {
          type empty;
        }
        leaf use-extended-flow-memory {
          type empty;
        }
        container flow-table-size {
          uses apply-group;
          uses apply-macro;
          leaf ipv4-flow-table-size {
            type uint32;
          }
          leaf ipv6-flow-table-size {
            type uint32;
          }
          leaf vpls-flow-table-size {
            type uint32;
          }
          leaf bridge-flow-table-size {
            type uint32;
          }
          leaf ipv6-extended-attrib {
            type empty;
          }
          leaf mpls-flow-table-size {
            type uint32;
          }
        }
      }
    }
  }

  grouping chassis-fpc-error-type {
    uses apply-group;
    uses apply-macro;
    container fatal {
      uses chassis-fpc-error-level-major-fatal;
    }
    container major {
      uses chassis-fpc-error-level-major-fatal;
    }
    container minor {
      uses chassis-fpc-error-level-minor;
    }
    list override-cmerror {
      key "name";
      ordered-by user;
      uses chassis-fru-cmerror-override-type;
    }
    container scope {
      uses chassis-fpc-scope-type;
    }
  }

  grouping chassis-fpc-error-level-major-fatal {
    uses apply-group;
    uses apply-macro;
    leaf threshold {
      type uint32;
    }
    list action {
      key "name";
      ordered-by user;
      leaf name {
        type string;
      }
      uses apply-group;
      uses apply-macro;
    }
  }

  grouping chassis-fpc-error-level-minor {
    uses apply-group;
    uses apply-macro;
    leaf threshold {
      type uint32;
    }
    list action {
      key "name";
      ordered-by user;
      leaf name {
        type string;
      }
      uses apply-group;
      uses apply-macro;
    }
  }

  grouping chassis-fpc-scope-type {
    uses apply-group;
    uses apply-macro;
    container board {
      uses chassis-fpc-scope-category;
    }
    container pfe {
      uses chassis-fpc-scope-category;
    }
  }

  grouping chassis-fpc-scope-category {
    uses apply-group;
    uses apply-macro;
    container category {
      uses chassis-fpc-scope-category-type;
    }
  }

  grouping chassis-fpc-scope-category-type {
    uses apply-group;
    uses apply-macro;
    container functional {
      uses chassis-fpc-scope-category-error-type;
    }
    container memory {
      uses chassis-fpc-scope-category-error-type;
    }
    container io {
      uses chassis-fpc-scope-category-error-type;
    }
    container storage {
      uses chassis-fpc-scope-category-error-type;
    }
    container switch {
      uses chassis-fpc-scope-category-error-type;
    }
    container processing {
      uses chassis-fpc-scope-category-error-type;
    }
  }

  grouping chassis-fpc-scope-category-error-type {
    uses apply-group;
    uses apply-macro;
    container fatal {
      uses chassis-fpc-error-level-type;
    }
    container major {
      uses chassis-fpc-error-level-type;
    }
    container minor {
      uses chassis-fpc-error-level-type;
    }
  }

  grouping chassis-fpc-error-level-type {
    uses apply-group;
    uses apply-macro;
    leaf threshold {
      type uint32;
    }
    list action {
      key "name";
      ordered-by user;
      leaf name {
        type string;
      }
      uses apply-group;
      uses apply-macro;
    }
  }

  grouping chassis-fpc-type {
    leaf name {
      type string;
    }
    uses apply-group;
    uses apply-macro;
    container system-mode {
      uses apply-group;
      uses apply-macro;
      choice choice-mode-104port {
        leaf mode-104port {
          type empty;
        }
        leaf allow-40g {
          type empty;
        }
      }
    }
    container auto-speed-detection {
      uses apply-group;
      uses apply-macro;
      leaf disable {
        type empty;
      }
    }
    container ukern-trace {
      uses apply-group;
      uses apply-macro;
      container log {
        presence "";
        uses apply-group;
        uses apply-macro;
        leaf app-type {
          mandatory true;
          type string;
        }
        leaf logging {
          mandatory true;
          type string;
        }
      }
    }
    container sanity-poll {
      uses apply-group;
      uses apply-macro;
      leaf retry-count {
        type uint32;
      }
      container on-error {
        uses apply-group;
        uses apply-macro;
        leaf raise-alarm {
          type empty;
        }
        leaf power {
          type string;
        }
        leaf write-coredump {
          type empty;
        }
      }
    }
    container forwarding-options {
      uses apply-group;
      uses apply-macro;
      choice choice-l2-profile-one {
        container l2-profile-one {
          presence "enable l2-profile-one";
          uses apply-group;
          uses apply-macro;
          leaf num-65-127-prefix {
            type int32;
          }
        }
        container l2-profile-two {
          presence "enable l2-profile-two";
          uses apply-group;
          uses apply-macro;
          leaf num-65-127-prefix {
            type int32;
          }
        }
        container l2-profile-three {
          presence "enable l2-profile-three";
          uses apply-group;
          uses apply-macro;
          leaf num-65-127-prefix {
            type int32;
          }
        }
        container l3-profile {
          presence "enable l3-profile";
          uses apply-group;
          uses apply-macro;
          leaf num-65-127-prefix {
            type int32;
          }
        }
        container lpm-profile {
          presence "enable lpm-profile";
          uses apply-group;
          uses apply-macro;
          leaf prefix-65-127-disable {
            type empty;
          }
        }
        container exact-match-profile {
          presence "enable exact-match-profile";
          uses apply-group;
          uses apply-macro;
          leaf num-65-127-prefix {
            type int32;
          }
        }
        container custom-profile {
          uses apply-group;
          uses apply-macro;
          container l2-entries {
            uses apply-group;
            uses apply-macro;
            leaf num-banks {
              type int32;
            }
          }
          container l3-entries {
            uses apply-group;
            uses apply-macro;
            leaf num-banks {
              type int32;
            }
          }
          container exact-match-entries {
            uses apply-group;
            uses apply-macro;
            leaf num-banks {
              type int32;
            }
          }
          container lpm-entries {
            uses apply-group;
            uses apply-macro;
            leaf num-banks {
              type string;
            }
            leaf prefix-65-127-disable {
              type empty;
            }
          }
          leaf num-65-127-prefix {
            type int32;
          }
        }
      }
    }
    list pic {
      key "name";
      uses chassis-pic-type;
    }
    container optical-options {
      uses apply-group;
      uses apply-macro;
      leaf disable-edfa {
        type empty;
      }
      leaf no-disable-edfa {
        type empty;
      }
      leaf disable-osc {
        type empty;
      }
      leaf no-disable-osc {
        type empty;
      }
      list wavelength {
        key "name";
        leaf name {
          type string;
        }
        uses apply-group;
        uses apply-macro;
        choice choice-switch {
          container switch {
            presence "";
            uses apply-group;
            uses apply-macro;
            leaf interface-name {
              type string;
              mandatory true;
            }
          }
          leaf wss-express-in {
            type empty;
          }
        }
      }
      container tca {
        uses apply-group;
        uses apply-macro;
        container osc-tx-power-high-tca {
          uses apply-group;
          uses apply-macro;
          leaf enable-tca {
            type empty;
          }
          leaf no-enable-tca {
            type empty;
          }
          leaf threshold {
            type string;
          }
          leaf threshold-24hrs {
            type string;
          }
        }
        container osc-tx-power-low-tca {
          uses apply-group;
          uses apply-macro;
          leaf enable-tca {
            type empty;
          }
          leaf no-enable-tca {
            type empty;
          }
          leaf threshold {
            type string;
          }
          leaf threshold-24hrs {
            type string;
          }
        }
        container osc-rx-power-high-tca {
          uses apply-group;
          uses apply-macro;
          leaf enable-tca {
            type empty;
          }
          leaf no-enable-tca {
            type empty;
          }
          leaf threshold {
            type string;
          }
          leaf threshold-24hrs {
            type string;
          }
        }
        container osc-rx-power-low-tca {
          uses apply-group;
          uses apply-macro;
          leaf enable-tca {
            type empty;
          }
          leaf no-enable-tca {
            type empty;
          }
          leaf threshold {
            type string;
          }
          leaf threshold-24hrs {
            type string;
          }
        }
        container osc-fiber-loss-high-tca {
          uses apply-group;
          uses apply-macro;
          leaf enable-tca {
            type empty;
          }
          leaf no-enable-tca {
            type empty;
          }
          leaf threshold {
            type string;
          }
          leaf threshold-24hrs {
            type string;
          }
        }
        container osc-fiber-loss-low-tca {
          uses apply-group;
          uses apply-macro;
          leaf enable-tca {
            type empty;
          }
          leaf no-enable-tca {
            type empty;
          }
          leaf threshold {
            type string;
          }
          leaf threshold-24hrs {
            type string;
          }
        }
        container lout-voa-high-tca {
          uses apply-group;
          uses apply-macro;
          leaf enable-tca {
            type empty;
          }
          leaf no-enable-tca {
            type empty;
          }
          leaf threshold {
            type string;
          }
          leaf threshold-24hrs {
            type string;
          }
        }
        container lout-voa-low-tca {
          uses apply-group;
          uses apply-macro;
          leaf enable-tca {
            type empty;
          }
          leaf no-enable-tca {
            type empty;
          }
          leaf threshold {
            type string;
          }
          leaf threshold-24hrs {
            type string;
          }
        }
        container edfa1-in-power-high-tca {
          uses apply-group;
          uses apply-macro;
          leaf enable-tca {
            type empty;
          }
          leaf no-enable-tca {
            type empty;
          }
          leaf threshold {
            type string;
          }
          leaf threshold-24hrs {
            type string;
          }
        }
        container edfa1-in-power-low-tca {
          uses apply-group;
          uses apply-macro;
          leaf enable-tca {
            type empty;
          }
          leaf no-enable-tca {
            type empty;
          }
          leaf threshold {
            type string;
          }
          leaf threshold-24hrs {
            type string;
          }
        }
        container edfa1-out-power-high-tca {
          uses apply-group;
          uses apply-macro;
          leaf enable-tca {
            type empty;
          }
          leaf no-enable-tca {
            type empty;
          }
          leaf threshold {
            type string;
          }
          leaf threshold-24hrs {
            type string;
          }
        }
        container edfa1-out-power-low-tca {
          uses apply-group;
          uses apply-macro;
          leaf enable-tca {
            type empty;
          }
          leaf no-enable-tca {
            type empty;
          }
          leaf threshold {
            type string;
          }
          leaf threshold-24hrs {
            type string;
          }
        }
        container edfa1-sig-power-high-tca {
          uses apply-group;
          uses apply-macro;
          leaf enable-tca {
            type empty;
          }
          leaf no-enable-tca {
            type empty;
          }
          leaf threshold {
            type string;
          }
          leaf threshold-24hrs {
            type string;
          }
        }
        container edfa1-sig-power-low-tca {
          uses apply-group;
          uses apply-macro;
          leaf enable-tca {
            type empty;
          }
          leaf no-enable-tca {
            type empty;
          }
          leaf threshold {
            type string;
          }
          leaf threshold-24hrs {
            type string;
          }
        }
        container edfa1-awg-high-tca {
          uses apply-group;
          uses apply-macro;
          leaf enable-tca {
            type empty;
          }
          leaf no-enable-tca {
            type empty;
          }
          leaf threshold {
            type string;
          }
          leaf threshold-24hrs {
            type string;
          }
        }
        container edfa1-awg-low-tca {
          uses apply-group;
          uses apply-macro;
          leaf enable-tca {
            type empty;
          }
          leaf no-enable-tca {
            type empty;
          }
          leaf threshold {
            type string;
          }
          leaf threshold-24hrs {
            type string;
          }
        }
        container edfa1-express-high-tca {
          uses apply-group;
          uses apply-macro;
          leaf enable-tca {
            type empty;
          }
          leaf no-enable-tca {
            type empty;
          }
          leaf threshold {
            type string;
          }
          leaf threshold-24hrs {
            type string;
          }
        }
        container edfa1-express-low-tca {
          uses apply-group;
          uses apply-macro;
          leaf enable-tca {
            type empty;
          }
          leaf no-enable-tca {
            type empty;
          }
          leaf threshold {
            type string;
          }
          leaf threshold-24hrs {
            type string;
          }
        }
        container edfa2-in-power-high-tca {
          uses apply-group;
          uses apply-macro;
          leaf enable-tca {
            type empty;
          }
          leaf no-enable-tca {
            type empty;
          }
          leaf threshold {
            type string;
          }
          leaf threshold-24hrs {
            type string;
          }
        }
        container edfa2-in-power-low-tca {
          uses apply-group;
          uses apply-macro;
          leaf enable-tca {
            type empty;
          }
          leaf no-enable-tca {
            type empty;
          }
          leaf threshold {
            type string;
          }
          leaf threshold-24hrs {
            type string;
          }
        }
        container edfa2-out-power-high-tca {
          uses apply-group;
          uses apply-macro;
          leaf enable-tca {
            type empty;
          }
          leaf no-enable-tca {
            type empty;
          }
          leaf threshold {
            type string;
          }
          leaf threshold-24hrs {
            type string;
          }
        }
        container edfa2-out-power-low-tca {
          uses apply-group;
          uses apply-macro;
          leaf enable-tca {
            type empty;
          }
          leaf no-enable-tca {
            type empty;
          }
          leaf threshold {
            type string;
          }
          leaf threshold-24hrs {
            type string;
          }
        }
        container edfa2-sig-power-high-tca {
          uses apply-group;
          uses apply-macro;
          leaf enable-tca {
            type empty;
          }
          leaf no-enable-tca {
            type empty;
          }
          leaf threshold {
            type string;
          }
          leaf threshold-24hrs {
            type string;
          }
        }
        container edfa2-sig-power-low-tca {
          uses apply-group;
          uses apply-macro;
          leaf enable-tca {
            type empty;
          }
          leaf no-enable-tca {
            type empty;
          }
          leaf threshold {
            type string;
          }
          leaf threshold-24hrs {
            type string;
          }
        }
        container edfa2-awg-high-tca {
          uses apply-group;
          uses apply-macro;
          leaf enable-tca {
            type empty;
          }
          leaf no-enable-tca {
            type empty;
          }
          leaf threshold {
            type string;
          }
          leaf threshold-24hrs {
            type string;
          }
        }
        container edfa2-awg-low-tca {
          uses apply-group;
          uses apply-macro;
          leaf enable-tca {
            type empty;
          }
          leaf no-enable-tca {
            type empty;
          }
          leaf threshold {
            type string;
          }
          leaf threshold-24hrs {
            type string;
          }
        }
        container edfa2-express-high-tca {
          uses apply-group;
          uses apply-macro;
          leaf enable-tca {
            type empty;
          }
          leaf no-enable-tca {
            type empty;
          }
          leaf threshold {
            type string;
          }
          leaf threshold-24hrs {
            type string;
          }
        }
        container edfa2-express-low-tca {
          uses apply-group;
          uses apply-macro;
          leaf enable-tca {
            type empty;
          }
          leaf no-enable-tca {
            type empty;
          }
          leaf threshold {
            type string;
          }
          leaf threshold-24hrs {
            type string;
          }
        }
        container ocm-power-high-line-out-tca {
          uses apply-group;
          uses apply-macro;
          leaf enable-tca {
            type empty;
          }
          leaf no-enable-tca {
            type empty;
          }
          leaf threshold {
            type string;
          }
          leaf threshold-24hrs {
            type string;
          }
        }
        container ocm-power-low-line-out-tca {
          uses apply-group;
          uses apply-macro;
          leaf enable-tca {
            type empty;
          }
          leaf no-enable-tca {
            type empty;
          }
          leaf threshold {
            type string;
          }
          leaf threshold-24hrs {
            type string;
          }
        }
      }
      container expansion-card {
        uses apply-group;
        uses apply-macro;
        container fpc {
          presence "";
          uses apply-group;
          uses apply-macro;
          leaf fpc-slot {
            mandatory true;
            type uint32;
          }
        }
      }
      container express-in {
        uses apply-group;
        uses apply-macro;
        container fpc {
          presence "";
          uses apply-group;
          uses apply-macro;
          leaf fpc-slot {
            mandatory true;
            type uint32;
          }
        }
      }
      container amplifier-chain {
        uses apply-group;
        uses apply-macro;
        leaf anchor-iplc {
          type empty;
        }
        leaf no-anchor-iplc {
          type empty;
        }
        leaf osc-ip {
          type string;
        }
        leaf osc-mac {
          type string;
        }
        list ila {
          key "name";
          leaf name {
            type key-attribute-ulong-type;
          }
          uses apply-group;
          uses apply-macro;
          container ila-options {
            uses apply-group;
            uses apply-macro;
            leaf ila-ipv4-address {
              type string;
            }
            leaf ila-user {
              type string;
            }
            leaf ila-password {
              type unreadable;
            }
            container edfa-a-b {
              uses apply-group;
              uses apply-macro;
              container tca-input-power-low {
                uses apply-group;
                uses apply-macro;
                leaf enable-tca {
                  type empty;
                }
                leaf no-enable-tca {
                  type empty;
                }
                leaf threshold {
                  type string;
                }
                leaf threshold-24hrs {
                  type string;
                }
              }
              container tca-input-power-high {
                uses apply-group;
                uses apply-macro;
                leaf enable-tca {
                  type empty;
                }
                leaf no-enable-tca {
                  type empty;
                }
                leaf threshold {
                  type string;
                }
                leaf threshold-24hrs {
                  type string;
                }
              }
              container tca-output-power-low {
                uses apply-group;
                uses apply-macro;
                leaf enable-tca {
                  type empty;
                }
                leaf no-enable-tca {
                  type empty;
                }
                leaf threshold {
                  type string;
                }
                leaf threshold-24hrs {
                  type string;
                }
              }
              container tca-output-power-high {
                uses apply-group;
                uses apply-macro;
                leaf enable-tca {
                  type empty;
                }
                leaf no-enable-tca {
                  type empty;
                }
                leaf threshold {
                  type string;
                }
                leaf threshold-24hrs {
                  type string;
                }
              }
              container tca-signal-output-power-low {
                uses apply-group;
                uses apply-macro;
                leaf enable-tca {
                  type empty;
                }
                leaf no-enable-tca {
                  type empty;
                }
                leaf threshold {
                  type string;
                }
                leaf threshold-24hrs {
                  type string;
                }
              }
              container tca-signal-output-power-high {
                uses apply-group;
                uses apply-macro;
                leaf enable-tca {
                  type empty;
                }
                leaf no-enable-tca {
                  type empty;
                }
                leaf threshold {
                  type string;
                }
                leaf threshold-24hrs {
                  type string;
                }
              }
              container tca-pump0-current-low {
                uses apply-group;
                uses apply-macro;
                leaf enable-tca {
                  type empty;
                }
                leaf no-enable-tca {
                  type empty;
                }
                leaf threshold {
                  type string;
                }
                leaf threshold-24hrs {
                  type string;
                }
              }
              container tca-pump0-current-high {
                uses apply-group;
                uses apply-macro;
                leaf enable-tca {
                  type empty;
                }
                leaf no-enable-tca {
                  type empty;
                }
                leaf threshold {
                  type string;
                }
                leaf threshold-24hrs {
                  type string;
                }
              }
              container tca-pump1-current-low {
                uses apply-group;
                uses apply-macro;
                leaf enable-tca {
                  type empty;
                }
                leaf no-enable-tca {
                  type empty;
                }
                leaf threshold {
                  type string;
                }
                leaf threshold-24hrs {
                  type string;
                }
              }
              container tca-pump1-current-high {
                uses apply-group;
                uses apply-macro;
                leaf enable-tca {
                  type empty;
                }
                leaf no-enable-tca {
                  type empty;
                }
                leaf threshold {
                  type string;
                }
                leaf threshold-24hrs {
                  type string;
                }
              }
              container tca-pump0-temperature-low {
                uses apply-group;
                uses apply-macro;
                leaf enable-tca {
                  type empty;
                }
                leaf no-enable-tca {
                  type empty;
                }
                leaf threshold {
                  type string;
                }
                leaf threshold-24hrs {
                  type string;
                }
              }
              container tca-pump0-temperature-high {
                uses apply-group;
                uses apply-macro;
                leaf enable-tca {
                  type empty;
                }
                leaf no-enable-tca {
                  type empty;
                }
                leaf threshold {
                  type string;
                }
                leaf threshold-24hrs {
                  type string;
                }
              }
              container tca-pump1-temperature-low {
                uses apply-group;
                uses apply-macro;
                leaf enable-tca {
                  type empty;
                }
                leaf no-enable-tca {
                  type empty;
                }
                leaf threshold {
                  type string;
                }
                leaf threshold-24hrs {
                  type string;
                }
              }
              container tca-pump1-temperature-high {
                uses apply-group;
                uses apply-macro;
                leaf enable-tca {
                  type empty;
                }
                leaf no-enable-tca {
                  type empty;
                }
                leaf threshold {
                  type string;
                }
                leaf threshold-24hrs {
                  type string;
                }
              }
            }
            container voa-a {
              uses apply-group;
              uses apply-macro;
              container tca-attenuation-low {
                uses apply-group;
                uses apply-macro;
                leaf enable-tca {
                  type empty;
                }
                leaf no-enable-tca {
                  type empty;
                }
                leaf threshold {
                  type string;
                }
                leaf threshold-24hrs {
                  type string;
                }
              }
              container tca-attenuation-high {
                uses apply-group;
                uses apply-macro;
                leaf enable-tca {
                  type empty;
                }
                leaf no-enable-tca {
                  type empty;
                }
                leaf threshold {
                  type string;
                }
                leaf threshold-24hrs {
                  type string;
                }
              }
            }
            container osc-a {
              uses apply-group;
              uses apply-macro;
              container osc-tx-power-high-tca {
                uses apply-group;
                uses apply-macro;
                leaf enable-tca {
                  type empty;
                }
                leaf no-enable-tca {
                  type empty;
                }
                leaf threshold {
                  type string;
                }
                leaf threshold-24hrs {
                  type string;
                }
              }
              container osc-tx-power-low-tca {
                uses apply-group;
                uses apply-macro;
                leaf enable-tca {
                  type empty;
                }
                leaf no-enable-tca {
                  type empty;
                }
                leaf threshold {
                  type string;
                }
                leaf threshold-24hrs {
                  type string;
                }
              }
              container osc-rx-power-high-tca {
                uses apply-group;
                uses apply-macro;
                leaf enable-tca {
                  type empty;
                }
                leaf no-enable-tca {
                  type empty;
                }
                leaf threshold {
                  type string;
                }
                leaf threshold-24hrs {
                  type string;
                }
              }
              container osc-rx-power-low-tca {
                uses apply-group;
                uses apply-macro;
                leaf enable-tca {
                  type empty;
                }
                leaf no-enable-tca {
                  type empty;
                }
                leaf threshold {
                  type string;
                }
                leaf threshold-24hrs {
                  type string;
                }
              }
              container osc-fiber-loss-high-tca {
                uses apply-group;
                uses apply-macro;
                leaf enable-tca {
                  type empty;
                }
                leaf no-enable-tca {
                  type empty;
                }
                leaf threshold {
                  type string;
                }
                leaf threshold-24hrs {
                  type string;
                }
              }
              container osc-fiber-loss-low-tca {
                uses apply-group;
                uses apply-macro;
                leaf enable-tca {
                  type empty;
                }
                leaf no-enable-tca {
                  type empty;
                }
                leaf threshold {
                  type string;
                }
                leaf threshold-24hrs {
                  type string;
                }
              }
            }
            container edfa-b-a {
              uses apply-group;
              uses apply-macro;
              container tca-input-power-low {
                uses apply-group;
                uses apply-macro;
                leaf enable-tca {
                  type empty;
                }
                leaf no-enable-tca {
                  type empty;
                }
                leaf threshold {
                  type string;
                }
                leaf threshold-24hrs {
                  type string;
                }
              }
              container tca-input-power-high {
                uses apply-group;
                uses apply-macro;
                leaf enable-tca {
                  type empty;
                }
                leaf no-enable-tca {
                  type empty;
                }
                leaf threshold {
                  type string;
                }
                leaf threshold-24hrs {
                  type string;
                }
              }
              container tca-output-power-low {
                uses apply-group;
                uses apply-macro;
                leaf enable-tca {
                  type empty;
                }
                leaf no-enable-tca {
                  type empty;
                }
                leaf threshold {
                  type string;
                }
                leaf threshold-24hrs {
                  type string;
                }
              }
              container tca-output-power-high {
                uses apply-group;
                uses apply-macro;
                leaf enable-tca {
                  type empty;
                }
                leaf no-enable-tca {
                  type empty;
                }
                leaf threshold {
                  type string;
                }
                leaf threshold-24hrs {
                  type string;
                }
              }
              container tca-signal-output-power-low {
                uses apply-group;
                uses apply-macro;
                leaf enable-tca {
                  type empty;
                }
                leaf no-enable-tca {
                  type empty;
                }
                leaf threshold {
                  type string;
                }
                leaf threshold-24hrs {
                  type string;
                }
              }
              container tca-signal-output-power-high {
                uses apply-group;
                uses apply-macro;
                leaf enable-tca {
                  type empty;
                }
                leaf no-enable-tca {
                  type empty;
                }
                leaf threshold {
                  type string;
                }
                leaf threshold-24hrs {
                  type string;
                }
              }
              container tca-pump0-current-low {
                uses apply-group;
                uses apply-macro;
                leaf enable-tca {
                  type empty;
                }
                leaf no-enable-tca {
                  type empty;
                }
                leaf threshold {
                  type string;
                }
                leaf threshold-24hrs {
                  type string;
                }
              }
              container tca-pump0-current-high {
                uses apply-group;
                uses apply-macro;
                leaf enable-tca {
                  type empty;
                }
                leaf no-enable-tca {
                  type empty;
                }
                leaf threshold {
                  type string;
                }
                leaf threshold-24hrs {
                  type string;
                }
              }
              container tca-pump1-current-low {
                uses apply-group;
                uses apply-macro;
                leaf enable-tca {
                  type empty;
                }
                leaf no-enable-tca {
                  type empty;
                }
                leaf threshold {
                  type string;
                }
                leaf threshold-24hrs {
                  type string;
                }
              }
              container tca-pump1-current-high {
                uses apply-group;
                uses apply-macro;
                leaf enable-tca {
                  type empty;
                }
                leaf no-enable-tca {
                  type empty;
                }
                leaf threshold {
                  type string;
                }
                leaf threshold-24hrs {
                  type string;
                }
              }
              container tca-pump0-temperature-low {
                uses apply-group;
                uses apply-macro;
                leaf enable-tca {
                  type empty;
                }
                leaf no-enable-tca {
                  type empty;
                }
                leaf threshold {
                  type string;
                }
                leaf threshold-24hrs {
                  type string;
                }
              }
              container tca-pump0-temperature-high {
                uses apply-group;
                uses apply-macro;
                leaf enable-tca {
                  type empty;
                }
                leaf no-enable-tca {
                  type empty;
                }
                leaf threshold {
                  type string;
                }
                leaf threshold-24hrs {
                  type string;
                }
              }
              container tca-pump1-temperature-low {
                uses apply-group;
                uses apply-macro;
                leaf enable-tca {
                  type empty;
                }
                leaf no-enable-tca {
                  type empty;
                }
                leaf threshold {
                  type string;
                }
                leaf threshold-24hrs {
                  type string;
                }
              }
              container tca-pump1-temperature-high {
                uses apply-group;
                uses apply-macro;
                leaf enable-tca {
                  type empty;
                }
                leaf no-enable-tca {
                  type empty;
                }
                leaf threshold {
                  type string;
                }
                leaf threshold-24hrs {
                  type string;
                }
              }
            }
            container voa-b {
              uses apply-group;
              uses apply-macro;
              container tca-attenuation-low {
                uses apply-group;
                uses apply-macro;
                leaf enable-tca {
                  type empty;
                }
                leaf no-enable-tca {
                  type empty;
                }
                leaf threshold {
                  type string;
                }
                leaf threshold-24hrs {
                  type string;
                }
              }
              container tca-attenuation-high {
                uses apply-group;
                uses apply-macro;
                leaf enable-tca {
                  type empty;
                }
                leaf no-enable-tca {
                  type empty;
                }
                leaf threshold {
                  type string;
                }
                leaf threshold-24hrs {
                  type string;
                }
              }
            }
            container osc-b {
              uses apply-group;
              uses apply-macro;
              container osc-tx-power-high-tca {
                uses apply-group;
                uses apply-macro;
                leaf enable-tca {
                  type empty;
                }
                leaf no-enable-tca {
                  type empty;
                }
                leaf threshold {
                  type string;
                }
                leaf threshold-24hrs {
                  type string;
                }
              }
              container osc-tx-power-low-tca {
                uses apply-group;
                uses apply-macro;
                leaf enable-tca {
                  type empty;
                }
                leaf no-enable-tca {
                  type empty;
                }
                leaf threshold {
                  type string;
                }
                leaf threshold-24hrs {
                  type string;
                }
              }
              container osc-rx-power-high-tca {
                uses apply-group;
                uses apply-macro;
                leaf enable-tca {
                  type empty;
                }
                leaf no-enable-tca {
                  type empty;
                }
                leaf threshold {
                  type string;
                }
                leaf threshold-24hrs {
                  type string;
                }
              }
              container osc-rx-power-low-tca {
                uses apply-group;
                uses apply-macro;
                leaf enable-tca {
                  type empty;
                }
                leaf no-enable-tca {
                  type empty;
                }
                leaf threshold {
                  type string;
                }
                leaf threshold-24hrs {
                  type string;
                }
              }
              container osc-fiber-loss-high-tca {
                uses apply-group;
                uses apply-macro;
                leaf enable-tca {
                  type empty;
                }
                leaf no-enable-tca {
                  type empty;
                }
                leaf threshold {
                  type string;
                }
                leaf threshold-24hrs {
                  type string;
                }
              }
              container osc-fiber-loss-low-tca {
                uses apply-group;
                uses apply-macro;
                leaf enable-tca {
                  type empty;
                }
                leaf no-enable-tca {
                  type empty;
                }
                leaf threshold {
                  type string;
                }
                leaf threshold-24hrs {
                  type string;
                }
              }
            }
          }
        }
      }
    }
    leaf power {
      type string;
    }
    container traffic-manager {
      uses apply-group;
      uses apply-macro;
      leaf buffer-monitor-enable {
        type empty;
      }
      container queue-threshold {
        uses apply-group;
        uses apply-macro;
        container fabric-queue {
          uses apply-group;
          uses apply-macro;
          list priority {
            key "name";
            ordered-by user;
            leaf name {
              mandatory true;
              type string;
            }
            uses apply-group;
            uses apply-macro;
            leaf threshold {
              mandatory true;
              type uint32;
            }
          }
        }
        container wan-queue {
          uses apply-group;
          uses apply-macro;
          list priority {
            key "name";
            ordered-by user;
            leaf name {
              mandatory true;
              type string;
            }
            uses apply-group;
            uses apply-macro;
            leaf threshold {
              mandatory true;
              type uint32;
            }
          }
        }
      }
      leaf enhanced-priority-mode {
        type empty;
      }
      leaf no-enhanced-priority-mode {
        type empty;
      }
      leaf packet-timestamp {
        type string;
      }
    }
    leaf max-power {
      type string;
    }
    leaf route-localization {
      type string;
    }
    leaf vpn-localization {
      type string;
    }
    leaf power-budget-priority {
      type uint32;
    }
    choice choice-9 {
      leaf disable-power {
        type empty;
      }
      leaf allow-sram-parity-errors {
        type empty;
      }
    }
    choice choice-performance-mode {
      container performance-mode {
        presence "enable performance-mode";
        uses apply-group;
        uses apply-macro;
        leaf number-of-ucode-workers {
          type uint32;
        }
      }
      leaf lite-mode {
        type empty;
      }
    }
    leaf cfp-to-et {
      type empty;
    }
    leaf np-cache {
      type empty;
    }
    leaf offline {
      type empty;
    }
    leaf offline-on-fabric-bandwidth-reduction {
      type empty;
    }
    leaf ir-mode {
      type string;
    }
    leaf license-mode {
      type string;
    }
    container fabric {
      presence "enable fabric";
      uses apply-group;
      uses apply-macro;
      leaf blackhole-action {
        type string;
      }
      container bandwidth-degradation {
        presence "";
        uses apply-group;
        uses apply-macro;
        leaf percentage {
          mandatory true;
          type uint32;
        }
        leaf no-fabric-switchover {
          type empty;
        }
        leaf action {
          mandatory true;
          type string;
        }
      }
      container undocumented {
        container no-cell-share {
          presence "true";
        }
      }
    }
    list port-mirror-instance {
      key "name";
      ordered-by user;
      leaf name {
        type key-attribute-string-type;
      }
      uses apply-group;
      uses apply-macro;
    }
    list sampling-instance {
      key "name";
      ordered-by user;
      leaf name {
        type key-attribute-string-type;
      }
      uses apply-group;
      uses apply-macro;
    }
    container inline-services {
      uses apply-group;
      uses apply-macro;
      leaf flex-flow-sizing {
        type empty;
      }
      leaf use-extended-flow-memory {
        type empty;
      }
      container flow-table-size {
        uses apply-group;
        uses apply-macro;
        leaf ipv4-flow-table-size {
          type uint32;
        }
        leaf ipv6-flow-table-size {
          type uint32;
        }
        leaf bridge-flow-table-size {
          type uint32;
        }
        leaf vpls-flow-table-size {
          type uint32;
        }
        leaf ipv6-extended-attrib {
          type empty;
        }
        leaf mpls-flow-table-size {
          type uint32;
        }
      }
      leaf report-zero-oif-gw-on-discard {
        type empty;
      }
    }
    container inline-video-monitoring {
      uses apply-group;
      uses apply-macro;
      leaf maximum-flows-count {
        type uint32;
      }
      leaf flow-table-size {
        type uint32;
      }
    }
    container application-services {
      presence "";
      uses apply-group;
      uses apply-macro;
      leaf package {
        type string;
      }
    }
    container slamon-services {
      uses apply-group;
      uses apply-macro;
      leaf rfc2544 {
        type empty;
      }
    }
    leaf flexible-queuing-mode {
      type empty;
    }
    leaf loopback-device-count {
      type uint32;
    }
    leaf interasic-linkerror-recovery-enable {
      type empty;
    }
    leaf number-of-ports {
      type string;
    }
    list pfe {
      key "name";
      uses chassis-pfe-type;
    }
    leaf service-package {
      type string;
    }
    leaf max-queues {
      type string;
    }
    leaf bandwidth {
      type string;
    }
    leaf pfe-bandwidth {
      type string;
    }
    container error {
      presence "enable error";
      uses chassis-fpc-error-type;
    }
    list ether-type {
      key "name";
      ordered-by user;
      leaf name {
        type key-attribute-ulong-type;
      }
      uses apply-group;
      uses apply-macro;
      leaf etype {
        type string;
      }
    }
    container openflow {
      uses apply-group;
      uses apply-macro;
      leaf access-list-partition {
        units "percents";
        type uint32;
      }
      leaf buffer-partition {
        units "percents";
        type uint32;
      }
    }
    container undocumented {
      leaf non-nebs-optics-overheat-trigger {
        type uint16;
      }
    }
  }

  grouping chassis-fru-cmerror-override-type {
    leaf name {
      type key-attribute-string-type;
    }
    uses apply-group;
    uses apply-macro;
    leaf state {
      type string;
    }
    leaf severity {
      type string;
    }
    container pfe {
      presence "enable pfe";
      uses apply-group;
      uses apply-macro;
      leaf all {
        type empty;
      }
    }
  }

  grouping chassis-pem-type {
    uses apply-group;
    uses apply-macro;
    leaf minimum {
      type uint32;
    }
    leaf feeds {
      type uint32;
    }
    leaf input-current {
      type string;
    }
  }

  grouping chassis-pfe-type {
    leaf name {
      type string;
    }
    uses apply-group;
    uses apply-macro;
    container forwarding-packages {
      uses apply-group;
      uses apply-macro;
      container mobility {
        uses apply-group;
        uses apply-macro;
        choice choice-ggsn-pgw {
          leaf ggsn-pgw {
            type empty;
          }
          leaf sgw {
            type empty;
          }
        }
      }
    }
    leaf tunnel-services {
      type empty;
    }
    container exception-reporting {
      list category {
        key "name";
        ordered-by user;
        leaf name {
          type string;
        }
        leaf inline-monitoring-instance {
          type string;
        }
      }
    }
  }

  grouping chassis-pic-type {
    leaf name {
      type string;
    }
    uses apply-group;
    uses apply-macro;
    leaf pic-mode {
      type string;
    }
    list tunnel-port {
      key "name";
      uses chassis-port-type;
    }
    container tunnel-services {
      presence "enable tunnel-services";
      uses apply-group;
      uses apply-macro;
      leaf bandwidth {
        type string;
      }
      leaf tunnel-only {
        type empty;
      }
      list tunnel-port {
        key "name";
        ordered-by user;
        leaf name {
          type string;
        }
        leaf bandwidth {
          type string;
        }
      }
    }
    leaf interface-type {
      type string;
    }
    container inline-services {
      presence "";
      uses apply-group;
      uses apply-macro;
      leaf bandwidth {
        type string;
      }
    }
    choice choice-5 {
      container adaptive-services {
        uses apply-group;
        uses apply-macro;
        container service-package {
          uses apply-group;
          uses apply-macro;
          choice choice-3 {
            leaf layer-3 {
              type empty;
            }
            leaf layer-2 {
              type empty;
            }
            leaf layer-2-3 {
              type empty;
            }
            container extension-provider {
              presence "";
              uses apply-group;
              uses apply-macro;
              leaf control-cores {
                type uint32;
              }
              leaf data-cores {
                type uint32;
              }
              leaf object-cache-size {
                type uint32;
              }
              leaf forwarding-db-size {
                type uint32;
              }
              leaf policy-db-size {
                type uint32;
              }
              leaf wired-process-mem-size {
                type uint32;
              }
              container data-flow-affinity {
                presence "enable data-flow-affinity";
                uses apply-group;
                uses apply-macro;
                leaf hash-key {
                  type string;
                }
              }
              leaf session-offload {
                type empty;
              }
              list package {
                key "name";
                ordered-by user;
                leaf name {
                  type string;
                }
                uses apply-group;
                uses apply-macro;
              }
              list syslog {
                key "name";
                ordered-by user;
                leaf name {
                  type string;
                }
                uses apply-group;
                uses apply-macro;
                choice choice-3 {
                  leaf any {
                    type empty;
                  }
                  leaf emergency {
                    type empty;
                  }
                  leaf alert {
                    type empty;
                  }
                  leaf critical {
                    type empty;
                  }
                  leaf error {
                    type empty;
                  }
                  leaf warning {
                    type empty;
                  }
                  leaf notice {
                    type empty;
                  }
                  leaf info {
                    type empty;
                  }
                  leaf none {
                    type empty;
                  }
                }
                leaf destination {
                  type string;
                }
              }
            }
          }
        }
      }
      container monitoring-services {
        presence "";
        uses apply-group;
        uses apply-macro;
        leaf application {
          type string;
        }
      }
    }
    leaf no-mcast-replication {
      type empty;
    }
    container ggsn-services {
      uses apply-group;
      uses apply-macro;
      leaf application {
        type string;
      }
    }
    leaf framing {
      type string;
    }
    container synchronization {
      uses apply-group;
      uses apply-macro;
      choice choice-3 {
        leaf port {
          type uint32;
        }
      }
    }
    container recovered-clock {
      uses apply-group;
      uses apply-macro;
      leaf port {
        type uint32;
      }
    }
    leaf vtmapping {
      type string;
    }
    leaf no-concatenate {
      type empty;
    }
    leaf no-multi-rate {
      type empty;
    }
    leaf channelization {
      type empty;
    }
    leaf linerate-mode {
      type empty;
    }
    leaf mixed-rate-mode {
      type empty;
    }
    leaf no-pre-classifier {
      type empty;
    }
    leaf aggregate-ports {
      type empty;
    }
    leaf number-of-ports {
      type uint32;
    }
    leaf power {
      type string;
    }
    leaf pic-type {
      type string;
    }
    container aggregated-devices {
      uses apply-group;
      uses apply-macro;
      container ima {
        uses apply-group;
        uses apply-macro;
        leaf device-count {
          type uint32;
        }
      }
    }
    leaf sparse-dlcis {
      type empty;
    }
    leaf multi-link-layer-2-inline {
      type empty;
    }
    container q-pic-large-buffer {
      presence "enable q-pic-large-buffer";
      uses apply-group;
      uses apply-macro;
      choice choice-3 {
        leaf small-scale {
          type empty;
        }
        leaf large-scale {
          type empty;
        }
      }
    }
    container red-buffer-occupancy {
      uses apply-group;
      uses apply-macro;
      container weighted-averaged {
        presence "enable weighted-averaged";
        uses apply-group;
        uses apply-macro;
        leaf instant-usage-weight-exponent {
          type uint8;
        }
      }
    }
    container traffic-manager {
      uses apply-group;
      uses apply-macro;
      leaf ingress-shaping-overhead {
        type int32;
      }
      leaf egress-shaping-overhead {
        type int32;
      }
      leaf mode {
        type string;
      }
    }
    container idle-cell-format {
      uses apply-group;
      uses apply-macro;
      leaf itu-t {
        type empty;
      }
      leaf payload-pattern {
        type string;
      }
    }
    container atm-l2circuit-mode {
      uses apply-group;
      uses apply-macro;
      choice choice-3 {
        leaf aal5 {
          type empty;
        }
        leaf cell {
          type empty;
        }
        container trunk {
          presence "enable trunk";
          uses apply-group;
          uses apply-macro;
          choice choice-3 {
            container uni {
              presence "enable uni";
              uses apply-group;
              uses apply-macro;
            }
            container nni {
              presence "enable nni";
              uses apply-group;
              uses apply-macro;
            }
          }
        }
      }
    }
    leaf atm-cell-relay-accumulation {
      type empty;
    }
    container services-offload {
      presence "enable services-offload";
      uses apply-group;
      uses apply-macro;
    }
    leaf mlfr-uni-nni-bundles {
      type uint32;
    }
    leaf mlfr-uni-nni-bundles-inline {
      type uint32;
    }
    container ct3 {
      uses apply-group;
      uses apply-macro;
      list port {
        key "name";
        uses ct3-port-type;
      }
    }
    container ce1 {
      uses apply-group;
      uses apply-macro;
      list e1 {
        key "name";
        uses ce1-channel-type;
      }
    }
    leaf max-queues-per-interface {
      type string;
    }
    container shdsl {
      uses apply-group;
      uses apply-macro;
      leaf pic-mode {
        type string;
      }
    }
    container ds1 {
      uses apply-group;
      uses apply-macro;
      leaf pic-mode {
        type string;
      }
    }
    container ethernet {
      uses apply-group;
      uses apply-macro;
      leaf pic-mode {
        type string;
      }
    }
    leaf tunnel-queuing {
      type empty;
    }
    list port-mirror-instance {
      key "name";
      ordered-by user;
      leaf name {
        type key-attribute-string-type;
      }
      uses apply-group;
      uses apply-macro;
    }
    list port {
      key "name";
      uses chassis-pic-port-framing;
    }
    list port-range {
      key "port-range-low port-range-high";
      ordered-by user;
      leaf port-range-low {
        type key-attribute-ulong-type;
      }
      leaf port-range-high {
        type key-attribute-ulong-type;
      }
      uses apply-group;
      uses apply-macro;
      leaf short-reach-mode {
        type string;
      }
      leaf channel-speed {
        type string;
      }
    }
    container sfpplus {
      uses apply-group;
      uses apply-macro;
      leaf pic-mode {
        type string;
      }
    }
    container hash-key {
      uses apply-group;
      uses apply-macro;
      container family {
        uses apply-group;
        uses apply-macro;
        container inet {
          uses apply-group;
          uses apply-macro;
          container layer-3 {
            presence "enable layer-3";
            uses apply-group;
            uses apply-macro;
            leaf destination-address {
              type empty;
            }
          }
          container layer-4 {
            presence "enable layer-4";
            uses apply-group;
            uses apply-macro;
          }
          container symmetric-hash {
            presence "enable symmetric-hash";
            uses apply-group;
            uses apply-macro;
            leaf complement {
              type empty;
            }
          }
        }
        container multiservice {
          uses apply-group;
          uses apply-macro;
          leaf source-mac {
            type empty;
          }
          leaf destination-mac {
            type empty;
          }
          container payload {
            uses apply-group;
            uses apply-macro;
            container ip {
              uses apply-group;
              uses apply-macro;
              container layer-3 {
                presence "enable layer-3";
                uses apply-group;
                uses apply-macro;
                choice choice-3 {
                  leaf source-ip-only {
                    type empty;
                  }
                  leaf destination-ip-only {
                    type empty;
                  }
                }
              }
              leaf layer-4 {
                type empty;
              }
            }
          }
          container symmetric-hash {
            presence "enable symmetric-hash";
            uses apply-group;
            uses apply-macro;
            leaf complement {
              type empty;
            }
          }
        }
      }
    }
    leaf ingress-policer-overhead {
      units "bytes";
      type uint32;
    }
    leaf egress-policer-overhead {
      units "bytes";
      type uint32;
    }
    leaf account-layer2-overhead {
      type empty;
    }
    container forwarding-mode {
      uses apply-group;
      uses apply-macro;
      choice choice-3 {
        leaf sa-multicast {
          type empty;
        }
        container vlan-steering {
          presence "";
          uses apply-group;
          uses apply-macro;
          leaf vlan-rule {
            type string;
          }
        }
      }
    }
  }

  grouping ce1-channel-type {
    leaf name {
      type string;
    }
    uses apply-group;
    uses apply-macro;
    list channel-group {
      key "name";
      leaf name {
        type string;
      }
      leaf timeslots {
        type string;
      }
    }
  }

  grouping chassis-pic-port-framing {
    leaf name {
      type string;
    }
    uses apply-group;
    uses apply-macro;
    leaf short-reach-mode {
      type string;
    }
    leaf framing {
      type string;
    }
    leaf number-of-sub-ports {
      type uint32;
    }
    leaf unused {
      type empty;
    }
    leaf speed {
      type string;
    }
    leaf channel-speed {
      type string;
    }
    container forwarding-mode {
      uses apply-group;
      uses apply-macro;
      leaf sa-multicast {
        type empty;
      }
    }
    leaf no-mcast-replication {
      type empty;
    }
    container traffic-manager {
      uses apply-group;
      uses apply-macro;
      leaf mode {
        type string;
      }
    }
  }

  grouping chassis-port-type {
    leaf name {
      type key-attribute-ulong-type;
    }
    uses apply-group;
    uses apply-macro;
    leaf tunnel-services {
      type empty;
    }
  }

  grouping chassis-redundancy-type {
    uses apply-group;
    uses apply-macro;
    list routing-engine {
      key "name";
      uses chassis-rdd-re-type;
    }
    list ssb {
      key "name";
      uses chassis-rdd-id-type;
    }
    list cfeb {
      key "name";
      uses chassis-rdd-cfeb-id-type;
    }
    list sfm {
      key "name";
      uses chassis-rdd-sfm-id-type;
    }
    container failover {
      uses chassis-rdd-failover-type;
    }
    leaf keepalive-time {
      type uint32;
    }
    container graceful-switchover {
      presence "enable graceful-switchover";
      uses chassis-non-stop-forwarding-type;
    }
    container feb {
      uses apply-group;
      uses apply-macro;
      list redundancy-group {
        key "name";
        leaf name {
          type string;
        }
        uses apply-group;
        uses apply-macro;
        leaf description {
          type string;
        }
        list feb {
          key "name";
          leaf name {
            type string;
          }
          uses apply-group;
          uses apply-macro;
          choice choice-3 {
            leaf primary {
              type empty;
            }
            leaf backup {
              type empty;
            }
          }
        }
        leaf no-auto-failover {
          type empty;
        }
      }
    }
  }

  grouping chassis-non-stop-forwarding-type {
    uses apply-group;
    uses apply-macro;
  }

  grouping chassis-rdd-cfeb-id-type {
    leaf name {
      type string;
    }
    uses apply-group;
    uses apply-macro;
    choice choice-3 {
      leaf always {
        type empty;
      }
      leaf preferred {
        type empty;
      }
    }
  }

  grouping chassis-rdd-failover-type {
    uses apply-group;
    uses apply-macro;
    container category {
      presence "enable category";
      uses chassis_rdd_fail_cat_type;
    }
    leaf on-loss-of-keepalives {
      type empty;
    }
    leaf on-re-to-fpc-stale {
      type empty;
    }
    leaf on-disk-failure {
      type empty;
    }
    leaf not-on-disk-underperform {
      type empty;
    }
    leaf disk-read-threshold {
      type string;
    }
    leaf disk-write-threshold {
      type string;
    }
    leaf on-loss-of-vm-host-connection {
      type empty;
    }
  }

  grouping chassis_rdd_fail_cat_type {
    uses apply-advanced;
    container component-failure {
      presence "enable component-failure";
      uses chassis_rdd_fail_cat_sev_type;
    }
    container software-failure {
      presence "enable software-failure";
      uses chassis_rdd_fail_cat_sev_type;
    }
    container power-failure {
      presence "enable power-failure";
      uses chassis_rdd_fail_cat_sev_type;
    }
    container clock-failure {
      presence "enable clock-failure";
      uses chassis_rdd_fail_cat_sev_type;
    }
    container link-failure {
      presence "enable link-failure";
      uses chassis_rdd_fail_cat_sev_type;
    }
    container degraded-health {
      presence "enable degraded-health";
      uses chassis_rdd_fail_cat_sev_type;
    }
  }

  grouping chassis_rdd_fail_cat_sev_type {
    uses apply-advanced;
    container critical {
      presence "enable critical";
      uses chassis_rdd_fail_cat_sev_act_type;
    }
    container important {
      presence "enable important";
      uses chassis_rdd_fail_cat_sev_act_type;
    }
  }

  grouping chassis_rdd_fail_cat_sev_act_type {
    uses apply-advanced;
    leaf disable {
      type empty;
    }
  }

  grouping chassis-rdd-id-type {
    leaf name {
      type string;
    }
    uses apply-group;
    uses apply-macro;
    choice choice-3 {
      leaf always {
        type empty;
      }
      leaf preferred {
        type empty;
      }
    }
  }

  grouping chassis-rdd-re-type {
    leaf name {
      type string;
    }
    uses apply-group;
    uses apply-macro;
    choice choice-3 {
      leaf master {
        type empty;
      }
      leaf backup {
        type empty;
      }
      leaf disabled {
        type empty;
      }
    }
  }

  grouping chassis-rdd-sfm-id-type {
    leaf name {
      type string;
    }
    uses apply-group;
    uses apply-macro;
    choice choice-3 {
      leaf always {
        type empty;
      }
      leaf preferred {
        type empty;
      }
    }
  }

  grouping chassis-routing-engine-type {
    uses apply-group;
    uses apply-macro;
    container on-disk-failure {
      uses chassis-re-on-disk-failure;
    }
    container bios {
      uses apply-group;
      uses apply-macro;
      leaf no-auto-upgrade {
        type empty;
      }
    }
    container usb-wwan {
      presence "";
      uses apply-group;
      uses apply-macro;
      leaf port {
        type string;
      }
    }
    list red-group {
      key "name";
      ordered-by user;
      leaf name {
        type string;
      }
      uses apply-group;
      uses apply-macro;
      list re-member {
        key "name";
        leaf name {
          type string;
        }
        uses apply-group;
        uses apply-macro;
      }
    }
  }

  grouping chassis-re-on-disk-failure {
    uses apply-group;
    uses apply-macro;
    choice choice-3 {
      leaf disk-failure-action {
        type string;
      }
    }
  }

  grouping chassis-sfm-type {
    leaf name {
      type string;
    }
    uses apply-group;
    uses apply-macro;
    choice choice-3;
    leaf power {
      type string;
    }
    choice choice-6;
  }

  grouping chassis-sib-type {
    uses apply-group;
    uses apply-macro;
    leaf minimum {
      type uint32;
    }
  }

  grouping chassisd-redundancy-group-type {
    uses apply-group;
    uses apply-macro;
    container interface-type {
      uses apply-group;
      uses apply-macro;
      container redundant-logical-tunnel {
        uses apply-group;
        uses apply-macro;
        leaf device-count {
          type uint32;
        }
      }
      container redundant-virtual-tunnel {
        uses apply-group;
        uses apply-macro;
        leaf device-count {
          type uint32;
        }
      }
    }
  }

  grouping chassisd-agg-container-type {
    uses apply-group;
    uses apply-macro;
    leaf device-count {
      type uint32;
    }
  }

  grouping chassisd-agg-enet-type {
    uses apply-group;
    uses apply-macro;
    leaf device-count {
      type uint32;
    }
    container lacp {
      uses apply-group;
      uses apply-macro;
      leaf system-priority {
        type string;
      }
      container link-protection {
        presence "enable link-protection";
        uses apply-group;
        uses apply-macro;
        leaf non-revertive {
          type empty;
        }
      }
    }
  }

  grouping chassisd-agg-pos-type {
    uses apply-group;
    uses apply-macro;
    leaf device-count {
      type string;
    }
  }

  grouping chassisd-provider-instance-type {
    uses apply-group;
    uses apply-macro;
    leaf device-count {
      type uint32;
    }
  }

  grouping client-address-object {
    leaf name {
      type ipprefix;
    }
    uses apply-group;
    uses apply-macro;
    leaf restrict {
      type empty;
    }
  }

  grouping clients-object {
    leaf name {
      type key-attribute-string-type;
    }
    uses apply-group;
    uses apply-macro;
    list remote-protected-resources {
      key "name";
      ordered-by user;
      leaf name {
        type ipv4prefix-mandatory;
      }
    }
    list remote-exceptions {
      key "name";
      ordered-by user;
      leaf name {
        type ipv4prefix-mandatory;
      }
    }
    leaf ipsec-vpn {
      type string;
    }
    list user {
      key "name";
      leaf name {
        type string;
      }
    }
  }

  grouping collector-destinations-type {
    leaf name {
      type string;
    }
    uses apply-group;
    uses apply-macro;
    leaf password {
      type unreadable;
    }
  }

  grouping collector-transfer-log-archive-type {
    uses apply-group;
    uses apply-macro;
    leaf filename-prefix {
      type string;
    }
    leaf maximum-age {
      type uint32;
    }
    list archive-sites {
      key "name";
      ordered-by user;
      leaf name {
        type string;
      }
      leaf password {
        type unreadable;
      }
    }
  }

  grouping command-list-type {
    leaf name {
      type key-attribute-string-type;
    }
    uses apply-group;
    uses apply-macro;
    leaf-list value {
      ordered-by user;
      type string;
    }
  }

  grouping content-filtering-feature {
    uses apply-group;
    uses apply-macro;
    container traceoptions {
      uses content-filtering-traceoptions;
    }
    list profile {
      key "name";
      ordered-by user;
      leaf name {
        type key-attribute-string-type;
      }
      uses apply-group;
      uses apply-macro;
      leaf permit-command {
        type string;
      }
      leaf block-command {
        type string;
      }
      leaf block-extension {
        type string;
      }
      container block-mime {
        presence "enable block-mime";
        uses apply-group;
        uses apply-macro;
        leaf list {
          type string;
        }
        leaf exception {
          type string;
        }
      }
      container block-content-type {
        uses apply-group;
        uses apply-macro;
        leaf activex {
          type empty;
        }
        leaf java-applet {
          type empty;
        }
        leaf exe {
          type empty;
        }
        leaf zip {
          type empty;
        }
        leaf http-cookie {
          type empty;
        }
      }
      container notification-options {
        presence "enable notification-options";
        uses apply-group;
        uses apply-macro;
        leaf type {
          type string;
        }
        leaf notify-mail-sender {
          type empty;
        }
        leaf no-notify-mail-sender {
          type empty;
        }
        leaf custom-message {
          type string;
        }
      }
    }
  }

  grouping content-filtering-traceoptions {
    uses apply-group;
    uses apply-macro;
    list flag {
      key "name";
      ordered-by user;
      leaf name {
        type string;
      }
    }
  }

  grouping cos-application-profile-object {
    leaf name {
      type key-attribute-string-type;
    }
    uses apply-group;
    uses apply-macro;
    container sip {
      presence "enable sip";
      uses apply-group;
      uses apply-macro;
      container voice {
        presence "enable voice";
        uses apply-group;
        uses apply-macro;
        leaf dscp {
          type string;
        }
        leaf forwarding-class {
          type string;
        }
      }
      container video {
        presence "enable video";
        uses apply-group;
        uses apply-macro;
        leaf dscp {
          type string;
        }
        leaf forwarding-class {
          type string;
        }
      }
    }
    container ftp {
      presence "enable ftp";
      uses apply-group;
      uses apply-macro;
      container data {
        presence "enable data";
        uses apply-group;
        uses apply-macro;
        leaf dscp {
          type string;
        }
        leaf forwarding-class {
          type string;
        }
      }
    }
  }

  grouping cos-policer {
    leaf name {
      type string;
    }
    uses apply-group;
    uses apply-macro;
    container premium {
      presence "";
      uses ethernet-policer;
    }
    container aggregate {
      presence "";
      uses ethernet-policer;
    }
  }

  grouping cos-policer-input-priority-map {
    uses apply-group;
    uses apply-macro;
    container ieee-802.1p {
      uses apply-group;
      uses apply-macro;
      leaf-list premium {
        ordered-by user;
        type uint32;
      }
    }
  }

  grouping cos-policer-output-priority-map {
    uses apply-group;
    uses apply-macro;
    container classifier {
      uses apply-group;
      uses apply-macro;
      container premium {
        uses apply-group;
        uses apply-macro;
        list forwarding-class {
          key "name";
          ordered-by user;
          leaf name {
            type string;
          }
          uses apply-group;
          uses apply-macro;
          list loss-priority {
            key "name";
            ordered-by user;
            leaf name {
              type string;
            }
          }
        }
      }
    }
  }

  grouping cos-rule-object {
    leaf name {
      type key-attribute-string-type;
    }
    uses apply-group;
    uses apply-macro;
    leaf match-direction {
      type string;
    }
    list term {
      key "name";
      ordered-by user;
      leaf name {
        type key-attribute-string-type;
      }
      uses apply-group;
      uses apply-macro;
      container from {
        uses sfw-match-object;
      }
      container then {
        uses apply-group;
        uses apply-macro;
        leaf dscp {
          type string;
        }
        leaf forwarding-class {
          type string;
        }
        leaf application-profile {
          type string;
        }
        leaf syslog {
          type empty;
        }
        choice choice-11 {
          leaf reflexive {
            type empty;
          }
          leaf revert {
            type empty;
          }
          container reverse {
            presence "enable reverse";
            uses apply-group;
            uses apply-macro;
            leaf dscp {
              type string;
            }
            leaf forwarding-class {
              type string;
            }
            leaf application-profile {
              type string;
            }
            leaf syslog {
              type empty;
            }
          }
        }
      }
    }
  }

  grouping country {
    uses apply-group;
    uses apply-macro;
    choice choice-3 {
      leaf AE {
        type empty;
      }
      leaf AG {
        type empty;
      }
      leaf AN {
        type empty;
      }
      leaf AR {
        type empty;
      }
      leaf AS {
        type empty;
      }
      leaf AT {
        type empty;
      }
      leaf AU {
        type empty;
      }
      leaf AW {
        type empty;
      }
      leaf AZ {
        type empty;
      }
      leaf BA {
        type empty;
      }
      leaf BB {
        type empty;
      }
      leaf BD {
        type empty;
      }
      leaf BE {
        type empty;
      }
      leaf BG {
        type empty;
      }
      leaf BH {
        type empty;
      }
      leaf BM {
        type empty;
      }
      leaf BN {
        type empty;
      }
      leaf BO {
        type empty;
      }
      leaf BR {
        type empty;
      }
      leaf BS {
        type empty;
      }
      leaf BT {
        type empty;
      }
      leaf BY {
        type empty;
      }
      leaf CA {
        type empty;
      }
      leaf CH {
        type empty;
      }
      leaf CL {
        type empty;
      }
      leaf CN {
        type empty;
      }
      leaf CO {
        type empty;
      }
      leaf CR {
        type empty;
      }
      leaf CU {
        type empty;
      }
      leaf CV {
        type empty;
      }
      leaf CY {
        type empty;
      }
      leaf CZ {
        type empty;
      }
      leaf DE {
        type empty;
      }
      leaf DK {
        type empty;
      }
      leaf DM {
        type empty;
      }
      leaf DO {
        type empty;
      }
      leaf EC {
        type empty;
      }
      leaf EE {
        type empty;
      }
      leaf EG {
        type empty;
      }
      leaf ES {
        type empty;
      }
      leaf FI {
        type empty;
      }
      leaf FK {
        type empty;
      }
      leaf FM {
        type empty;
      }
      leaf FR {
        type empty;
      }
      leaf GB {
        type empty;
      }
      leaf GF {
        type empty;
      }
      leaf GG {
        type empty;
      }
      leaf GI {
        type empty;
      }
      leaf GP {
        type empty;
      }
      leaf GR {
        type empty;
      }
      leaf GT {
        type empty;
      }
      leaf GU {
        type empty;
      }
      leaf HK {
        type empty;
      }
      leaf HN {
        type empty;
      }
      leaf HR {
        type empty;
      }
      leaf HT {
        type empty;
      }
      leaf HU {
        type empty;
      }
      leaf ID {
        type empty;
      }
      leaf IE {
        type empty;
      }
      leaf IL {
        type empty;
      }
      leaf IM {
        type empty;
      }
      leaf IN {
        type empty;
      }
      leaf IR {
        type empty;
      }
      leaf IS {
        type empty;
      }
      leaf IT {
        type empty;
      }
      leaf JE {
        type empty;
      }
      leaf JM {
        type empty;
      }
      leaf JO {
        type empty;
      }
      leaf JP {
        type empty;
      }
      leaf KE {
        type empty;
      }
      leaf KI {
        type empty;
      }
      leaf KR {
        type empty;
      }
      leaf KW {
        type empty;
      }
      leaf KY {
        type empty;
      }
      leaf LA {
        type empty;
      }
      leaf LB {
        type empty;
      }
      leaf LI {
        type empty;
      }
      leaf LK {
        type empty;
      }
      leaf LS {
        type empty;
      }
      leaf LT {
        type empty;
      }
      leaf LU {
        type empty;
      }
      leaf LV {
        type empty;
      }
      leaf MA {
        type empty;
      }
      leaf MC {
        type empty;
      }
      leaf MK {
        type empty;
      }
      leaf MO {
        type empty;
      }
      leaf MP {
        type empty;
      }
      leaf MQ {
        type empty;
      }
      leaf MR {
        type empty;
      }
      leaf MT {
        type empty;
      }
      leaf MU {
        type empty;
      }
      leaf MV {
        type empty;
      }
      leaf MW {
        type empty;
      }
      leaf MX {
        type empty;
      }
      leaf MY {
        type empty;
      }
      leaf NG {
        type empty;
      }
      leaf NI {
        type empty;
      }
      leaf NL {
        type empty;
      }
      leaf NO {
        type empty;
      }
      leaf NZ {
        type empty;
      }
      leaf OM {
        type empty;
      }
      leaf PA {
        type empty;
      }
      leaf PE {
        type empty;
      }
      leaf PG {
        type empty;
      }
      leaf PH {
        type empty;
      }
      leaf PK {
        type empty;
      }
      leaf PL {
        type empty;
      }
      leaf PM {
        type empty;
      }
      leaf PR {
        type empty;
      }
      leaf PT {
        type empty;
      }
      leaf RE {
        type empty;
      }
      leaf RO {
        type empty;
      }
      leaf RU {
        type empty;
      }
      leaf SA {
        type empty;
      }
      leaf SE {
        type empty;
      }
      leaf SG {
        type empty;
      }
      leaf SI {
        type empty;
      }
      leaf SK {
        type empty;
      }
      leaf SV {
        type empty;
      }
      leaf SY {
        type empty;
      }
      leaf TH {
        type empty;
      }
      leaf TJ {
        type empty;
      }
      leaf TN {
        type empty;
      }
      leaf TR {
        type empty;
      }
      leaf TT {
        type empty;
      }
      leaf TW {
        type empty;
      }
      leaf TZ {
        type empty;
      }
      leaf UA {
        type empty;
      }
      leaf UM {
        type empty;
      }
      leaf US {
        type empty;
      }
      leaf UY {
        type empty;
      }
      leaf UZ {
        type empty;
      }
      leaf VA {
        type empty;
      }
      leaf VE {
        type empty;
      }
      leaf VG {
        type empty;
      }
      leaf VI {
        type empty;
      }
      leaf VN {
        type empty;
      }
      leaf YT {
        type empty;
      }
      leaf ZA {
        type empty;
      }
      leaf ZM {
        type empty;
      }
    }
  }

  grouping cpcd-rule-object-type {
    leaf name {
      type key-attribute-string-type;
    }
    uses apply-group;
    uses apply-macro;
    leaf match-direction {
      type string;
    }
    list term {
      key "name";
      ordered-by user;
      leaf name {
        type key-attribute-string-type;
      }
      uses apply-group;
      uses apply-macro;
      container from {
        uses cpcd-match-object-type;
      }
      container then {
        uses cpcd-action-object-type;
      }
    }
  }

  grouping cpcd-action-object-type {
    uses apply-group;
    uses apply-macro;
    choice choice-3 {
      leaf accept {
        type empty;
      }
      container rewrite {
        presence "enable rewrite";
        uses apply-group;
        uses apply-macro;
        leaf destination-address {
          type ipaddr;
        }
        leaf destination-port {
          type int32;
        }
      }
      container redirect {
        presence "";
        leaf url {
          type string;
          mandatory true;
        }
      }
    }
    leaf syslog {
      type empty;
    }
  }

  grouping cpcd-match-object-type {
    uses apply-group;
    uses apply-macro;
    list destination-address {
      key "name";
      ordered-by user;
      leaf name {
        type string;
      }
      leaf except {
        type empty;
      }
    }
    list destination-address-range {
      key "low high";
      ordered-by user;
      leaf low {
        type ipaddr;
      }
      leaf high {
        type ipaddr;
      }
      leaf except {
        type empty;
      }
    }
    list destination-prefix-list {
      key "name";
      ordered-by user;
      leaf name {
        type string;
      }
      leaf except {
        type empty;
      }
    }
    list applications {
      key "name";
      ordered-by user;
      leaf name {
        type key-attribute-string-type;
      }
      uses apply-group;
      uses apply-macro;
      leaf application-protocol {
        type string;
      }
      leaf protocol {
        type string;
      }
      leaf source-port {
        type string;
      }
      leaf destination-port {
        type string;
      }
    }
  }

  grouping cpcd-trace-options-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    list flag {
      key "name";
      ordered-by user;
      leaf name {
        type string;
      }
    }
  }

  grouping ct3-port-type {
    leaf name {
      type string;
    }
    uses apply-group;
    uses apply-macro;
    list t1 {
      key "name";
      uses ct3-channel-type;
    }
  }

  grouping ct3-channel-type {
    leaf name {
      type string;
    }
    uses apply-group;
    uses apply-macro;
    list channel-group {
      key "name";
      leaf name {
        type string;
      }
      leaf timeslots {
        type string;
      }
    }
  }

  grouping custom-attack-group-type {
    leaf name {
      type string;
    }
    uses apply-group;
    uses apply-macro;
    leaf-list group-members {
      type string;
      ordered-by user;
    }
  }

  grouping custom-attack-type {
    leaf name {
      type string;
    }
    uses apply-group;
    uses apply-macro;
    leaf recommended-action {
      type string;
    }
    leaf severity {
      type string;
    }
    container time-binding {
      leaf count {
        type uint32;
      }
      leaf scope {
        type string;
      }
    }
    container attack-type {
      uses apply-group;
      uses apply-macro;
      container signature {
        presence "";
        uses apply-group;
        uses apply-macro;
        container protocol-binding {
          uses apply-group;
          uses apply-macro;
          choice choice-3 {
            container tcp {
              presence "enable tcp";
              uses apply-group;
              uses apply-macro;
              list minimum-port {
                key "name";
                ordered-by user;
                uses port-range;
              }
            }
            container udp {
              presence "enable udp";
              uses apply-group;
              uses apply-macro;
              list minimum-port {
                key "name";
                ordered-by user;
                uses port-range;
              }
            }
            container rpc {
              presence "";
              uses apply-group;
              uses apply-macro;
              leaf program-number {
                type uint32;
              }
            }
            leaf icmp {
              type empty;
            }
            leaf icmpv6 {
              type empty;
            }
            container ip {
              presence "";
              uses apply-group;
              uses apply-macro;
              leaf protocol-number {
                type uint32;
              }
            }
            container ipv6 {
              presence "";
              uses apply-group;
              uses apply-macro;
              leaf protocol-number {
                type uint32;
              }
            }
            leaf application {
              type string;
            }
            leaf nested-application {
              type string;
            }
          }
        }
        leaf context {
          type string;
        }
        leaf pattern {
          type string;
        }
        leaf regexp {
          type string;
        }
        leaf negate {
          type empty;
        }
        leaf direction {
          type string;
        }
        leaf shellcode {
          type string;
        }
        container protocol {
          uses apply-group;
          uses apply-macro;
          container ipv4 {
            uses apply-group;
            uses apply-macro;
            container tos {
              presence "";
              leaf match {
                type string;
              }
              leaf value {
                type uint32;
              }
            }
            container total-length {
              presence "";
              leaf match {
                type string;
              }
              leaf value {
                type uint32;
              }
            }
            container identification {
              presence "";
              leaf match {
                type string;
              }
              leaf value {
                type uint32;
              }
            }
            container ip-flags {
              presence "enable ip-flags";
              leaf rb {
                type empty;
              }
              leaf no-rb {
                type empty;
              }
              leaf mf {
                type empty;
              }
              leaf no-mf {
                type empty;
              }
              leaf df {
                type empty;
              }
              leaf no-df {
                type empty;
              }
            }
            container ttl {
              presence "";
              leaf match {
                type string;
              }
              leaf value {
                type uint32;
              }
            }
            container protocol {
              presence "";
              leaf match {
                type string;
              }
              leaf value {
                type uint32;
              }
            }
            container source {
              presence "";
              leaf match {
                type string;
              }
              leaf value {
                type ipv4addr;
              }
            }
            container destination {
              presence "";
              leaf match {
                type string;
              }
              leaf value {
                type ipv4addr;
              }
            }
          }
          container ipv6 {
            uses apply-group;
            uses apply-macro;
            container traffic-class {
              presence "";
              leaf match {
                type string;
              }
              leaf value {
                type uint32;
              }
            }
            container payload-length {
              presence "";
              leaf match {
                type string;
              }
              leaf value {
                type uint32;
              }
            }
            container flow-label {
              presence "";
              leaf match {
                type string;
              }
              leaf value {
                type uint32;
              }
            }
            container hop-limit {
              presence "";
              leaf match {
                type string;
              }
              leaf value {
                type uint32;
              }
            }
            container next-header {
              presence "";
              leaf match {
                type string;
              }
              leaf value {
                type uint32;
              }
            }
            container source {
              presence "";
              leaf match {
                type string;
              }
              leaf value {
                type ipv6addr;
              }
            }
            container destination {
              presence "";
              leaf match {
                type string;
              }
              leaf value {
                type ipv6addr;
              }
            }
          }
          container tcp {
            uses apply-group;
            uses apply-macro;
            container source-port {
              presence "";
              leaf match {
                type string;
              }
              leaf value {
                type uint32;
              }
            }
            container destination-port {
              presence "";
              leaf match {
                type string;
              }
              leaf value {
                type uint32;
              }
            }
            container sequence-number {
              presence "";
              leaf match {
                type string;
              }
              leaf value {
                type uint32;
              }
            }
            container ack-number {
              presence "";
              leaf match {
                type string;
              }
              leaf value {
                type uint32;
              }
            }
            container header-length {
              presence "";
              leaf match {
                type string;
              }
              leaf value {
                type uint32;
              }
            }
            container window-size {
              presence "";
              leaf match {
                type string;
              }
              leaf value {
                type uint32;
              }
            }
            container urgent-pointer {
              presence "";
              leaf match {
                type string;
              }
              leaf value {
                type uint32;
              }
            }
            container tcp-flags {
              presence "enable tcp-flags";
              leaf r1 {
                type empty;
              }
              leaf no-r1 {
                type empty;
              }
              leaf r2 {
                type empty;
              }
              leaf no-r2 {
                type empty;
              }
              leaf urg {
                type empty;
              }
              leaf no-urg {
                type empty;
              }
              leaf ack {
                type empty;
              }
              leaf no-ack {
                type empty;
              }
              leaf psh {
                type empty;
              }
              leaf no-psh {
                type empty;
              }
              leaf rst {
                type empty;
              }
              leaf no-rst {
                type empty;
              }
              leaf syn {
                type empty;
              }
              leaf no-syn {
                type empty;
              }
              leaf fin {
                type empty;
              }
              leaf no-fin {
                type empty;
              }
            }
            container option {
              presence "";
              leaf match {
                type string;
              }
              leaf value {
                type uint32;
              }
            }
            container data-length {
              presence "";
              leaf match {
                type string;
              }
              leaf value {
                type uint32;
              }
            }
            container window-scale {
              presence "";
              leaf match {
                type string;
              }
              leaf value {
                type uint32;
              }
            }
            container mss {
              presence "";
              leaf match {
                type string;
              }
              leaf value {
                type uint32;
              }
            }
          }
          container udp {
            uses apply-group;
            uses apply-macro;
            container source-port {
              presence "";
              leaf match {
                type string;
              }
              leaf value {
                type uint32;
              }
            }
            container destination-port {
              presence "";
              leaf match {
                type string;
              }
              leaf value {
                type uint32;
              }
            }
            container data-length {
              presence "";
              leaf match {
                type string;
              }
              leaf value {
                type uint32;
              }
            }
          }
          container icmp {
            uses apply-group;
            uses apply-macro;
            container type {
              presence "";
              uses apply-group;
              uses apply-macro;
              leaf match {
                type string;
              }
              leaf value {
                type uint32;
              }
            }
            container code {
              presence "";
              leaf match {
                type string;
              }
              leaf value {
                type uint32;
              }
            }
            container identification {
              presence "";
              leaf match {
                type string;
              }
              leaf value {
                type uint32;
              }
            }
            container sequence-number {
              presence "";
              leaf match {
                type string;
              }
              leaf value {
                type uint32;
              }
            }
            container data-length {
              presence "";
              leaf match {
                type string;
              }
              leaf value {
                type uint32;
              }
            }
          }
          container icmpv6 {
            uses apply-group;
            uses apply-macro;
            container type {
              presence "";
              uses apply-group;
              uses apply-macro;
              leaf match {
                type string;
              }
              leaf value {
                type uint32;
              }
            }
            container code {
              presence "";
              leaf match {
                type string;
              }
              leaf value {
                type uint32;
              }
            }
            container identification {
              presence "";
              leaf match {
                type string;
              }
              leaf value {
                type uint32;
              }
            }
            container sequence-number {
              presence "";
              leaf match {
                type string;
              }
              leaf value {
                type uint32;
              }
            }
            container data-length {
              presence "";
              leaf match {
                type string;
              }
              leaf value {
                type uint32;
              }
            }
          }
        }
      }
      container anomaly {
        presence "";
        uses apply-group;
        uses apply-macro;
        leaf service {
          type string;
        }
        leaf test {
          type string;
        }
        leaf direction {
          type string;
        }
        leaf shellcode {
          type string;
        }
      }
      container chain {
        presence "";
        uses apply-group;
        uses apply-macro;
        container protocol-binding {
          uses apply-group;
          uses apply-macro;
          choice choice-3 {
            container tcp {
              presence "enable tcp";
              uses apply-group;
              uses apply-macro;
              list minimum-port {
                key "name";
                ordered-by user;
                uses port-range;
              }
            }
            container udp {
              presence "enable udp";
              uses apply-group;
              uses apply-macro;
              list minimum-port {
                key "name";
                ordered-by user;
                uses port-range;
              }
            }
            container rpc {
              presence "";
              uses apply-group;
              uses apply-macro;
              leaf program-number {
                type uint32;
              }
            }
            leaf icmp {
              type empty;
            }
            leaf icmpv6 {
              type empty;
            }
            container ip {
              presence "";
              uses apply-group;
              uses apply-macro;
              leaf protocol-number {
                type uint32;
              }
            }
            container ipv6 {
              presence "";
              uses apply-group;
              uses apply-macro;
              leaf protocol-number {
                type uint32;
              }
            }
            leaf application {
              type string;
            }
            leaf nested-application {
              type string;
            }
          }
        }
        leaf scope {
          type string;
        }
        leaf order {
          type empty;
        }
        leaf reset {
          type empty;
        }
        leaf expression {
          type string;
        }
        list member {
          key "name";
          ordered-by user;
          uses chain-member-type;
        }
      }
    }
  }

  grouping chain-member-type {
    leaf name {
      type string;
    }
    uses apply-group;
    uses apply-macro;
    container attack-type {
      presence "enable attack-type";
      uses apply-group;
      uses apply-macro;
      container signature {
        presence "";
        uses apply-group;
        uses apply-macro;
        leaf context {
          type string;
        }
        leaf pattern {
          type string;
        }
        leaf regexp {
          type string;
        }
        leaf negate {
          type empty;
        }
        leaf direction {
          type string;
        }
        leaf shellcode {
          type string;
        }
        container protocol {
          uses apply-group;
          uses apply-macro;
          container ipv4 {
            uses apply-group;
            uses apply-macro;
            container tos {
              presence "";
              leaf match {
                type string;
              }
              leaf value {
                type uint32;
              }
            }
            container total-length {
              presence "";
              leaf match {
                type string;
              }
              leaf value {
                type uint32;
              }
            }
            container identification {
              presence "";
              leaf match {
                type string;
              }
              leaf value {
                type uint32;
              }
            }
            container ip-flags {
              presence "enable ip-flags";
              leaf rb {
                type empty;
              }
              leaf no-rb {
                type empty;
              }
              leaf mf {
                type empty;
              }
              leaf no-mf {
                type empty;
              }
              leaf df {
                type empty;
              }
              leaf no-df {
                type empty;
              }
            }
            container ttl {
              presence "";
              leaf match {
                type string;
              }
              leaf value {
                type uint32;
              }
            }
            container protocol {
              presence "";
              leaf match {
                type string;
              }
              leaf value {
                type uint32;
              }
            }
            container source {
              presence "";
              leaf match {
                type string;
              }
              leaf value {
                type ipv4addr;
              }
            }
            container destination {
              presence "";
              leaf match {
                type string;
              }
              leaf value {
                type ipv4addr;
              }
            }
          }
          container ipv6 {
            uses apply-group;
            uses apply-macro;
            container traffic-class {
              presence "";
              leaf match {
                type string;
              }
              leaf value {
                type uint32;
              }
            }
            container payload-length {
              presence "";
              leaf match {
                type string;
              }
              leaf value {
                type uint32;
              }
            }
            container flow-label {
              presence "";
              leaf match {
                type string;
              }
              leaf value {
                type uint32;
              }
            }
            container hop-limit {
              presence "";
              leaf match {
                type string;
              }
              leaf value {
                type uint32;
              }
            }
            container next-header {
              presence "";
              leaf match {
                type string;
              }
              leaf value {
                type uint32;
              }
            }
            container source {
              presence "";
              leaf match {
                type string;
              }
              leaf value {
                type ipv6addr;
              }
            }
            container destination {
              presence "";
              leaf match {
                type string;
              }
              leaf value {
                type ipv6addr;
              }
            }
          }
          container tcp {
            uses apply-group;
            uses apply-macro;
            container source-port {
              presence "";
              leaf match {
                type string;
              }
              leaf value {
                type uint32;
              }
            }
            container destination-port {
              presence "";
              leaf match {
                type string;
              }
              leaf value {
                type uint32;
              }
            }
            container sequence-number {
              presence "";
              leaf match {
                type string;
              }
              leaf value {
                type uint32;
              }
            }
            container ack-number {
              presence "";
              leaf match {
                type string;
              }
              leaf value {
                type uint32;
              }
            }
            container header-length {
              presence "";
              leaf match {
                type string;
              }
              leaf value {
                type uint32;
              }
            }
            container window-size {
              presence "";
              leaf match {
                type string;
              }
              leaf value {
                type uint32;
              }
            }
            container urgent-pointer {
              presence "";
              leaf match {
                type string;
              }
              leaf value {
                type uint32;
              }
            }
            container tcp-flags {
              presence "enable tcp-flags";
              leaf r1 {
                type empty;
              }
              leaf no-r1 {
                type empty;
              }
              leaf r2 {
                type empty;
              }
              leaf no-r2 {
                type empty;
              }
              leaf urg {
                type empty;
              }
              leaf no-urg {
                type empty;
              }
              leaf ack {
                type empty;
              }
              leaf no-ack {
                type empty;
              }
              leaf psh {
                type empty;
              }
              leaf no-psh {
                type empty;
              }
              leaf rst {
                type empty;
              }
              leaf no-rst {
                type empty;
              }
              leaf syn {
                type empty;
              }
              leaf no-syn {
                type empty;
              }
              leaf fin {
                type empty;
              }
              leaf no-fin {
                type empty;
              }
            }
            container option {
              presence "";
              leaf match {
                type string;
              }
              leaf value {
                type uint32;
              }
            }
            container data-length {
              presence "";
              leaf match {
                type string;
              }
              leaf value {
                type uint32;
              }
            }
            container window-scale {
              presence "";
              leaf match {
                type string;
              }
              leaf value {
                type uint32;
              }
            }
            container mss {
              presence "";
              leaf match {
                type string;
              }
              leaf value {
                type uint32;
              }
            }
          }
          container udp {
            uses apply-group;
            uses apply-macro;
            container source-port {
              presence "";
              leaf match {
                type string;
              }
              leaf value {
                type uint32;
              }
            }
            container destination-port {
              presence "";
              leaf match {
                type string;
              }
              leaf value {
                type uint32;
              }
            }
            container data-length {
              presence "";
              leaf match {
                type string;
              }
              leaf value {
                type uint32;
              }
            }
          }
          container icmp {
            uses apply-group;
            uses apply-macro;
            container type {
              presence "";
              uses apply-group;
              uses apply-macro;
              leaf match {
                type string;
              }
              leaf value {
                type uint32;
              }
            }
            container code {
              presence "";
              leaf match {
                type string;
              }
              leaf value {
                type uint32;
              }
            }
            container identification {
              presence "";
              leaf match {
                type string;
              }
              leaf value {
                type uint32;
              }
            }
            container sequence-number {
              presence "";
              leaf match {
                type string;
              }
              leaf value {
                type uint32;
              }
            }
            container data-length {
              presence "";
              leaf match {
                type string;
              }
              leaf value {
                type uint32;
              }
            }
          }
          container icmpv6 {
            uses apply-group;
            uses apply-macro;
            container type {
              presence "";
              uses apply-group;
              uses apply-macro;
              leaf match {
                type string;
              }
              leaf value {
                type uint32;
              }
            }
            container code {
              presence "";
              leaf match {
                type string;
              }
              leaf value {
                type uint32;
              }
            }
            container identification {
              presence "";
              leaf match {
                type string;
              }
              leaf value {
                type uint32;
              }
            }
            container sequence-number {
              presence "";
              leaf match {
                type string;
              }
              leaf value {
                type uint32;
              }
            }
            container data-length {
              presence "";
              leaf match {
                type string;
              }
              leaf value {
                type uint32;
              }
            }
          }
        }
      }
      container anomaly {
        presence "";
        uses apply-group;
        uses apply-macro;
        leaf test {
          type string;
        }
        leaf direction {
          type string;
        }
        leaf shellcode {
          type string;
        }
      }
    }
  }

  grouping dcd-rx-bucket-config {
    uses apply-group;
    uses apply-macro;
    leaf overflow {
      type string;
    }
    leaf rate {
      type uint32;
    }
    leaf threshold {
      type uint32;
    }
  }

  grouping dcd-shaping-config {
    uses apply-group;
    uses apply-macro;
    choice choice-3 {
      container cbr {
        presence "";
        leaf cbr-value {
          type string;
        }
        leaf cdvt {
          type uint32;
        }
      }
      container vbr {
        presence "";
        leaf peak {
          type string;
        }
        leaf sustained {
          type string;
        }
        leaf burst {
          type string;
        }
        leaf cdvt {
          type uint32;
        }
      }
      container rtvbr {
        presence "";
        leaf peak {
          type string;
        }
        leaf sustained {
          type string;
        }
        leaf burst {
          type string;
        }
        leaf cdvt {
          type uint32;
        }
      }
    }
    leaf queue-length {
      type uint32;
    }
  }

  grouping dcd-tx-bucket-config {
    uses apply-group;
    uses apply-macro;
    leaf overflow {
      type string;
    }
    leaf rate {
      type uint32;
    }
    leaf threshold {
      type uint32;
    }
  }

  grouping demux-options-type {
    uses apply-group;
    uses apply-macro;
    leaf underlying-interface {
      type string;
    }
  }

  grouping dfc-group-type {
    leaf name {
      type key-attribute-string-type;
    }
    uses apply-group;
    uses apply-macro;
    leaf-list interfaces {
      type interface-device;
      ordered-by user;
    }
    leaf input-packet-rate-threshold {
      type string;
    }
    leaf max-duplicates {
      type uint32;
    }
    leaf duplicates-dropped-periodicity {
      type uint32;
    }
    container pic-memory-threshold {
      leaf percentage {
        type uint32;
      }
    }
    list control-source {
      key "name";
      ordered-by user;
      uses dfc-control-source-type;
    }
    list content-destination {
      key "name";
      ordered-by user;
      uses content-destination-type;
    }
  }

  grouping content-destination-type {
    leaf name {
      type key-attribute-string-type;
    }
    uses apply-group;
    uses apply-macro;
    leaf address {
      type ipv4addr;
    }
    leaf ttl {
      type uint32;
    }
    leaf soft-limit-clear {
      type string;
    }
    leaf soft-limit {
      type string;
    }
    leaf hard-limit-target {
      type string;
    }
    leaf hard-limit {
      type string;
    }
  }

  grouping dfc-control-source-type {
    leaf name {
      type key-attribute-string-type;
    }
    uses apply-group;
    uses apply-macro;
    leaf-list source-addresses {
      type ipv4addr;
      ordered-by user;
    }
    leaf service-port {
      type uint16;
    }
    list notification-targets {
      key "name";
      uses dfc-notification-target-type;
    }
    leaf no-syslog {
      type empty;
    }
    leaf shared-key {
      type string;
    }
    leaf-list allowed-destinations {
      ordered-by user;
      type string;
    }
    leaf minimum-priority {
      type uint32;
    }
  }

  grouping dfc-notification-target-type {
    leaf name {
      type ipv4addr;
    }
    uses apply-group;
    uses apply-macro;
    leaf port {
      type uint16;
    }
  }

  grouping drop-policy-term {
    leaf name {
      type string;
    }
    uses apply-advanced;
    container from {
      uses apply-advanced;
      container source-address {
        presence "enable source-address";
        uses li_policy_addr_simple_object;
      }
      container destination-address {
        presence "enable destination-address";
        uses li_policy_addr_simple_object;
      }
      choice source-port_choice {
        case case_1 {
          container source-port {
            uses match_li_simple_port_value;
          }
        }
      }
      choice destination-port_choice {
        case case_1 {
          container destination-port {
            uses match_li_simple_port_value;
          }
        }
      }
      choice protocol_choice {
        case case_1 {
          container protocol {
            uses match_li_simple_protocol_value;
          }
        }
      }
      choice dscp_choice {
        case case_1 {
          container dscp {
            uses match_li_simple_dscp_value;
          }
        }
      }
    }
  }

  grouping drop-policy6-term {
    leaf name {
      type string;
    }
    uses apply-advanced;
    container from {
      uses apply-advanced;
      container source-address {
        presence "enable source-address";
        uses li_policy_addr6_simple_object;
      }
      container destination-address {
        presence "enable destination-address";
        uses li_policy_addr6_simple_object;
      }
      choice source-port_choice {
        case case_1 {
          container source-port {
            uses match_li_simple_port_value;
          }
        }
      }
      choice destination-port_choice {
        case case_1 {
          container destination-port {
            uses match_li_simple_port_value;
          }
        }
      }
      choice protocol_choice {
        case case_1 {
          container protocol {
            uses match_li_simple_protocol_value;
          }
        }
      }
      choice dscp_choice {
        case case_1 {
          container dscp {
            uses match_li_simple_dscp_value;
          }
        }
      }
    }
  }

  grouping match_li_simple_dscp_value {
    uses apply-advanced;
    leaf value_keyword {
      type string;
    }
  }

  grouping match_li_simple_port_value {
    uses apply-advanced;
    leaf value_keyword {
      type string;
    }
  }

  grouping match_li_simple_protocol_value {
    uses apply-advanced;
    leaf value_keyword {
      type string;
    }
  }

  grouping li_policy_addr6_simple_object {
    uses apply-advanced;
    leaf address {
      type ipv6prefix;
    }
  }

  grouping li_policy_addr_simple_object {
    uses apply-advanced;
    leaf address {
      type ipv4prefix;
    }
  }

  grouping dhcp-client-type {
    uses apply-group;
    uses apply-macro;
    container client-identifier {
      uses apply-group;
      uses apply-macro;
      choice choice-ascii {
        leaf ascii {
          type string;
        }
        leaf hexadecimal {
          type string;
        }
      }
      container user-id {
        choice choice-ascii {
          leaf ascii {
            type string;
          }
          leaf hexadecimal {
            type string;
          }
        }
      }
      container prefix {
        uses apply-group;
        uses apply-macro;
        leaf host-name {
          type empty;
        }
        leaf logical-system-name {
          type empty;
        }
        leaf routing-instance-name {
          type empty;
        }
      }
      leaf use-interface-description {
        type string;
      }
    }
    container no-dns-install {
      presence "enable no-dns-install";
      uses apply-group;
      uses apply-macro;
    }
    leaf lease-time {
      units "seconds";
      type string;
    }
    leaf retransmission-attempt {
      type uint32;
    }
    leaf retransmission-interval {
      units "seconds";
      type uint32;
    }
    leaf metric {
      type uint32;
    }
    leaf server-address {
      type ipv4addr;
    }
    leaf update-server {
      type empty;
    }
    leaf vendor-id {
      type string;
    }
    leaf force-discover {
      type empty;
    }
    container options {
      uses apply-group;
      uses apply-macro;
      list number {
        key "name";
        leaf name {
          type string;
        }
        choice option-type-choice {
          case case_1 {
            leaf hex-string {
              type string;
            }
          }
        }
      }
      leaf no-hostname {
        type empty;
      }
    }
    list requested-options {
      key "name";
      leaf name {
        type string;
      }
    }
  }

  grouping dslite-object {
    leaf name {
      type key-attribute-string-type;
    }
    uses apply-group;
    uses apply-macro;
    leaf softwire-address {
      type ipv6addr;
    }
    leaf mtu-v6 {
      type uint32;
    }
    leaf auto-update-mtu {
      type empty;
    }
    leaf flow-limit {
      type uint32;
    }
  }

  grouping dynamic-attack-group-type {
    leaf name {
      type string;
    }
    uses apply-group;
    uses apply-macro;
    container filters {
      uses apply-group;
      uses apply-macro;
      container direction {
        presence "";
        uses apply-group;
        uses apply-macro;
        leaf expression {
          type string;
        }
        leaf-list values {
          ordered-by user;
          type string;
        }
      }
      container severity {
        presence "";
        uses apply-group;
        uses apply-macro;
        leaf-list values {
          ordered-by user;
          type string;
        }
      }
      container type {
        presence "";
        uses apply-group;
        uses apply-macro;
        leaf-list values {
          ordered-by user;
          type string;
        }
      }
      leaf recommended {
        type empty;
      }
      container performance {
        presence "";
        uses apply-group;
        uses apply-macro;
        leaf-list values {
          ordered-by user;
          type string;
        }
      }
      container category {
        presence "";
        uses apply-group;
        uses apply-macro;
        leaf-list values {
          type string;
          ordered-by user;
        }
      }
      container service {
        presence "";
        uses apply-group;
        uses apply-macro;
        leaf-list values {
          type string;
          ordered-by user;
        }
      }
      container false-positives {
        presence "";
        uses apply-group;
        uses apply-macro;
        leaf-list values {
          ordered-by user;
          type string;
        }
      }
      container products {
        presence "";
        uses apply-group;
        uses apply-macro;
        leaf-list values {
          type string;
          ordered-by user;
        }
      }
    }
  }

  grouping dynamic-ifbw-parms-type {
    uses apply-group;
    uses apply-macro;
    leaf bandwidth {
      type uint32;
    }
    leaf resource {
      type uint32;
    }
    leaf latency {
      type uint32;
    }
    leaf quality {
      type uint32;
    }
    leaf data-rate {
      type uint32;
    }
    leaf threshold {
      type uint32;
    }
    container credit {
      presence "enable credit";
      uses apply-group;
      uses apply-macro;
      leaf interval {
        type uint16;
      }
    }
  }

  grouping dynamic-ipv4-type {
    uses apply-group;
    uses apply-macro;
    container address-ranges {
      presence "";
      uses apply-group;
      uses apply-macro;
      list dynamic-profile {
        key "name";
        ordered-by user;
        leaf name {
          type string;
        }
        uses apply-group;
        uses apply-macro;
        list network {
          key "name";
          ordered-by user;
          leaf name {
            type ipv4prefix;
          }
          uses apply-group;
          uses apply-macro;
          list range {
            key "name";
            ordered-by user;
            leaf name {
              type string;
            }
            uses apply-group;
            uses apply-macro;
            leaf low {
              mandatory true;
              type ipv4prefix;
            }
            leaf high {
              mandatory true;
              type ipv4prefix;
            }
          }
        }
      }
      container authentication {
        uses dynamic-ip-authentication-type;
      }
    }
  }

  grouping dynamic-ip-authentication-type {
    uses apply-group;
    uses apply-macro;
    leaf password {
      type string;
    }
    container username-include {
      uses apply-group;
      uses apply-macro;
      leaf delimiter {
        type string;
      }
      leaf domain-name {
        type string;
      }
      leaf user-prefix {
        type string;
      }
      leaf auth-server-realm {
        type string;
      }
      leaf interface-name {
        type empty;
      }
      leaf source-address {
        type empty;
      }
    }
  }

  grouping dynamic-ipv6-type {
    uses apply-group;
    uses apply-macro;
    container prefix-ranges {
      presence "";
      uses apply-group;
      uses apply-macro;
      list dynamic-profile {
        key "name";
        ordered-by user;
        leaf name {
          type string;
        }
        uses apply-group;
        uses apply-macro;
        list prefix {
          key "name";
          ordered-by user;
          leaf name {
            type ipv6prefix;
          }
          uses apply-group;
          uses apply-macro;
          list range {
            key "name";
            ordered-by user;
            leaf name {
              type string;
            }
            uses apply-group;
            uses apply-macro;
            leaf low {
              mandatory true;
              type ipv6prefix;
            }
            leaf high {
              mandatory true;
              type ipv6prefix;
            }
          }
        }
      }
      container authentication {
        uses dynamic-ip-authentication-type;
      }
    }
  }

  grouping e2e-action-profile {
    leaf name {
      type key-attribute-string-type;
    }
    uses apply-group;
    uses apply-macro;
    leaf preserve-trace-order {
      type empty;
    }
    leaf record-pic-history {
      type empty;
    }
    list event {
      key "name";
      ordered-by user;
      uses e2e-event;
    }
    list module {
      key "name";
      ordered-by user;
      uses e2e-module;
    }
  }

  grouping e2e-event {
    leaf name {
      type string;
    }
    uses apply-group;
    uses apply-macro;
    leaf trace {
      type empty;
    }
    leaf count {
      type empty;
    }
    leaf packet-summary {
      type empty;
    }
    leaf packet-dump {
      type empty;
    }
  }

  grouping e2e-module {
    leaf name {
      type string;
    }
    uses apply-group;
    uses apply-macro;
    list flag {
      key "name";
      ordered-by user;
      leaf name {
        type string;
      }
    }
  }

  grouping end-to-end-debug-filter {
    leaf name {
      type key-attribute-string-type;
    }
    uses apply-group;
    uses apply-macro;
    leaf action-profile {
      type string;
    }
    leaf protocol {
      type string;
    }
    leaf source-prefix {
      type ipprefix;
    }
    leaf destination-prefix {
      type ipprefix;
    }
    leaf source-port {
      type string;
    }
    leaf destination-port {
      type string;
    }
    leaf interface {
      type interface-name;
    }
  }

  grouping epd-threshold-config {
    uses apply-group;
    uses apply-macro;
    leaf epd-threshold-plp0 {
      type string;
    }
    leaf plp1 {
      type string;
    }
  }

  grouping es-filter {
    leaf name {
      type string;
    }
    uses apply-group;
    uses apply-macro;
    leaf interface-specific {
      type empty;
    }
    leaf physical-interface-filter {
      type empty;
    }
    list term {
      key "name";
      ordered-by user;
      leaf name {
        type string;
      }
      uses apply-group;
      uses apply-macro;
      container from {
        uses apply-group;
        uses apply-macro;
        list interface {
          key "name";
          ordered-by user;
          uses match-interface-object;
        }
        list source-mac-address {
          key "name";
          ordered-by user;
          uses firewall-mac-addr-object;
        }
        list destination-mac-address {
          key "name";
          ordered-by user;
          uses firewall-mac-addr-object;
        }
        choice choice-9 {
          leaf-list ether-type {
            ordered-by user;
            type string;
          }
          leaf-list ether-type-except {
            ordered-by user;
            type string;
          }
        }
        choice choice-l2-encap-type {
          leaf-list l2-encap-type {
            ordered-by user;
            type string;
          }
          leaf-list l2-encap-type-except {
            ordered-by user;
            type string;
          }
        }
        choice choice-10 {
          leaf-list vlan {
            type string;
            ordered-by user;
          }
          leaf-list vlan-except {
            type string;
            ordered-by user;
          }
        }
        choice choice-11 {
          leaf-list dot1q-tag {
            type string;
            ordered-by user;
          }
          leaf-list dot1q-tag-except {
            type string;
            ordered-by user;
          }
        }
        choice choice-12 {
          leaf-list dot1q-user-priority {
            ordered-by user;
            type string;
          }
          leaf-list dot1q-user-priority-except {
            ordered-by user;
            type string;
          }
        }
        list address {
          key "name";
          ordered-by user;
          uses firewall-addr-object;
        }
        list source-address {
          key "name";
          ordered-by user;
          uses firewall-addr-object;
        }
        list destination-address {
          key "name";
          ordered-by user;
          uses firewall-addr-object;
        }
        choice choice-19 {
          leaf-list dscp {
            ordered-by user;
            type string;
          }
          leaf-list dscp-except {
            ordered-by user;
            type string;
          }
        }
        choice choice-20 {
          leaf-list precedence {
            ordered-by user;
            type string;
          }
          leaf-list precedence-except {
            ordered-by user;
            type string;
          }
        }
        choice choice-21 {
          leaf-list ip-options {
            ordered-by user;
            type string;
          }
          leaf-list ip-options-except {
            ordered-by user;
            type string;
          }
        }
        leaf fragment-flags {
          type string;
        }
        leaf is-fragment {
          type empty;
        }
        choice choice-26 {
          leaf-list protocol {
            ordered-by user;
            type string;
          }
          leaf-list protocol-except {
            ordered-by user;
            type string;
          }
        }
        choice choice-27 {
          leaf-list source-port {
            ordered-by user;
            type string;
          }
          leaf-list source-port-except {
            ordered-by user;
            type string;
          }
        }
        choice choice-28 {
          leaf-list destination-port {
            ordered-by user;
            type string;
          }
          leaf-list destination-port-except {
            ordered-by user;
            type string;
          }
        }
        choice choice-29 {
          leaf-list port {
            ordered-by user;
            type string;
          }
          leaf-list port-except {
            ordered-by user;
            type string;
          }
        }
        leaf tcp-flags {
          type string;
        }
        leaf tcp-initial {
          type empty;
        }
        leaf tcp-established {
          type empty;
        }
        choice choice-36 {
          leaf-list icmp-type {
            ordered-by user;
            type string;
          }
          leaf-list icmp-type-except {
            ordered-by user;
            type string;
          }
        }
        choice choice-37 {
          leaf-list icmp-code {
            ordered-by user;
            type string;
          }
          leaf-list icmp-code-except {
            ordered-by user;
            type string;
          }
        }
        list source-prefix-list {
          key "name";
          ordered-by user;
          uses firewall-prefix-list;
        }
        list destination-prefix-list {
          key "name";
          ordered-by user;
          uses firewall-prefix-list;
        }
        list ip-source-address {
          key "name";
          ordered-by user;
          uses firewall-addr-object;
        }
        list ip-destination-address {
          key "name";
          ordered-by user;
          uses firewall-addr-object;
        }
        choice choice-ip-protocol {
          leaf-list ip-protocol {
            ordered-by user;
            type string;
          }
          leaf-list ip-protocol-except {
            ordered-by user;
            type string;
          }
        }
        choice choice-ip-precedence {
          leaf-list ip-precedence {
            ordered-by user;
            type string;
          }
          leaf-list ip-precedence-except {
            ordered-by user;
            type string;
          }
        }
        choice choice-interface-group {
          leaf-list interface-group {
            type string;
            ordered-by user;
          }
          leaf-list interface-group-except {
            type string;
            ordered-by user;
          }
        }
        choice choice-vlan-ether-type {
          leaf-list vlan-ether-type {
            ordered-by user;
            type string;
          }
          leaf-list vlan-ether-type-except {
            ordered-by user;
            type string;
          }
        }
        choice choice-loss-priority {
          leaf-list loss-priority {
            ordered-by user;
            type string;
          }
          leaf-list loss-priority-except {
            ordered-by user;
            type string;
          }
        }
        choice choice-learn-vlan-id {
          leaf-list learn-vlan-id {
            type string;
            ordered-by user;
          }
          leaf-list learn-vlan-id-except {
            type string;
            ordered-by user;
          }
        }
        choice choice-learn-vlan-1p-priority {
          leaf-list learn-vlan-1p-priority {
            type uint32;
            ordered-by user;
          }
          leaf-list learn-vlan-1p-priority-except {
            type uint32;
            ordered-by user;
          }
        }
        choice choice-user-vlan-id {
          leaf-list user-vlan-id {
            type string;
            ordered-by user;
          }
          leaf-list user-vlan-id-except {
            type string;
            ordered-by user;
          }
        }
        choice choice-user-vlan-1p-priority {
          leaf-list user-vlan-1p-priority {
            type uint32;
            ordered-by user;
          }
          leaf-list user-vlan-1p-priority-except {
            type uint32;
            ordered-by user;
          }
        }
        choice choice-learn-vlan-dei {
          leaf-list learn-vlan-dei {
            type uint32;
            ordered-by user;
          }
          leaf-list learn-vlan-dei-except {
            type uint32;
            ordered-by user;
          }
        }
        choice choice-traffic-type {
          leaf-list traffic-type {
            ordered-by user;
            type string;
          }
          leaf-list traffic-type-except {
            ordered-by user;
            type string;
          }
        }
        list ip-address {
          key "name";
          ordered-by user;
          uses firewall-addr-object;
        }
        list interface-set {
          key "name";
          ordered-by user;
          uses match-interface-set-object;
        }
        list prefix-list {
          key "name";
          ordered-by user;
          uses firewall-prefix-list;
        }
        choice choice-isid {
          leaf-list isid {
            type string;
            ordered-by user;
          }
          leaf-list isid-except {
            type string;
            ordered-by user;
          }
        }
        choice choice-isid-priority-code-point {
          leaf-list isid-priority-code-point {
            type uint32;
            ordered-by user;
          }
          leaf-list isid-priority-code-point-except {
            type uint32;
            ordered-by user;
          }
        }
        choice choice-isid-dei {
          leaf-list isid-dei {
            type uint32;
            ordered-by user;
          }
          leaf-list isid-dei-except {
            type uint32;
            ordered-by user;
          }
        }
        choice choice-forwarding-class {
          leaf-list forwarding-class {
            type string;
            ordered-by user;
          }
          leaf-list forwarding-class-except {
            type string;
            ordered-by user;
          }
        }
        container to-fabric {
          presence "enable to-fabric";
          uses to-fabric-object;
        }
        leaf from-fabric {
          type empty;
        }
        leaf-list arp-type {
          ordered-by user;
          type string;
        }
        container flexible-match-mask {
          presence "";
          uses match-L2-flexible-mask;
        }
        container flexible-match-range {
          presence "enable flexible-match-range";
          uses match-L2-flexible-range;
        }
        container ip-version {
          uses apply-group;
          uses apply-macro;
          container ipv4 {
            uses apply-group;
            uses apply-macro;
            list address {
              key "name";
              ordered-by user;
              uses firewall-addr-object;
            }
            list source-address {
              key "name";
              ordered-by user;
              uses firewall-addr-object;
            }
            list destination-address {
              key "name";
              ordered-by user;
              uses firewall-addr-object;
            }
            choice choice-dscp {
              leaf-list dscp {
                ordered-by user;
                type string;
              }
              leaf-list dscp-except {
                ordered-by user;
                type string;
              }
            }
            choice choice-precedence {
              leaf-list precedence {
                ordered-by user;
                type string;
              }
              leaf-list precedence-except {
                ordered-by user;
                type string;
              }
            }
            choice choice-ip-options {
              leaf-list ip-options {
                ordered-by user;
                type string;
              }
              leaf-list ip-options-except {
                ordered-by user;
                type string;
              }
            }
            leaf fragment-flags {
              type string;
            }
            leaf is-fragment {
              type empty;
            }
            choice choice-protocol {
              leaf-list protocol {
                ordered-by user;
                type string;
              }
              leaf-list protocol-except {
                ordered-by user;
                type string;
              }
            }
            choice choice-source-port {
              leaf-list source-port {
                ordered-by user;
                type string;
              }
              leaf-list source-port-except {
                ordered-by user;
                type string;
              }
            }
            choice choice-destination-port {
              leaf-list destination-port {
                ordered-by user;
                type string;
              }
              leaf-list destination-port-except {
                ordered-by user;
                type string;
              }
            }
            choice choice-port {
              leaf-list port {
                ordered-by user;
                type string;
              }
              leaf-list port-except {
                ordered-by user;
                type string;
              }
            }
            leaf tcp-flags {
              type string;
            }
            leaf tcp-initial {
              type empty;
            }
            leaf tcp-established {
              type empty;
            }
            choice choice-icmp-type {
              leaf-list icmp-type {
                ordered-by user;
                type string;
              }
              leaf-list icmp-type-except {
                ordered-by user;
                type string;
              }
            }
            choice choice-icmp-code {
              leaf-list icmp-code {
                ordered-by user;
                type string;
              }
              leaf-list icmp-code-except {
                ordered-by user;
                type string;
              }
            }
            list source-prefix-list {
              key "name";
              ordered-by user;
              uses firewall-prefix-list;
            }
            list destination-prefix-list {
              key "name";
              ordered-by user;
              uses firewall-prefix-list;
            }
            list ip-source-address {
              key "name";
              ordered-by user;
              uses firewall-addr-object;
            }
            list ip-destination-address {
              key "name";
              ordered-by user;
              uses firewall-addr-object;
            }
            choice choice-ip-protocol {
              leaf-list ip-protocol {
                ordered-by user;
                type string;
              }
              leaf-list ip-protocol-except {
                ordered-by user;
                type string;
              }
            }
            choice choice-ip-precedence {
              leaf-list ip-precedence {
                ordered-by user;
                type string;
              }
              leaf-list ip-precedence-except {
                ordered-by user;
                type string;
              }
            }
          }
          container ipv6 {
            uses apply-group;
            uses apply-macro;
            list source-address {
              key "name";
              ordered-by user;
              uses firewall-addr6-object;
            }
            list destination-address {
              key "name";
              ordered-by user;
              uses firewall-addr6-object;
            }
            choice choice-traffic-class {
              leaf-list traffic-class {
                ordered-by user;
                type string;
              }
              leaf-list traffic-class-except {
                ordered-by user;
                type string;
              }
            }
            choice choice-next-header {
              leaf-list next-header {
                ordered-by user;
                type string;
              }
              leaf-list next-header-except {
                ordered-by user;
                type string;
              }
            }
            choice choice-payload-protocol {
              leaf-list payload-protocol {
                ordered-by user;
                type string;
              }
              leaf-list payload-protocol-except {
                ordered-by user;
                type string;
              }
            }
            choice choice-source-port {
              leaf-list source-port {
                ordered-by user;
                type string;
              }
              leaf-list source-port-except {
                ordered-by user;
                type string;
              }
            }
            choice choice-destination-port {
              leaf-list destination-port {
                ordered-by user;
                type string;
              }
              leaf-list destination-port-except {
                ordered-by user;
                type string;
              }
            }
            choice choice-port {
              leaf-list port {
                ordered-by user;
                type string;
              }
              leaf-list port-except {
                ordered-by user;
                type string;
              }
            }
            choice choice-extension-header {
              leaf-list extension-header {
                ordered-by user;
                type string;
              }
              leaf-list extension-header-except {
                ordered-by user;
                type string;
              }
            }
            leaf tcp-flags {
              type string;
            }
            leaf tcp-initial {
              type empty;
            }
            leaf tcp-established {
              type empty;
            }
            choice choice-icmp-type {
              leaf-list icmp-type {
                ordered-by user;
                type string;
              }
              leaf-list icmp-type-except {
                ordered-by user;
                type string;
              }
            }
            choice choice-icmp-code {
              leaf-list icmp-code {
                ordered-by user;
                type string;
              }
              leaf-list icmp-code-except {
                ordered-by user;
                type string;
              }
            }
            list source-prefix-list {
              key "name";
              ordered-by user;
              uses firewall-prefix-list;
            }
            list destination-prefix-list {
              key "name";
              ordered-by user;
              uses firewall-prefix-list;
            }
            list ip6-source-address {
              key "name";
              ordered-by user;
              uses firewall-addr6-object;
            }
            list ip6-destination-address {
              key "name";
              ordered-by user;
              uses firewall-addr6-object;
            }
          }
        }
        container vxlan {
          uses apply-group;
          uses apply-macro;
          choice choice-vni {
            leaf-list vni {
              type string;
              ordered-by user;
            }
            leaf-list vni-except {
              type string;
              ordered-by user;
            }
          }
          choice choice-rsvd1 {
            leaf-list rsvd1 {
              type string;
              ordered-by user;
            }
            leaf-list rsvd1-except {
              type string;
              ordered-by user;
            }
          }
          choice choice-rsvd2 {
            leaf-list rsvd2 {
              type string;
              ordered-by user;
            }
            leaf-list rsvd2-except {
              type string;
              ordered-by user;
            }
          }
          container flags {
            presence "";
            uses match-flags-value;
          }
        }
      }
      container then {
        uses apply-group;
        uses apply-macro;
        choice choice-3 {
          leaf accept {
            type empty;
          }
          leaf discard {
            type empty;
          }
          leaf next {
            type string;
          }
        }
        leaf log {
          type empty;
        }
        leaf syslog {
          type empty;
        }
        leaf forwarding-class {
          type string;
        }
        leaf analyzer {
          type string;
        }
        leaf port-mirror-instance {
          type string;
        }
        leaf port-mirror {
          type empty;
        }
        leaf inline-monitoring-instance {
          type string;
        }
        leaf inband-flow-telemetry-init {
          type string;
        }
        leaf inband-flow-telemetry-terminate {
          type string;
        }
        leaf next-hop-group {
          type string;
        }
        leaf loss-priority {
          type string;
        }
        leaf count {
          type string;
        }
        choice choice-16 {
          leaf policer {
            type string;
          }
          container three-color-policer {
            uses apply-group;
            uses apply-macro;
            choice choice-3 {
              leaf single-rate {
                type string;
              }
              leaf single-packet-rate {
                type string;
              }
              leaf two-rate {
                type string;
              }
              leaf two-packet-rate {
                type string;
              }
            }
          }
          leaf hierarchical-policer {
            type string;
          }
        }
        leaf vlan {
          type string;
        }
        leaf interface {
          type interface-unit;
        }
        container vxlan {
          uses apply-group;
          uses apply-macro;
          leaf flags {
            type string;
          }
          leaf rsvd1 {
            type string;
          }
          leaf rsvd2 {
            type string;
          }
        }
      }
      container template {
        uses apply-group;
        uses apply-macro;
        leaf template-name {
          type string;
        }
      }
    }
  }

  grouping ethernet-switching-type {
    uses apply-group;
    uses apply-macro;
    leaf port-mode {
      type string;
    }
    leaf interface-mode {
      type string;
    }
    leaf reflective-relay {
      type empty;
    }
    choice choice-vlan {
      container vlan {
        uses apply-group;
        uses apply-macro;
        leaf-list members {
          type string;
        }
      }
      container inner-vlan {
        uses apply-group;
        uses apply-macro;
        leaf-list members {
          type string;
        }
      }
      leaf-list inner-vlan-id-list {
        type string;
        ordered-by user;
      }
    }
    leaf bridge-domain-type {
      type string;
    }
    container vlan-rewrite {
      uses apply-group;
      uses apply-macro;
      list translate {
        key "name";
        ordered-by user;
        leaf name {
          type key-attribute-ulong-type;
        }
        leaf to-vlan-id {
          type uint32;
        }
      }
    }
    leaf native-vlan-id {
      type string;
    }
    leaf isid-list {
      type string;
    }
    leaf core-facing {
      type empty;
    }
    container filter {
      uses apply-group;
      uses apply-macro;
      leaf input {
        type string;
      }
      leaf input-precedence {
        type uint32;
      }
      leaf-list input-list {
        type string;
        ordered-by user;
      }
      leaf output {
        type string;
      }
      leaf output-precedence {
        type uint32;
      }
      leaf-list output-list {
        type string;
        ordered-by user;
      }
      container adf {
        presence "";
        uses apply-group;
        uses apply-macro;
        list rule {
          key "name";
          ordered-by user;
          leaf name {
            type string;
          }
          uses apply-group;
          uses apply-macro;
        }
        leaf counter {
          type empty;
        }
        leaf input-precedence {
          type uint32;
        }
        leaf not-mandatory {
          type empty;
        }
        leaf output-precedence {
          type uint32;
        }
      }
      leaf group {
        type uint32;
      }
    }
    container policer {
      uses apply-group;
      uses apply-macro;
      leaf input {
        type string;
      }
      leaf output {
        type string;
      }
    }
    container storm-control {
      presence "";
      uses apply-group;
      uses apply-macro;
      leaf profile-name {
        type string;
      }
    }
    container recovery-timeout {
      leaf time-in-seconds {
        units "seconds";
        type uint32;
      }
    }
  }

  grouping ethernet-policer {
    uses apply-group;
    uses apply-macro;
    choice choice-3 {
      leaf bandwidth-limit {
        type string;
      }
    }
    leaf burst-size-limit {
      type string;
    }
  }

  grouping extension-list-type {
    leaf name {
      type key-attribute-string-type;
    }
    uses apply-group;
    uses apply-macro;
    leaf-list value {
      ordered-by user;
      type string;
    }
  }

  grouping fibre-channel-type {
    uses apply-group;
    uses apply-macro;
    leaf port-mode {
      type string;
    }
    leaf no-npiv {
      type empty;
    }
    container fc-fabric {
      uses apply-group;
      uses apply-macro;
      leaf-list members {
        ordered-by user;
        type string;
      }
    }
    leaf native-fabric {
      type string;
    }
  }

  grouping file-specification-type {
    leaf name {
      type string;
    }
    uses apply-group;
    uses apply-macro;
    leaf name-format {
      type string;
    }
    leaf data-format {
      type string;
    }
    container transfer {
      leaf timeout {
        type uint32;
      }
      leaf record-level {
        type uint32;
      }
    }
  }

  grouping firewall-addr-object {
    leaf name {
      type ipv4prefix;
    }
    uses apply-group;
    uses apply-macro;
    leaf except {
      type empty;
    }
  }

  grouping firewall_addr6_object {
    leaf name {
      type ipv6prefix;
    }
    leaf except {
      type empty;
    }
  }

  grouping match_L2_flexible_mask {
    uses apply-advanced;
    leaf match-start {
      type string;
    }
    leaf byte-offset {
      type string;
    }
    leaf bit-offset {
      type string;
    }
    leaf bit-length {
      type string;
    }
    leaf mask-in-hex {
      type string;
    }
    leaf prefix {
      type string;
    }
    leaf flexible-mask-name {
      type string;
    }
  }

  grouping match_L2_flexible_range {
    uses apply-advanced;
    leaf match-start {
      type string;
    }
    leaf byte-offset {
      type string;
    }
    leaf bit-offset {
      type string;
    }
    leaf bit-length {
      type string;
    }
    choice range_choice {
      case case_1 {
        leaf range {
          type string;
        }
      }
      case case_2 {
        leaf range-except {
          type string;
        }
      }
    }
    leaf flexible-range-name {
      type string;
    }
  }

  grouping firewall-flexible-match {
    leaf name {
      type string;
    }
    uses apply-group;
    uses apply-macro;
    leaf match-start {
      mandatory true;
      type string;
    }
    leaf byte-offset {
      type uint32;
    }
    leaf bit-offset {
      type uint32;
    }
    leaf bit-length {
      type uint32;
      mandatory true;
    }
  }

  grouping firewall-hierpolicer {
    leaf name {
      type string;
    }
    uses apply-group;
    uses apply-macro;
    choice choice-3 {
      leaf logical-interface-policer {
        type empty;
      }
      leaf physical-interface-policer {
        type empty;
      }
    }
    leaf shared-bandwidth-policer {
      type empty;
    }
    leaf filter-specific {
      type empty;
    }
    container aggregate {
      presence "";
      uses hierarchical-policer-aggregate-bucket;
    }
    container premium {
      presence "";
      uses hierarchical-policer-premium-bucket;
    }
  }

  grouping firewall-load-balance-group {
    leaf name {
      type string;
    }
    uses apply-group;
    uses apply-macro;
    leaf-list next-hop-group {
      type string;
      ordered-by user;
    }
  }

  grouping firewall-mac-addr-object {
    leaf name {
      type mac-addr-prefix;
    }
    uses apply-group;
    uses apply-macro;
    leaf except {
      type empty;
    }
  }

  grouping firewall-policer {
    leaf name {
      type string;
    }
    uses apply-group;
    uses apply-macro;
    leaf filter-specific {
      type empty;
    }
    leaf logical-interface-policer {
      type empty;
    }
    leaf physical-interface-policer {
      type empty;
    }
    leaf logical-bandwidth-policer {
      type empty;
    }
    leaf shared-bandwidth-policer {
      type empty;
    }
    choice choice-if-exceeding {
      container if-exceeding {
        presence "";
        uses apply-group;
        uses apply-macro;
        choice choice-bandwidth-limit {
          leaf bandwidth-limit {
            type string;
            units "bits per second";
          }
          leaf bandwidth-percent {
            units "percent";
            type uint32;
          }
        }
        leaf burst-size-limit {
          type string;
          units "bytes";
        }
        container aggregate-policing {
          presence "enable aggregate-policing";
          uses apply-group;
          uses apply-macro;
          list policer {
            key "name";
            ordered-by user;
            leaf name {
              type string;
            }
            uses apply-group;
            uses apply-macro;
            leaf aggregate-sharing-mode {
              type string;
            }
          }
        }
      }
      container if-exceeding-pps {
        presence "";
        uses apply-group;
        uses apply-macro;
        leaf pps-limit {
          type string;
          units "packets per second";
        }
        leaf packet-burst {
          type string;
          mandatory true;
          units "packets";
        }
      }
    }
    container counter {
      presence "";
      uses apply-group;
      uses apply-macro;
      leaf counter-id {
        mandatory true;
        type uint32;
      }
    }
    container then {
      uses apply-group;
      uses apply-macro;
      leaf discard {
        type empty;
      }
      leaf loss-priority {
        type string;
      }
      leaf forwarding-class {
        type string;
      }
      leaf out-of-profile {
        type empty;
      }
    }
    container aggregate {
      presence "enable aggregate";
      uses apply-group;
      uses apply-macro;
      leaf global {
        type empty;
      }
    }
  }

  grouping firewall-prefix-list {
    leaf name {
      type string;
    }
    uses apply-group;
    uses apply-macro;
    leaf except {
      type empty;
    }
  }

  grouping flow-filter-type {
    leaf name {
      type key-attribute-string-type;
    }
    uses apply-group;
    uses apply-macro;
    leaf protocol {
      type string;
    }
    leaf source-prefix {
      type ipprefix;
    }
    leaf destination-prefix {
      type ipprefix;
    }
    leaf conn-tag {
      type uint32;
    }
    leaf logical-system {
      type string;
    }
    leaf source-port {
      type string;
    }
    leaf destination-port {
      type string;
    }
    leaf interface {
      type interface-name;
    }
  }

  grouping gateway-type {
    leaf name {
      type string;
    }
    uses apply-group;
    uses apply-macro;
    leaf service-interface {
      type interface-device;
    }
    container sip {
      presence "enable sip";
      uses apply-group;
      uses apply-macro;
      container timers {
        presence "enable timers";
        uses sip-timers-type;
      }
      list new-transaction-policy {
        key "name";
        ordered-by user;
        uses transaction-policy-type;
      }
      list new-transaction-policy-set {
        key "name";
        ordered-by user;
        uses new-transaction-set-type;
      }
      list new-registration-policy {
        key "name";
        ordered-by user;
        uses registration-policy-type;
      }
      list new-registration-policy-set {
        key "name";
        ordered-by user;
        uses new-registration-set-type;
      }
      list new-call-usage-policy {
        key "name";
        ordered-by user;
        uses call-usage-policy-type;
      }
      list new-call-usage-policy-set {
        key "name";
        ordered-by user;
        uses new-call-usage-set-type;
      }
      container routing-destinations {
        presence "enable routing-destinations";
        uses routing-destinations;
      }
      container message-manipulation-rules {
        uses header-manipulation-message-manipulation-rules-type;
      }
      leaf local-tag-prefix {
        type string;
      }
      list signaling-realms {
        key "name";
        ordered-by user;
        uses signaling-realm;
      }
      leaf local-uri-prefix {
        type string;
      }
    }
    list admission-control {
      key "name";
      ordered-by user;
      uses admission-control-type;
    }
    list service-point {
      key "name";
      ordered-by user;
      uses service-point-type;
    }
    container name-resolution-cache {
      presence "enable name-resolution-cache";
      uses name-resolution-cache-type;
    }
    container embedded-spdf {
      presence "enable embedded-spdf";
      uses apply-group;
      uses apply-macro;
      list service-class {
        key "name";
        ordered-by user;
        leaf name {
          type key-attribute-string-type;
        }
        uses apply-group;
        uses apply-macro;
        list term {
          key "name";
          ordered-by user;
          leaf name {
            type string;
          }
          uses apply-group;
          uses apply-macro;
          container from {
            presence "enable from";
            uses apply-group;
            uses apply-macro;
            leaf-list media-type {
              ordered-by user;
              type string;
            }
          }
          container then {
            presence "enable then";
            uses apply-group;
            uses apply-macro;
            leaf reject {
              type empty;
            }
            leaf committed-information-rate {
              type uint32;
            }
            leaf committed-burst-size {
              type uint32;
            }
            leaf dscp {
              type string;
            }
          }
        }
      }
    }
    container traceoptions {
      uses apply-group;
      uses apply-macro;
      container flag {
        presence "enable flag";
        uses apply-group;
        uses apply-macro;
        leaf minimum {
          type string;
        }
        leaf session-trace {
          type string;
        }
        container sip-stack {
          presence "enable sip-stack";
          uses apply-group;
          uses apply-macro;
          leaf event-tracing {
            type empty;
          }
          leaf ips-tracing {
            type empty;
          }
          leaf per-tracing {
            type empty;
          }
          leaf dev-logging {
            type empty;
          }
          leaf verbose-logging {
            type empty;
          }
          leaf pd-log-level {
            type string;
          }
          leaf pd-log-detail {
            type string;
          }
        }
        container signaling {
          presence "enable signaling";
          uses apply-group;
          uses apply-macro;
          leaf minimum {
            type string;
          }
          leaf sip-stack-wrapper {
            type string;
          }
          leaf b2b-wrapper {
            type string;
          }
          leaf ua {
            type string;
          }
          leaf b2b {
            type string;
          }
          leaf topology-hiding {
            type string;
          }
          leaf policy {
            type string;
          }
          leaf name-resolution-cache {
            type string;
          }
          leaf charging-trigger {
            type string;
          }
          leaf event-trigger {
            type string;
          }
        }
        container framework {
          presence "enable framework";
          uses apply-group;
          uses apply-macro;
          leaf minimum {
            type string;
          }
          leaf executor {
            type string;
          }
          leaf action {
            type string;
          }
          leaf event {
            type string;
          }
          leaf freezer {
            type string;
          }
          leaf memory-pool {
            type string;
          }
        }
        container datastore {
          presence "enable datastore";
          uses apply-group;
          uses apply-macro;
          leaf minimum {
            type string;
          }
          leaf data {
            type string;
          }
          leaf handle {
            type string;
          }
          leaf db {
            type string;
          }
        }
        container sbc-utils {
          presence "enable sbc-utils";
          uses apply-group;
          uses apply-macro;
          leaf minimum {
            type string;
          }
          leaf configuration {
            type string;
          }
          leaf ipc {
            type string;
          }
          leaf device-monitor {
            type string;
          }
          leaf memory-management {
            type string;
          }
          leaf message {
            type string;
          }
          leaf common {
            type string;
          }
          leaf user-interface {
            type string;
          }
          leaf memory-pool {
            type string;
          }
        }
      }
    }
  }

  grouping admission-control-type {
    leaf name {
      type string;
    }
    uses apply-group;
    uses apply-macro;
    container dialogs {
      presence "enable dialogs";
      uses apply-group;
      uses apply-macro;
      leaf maximum-concurrent {
        type uint32;
      }
      leaf committed-attempts-rate {
        type uint32;
      }
      leaf committed-burst-size {
        type uint32;
      }
    }
    container transactions {
      presence "enable transactions";
      uses apply-group;
      uses apply-macro;
      leaf maximum-concurrent {
        type uint32;
      }
      leaf committed-attempts-rate {
        type uint32;
      }
      leaf committed-burst-size {
        type uint32;
      }
    }
  }

  grouping call-usage-policy-type {
    leaf name {
      type string;
    }
    uses apply-group;
    uses apply-macro;
    list term {
      key "name";
      ordered-by user;
      leaf name {
        type string;
      }
      uses apply-group;
      uses apply-macro;
      container from {
        presence "enable from";
        uses apply-group;
        uses apply-macro;
        leaf-list source-address {
          type ipaddr;
          ordered-by user;
        }
        list method {
          key "name";
          ordered-by user;
          uses call-usage-method-type;
        }
        container request-uri {
          presence "enable request-uri";
          uses apply-group;
          uses apply-macro;
          leaf-list regular-expression {
            type regular-expression;
            ordered-by user;
          }
        }
        container contact {
          presence "enable contact";
          uses apply-group;
          uses apply-macro;
          leaf-list regular-expression {
            type regular-expression;
            ordered-by user;
          }
        }
      }
      container then {
        presence "enable then";
        uses new-call-then-type;
      }
    }
  }

  grouping call-usage-method-type {
    leaf name {
      type string;
    }
    uses apply-group;
    uses apply-macro;
  }

  grouping ggsn-pgw-apn-services {
    uses apply-group;
    uses apply-macro;
    container apns {
      uses apply-group;
      uses apply-macro;
      list apn {
        key "name";
        uses ggsn-pgw-apn;
      }
    }
  }

  grouping ggsn-pgw-apn {
    leaf name {
      type string;
    }
    uses apply-group;
    uses apply-macro;
    leaf maximum-bearers {
      type uint32;
    }
    leaf wait-accounting {
      type empty;
    }
    leaf block-visitors {
      type empty;
    }
    leaf allow-network-behind-mobile {
      type empty;
    }
    leaf local-policy-profile {
      type string;
    }
    leaf apn-type {
      type string;
    }
    leaf description {
      type string;
    }
    leaf apn-data-type {
      type string;
    }
    leaf mobile-interface {
      type interface-unit;
    }
    container address-assignment {
      presence "enable address-assignment";
      uses apply-group;
      uses apply-macro;
      choice choice-aaa {
        leaf aaa {
          type empty;
        }
        container local {
          presence "enable local";
          uses apply-group;
          uses apply-macro;
          leaf aaa-override {
            type empty;
          }
        }
        container dhcp-proxy-client {
          presence "enable dhcp-proxy-client";
          uses apply-group;
          uses apply-macro;
          leaf aaa-override {
            type empty;
          }
        }
      }
      container inet-pool {
        uses apply-group;
        uses apply-macro;
        leaf group {
          type string;
        }
        leaf pool {
          type string;
        }
        leaf-list exclude-pools {
          ordered-by user;
          type string;
        }
      }
      container inet6-pool {
        uses apply-group;
        uses apply-macro;
        leaf group {
          type string;
        }
        leaf pool {
          type string;
        }
        leaf-list exclude-v6pools {
          ordered-by user;
          type string;
        }
      }
      container dhcpv4-proxy-client-profile {
        presence "";
        uses apply-group;
        uses apply-macro;
        leaf logical-system {
          type string;
        }
        leaf routing-instance {
          type string;
        }
        leaf profile-name {
          type string;
        }
        leaf pool-name {
          type string;
        }
      }
      container dhcpv6-proxy-client-profile {
        presence "";
        uses apply-group;
        uses apply-macro;
        leaf logical-system {
          type string;
        }
        leaf routing-instance {
          type string;
        }
        leaf profile-name {
          type string;
        }
        leaf pool-name {
          type string;
        }
      }
      container allow-static-ip-address {
        presence "enable allow-static-ip-address";
        uses apply-group;
        uses apply-macro;
        leaf no-aaa-verify {
          type empty;
        }
      }
    }
    leaf session-timeout {
      units "hours";
      type uint32;
    }
    leaf idle-timeout {
      units "minutes";
      type uint32;
    }
    leaf idle-timeout-direction {
      type string;
    }
    leaf restriction-value {
      type uint32;
    }
    leaf aaa-profile {
      type string;
    }
    container user-options {
      uses apply-group;
      uses apply-macro;
      choice choice-user-name {
        leaf user-name {
          type string;
        }
        leaf use-msisdn {
          type empty;
        }
        leaf use-imsi {
          type empty;
        }
        leaf use-apnname {
          type empty;
        }
      }
      leaf password {
        type unreadable;
      }
      leaf override-pco {
        type empty;
      }
    }
    container charging {
      uses apply-group;
      uses apply-macro;
      leaf default-profile {
        type string;
      }
      leaf home-profile {
        type string;
      }
      leaf roamer-profile {
        type string;
      }
      leaf visitor-profile {
        type string;
      }
      leaf-list profile-selection-order {
        ordered-by user;
        type string;
      }
    }
    container dns-server {
      presence "enable dns-server";
      uses apply-group;
      uses apply-macro;
      leaf primary-v4 {
        type ipv4addr;
      }
      leaf secondary-v4 {
        type ipv4addr;
      }
      leaf primary-v6 {
        type ipv6addr;
      }
      leaf secondary-v6 {
        type ipv6addr;
      }
    }
    container nbns-server {
      presence "enable nbns-server";
      uses apply-group;
      uses apply-macro;
      leaf primary-v4 {
        type ipv4addr;
      }
      leaf secondary-v4 {
        type ipv4addr;
      }
    }
    list p-cscf {
      key "name";
      ordered-by user;
      leaf name {
        type ipaddr;
      }
      uses apply-group;
      uses apply-macro;
    }
    container selection-mode {
      presence "enable selection-mode";
      uses apply-group;
      uses apply-macro;
      leaf no-subscribed {
        type empty;
      }
      leaf from-ms {
        type empty;
      }
      leaf from-sgsn {
        type empty;
      }
    }
    leaf service-selection-profile {
      type string;
    }
    container network-behind-mobile {
      uses apply-group;
      uses apply-macro;
      list imsi {
        key "name";
        ordered-by user;
        leaf name {
          type key-attribute-string-type;
        }
        uses apply-group;
        uses apply-macro;
        leaf-list prefix-v4 {
          type ipv4prefix;
          ordered-by user;
        }
        leaf-list prefix-v6 {
          type ipv6prefix;
          ordered-by user;
        }
      }
    }
    leaf service-mode {
      type string;
    }
    container call-rate-statistics {
      presence "enable call-rate-statistics";
      uses apply-group;
      uses apply-macro;
      leaf interval {
        units "minutes";
        type uint32;
      }
      leaf history {
        type uint32;
      }
    }
    leaf pcef-profile {
      type string;
    }
    container verify-source-address {
      presence "enable verify-source-address";
      uses apply-group;
      uses apply-macro;
      leaf disable {
        type empty;
      }
    }
    container inter-mobile-traffic {
      uses apply-group;
      uses apply-macro;
      container redirect {
        presence "enable redirect";
        uses apply-group;
        uses apply-macro;
        leaf redirect-ip {
          type ipv4addr;
        }
        leaf routing-instance {
          type string;
        }
      }
      leaf deny {
        type empty;
      }
    }
  }

  grouping gtpp-peer {
    leaf name {
      type string;
    }
    uses apply-group;
    uses apply-macro;
    leaf destination-ipv4-address {
      type ipv4addr;
    }
    container source-interface {
      presence "";
      leaf interface-name {
        type interface-name;
      }
      leaf ipv4-address {
        type ipv4addr;
      }
    }
    leaf destination-port {
      type uint32;
    }
    leaf transport-protocol {
      type string;
    }
    leaf version {
      type string;
    }
    leaf echo-interval {
      units "seconds";
      type uint32;
    }
    leaf n3-requests {
      type uint16;
    }
    leaf t3-response {
      units "seconds";
      type uint16;
    }
    leaf header-type {
      type string;
    }
    leaf pending-queue-size {
      type uint32;
    }
    leaf down-detect-time {
      units "seconds";
      type uint32;
    }
    leaf reconnect-time {
      units "seconds";
      type uint32;
    }
    leaf no-path-management {
      type empty;
    }
  }

  grouping hcm-tag-rule-object {
    leaf name {
      type key-attribute-string-type;
    }
    uses apply-group;
    uses apply-macro;
    list term {
      key "name";
      ordered-by user;
      leaf name {
        type key-attribute-ulong-type;
      }
      uses apply-group;
      uses apply-macro;
      container from {
        presence "enable from";
        uses hcm-tag-match-object;
      }
      container then {
        uses apply-group;
        uses apply-macro;
        list tag {
          key "name";
          ordered-by user;
          leaf name {
            type key-attribute-string-type;
          }
          uses apply-group;
          uses apply-macro;
          leaf tag-header {
            type string;
          }
          leaf do-not-rename-existing-tag-header {
            type empty;
          }
          leaf tag-separator {
            type string;
          }
          leaf-list tag-attribute {
            type string;
            ordered-by user;
          }
          container encrypt {
            presence "";
            uses apply-group;
            uses apply-macro;
            leaf hash {
              type string;
            }
            leaf prefix {
              type string;
            }
          }
        }
        leaf count {
          type empty;
        }
      }
    }
  }

  grouping hcm-tag-match-object {
    uses apply-group;
    uses apply-macro;
    list destination-address {
      key "name";
      ordered-by user;
      uses sfw-addr-object;
    }
    list destination-address-range {
      key "low high";
      ordered-by user;
      leaf low {
        type ipaddr;
      }
      leaf high {
        type ipaddr;
      }
      leaf except {
        type empty;
      }
    }
    list destination-prefix-list {
      key "name";
      ordered-by user;
      leaf name {
        type string;
      }
      leaf except {
        type empty;
      }
    }
    leaf-list destination-ports {
      ordered-by user;
      type uint32;
    }
    list destination-port-range {
      key "low high";
      ordered-by user;
      leaf low {
        type key-attribute-ulong-type;
      }
      leaf high {
        type key-attribute-ulong-type;
      }
    }
  }

  grouping hcm-url-list-object {
    leaf name {
      type key-attribute-string-type;
    }
    uses apply-group;
    uses apply-macro;
    list host {
      key "name";
      ordered-by user;
      leaf name {
        type key-attribute-string-type;
      }
      uses apply-group;
      uses apply-macro;
    }
    list request-uri {
      key "name";
      ordered-by user;
      leaf name {
        type key-attribute-string-type;
      }
      uses apply-group;
      uses apply-macro;
    }
  }

  grouping hcm-url-rule-object {
    leaf name {
      type key-attribute-string-type;
    }
    uses apply-group;
    uses apply-macro;
    list term {
      key "name";
      ordered-by user;
      leaf name {
        type key-attribute-ulong-type;
      }
      uses apply-group;
      uses apply-macro;
      container from {
        presence "enable from";
        uses hcm-url-match-object;
      }
      container then {
        uses apply-group;
        uses apply-macro;
        leaf count {
          type empty;
        }
        leaf log-request {
          type empty;
        }
        choice choice-accept {
          leaf accept {
            type empty;
          }
          leaf discard {
            type empty;
          }
        }
      }
    }
  }

  grouping hcm-url-match-object {
    uses apply-group;
    uses apply-macro;
    list url-list {
      key "name";
      ordered-by user;
      leaf name {
        type key-attribute-string-type;
      }
      uses apply-group;
      uses apply-macro;
    }
    list url {
      key "name";
      ordered-by user;
      leaf name {
        type key-attribute-ulong-type;
      }
      uses apply-group;
      uses apply-macro;
      list host {
        key "name";
        ordered-by user;
        leaf name {
          type key-attribute-string-type;
        }
        uses apply-group;
        uses apply-macro;
      }
      list request-uri {
        key "name";
        ordered-by user;
        leaf name {
          type key-attribute-string-type;
        }
        uses apply-group;
        uses apply-macro;
      }
    }
  }

  grouping header-manipulation-message-manipulation-rules-type {
    uses apply-group;
    uses apply-macro;
    list manipulation-rule {
      key "name";
      ordered-by user;
      uses header-manipulation-manipulation-rule-type;
    }
  }

  grouping header-manipulation-manipulation-rule-type {
    leaf name {
      type string;
    }
    uses apply-group;
    uses apply-macro;
    container actions {
      uses header-manipulation-actions-type;
    }
  }

  grouping header-manipulation-actions-type {
    uses apply-group;
    uses apply-macro;
    list sip-header {
      key "name";
      ordered-by user;
      leaf name {
        type string;
      }
      uses apply-group;
      uses apply-macro;
      container field-value {
        uses header-manipulation-sip-header-field-value-type;
      }
    }
    container request-uri {
      presence "enable request-uri";
      uses apply-group;
      uses apply-macro;
      container field-value {
        presence "enable field-value";
        uses apply-group;
        uses apply-macro;
        list modify-regular-expression {
          key "name";
          ordered-by user;
          uses header-manipulation-modify-type;
        }
      }
    }
  }

  grouping header-manipulation-modify-type {
    leaf name {
      type regular-expression;
    }
    uses apply-group;
    uses apply-macro;
    leaf with {
      type string;
    }
  }

  grouping header-manipulation-sip-header-field-value-type {
    uses apply-group;
    uses apply-macro;
    leaf remove-all {
      type empty;
    }
    list remove-regular-expression {
      key "name";
      ordered-by user;
      uses header-manipulation-remove-type;
    }
    list reject-regular-expression {
      key "name";
      ordered-by user;
      uses header-manipulation-reject-type;
    }
    list modify-regular-expression {
      key "name";
      ordered-by user;
      uses header-manipulation-modify-type;
    }
    list add {
      key "name";
      ordered-by user;
      uses header-manipulation-add-type;
    }
    list add-missing {
      key "name";
      ordered-by user;
      uses header-manipulation-add-missing-type;
    }
    list add-overwrite {
      key "name";
      ordered-by user;
      uses header-manipulation-add-overwrite-type;
    }
  }

  grouping header-manipulation-add-missing-type {
    leaf name {
      type string;
    }
    uses apply-group;
    uses apply-macro;
  }

  grouping header-manipulation-add-overwrite-type {
    leaf name {
      type string;
    }
    uses apply-group;
    uses apply-macro;
  }

  grouping header-manipulation-add-type {
    leaf name {
      type string;
    }
    uses apply-group;
    uses apply-macro;
  }

  grouping header-manipulation-reject-type {
    leaf name {
      type regular-expression;
    }
    uses apply-group;
    uses apply-macro;
  }

  grouping header-manipulation-remove-type {
    leaf name {
      type regular-expression;
    }
    uses apply-group;
    uses apply-macro;
  }

  grouping hierarchical-policer-aggregate-bucket {
    uses apply-group;
    uses apply-macro;
    container if-exceeding {
      presence "";
      uses apply-group;
      uses apply-macro;
      choice choice-3 {
        leaf bandwidth-limit {
          type string;
        }
      }
      leaf burst-size-limit {
        type string;
      }
    }
    container then {
      uses apply-group;
      uses apply-macro;
      choice choice-3 {
        leaf discard {
          type empty;
        }
        leaf loss-priority {
          type string;
        }
        leaf forwarding-class {
          type string;
        }
      }
    }
  }

  grouping hierarchical-policer-premium-bucket {
    uses apply-group;
    uses apply-macro;
    container if-exceeding {
      presence "";
      uses apply-group;
      uses apply-macro;
      choice choice-3 {
        leaf bandwidth-limit {
          type string;
        }
      }
      leaf burst-size-limit {
        type string;
      }
    }
    container then {
      uses apply-group;
      uses apply-macro;
      choice choice-3 {
        leaf discard {
          type empty;
        }
      }
    }
  }

  grouping log-object {
    uses apply-group;
    uses apply-macro;
    list exclude {
      key "name";
      ordered-by user;
      leaf name {
        type string;
      }
      uses apply-group;
      uses apply-macro;
      leaf destination-address {
        type ipaddr;
      }
      leaf destination-port {
        type uint32;
      }
      leaf event-id {
        type string;
      }
      leaf failure {
        type empty;
      }
      leaf interface-name {
        type string;
      }
      leaf policy-name {
        type string;
      }
      leaf process {
        type string;
      }
      leaf protocol {
        type string;
      }
      leaf source-address {
        type ipaddr;
      }
      leaf source-port {
        type uint32;
      }
      leaf success {
        type empty;
      }
      leaf username {
        type string;
      }
    }
    leaf limit {
      type uint32;
    }
    container cache {
      presence "enable cache";
      uses apply-group;
      uses apply-macro;
      list exclude {
        key "name";
        ordered-by user;
        leaf name {
          type string;
        }
        uses apply-group;
        uses apply-macro;
        leaf destination-address {
          type ipaddr;
        }
        leaf destination-port {
          type uint32;
        }
        leaf event-id {
          type string;
        }
        leaf failure {
          type empty;
        }
        leaf interface-name {
          type string;
        }
        leaf policy-name {
          type string;
        }
        leaf process {
          type string;
        }
        leaf protocol {
          type string;
        }
        leaf source-address {
          type ipaddr;
        }
        leaf source-port {
          type uint32;
        }
        leaf success {
          type empty;
        }
        leaf username {
          type string;
        }
      }
      leaf limit {
        type uint32;
      }
    }
    list host {
      key "name";
      ordered-by user;
      leaf name {
        type string;
      }
      uses apply-group;
      uses apply-macro;
      list contents {
        key "name";
        leaf name {
          type string;
        }
        choice choice-any {
          leaf any {
            type empty;
          }
          leaf emergency {
            type empty;
          }
          leaf alert {
            type empty;
          }
          leaf critical {
            type empty;
          }
          leaf error {
            type empty;
          }
          leaf warning {
            type empty;
          }
          leaf notice {
            type empty;
          }
          leaf info {
            type empty;
          }
          leaf none {
            type empty;
          }
        }
      }
      leaf facility-override {
        type string;
      }
      leaf log-prefix {
        type string;
      }
      leaf port {
        type uint16;
      }
      container class {
        uses apply-group;
        uses apply-macro;
        container session-logs {
          presence "enable session-logs";
          uses apply-group;
          uses apply-macro;
          container open {
            presence "enable open";
            uses apply-group;
            uses apply-macro;
          }
          container close {
            presence "enable close";
            uses apply-group;
            uses apply-macro;
          }
        }
        container packet-logs {
          presence "enable packet-logs";
          uses apply-group;
          uses apply-macro;
        }
        container stateful-firewall-logs {
          presence "enable stateful-firewall-logs";
          uses apply-group;
          uses apply-macro;
        }
        container alg-logs {
          presence "enable alg-logs";
          uses apply-group;
          uses apply-macro;
        }
        container nat-logs {
          presence "enable nat-logs";
          uses apply-group;
          uses apply-macro;
          container deterministic-nat-configuration-log {
            presence "enable deterministic-nat-configuration-log";
            uses apply-group;
            uses apply-macro;
          }
        }
        container ids-logs {
          presence "enable ids-logs";
          uses apply-group;
          uses apply-macro;
        }
        container pcp-logs {
          presence "enable pcp-logs";
          container map {
            presence "enable map";
            uses apply-group;
            uses apply-macro;
          }
          container debug {
            presence "enable debug";
            uses apply-group;
            uses apply-macro;
          }
        }
        container ha-logs {
          uses apply-group;
          uses apply-macro;
          container open-synchronized {
            presence "enable open-synchronized";
            uses apply-group;
            uses apply-macro;
          }
          container close-synchronized {
            presence "enable close-synchronized";
            uses apply-group;
            uses apply-macro;
          }
        }
        container urlf-logs {
          presence "enable urlf-logs";
          uses apply-group;
          uses apply-macro;
        }
      }
      leaf source-address {
        type ipv4addr;
      }
      container tcp-log {
        presence "";
        uses apply-group;
        uses apply-macro;
        leaf source-address {
          mandatory true;
          type ipaddr;
        }
        leaf vrf-name {
          type string;
        }
        leaf ssl-profile {
          type string;
        }
      }
    }
    leaf message-rate-limit {
      units "messages per second";
      type uint32;
    }
    leaf disable {
      type empty;
    }
    leaf utc-timestamp {
      type empty;
    }
    leaf mode {
      type string;
    }
    leaf event-rate {
      units "logs per second";
      type uint32;
    }
    leaf format {
      type string;
    }
    leaf rate-cap {
      units "logs per second";
      type uint32;
    }
    leaf max-database-record {
      type uint32;
    }
    container report {
      presence "enable report";
      uses apply-group;
      uses apply-macro;
    }
    choice choice-source-address {
      leaf source-address {
        type ipaddr;
      }
      leaf source-interface {
        type interface-name;
      }
    }
    container transport {
      presence "enable transport";
      uses apply-group;
      uses apply-macro;
      container apply-advanced {
        uses apply-group;
        uses apply-macro;
      }
      leaf tcp-connections {
        type uint32;
      }
      leaf protocol {
        type string;
      }
      leaf tls-profile {
        type string;
      }
    }
    leaf facility-override {
      type string;
    }
    leaf local-log-tag {
      type string;
    }
    list local-category {
      key "name";
      ordered-by user;
      leaf name {
        type string;
      }
      uses apply-group;
      uses apply-macro;
    }
    list stream {
      key "name";
      ordered-by user;
      leaf name {
        type key-attribute-string-type;
      }
      uses apply-group;
      uses apply-macro;
      leaf severity {
        type string;
      }
      leaf format {
        type string;
      }
      list category {
        key "name";
        ordered-by user;
        leaf name {
          type string;
        }
        uses apply-group;
        uses apply-macro;
      }
      list filter {
        key "name";
        ordered-by user;
        leaf name {
          type string;
        }
        uses apply-group;
        uses apply-macro;
      }
      container host {
        presence "";
        uses host-object;
      }
      container rate-limit {
        presence "";
        uses apply-group;
        uses apply-macro;
        leaf rate {
          mandatory true;
          units "logs per second";
          type uint32;
        }
      }
      container file {
        presence "";
        uses apply-group;
        uses apply-macro;
        leaf localfilename {
          mandatory true;
          type string;
        }
        leaf size {
          type uint32;
        }
        leaf rotation {
          type uint32;
        }
        leaf allow-duplicates {
          type empty;
        }
      }
    }
    container file {
      uses apply-group;
      uses apply-macro;
      leaf filename {
        type string;
      }
      leaf size {
        type uint32;
      }
      leaf path {
        type string;
      }
      leaf files {
        type uint32;
      }
    }
    container traceoptions {
      uses apply-group;
      uses apply-macro;
      leaf no-remote-trace {
        type empty;
      }
      container file {
        leaf filename {
          type string;
        }
        leaf size {
          type string;
        }
        leaf files {
          type uint32;
        }
        leaf world-readable {
          type empty;
        }
        leaf no-world-readable {
          type empty;
        }
        leaf match {
          type regular-expression;
        }
      }
      list flag {
        key "name";
        ordered-by user;
        leaf name {
          type string;
        }
      }
    }
    list profile {
      key "name";
      ordered-by user;
      leaf name {
        mandatory true;
        type key-attribute-string-type;
      }
      uses apply-group;
      uses apply-macro;
      list stream-name {
        key "name";
        ordered-by user;
        leaf name {
          type string;
        }
        uses apply-group;
        uses apply-macro;
      }
      container category {
        presence "enable category";
        uses apply-group;
        uses apply-macro;
        container session {
          presence "enable session";
          uses apply-group;
          uses apply-macro;
          list field-extra-name {
            key "name";
            leaf name {
              type string;
            }
            uses apply-group;
            uses apply-macro;
          }
          list field-name {
            key "name";
            ordered-by user;
            leaf name {
              type string;
            }
            uses apply-group;
            uses apply-macro;
          }
        }
        container webfilter {
          presence "enable webfilter";
          uses apply-group;
          uses apply-macro;
          list field-extra-name {
            key "name";
            leaf name {
              type string;
            }
            uses apply-group;
            uses apply-macro;
          }
          list field-name {
            key "name";
            ordered-by user;
            leaf name {
              type string;
            }
            uses apply-group;
            uses apply-macro;
          }
        }
        container antivirus {
          presence "enable antivirus";
          uses apply-group;
          uses apply-macro;
          list field-extra-name {
            key "name";
            leaf name {
              type string;
            }
            uses apply-group;
            uses apply-macro;
          }
          list field-name {
            key "name";
            ordered-by user;
            leaf name {
              type string;
            }
            uses apply-group;
            uses apply-macro;
          }
        }
        container content-filter {
          presence "enable content-filter";
          uses apply-group;
          uses apply-macro;
          list field-extra-name {
            key "name";
            leaf name {
              type string;
            }
            uses apply-group;
            uses apply-macro;
          }
          list field-name {
            key "name";
            ordered-by user;
            leaf name {
              type string;
            }
            uses apply-group;
            uses apply-macro;
          }
        }
        container antispam {
          presence "enable antispam";
          uses apply-group;
          uses apply-macro;
          list field-extra-name {
            key "name";
            leaf name {
              type string;
            }
            uses apply-group;
            uses apply-macro;
          }
          list field-name {
            key "name";
            ordered-by user;
            leaf name {
              type string;
            }
            uses apply-group;
            uses apply-macro;
          }
        }
        container idp {
          presence "enable idp";
          uses apply-group;
          uses apply-macro;
          list field-extra-name {
            key "name";
            leaf name {
              type string;
            }
            uses apply-group;
            uses apply-macro;
          }
          list field-name {
            key "name";
            ordered-by user;
            leaf name {
              type string;
            }
            uses apply-group;
            uses apply-macro;
          }
        }
        container secintel {
          presence "enable secintel";
          uses apply-group;
          uses apply-macro;
          list field-extra-name {
            key "name";
            leaf name {
              type string;
            }
            uses apply-group;
            uses apply-macro;
          }
          list field-name {
            key "name";
            ordered-by user;
            leaf name {
              type string;
            }
            uses apply-group;
            uses apply-macro;
          }
        }
        container aamw {
          presence "enable aamw";
          uses apply-group;
          uses apply-macro;
          list field-extra-name {
            key "name";
            leaf name {
              type string;
            }
            uses apply-group;
            uses apply-macro;
          }
          list field-name {
            key "name";
            ordered-by user;
            leaf name {
              type string;
            }
            uses apply-group;
            uses apply-macro;
          }
        }
        container ssl-proxy {
          presence "enable ssl-proxy";
          uses apply-group;
          uses apply-macro;
          list field-extra-name {
            key "name";
            leaf name {
              type string;
            }
            uses apply-group;
            uses apply-macro;
          }
          list field-name {
            key "name";
            ordered-by user;
            leaf name {
              type string;
            }
            uses apply-group;
            uses apply-macro;
          }
        }
        container apptrack {
          presence "enable apptrack";
          uses apply-group;
          uses apply-macro;
          list field-extra-name {
            key "name";
            leaf name {
              type string;
            }
            uses apply-group;
            uses apply-macro;
          }
          list field-name {
            key "name";
            ordered-by user;
            leaf name {
              type string;
            }
            uses apply-group;
            uses apply-macro;
          }
        }
      }
      container default-profile {
        presence "enable default-profile";
        uses apply-group;
        uses apply-macro;
        leaf activate {
          type empty;
        }
      }
      container template {
        presence "enable template";
        uses apply-group;
        uses apply-macro;
        choice choice-traditional-firewall {
          leaf traditional-firewall {
            type empty;
          }
          leaf unified-ngfw {
            type empty;
          }
          leaf sd-wan {
            type empty;
          }
        }
      }
    }
  }

  grouping host-object {
    uses apply-group;
    uses apply-macro;
    leaf ipaddr {
      type ipaddr;
    }
    leaf port {
      type uint16;
    }
    leaf routing-instance {
      type string;
    }
    leaf log-tag {
      type string;
    }
  }

  grouping idp-policy-type {
    leaf name {
      type string;
    }
    uses apply-group;
    uses apply-macro;
    container rulebase-ips {
      uses apply-group;
      uses apply-macro;
      list rule {
        key "name";
        ordered-by user;
        leaf name {
          type string;
        }
        uses apply-group;
        uses apply-macro;
        leaf description {
          type string;
        }
        container match {
          uses apply-group;
          uses apply-macro;
          leaf from-zone {
            type string;
          }
          choice choice-5 {
            leaf-list source-address {
              ordered-by user;
              type string;
            }
            leaf-list source-except {
              ordered-by user;
              type string;
            }
            leaf-list source-prefix {
              type ipv4prefix;
              ordered-by user;
            }
            leaf-list source-prefix-except {
              type ipv4prefix;
              ordered-by user;
            }
          }
          leaf to-zone {
            type string;
          }
          choice choice-8 {
            leaf-list destination-address {
              ordered-by user;
              type string;
            }
            leaf-list destination-except {
              ordered-by user;
              type string;
            }
            leaf-list destination-prefix {
              type ipv4prefix;
              ordered-by user;
            }
            leaf-list destination-prefix-except {
              type ipv4prefix;
              ordered-by user;
            }
          }
          leaf application {
            type string;
          }
          container attacks {
            uses apply-group;
            uses apply-macro;
            leaf-list custom-attacks {
              type string;
              ordered-by user;
            }
            leaf-list custom-attack-groups {
              type string;
              ordered-by user;
            }
            leaf-list dynamic-attack-groups {
              type string;
              ordered-by user;
            }
            leaf-list predefined-attacks {
              type string;
              ordered-by user;
            }
            leaf-list predefined-attack-groups {
              type string;
              ordered-by user;
            }
          }
        }
        container then {
          presence "";
          uses apply-group;
          uses apply-macro;
          container action {
            choice choice-3 {
              leaf no-action {
                type empty;
              }
              leaf ignore-connection {
                type empty;
              }
              container mark-diffserv {
                presence "";
                uses apply-group;
                uses apply-macro;
                leaf codepoint {
                  type uint32;
                }
              }
              leaf drop-packet {
                type empty;
              }
              leaf drop-connection {
                type empty;
              }
              leaf close-client {
                type empty;
              }
              leaf close-server {
                type empty;
              }
              leaf close-client-and-server {
                type empty;
              }
              leaf recommended {
                type empty;
              }
            }
          }
          container ip-action {
            uses apply-group;
            uses apply-macro;
            choice choice-3 {
              leaf ip-notify {
                type empty;
              }
              leaf ip-close {
                type empty;
              }
              leaf ip-block {
                type empty;
              }
            }
            leaf target {
              type string;
            }
            leaf log {
              type empty;
            }
            leaf timeout {
              type uint32;
            }
            leaf refresh-timeout {
              type empty;
            }
          }
          container notification {
            presence "enable notification";
            uses apply-group;
            uses apply-macro;
            container log-attacks {
              presence "enable log-attacks";
              uses apply-group;
              uses apply-macro;
              leaf alert {
                type empty;
              }
            }
            container packet-log {
              presence "enable packet-log";
              uses apply-group;
              uses apply-macro;
              leaf pre-attack {
                type uint32;
              }
              leaf post-attack {
                type uint32;
              }
              leaf post-attack-timeout {
                type uint32;
              }
            }
          }
          leaf severity {
            type string;
          }
        }
        leaf terminal {
          type empty;
        }
      }
    }
    container rulebase-exempt {
      uses apply-group;
      uses apply-macro;
      list rule {
        key "name";
        ordered-by user;
        leaf name {
          type string;
        }
        uses apply-group;
        uses apply-macro;
        leaf description {
          type string;
        }
        container match {
          uses apply-group;
          uses apply-macro;
          leaf from-zone {
            type string;
          }
          choice choice-5 {
            leaf-list source-address {
              ordered-by user;
              type string;
            }
            leaf-list source-except {
              ordered-by user;
              type string;
            }
            leaf-list source-prefix {
              type ipv4prefix;
              ordered-by user;
            }
            leaf-list source-prefix-except {
              type ipv4prefix;
              ordered-by user;
            }
          }
          leaf to-zone {
            type string;
          }
          choice choice-8 {
            leaf-list destination-address {
              ordered-by user;
              type string;
            }
            leaf-list destination-except {
              ordered-by user;
              type string;
            }
            leaf-list destination-prefix {
              type ipv4prefix;
              ordered-by user;
            }
            leaf-list destination-prefix-except {
              type ipv4prefix;
              ordered-by user;
            }
          }
          container attacks {
            uses apply-group;
            uses apply-macro;
            leaf-list custom-attacks {
              type string;
              ordered-by user;
            }
            leaf-list custom-attack-groups {
              type string;
              ordered-by user;
            }
            leaf-list dynamic-attack-groups {
              type string;
              ordered-by user;
            }
            leaf-list predefined-attacks {
              type string;
              ordered-by user;
            }
            leaf-list predefined-attack-groups {
              type string;
              ordered-by user;
            }
          }
        }
      }
    }
    container rulebase-ddos {
      uses apply-group;
      uses apply-macro;
      list rule {
        key "name";
        ordered-by user;
        leaf name {
          type string;
        }
        uses apply-group;
        uses apply-macro;
        leaf description {
          type string;
        }
        container match {
          uses apply-group;
          uses apply-macro;
          leaf from-zone {
            type string;
          }
          choice choice-5 {
            leaf-list source-address {
              ordered-by user;
              type string;
            }
            leaf-list source-except {
              ordered-by user;
              type string;
            }
            leaf-list source-prefix {
              type ipv4prefix;
              ordered-by user;
            }
            leaf-list source-prefix-except {
              type ipv4prefix;
              ordered-by user;
            }
          }
          leaf to-zone {
            type string;
          }
          choice choice-8 {
            leaf-list destination-address {
              ordered-by user;
              type string;
            }
            leaf-list destination-except {
              ordered-by user;
              type string;
            }
            leaf-list destination-prefix {
              type ipv4prefix;
              ordered-by user;
            }
            leaf-list destination-prefix-except {
              type ipv4prefix;
              ordered-by user;
            }
          }
          leaf application {
            type string;
          }
          container application-ddos {
            presence "";
            uses apply-group;
            uses apply-macro;
            leaf application-name {
              type string;
            }
          }
        }
        container then {
          presence "";
          uses apply-group;
          uses apply-macro;
          container action {
            choice choice-3 {
              leaf no-action {
                type empty;
              }
              leaf drop-packet {
                type empty;
              }
              leaf drop-connection {
                type empty;
              }
              leaf close-server {
                type empty;
              }
            }
          }
          container ip-action {
            uses apply-group;
            uses apply-macro;
            choice choice-3 {
              leaf ip-notify {
                type empty;
              }
              leaf ip-block {
                type empty;
              }
              leaf ip-close {
                type empty;
              }
              leaf ip-connection-rate-limit {
                type uint32;
              }
            }
            leaf log {
              type empty;
            }
            leaf timeout {
              type uint32;
            }
            leaf refresh-timeout {
              type empty;
            }
          }
          container notification {
            uses apply-group;
            uses apply-macro;
            container log-attacks {
              presence "enable log-attacks";
              uses apply-group;
              uses apply-macro;
              leaf alert {
                type empty;
              }
            }
          }
        }
      }
    }
  }

  grouping idpd-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    list flag {
      key "name";
      ordered-by user;
      leaf name {
        type string;
      }
    }
    leaf level {
      type string;
    }
  }

  grouping ids-option-type {
    leaf name {
      type key-attribute-string-type;
    }
    uses apply-group;
    uses apply-macro;
    leaf description {
      type string;
    }
    leaf alarm-without-drop {
      type empty;
    }
    container icmp {
      uses apply-group;
      uses apply-macro;
      container ip-sweep {
        presence "enable ip-sweep";
        leaf threshold {
          type uint32;
        }
      }
      leaf fragment {
        type empty;
      }
      leaf large {
        type empty;
      }
      container flood {
        presence "enable flood";
        leaf threshold {
          type uint32;
        }
      }
      leaf ping-death {
        type empty;
      }
    }
    container ip {
      uses apply-group;
      uses apply-macro;
      leaf bad-option {
        type empty;
      }
      leaf record-route-option {
        type empty;
      }
      leaf timestamp-option {
        type empty;
      }
      leaf security-option {
        type empty;
      }
      leaf stream-option {
        type empty;
      }
      leaf spoofing {
        type empty;
      }
      leaf source-route-option {
        type empty;
      }
      leaf loose-source-route-option {
        type empty;
      }
      leaf strict-source-route-option {
        type empty;
      }
      leaf unknown-protocol {
        type empty;
      }
      leaf block-frag {
        type empty;
      }
      leaf tear-drop {
        type empty;
      }
    }
    container tcp {
      uses apply-group;
      uses apply-macro;
      leaf syn-fin {
        type empty;
      }
      leaf fin-no-ack {
        type empty;
      }
      leaf tcp-no-flag {
        type empty;
      }
      leaf syn-frag {
        type empty;
      }
      container port-scan {
        presence "enable port-scan";
        leaf threshold {
          type uint32;
        }
      }
      container syn-ack-ack-proxy {
        presence "enable syn-ack-ack-proxy";
        leaf threshold {
          type uint32;
        }
      }
      container syn-flood {
        presence "enable syn-flood";
        uses apply-group;
        uses apply-macro;
        leaf alarm-threshold {
          type uint32;
        }
        leaf attack-threshold {
          type uint32;
        }
        leaf source-threshold {
          type uint32;
        }
        leaf destination-threshold {
          type uint32;
        }
        leaf timeout {
          type uint32;
        }
        container undocumented {
          leaf queue-size {
            type uint32;
          }
        }
      }
      leaf land {
        type empty;
      }
      leaf winnuke {
        type empty;
      }
      container tcp-sweep {
        presence "enable tcp-sweep";
        leaf threshold {
          type uint32;
        }
      }
    }
    container udp {
      uses apply-group;
      uses apply-macro;
      container flood {
        presence "enable flood";
        leaf threshold {
          type uint32;
        }
      }
      container udp-sweep {
        presence "enable udp-sweep";
        leaf threshold {
          type uint32;
        }
      }
    }
    container limit-session {
      uses apply-group;
      uses apply-macro;
      leaf source-ip-based {
        type uint32;
      }
      leaf destination-ip-based {
        type uint32;
      }
    }
  }

  grouping ids-rule-object {
    leaf name {
      type key-attribute-string-type;
    }
    uses apply-group;
    uses apply-macro;
    leaf match-direction {
      type string;
    }
    list term {
      key "name";
      ordered-by user;
      leaf name {
        type key-attribute-string-type;
      }
      uses apply-group;
      uses apply-macro;
      container from {
        uses sfw-match-object;
      }
      container then {
        uses apply-group;
        uses apply-macro;
        choice choice-3 {
          leaf force-entry {
            type empty;
          }
          leaf ignore-entry {
            type empty;
          }
          leaf user-interface {
            type string;
          }
        }
        container aggregation {
          uses apply-group;
          uses apply-macro;
          leaf source-prefix {
            type int32;
          }
          leaf destination-prefix {
            type int32;
          }
          leaf source-prefix-ipv6 {
            type int32;
          }
          leaf destination-prefix-ipv6 {
            type int32;
          }
        }
        container logging {
          uses apply-group;
          uses apply-macro;
          leaf threshold {
            type int32;
          }
          leaf syslog {
            type empty;
          }
        }
        container syn-cookie {
          presence "";
          uses apply-group;
          uses apply-macro;
          leaf threshold {
            type int32;
          }
          leaf mss {
            type int32;
          }
        }
        container session-limit {
          uses apply-group;
          uses apply-macro;
          container by-source {
            presence "enable by-source";
            uses ids-limit-type;
          }
          container by-destination {
            presence "enable by-destination";
            uses ids-limit-type;
          }
          container by-pair {
            presence "enable by-pair";
            uses ids-limit-type;
          }
        }
      }
    }
  }

  grouping ids-limit-type {
    uses apply-group;
    uses apply-macro;
    leaf maximum {
      type string;
    }
    leaf rate {
      type string;
    }
    leaf packets {
      type string;
    }
    leaf hold-time {
      type int32;
    }
  }

  grouping inet6-dialer-filter {
    leaf name {
      type string;
    }
    uses apply-group;
    uses apply-macro;
    leaf-list accounting-profile {
      type string;
      ordered-by user;
    }
    list term {
      key "name";
      ordered-by user;
      leaf name {
        type string;
      }
      uses apply-group;
      uses apply-macro;
      container from {
        uses apply-group;
        uses apply-macro;
        list source-address {
          key "name";
          ordered-by user;
          uses firewall-addr6-object;
        }
        list destination-address {
          key "name";
          ordered-by user;
          uses firewall-addr6-object;
        }
        list address {
          key "name";
          ordered-by user;
          uses firewall-addr6-object;
        }
        list source-prefix-list {
          key "name";
          ordered-by user;
          uses firewall-prefix-list;
        }
        list destination-prefix-list {
          key "name";
          ordered-by user;
          uses firewall-prefix-list;
        }
        list prefix-list {
          key "name";
          ordered-by user;
          uses firewall-prefix-list;
        }
        choice choice-15 {
          leaf-list packet-length {
            type string;
            ordered-by user;
          }
          leaf-list packet-length-except {
            type string;
            ordered-by user;
          }
        }
        choice choice-16 {
          leaf-list next-header {
            ordered-by user;
            type string;
          }
          leaf-list next-header-except {
            ordered-by user;
            type string;
          }
        }
        choice choice-17 {
          leaf-list icmp-type {
            ordered-by user;
            type string;
          }
          leaf-list icmp-type-except {
            ordered-by user;
            type string;
          }
        }
        choice choice-18 {
          leaf-list icmp-code {
            ordered-by user;
            type string;
          }
          leaf-list icmp-code-except {
            ordered-by user;
            type string;
          }
        }
        choice choice-19 {
          leaf-list source-port {
            ordered-by user;
            type string;
          }
          leaf-list source-port-except {
            ordered-by user;
            type string;
          }
        }
        choice choice-20 {
          leaf-list destination-port {
            ordered-by user;
            type string;
          }
          leaf-list destination-port-except {
            ordered-by user;
            type string;
          }
        }
        choice choice-21 {
          leaf-list port {
            ordered-by user;
            type string;
          }
          leaf-list port-except {
            ordered-by user;
            type string;
          }
        }
      }
      container then {
        uses apply-group;
        uses apply-macro;
        leaf log {
          type empty;
        }
        leaf syslog {
          type empty;
        }
        leaf sample {
          type empty;
        }
        choice choice-9 {
          leaf note {
            type empty;
          }
          leaf ignore {
            type empty;
          }
        }
      }
    }
  }

  grouping firewall-addr6-object {
    leaf name {
      type ipv6prefix;
    }
    uses apply-group;
    uses apply-macro;
    leaf except {
      type empty;
    }
  }

  grouping inet6-filter {
    leaf name {
      type string;
    }
    uses apply-group;
    uses apply-macro;
    leaf promote {
      type string;
    }
    leaf-list accounting-profile {
      type string;
      ordered-by user;
    }
    leaf interface-specific {
      type empty;
    }
    leaf scale-optimized {
      type empty;
    }
    leaf enhanced-mode {
      type empty;
    }
    leaf interface-shared {
      type empty;
    }
    leaf enhanced-mode-override {
      type empty;
    }
    leaf physical-interface-filter {
      type empty;
    }
    leaf fast-lookup-filter {
      type empty;
    }
    leaf instance-shared {
      type empty;
    }
    list term {
      key "name";
      ordered-by user;
      leaf name {
        type string;
      }
      uses apply-group;
      uses apply-macro;
      leaf filter {
        type string;
      }
      container from {
        uses apply-group;
        uses apply-macro;
        choice choice-3 {
          leaf-list destination-class {
            type string;
            ordered-by user;
          }
          leaf-list destination-class-except {
            type string;
            ordered-by user;
          }
          leaf-list source-class {
            type string;
            ordered-by user;
          }
          leaf-list source-class-except {
            type string;
            ordered-by user;
          }
        }
        choice choice-4 {
          leaf-list interface-group {
            type string;
            ordered-by user;
          }
          leaf-list interface-group-except {
            type string;
            ordered-by user;
          }
        }
        list source-address {
          key "name";
          ordered-by user;
          uses firewall-addr6-object;
        }
        list destination-address {
          key "name";
          ordered-by user;
          uses firewall-addr6-object;
        }
        list address {
          key "name";
          ordered-by user;
          uses firewall-addr6-object;
        }
        list source-prefix-list {
          key "name";
          ordered-by user;
          uses firewall-prefix-list;
        }
        list destination-prefix-list {
          key "name";
          ordered-by user;
          uses firewall-prefix-list;
        }
        list prefix-list {
          key "name";
          ordered-by user;
          uses firewall-prefix-list;
        }
        choice choice-17 {
          leaf-list next-header {
            ordered-by user;
            type string;
          }
          leaf-list next-header-except {
            ordered-by user;
            type string;
          }
        }
        choice choice-payload-protocol {
          leaf-list payload-protocol {
            ordered-by user;
            type string;
          }
          leaf-list payload-protocol-except {
            ordered-by user;
            type string;
          }
        }
        choice choice-18 {
          leaf-list source-port {
            ordered-by user;
            type string;
          }
          leaf-list source-port-except {
            ordered-by user;
            type string;
          }
        }
        choice choice-19 {
          leaf-list destination-port {
            ordered-by user;
            type string;
          }
          leaf-list destination-port-except {
            ordered-by user;
            type string;
          }
        }
        choice choice-20 {
          leaf-list port {
            ordered-by user;
            type string;
          }
          leaf-list port-except {
            ordered-by user;
            type string;
          }
        }
        choice choice-extension-header {
          leaf-list extension-header {
            ordered-by user;
            type string;
          }
          leaf-list extension-header-except {
            ordered-by user;
            type string;
          }
        }
        choice choice-21 {
          leaf-list packet-length {
            type string;
            ordered-by user;
          }
          leaf-list packet-length-except {
            type string;
            ordered-by user;
          }
        }
        choice choice-22 {
          leaf-list traffic-class {
            ordered-by user;
            type string;
          }
          leaf-list traffic-class-except {
            ordered-by user;
            type string;
          }
        }
        choice choice-23 {
          leaf-list icmp-type {
            ordered-by user;
            type string;
          }
          leaf-list icmp-type-except {
            ordered-by user;
            type string;
          }
        }
        choice choice-24 {
          leaf-list icmp-code {
            ordered-by user;
            type string;
          }
          leaf-list icmp-code-except {
            ordered-by user;
            type string;
          }
        }
        leaf tcp-initial {
          type empty;
        }
        leaf tcp-established {
          type empty;
        }
        leaf tcp-flags {
          type string;
        }
        list interface {
          key "name";
          ordered-by user;
          uses match-interface-object;
        }
        list interface-set {
          key "name";
          ordered-by user;
          uses match-interface-set-object;
        }
        choice choice-35 {
          leaf-list forwarding-class {
            type string;
            ordered-by user;
          }
          leaf-list forwarding-class-except {
            type string;
            ordered-by user;
          }
        }
        choice choice-36 {
          leaf-list loss-priority {
            ordered-by user;
            type string;
          }
          leaf-list loss-priority-except {
            ordered-by user;
            type string;
          }
        }
        leaf service-filter-hit {
          type empty;
        }
        choice choice-hop-limit {
          leaf-list hop-limit {
            type string;
            ordered-by user;
          }
          leaf-list hop-limit-except {
            type string;
            ordered-by user;
          }
        }
        leaf is-fragment {
          type empty;
        }
        leaf first-fragment {
          type empty;
        }
        leaf last-fragment {
          type empty;
        }
        choice flex-mask_choice {
          case case_1 {
            container flexible-match-mask {
              presence "enable flexible-match-mask";
              uses match_L3_flexible_mask;
            }
          }
        }
        choice flex-range_choice {
          case case_1 {
            container flexible-match-range {
              presence "enable flexible-match-range";
              uses match_L3_flexible_range;
            }
          }
        }
        choice gre-key_choice {
          case case_1 {
            leaf-list gre-key {
              ordered-by user;
              type string;
            }
          }
          case case_2 {
            leaf-list gre-key-except {
              ordered-by user;
              type string;
            }
          }
        }
        choice policy-map_choice {
          case case_1 {
            leaf-list policy-map {
              ordered-by user;
              type string;
            }
          }
          case case_2 {
            leaf-list policy-map-except {
              ordered-by user;
              type string;
            }
          }
        }
        choice slice_choice {
          case case_1 {
            leaf-list slice {
              ordered-by user;
              type string;
            }
          }
          case case_2 {
            leaf-list slice-except {
              ordered-by user;
              type string;
            }
          }
        }
        container vxlan {
          uses apply-advanced;
          choice vni_choice {
            case case_1 {
              leaf-list vni {
                ordered-by user;
                type string;
              }
            }
            case case_2 {
              leaf-list vni-except {
                ordered-by user;
                type string;
              }
            }
          }
          choice rsvd1_choice {
            case case_1 {
              leaf-list rsvd1 {
                ordered-by user;
                type string;
              }
            }
            case case_2 {
              leaf-list rsvd1-except {
                ordered-by user;
                type string;
              }
            }
          }
          choice rsvd2_choice {
            case case_1 {
              leaf-list rsvd2 {
                ordered-by user;
                type string;
              }
            }
            case case_2 {
              leaf-list rsvd2-except {
                ordered-by user;
                type string;
              }
            }
          }
          container flags {
            uses match-flags-value;
          }
        }
        container gtp-header {
          uses apply-advanced;
          leaf-list gtp-teid {
            ordered-by user;
            type string;
          }
          container ipv4 {
            presence "enable ipv4";
            uses apply-advanced;
            choice protocol_choice {
              case case_1 {
                leaf-list protocol {
                  ordered-by user;
                  type string;
                }
              }
              case case_2 {
                leaf-list protocol-except {
                  ordered-by user;
                  type string;
                }
              }
            }
            choice source-port_choice {
              case case_1 {
                leaf-list source-port {
                  ordered-by user;
                  type string;
                }
              }
              case case_2 {
                leaf-list source-port-except {
                  ordered-by user;
                  type string;
                }
              }
            }
            choice destination-port_choice {
              case case_1 {
                leaf-list destination-port {
                  ordered-by user;
                  type string;
                }
              }
              case case_2 {
                leaf-list destination-port-except {
                  ordered-by user;
                  type string;
                }
              }
            }
            list source-address {
              key "name";
              ordered-by user;
              uses firewall-addr-object;
            }
            list destination-address {
              key "name";
              ordered-by user;
              uses firewall-addr-object;
            }
            list source-prefix-list {
              key "name";
              ordered-by user;
              uses firewall-prefix-list;
            }
            list destination-prefix-list {
              key "name";
              ordered-by user;
              uses firewall-prefix-list;
            }
          }
          container ipv6 {
            presence "enable ipv6";
            uses apply-advanced;
            choice next-header_choice {
              case case_1 {
                leaf-list next-header {
                  ordered-by user;
                  type string;
                }
              }
              case case_2 {
                leaf-list next-header-except {
                  ordered-by user;
                  type string;
                }
              }
            }
            choice source-port_choice {
              case case_1 {
                leaf-list source-port {
                  ordered-by user;
                  type string;
                }
              }
              case case_2 {
                leaf-list source-port-except {
                  ordered-by user;
                  type string;
                }
              }
            }
            choice destination-port_choice {
              case case_1 {
                leaf-list destination-port {
                  ordered-by user;
                  type string;
                }
              }
              case case_2 {
                leaf-list destination-port-except {
                  ordered-by user;
                  type string;
                }
              }
            }
            list source-address {
              key "name";
              ordered-by user;
              uses firewall_addr6_object;
            }
            list destination-address {
              key "name";
              ordered-by user;
              uses firewall_addr6_object;
            }
            list source-prefix-list {
              key "name";
              ordered-by user;
              uses firewall-prefix-list;
            }
            list destination-prefix-list {
              key "name";
              ordered-by user;
              uses firewall-prefix-list;
            }
          }
        }
      }
      container then {
        uses apply-group;
        uses apply-macro;
        choice choice-3 {
          leaf policer {
            type string;
          }
          container three-color-policer {
            uses apply-group;
            uses apply-macro;
            choice choice-3 {
              leaf single-rate {
                type string;
              }
              leaf two-rate {
                type string;
              }
            }
          }
          leaf hierarchical-policer {
            type string;
          }
        }
        choice choice-clear-policy-map {
          leaf clear-policy-map {
            type empty;
          }
          leaf policy-map {
            type string;
          }
        }
        choice choice-traffic-class-count {
          leaf traffic-class-count {
            type string;
          }
          leaf count {
            type string;
          }
        }
        leaf service-accounting {
          type empty;
        }
        leaf service-accounting-deferred {
          type empty;
        }
        leaf log {
          type empty;
        }
        leaf pkt-trace {
          type empty;
        }
        leaf syslog {
          type empty;
        }
        leaf sample {
          type empty;
        }
        leaf port-mirror-instance {
          type string;
        }
        leaf port-mirror {
          type empty;
        }
        leaf inline-monitoring-instance {
          type string;
        }
        leaf analyzer {
          type string;
        }
        leaf l2-mirror {
          type empty;
        }
        leaf loss-priority {
          type string;
        }
        leaf forwarding-class {
          type string;
        }
        leaf traffic-class {
          type string;
        }
        leaf skip-services {
          type empty;
        }
        leaf service-filter-hit {
          type empty;
        }
        leaf force-premium {
          type empty;
        }
        leaf exclude-accounting {
          type empty;
        }
        choice choice-26 {
          container decapsulate {
            presence "enable decapsulate";
            choice choice-gre {
              container gre {
                presence "enable gre";
                uses apply-group;
                uses apply-macro;
                leaf-list sample {
                  ordered-by user;
                  type string;
                }
                leaf no-decrement-ttl {
                  type empty;
                }
                leaf forwarding-class {
                  type string;
                }
                leaf interface-group {
                  type uint32;
                }
                container routing-instance {
                  presence "";
                  leaf routing-instance-name {
                    type string;
                    mandatory true;
                  }
                }
              }
              container gre-in-udp {
                presence "enable gre-in-udp";
                uses apply-group;
                uses apply-macro;
                leaf-list sample {
                  ordered-by user;
                  type string;
                }
                leaf no-decrement-ttl {
                  type empty;
                }
                leaf forwarding-class {
                  type string;
                }
                leaf interface-group {
                  type uint32;
                }
                container routing-instance {
                  presence "";
                  leaf routing-instance-name {
                    type string;
                    mandatory true;
                  }
                }
              }
              container mpls-in-udp {
                presence "enable mpls-in-udp";
                uses apply-group;
                uses apply-macro;
                leaf-list sample {
                  ordered-by user;
                  type string;
                }
                leaf no-decrement-ttl {
                  type empty;
                }
                leaf forwarding-class {
                  type string;
                }
                leaf interface-group {
                  type uint32;
                }
                container routing-instance {
                  presence "";
                  leaf routing-instance-name {
                    type string;
                    mandatory true;
                  }
                }
              }
              container l2tp {
                presence "";
                uses apply-group;
                uses apply-macro;
                leaf-list sample {
                  ordered-by user;
                  type string;
                }
                leaf no-decrement-ttl {
                  type empty;
                }
                leaf forwarding-class {
                  type string;
                }
                leaf interface-group {
                  type uint32;
                }
                leaf-list cookie {
                  ordered-by user;
                  type string;
                }
                leaf output-interface {
                  type interface-unit;
                }
              }
            }
          }
          container encapsulate {
            presence "";
            leaf tunnel-end-point {
              type string;
              mandatory true;
            }
          }
          leaf accept {
            type empty;
          }
          leaf discard {
            type empty;
          }
          leaf next {
            type string;
          }
          leaf next-hop-group {
            type string;
          }
          list logical-system {
            key "logical-system-name";
            ordered-by user;
            leaf logical-system-name {
              type string;
            }
            container routing-instance {
              presence "";
              leaf routing-instance-name {
                type string;
              }
              leaf topology {
                type string;
              }
            }
            leaf topology {
              type string;
            }
          }
          container routing-instance {
            presence "";
            leaf routing-instance-name {
              type string;
            }
            leaf topology {
              type string;
            }
          }
          leaf topology {
            type string;
          }
          container next-ip6 {
            leaf address {
              type ipv6prefix;
            }
            container routing-instance {
              presence "";
              leaf routing-instance-name {
                type string;
                mandatory true;
              }
              leaf topology {
                type string;
              }
            }
          }
          container next-interface {
            presence "";
            uses apply-group;
            uses apply-macro;
            leaf interface-name {
              mandatory true;
              type string;
            }
            container routing-instance {
              presence "";
              leaf routing-instance-name {
                type string;
                mandatory true;
              }
              leaf topology {
                type string;
              }
            }
            choice choice-accept {
              leaf accept {
                type empty;
              }
              leaf next {
                type string;
              }
            }
          }
          container reject {
            presence "enable reject";
            choice choice-3 {
              leaf no-route {
                type empty;
              }
              leaf administratively-prohibited {
                type empty;
              }
              leaf beyond-scope {
                type empty;
              }
              leaf address-unreachable {
                type empty;
              }
              leaf port-unreachable {
                type empty;
              }
              leaf tcp-reset {
                type empty;
              }
              leaf fragmentation-needed {
                type empty;
              }
            }
          }
        }
      }
    }
  }

  grouping inet6-fuf {
    leaf name {
      type string;
    }
    uses apply-group;
    uses apply-macro;
    leaf interface-specific {
      type empty;
    }
    leaf-list match-order {
      ordered-by user;
      type string;
    }
    list term {
      key "name";
      ordered-by user;
      leaf name {
        type string;
      }
      uses apply-group;
      uses apply-macro;
      leaf only-at-create {
        type empty;
      }
      container from {
        uses apply-group;
        uses apply-macro;
        container source-address {
          uses firewall-addr6-simple-object;
        }
        container destination-address {
          uses firewall-addr6-simple-object;
        }
        choice choice-7 {
          container source-port {
            uses match-simple-port-value;
          }
        }
        choice choice-8 {
          container destination-port {
            uses match-simple-port-value;
          }
        }
        choice choice-9 {
          container next-header {
            uses match-simple-protocol-value;
          }
        }
        choice choice-10 {
          container traffic-class {
            uses match-simple-dscp-value;
          }
        }
        leaf match-terms {
          type string;
        }
      }
      container then {
        uses apply-group;
        uses apply-macro;
        choice choice-3 {
          leaf policer {
            type string;
          }
        }
        leaf count {
          type string;
        }
        leaf service-accounting {
          type empty;
        }
        leaf log {
          type empty;
        }
        leaf port-mirror {
          type empty;
        }
        leaf loss-priority {
          type string;
        }
        leaf forwarding-class {
          type string;
        }
        leaf action-terms {
          type string;
        }
        choice choice-18 {
          leaf accept {
            type empty;
          }
          leaf discard {
            type empty;
          }
          container routing-instance {
            presence "";
            leaf routing-instance-name {
              type string;
            }
            leaf topology {
              type string;
            }
          }
        }
      }
    }
  }

  grouping firewall-addr6-simple-object {
    uses apply-group;
    uses apply-macro;
    leaf address {
      type ipv6prefix;
    }
  }

  grouping inet6-service-filter {
    leaf name {
      type string;
    }
    uses apply-group;
    uses apply-macro;
    list term {
      key "name";
      ordered-by user;
      leaf name {
        type string;
      }
      uses apply-group;
      uses apply-macro;
      container from {
        uses apply-group;
        uses apply-macro;
        choice choice-3 {
          leaf-list interface-group {
            type string;
            ordered-by user;
          }
          leaf-list interface-group-except {
            type string;
            ordered-by user;
          }
        }
        list source-address {
          key "name";
          ordered-by user;
          uses firewall-addr6-object;
        }
        list destination-address {
          key "name";
          ordered-by user;
          uses firewall-addr6-object;
        }
        list address {
          key "name";
          ordered-by user;
          uses firewall-addr6-object;
        }
        list source-prefix-list {
          key "name";
          ordered-by user;
          uses firewall-prefix-list;
        }
        list destination-prefix-list {
          key "name";
          ordered-by user;
          uses firewall-prefix-list;
        }
        list prefix-list {
          key "name";
          ordered-by user;
          uses firewall-prefix-list;
        }
        choice choice-16 {
          leaf-list next-header {
            ordered-by user;
            type string;
          }
          leaf-list next-header-except {
            ordered-by user;
            type string;
          }
        }
        choice choice-17 {
          leaf-list source-port {
            ordered-by user;
            type string;
          }
          leaf-list source-port-except {
            ordered-by user;
            type string;
          }
        }
        choice choice-18 {
          leaf-list destination-port {
            ordered-by user;
            type string;
          }
          leaf-list destination-port-except {
            ordered-by user;
            type string;
          }
        }
        choice choice-19 {
          leaf-list port {
            ordered-by user;
            type string;
          }
          leaf-list port-except {
            ordered-by user;
            type string;
          }
        }
        choice choice-20 {
          leaf-list esp-spi {
            type string;
            ordered-by user;
          }
          leaf-list esp-spi-except {
            type string;
            ordered-by user;
          }
        }
        choice choice-21 {
          leaf-list ah-spi {
            type string;
            ordered-by user;
          }
          leaf-list ah-spi-except {
            type string;
            ordered-by user;
          }
        }
        leaf tcp-flags {
          type string;
        }
      }
      container then {
        uses apply-group;
        uses apply-macro;
        leaf count {
          type string;
        }
        leaf log {
          type empty;
        }
        leaf sample {
          type empty;
        }
        leaf port-mirror {
          type empty;
        }
        choice choice-11 {
          leaf service {
            type empty;
          }
          leaf skip {
            type empty;
          }
        }
      }
    }
  }

  grouping inet-dialer-filter {
    leaf name {
      type string;
    }
    uses apply-group;
    uses apply-macro;
    leaf-list accounting-profile {
      type string;
      ordered-by user;
    }
    list term {
      key "name";
      ordered-by user;
      leaf name {
        type string;
      }
      uses apply-group;
      uses apply-macro;
      container from {
        uses apply-group;
        uses apply-macro;
        list source-address {
          key "name";
          ordered-by user;
          uses firewall-addr-object;
        }
        list destination-address {
          key "name";
          ordered-by user;
          uses firewall-addr-object;
        }
        list address {
          key "name";
          ordered-by user;
          uses firewall-addr-object;
        }
        list source-prefix-list {
          key "name";
          ordered-by user;
          uses firewall-prefix-list;
        }
        list destination-prefix-list {
          key "name";
          ordered-by user;
          uses firewall-prefix-list;
        }
        list prefix-list {
          key "name";
          ordered-by user;
          uses firewall-prefix-list;
        }
        choice choice-15 {
          leaf-list packet-length {
            type string;
            ordered-by user;
          }
          leaf-list packet-length-except {
            type string;
            ordered-by user;
          }
        }
        choice choice-16 {
          leaf-list precedence {
            ordered-by user;
            type string;
          }
          leaf-list precedence-except {
            ordered-by user;
            type string;
          }
        }
        choice choice-17 {
          leaf-list dscp {
            ordered-by user;
            type string;
          }
          leaf-list dscp-except {
            ordered-by user;
            type string;
          }
        }
        choice choice-18 {
          leaf-list ip-options {
            ordered-by user;
            type string;
          }
          leaf-list ip-options-except {
            ordered-by user;
            type string;
          }
        }
        leaf is-fragment {
          type empty;
        }
        leaf first-fragment {
          type empty;
        }
        choice choice-23 {
          leaf-list fragment-offset {
            type string;
            ordered-by user;
          }
          leaf-list fragment-offset-except {
            type string;
            ordered-by user;
          }
        }
        leaf fragment-flags {
          type string;
        }
        choice choice-26 {
          leaf-list protocol {
            ordered-by user;
            type string;
          }
          leaf-list protocol-except {
            ordered-by user;
            type string;
          }
        }
        choice choice-27 {
          leaf-list ttl {
            type string;
            ordered-by user;
          }
          leaf-list ttl-except {
            type string;
            ordered-by user;
          }
        }
        choice choice-28 {
          leaf-list icmp-type {
            ordered-by user;
            type string;
          }
          leaf-list icmp-type-except {
            ordered-by user;
            type string;
          }
        }
        choice choice-29 {
          leaf-list icmp-code {
            ordered-by user;
            type string;
          }
          leaf-list icmp-code-except {
            ordered-by user;
            type string;
          }
        }
        choice choice-30 {
          leaf-list source-port {
            ordered-by user;
            type string;
          }
          leaf-list source-port-except {
            ordered-by user;
            type string;
          }
        }
        choice choice-31 {
          leaf-list destination-port {
            ordered-by user;
            type string;
          }
          leaf-list destination-port-except {
            ordered-by user;
            type string;
          }
        }
        choice choice-32 {
          leaf-list port {
            ordered-by user;
            type string;
          }
          leaf-list port-except {
            ordered-by user;
            type string;
          }
        }
        leaf tcp-initial {
          type empty;
        }
        leaf tcp-established {
          type empty;
        }
        leaf tcp-flags {
          type string;
        }
        choice choice-39 {
          leaf-list esp-spi {
            type string;
            ordered-by user;
          }
          leaf-list esp-spi-except {
            type string;
            ordered-by user;
          }
        }
        choice choice-40 {
          leaf-list ah-spi {
            type string;
            ordered-by user;
          }
          leaf-list ah-spi-except {
            type string;
            ordered-by user;
          }
        }
      }
      container then {
        uses apply-group;
        uses apply-macro;
        leaf log {
          type empty;
        }
        leaf syslog {
          type empty;
        }
        leaf sample {
          type empty;
        }
        choice choice-9 {
          leaf note {
            type empty;
          }
          leaf ignore {
            type empty;
          }
        }
      }
    }
  }

  grouping inet-filter {
    leaf name {
      type string;
    }
    uses apply-group;
    uses apply-macro;
    leaf-list accounting-profile {
      type string;
      ordered-by user;
    }
    leaf interface-specific {
      type empty;
    }
    leaf physical-interface-filter {
      type empty;
    }
    leaf enhanced-mode {
      type empty;
    }
    leaf interface-shared {
      type empty;
    }
    leaf enhanced-mode-override {
      type empty;
    }
    leaf instance-shared {
      type empty;
    }
    leaf fast-lookup-filter {
      type empty;
    }
    list term {
      key "name";
      ordered-by user;
      leaf name {
        type string;
      }
      uses apply-group;
      uses apply-macro;
      leaf filter {
        type string;
      }
      container from {
        uses apply-group;
        uses apply-macro;
        choice choice-3 {
          leaf-list destination-class {
            type string;
            ordered-by user;
          }
          leaf-list destination-class-except {
            type string;
            ordered-by user;
          }
          leaf-list source-class {
            type string;
            ordered-by user;
          }
          leaf-list source-class-except {
            type string;
            ordered-by user;
          }
        }
        choice choice-4 {
          leaf-list interface-group {
            type string;
            ordered-by user;
          }
          leaf-list interface-group-except {
            type string;
            ordered-by user;
          }
        }
        list source-address {
          key "name";
          ordered-by user;
          uses firewall-addr-object;
        }
        list destination-address {
          key "name";
          ordered-by user;
          uses firewall-addr-object;
        }
        list address {
          key "name";
          ordered-by user;
          uses firewall-addr-object;
        }
        list source-prefix-list {
          key "name";
          ordered-by user;
          uses firewall-prefix-list;
        }
        list destination-prefix-list {
          key "name";
          ordered-by user;
          uses firewall-prefix-list;
        }
        list prefix-list {
          key "name";
          ordered-by user;
          uses firewall-prefix-list;
        }
        choice choice-17 {
          leaf-list packet-length {
            type string;
            ordered-by user;
          }
          leaf-list packet-length-except {
            type string;
            ordered-by user;
          }
        }
        choice choice-18 {
          leaf-list dscp {
            ordered-by user;
            type string;
          }
          leaf-list dscp-except {
            ordered-by user;
            type string;
          }
        }
        choice choice-19 {
          leaf-list precedence {
            ordered-by user;
            type string;
          }
          leaf-list precedence-except {
            ordered-by user;
            type string;
          }
        }
        choice choice-20 {
          leaf-list ip-options {
            ordered-by user;
            type string;
          }
          leaf-list ip-options-except {
            ordered-by user;
            type string;
          }
        }
        leaf is-fragment {
          type empty;
        }
        leaf first-fragment {
          type empty;
        }
        leaf service-filter-hit {
          type empty;
        }
        choice choice-27 {
          leaf-list fragment-offset {
            type string;
            ordered-by user;
          }
          leaf-list fragment-offset-except {
            type string;
            ordered-by user;
          }
        }
        leaf fragment-flags {
          type string;
        }
        choice choice-30 {
          leaf-list protocol {
            ordered-by user;
            type string;
          }
          leaf-list protocol-except {
            ordered-by user;
            type string;
          }
        }
        choice choice-31 {
          leaf-list ttl {
            type string;
            ordered-by user;
          }
          leaf-list ttl-except {
            type string;
            ordered-by user;
          }
        }
        choice choice-32 {
          leaf-list icmp-type {
            ordered-by user;
            type string;
          }
          leaf-list icmp-type-except {
            ordered-by user;
            type string;
          }
        }
        choice choice-33 {
          leaf-list icmp-code {
            ordered-by user;
            type string;
          }
          leaf-list icmp-code-except {
            ordered-by user;
            type string;
          }
        }
        choice choice-34 {
          leaf-list source-port {
            ordered-by user;
            type string;
          }
          leaf-list source-port-except {
            ordered-by user;
            type string;
          }
        }
        choice choice-35 {
          leaf-list destination-port {
            ordered-by user;
            type string;
          }
          leaf-list destination-port-except {
            ordered-by user;
            type string;
          }
        }
        choice choice-36 {
          leaf-list port {
            ordered-by user;
            type string;
          }
          leaf-list port-except {
            ordered-by user;
            type string;
          }
        }
        leaf tcp-initial {
          type empty;
        }
        leaf tcp-established {
          type empty;
        }
        leaf tcp-flags {
          type string;
        }
        choice choice-43 {
          leaf-list esp-spi {
            type string;
            ordered-by user;
          }
          leaf-list esp-spi-except {
            type string;
            ordered-by user;
          }
        }
        choice choice-44 {
          leaf-list ah-spi {
            type string;
            ordered-by user;
          }
          leaf-list ah-spi-except {
            type string;
            ordered-by user;
          }
        }
        list interface {
          key "name";
          ordered-by user;
          uses match-interface-object;
        }
        list interface-set {
          key "name";
          ordered-by user;
          uses match-interface-set-object;
        }
        choice choice-49 {
          leaf-list forwarding-class {
            type string;
            ordered-by user;
          }
          leaf-list forwarding-class-except {
            type string;
            ordered-by user;
          }
        }
        choice choice-50 {
          leaf-list loss-priority {
            ordered-by user;
            type string;
          }
          leaf-list loss-priority-except {
            ordered-by user;
            type string;
          }
        }
      }
      container then {
        uses apply-group;
        uses apply-macro;
        choice choice-3 {
          leaf policer {
            type string;
          }
          container three-color-policer {
            uses apply-group;
            uses apply-macro;
            choice type-choice {
              case case_1 {
                leaf single-rate {
                  type string;
                }
              }
              case case_2 {
                leaf single-packet-rate {
                  type string;
                }
              }
              case case_3 {
                leaf two-rate {
                  type string;
                }
              }
              case case_4 {
                leaf two-packet-rate {
                  type string;
                }
              }
            }
          }
          leaf hierarchical-policer {
            type string;
          }
        }
        choice policy-map-choice {
          case case_1 {
            leaf clear-policy-map {
              type empty;
            }
          }
          case case_2 {
            leaf policy-map {
              type string;
            }
          }
        }
        leaf slice {
          type string;
        }
        choice inetcnt {
          case case_1 {
            leaf traffic-class-count {
              type string;
            }
          }
          case case_2 {
            leaf count {
              type string;
            }
          }
        }
        leaf service-accounting {
          type empty;
        }
        leaf skip-services {
          type empty;
        }
        leaf service-accounting-deferred {
          type empty;
        }
        leaf log {
          type empty;
        }
        leaf packet-mode {
          type empty;
        }
        leaf syslog {
          type empty;
        }
        leaf packet-capture {
          type empty;
        }
        leaf sample {
          type empty;
        }
        leaf port-mirror-instance {
          type string;
        }
        leaf port-mirror {
          type empty;
        }
        leaf analyzer {
          type string;
        }
        leaf inline-monitoring-instance {
          type string;
        }
        leaf inband-flow-telemetry-init {
          type string;
        }
        leaf inband-flow-telemetry-terminate {
          type string;
        }
        leaf l2-mirror {
          type empty;
        }
        leaf loss-priority {
          type string;
        }
        leaf forwarding-class {
          type string;
        }
        leaf service-filter-hit {
          type empty;
        }
        leaf force-premium {
          type empty;
        }
        leaf virtual-channel {
          type string;
        }
        choice choice-30 {
          leaf accept {
            type empty;
          }
          container discard {
            presence "enable discard";
            uses apply-group;
            uses apply-macro;
            leaf accounting {
              type string;
            }
          }
          leaf next {
            type string;
          }
          list logical-system {
            key "logical-system-name";
            ordered-by user;
            leaf logical-system-name {
              type string;
            }
            container routing-instance {
              presence "";
              leaf routing-instance-name {
                type string;
              }
              leaf topology {
                type string;
              }
            }
            leaf topology {
              type string;
            }
          }
          container routing-instance {
            presence "";
            leaf routing-instance-name {
              type string;
            }
            leaf topology {
              type string;
            }
          }
          leaf topology {
            type string;
          }
          container next-ip {
            leaf address {
              type ipv4prefix;
            }
            container routing-instance {
              presence "";
              leaf routing-instance-name {
                type string;
              }
              leaf topology {
                type string;
              }
            }
          }
          container next-interface {
            presence "";
            uses apply-group;
            uses apply-macro;
            leaf interface-name {
              type string;
            }
            container routing-instance {
              presence "";
              leaf routing-instance-name {
                type string;
              }
              leaf topology {
                type string;
              }
            }
            choice choice-accept {
              leaf accept {
                type empty;
              }
              leaf next {
                type string;
              }
            }
          }
          leaf ipsec-sa {
            type string;
          }
          leaf next-hop-group {
            type string;
          }
          container decapsulate {
            presence "enable decapsulate";
            choice choice-gre {
              container gre {
                presence "enable gre";
                uses apply-group;
                uses apply-macro;
                container routing-instance {
                  presence "";
                  leaf routing-instance-name {
                    type string;
                  }
                  leaf topology {
                    type string;
                  }
                }
                leaf sample {
                  type string;
                }
                leaf no-decrement-ttl {
                  type empty;
                }
                leaf forwarding-class {
                  type string;
                }
              }
              container l2tp {
                presence "";
                uses apply-group;
                uses apply-macro;
                leaf output-interface {
                  type interface-unit;
                }
                leaf-list cookie {
                  ordered-by user;
                  type string;
                }
                leaf sample {
                  type string;
                }
                leaf no-decrement-ttl {
                  type empty;
                }
                leaf forwarding-class {
                  type string;
                }
              }
            }
          }
          container encapsulate {
            presence "";
            leaf tunnel-end-point {
              type string;
            }
          }
          container reject {
            presence "enable reject";
            choice choice-3 {
              leaf network-unreachable {
                type empty;
              }
              leaf host-unreachable {
                type empty;
              }
              leaf protocol-unreachable {
                type empty;
              }
              leaf port-unreachable {
                type empty;
              }
              leaf fragmentation-needed {
                type empty;
              }
              leaf source-route-failed {
                type empty;
              }
              leaf network-unknown {
                type empty;
              }
              leaf host-unknown {
                type empty;
              }
              leaf source-host-isolated {
                type empty;
              }
              leaf network-prohibited {
                type empty;
              }
              leaf host-prohibited {
                type empty;
              }
              leaf bad-network-tos {
                type empty;
              }
              leaf bad-host-tos {
                type empty;
              }
              leaf administratively-prohibited {
                type empty;
              }
              leaf precedence-violation {
                type empty;
              }
              leaf precedence-cutoff {
                type empty;
              }
              leaf tcp-reset {
                type empty;
              }
            }
          }
          leaf load-balance {
            type string;
          }
        }
        leaf dscp {
          type string;
        }
        leaf prefix-action {
          type string;
        }
      }
    }
  }

  grouping inet-fuf {
    leaf name {
      type string;
    }
    uses apply-group;
    uses apply-macro;
    leaf interface-specific {
      type empty;
    }
    leaf-list match-order {
      ordered-by user;
      type string;
    }
    list term {
      key "name";
      ordered-by user;
      leaf name {
        type string;
      }
      uses apply-group;
      uses apply-macro;
      leaf only-at-create {
        type empty;
      }
      container from {
        uses apply-group;
        uses apply-macro;
        container source-address {
          uses firewall-addr-simple-object;
        }
        container destination-address {
          uses firewall-addr-simple-object;
        }
        choice choice-7 {
          container source-port {
            uses match-simple-port-value;
          }
        }
        choice choice-8 {
          container destination-port {
            uses match-simple-port-value;
          }
        }
        choice choice-9 {
          container protocol {
            uses match-simple-protocol-value;
          }
        }
        choice choice-10 {
          container dscp {
            uses match-simple-dscp-value;
          }
        }
        leaf match-terms {
          type string;
        }
      }
      container then {
        uses apply-group;
        uses apply-macro;
        choice choice-3 {
          leaf policer {
            type string;
          }
        }
        leaf count {
          type string;
        }
        leaf service-accounting {
          type empty;
        }
        leaf log {
          type empty;
        }
        leaf port-mirror {
          type empty;
        }
        leaf loss-priority {
          type string;
        }
        leaf forwarding-class {
          type string;
        }
        leaf action-terms {
          type string;
        }
        choice choice-18 {
          leaf accept {
            type empty;
          }
          leaf discard {
            type empty;
          }
          container routing-instance {
            presence "";
            leaf routing-instance-name {
              type string;
            }
            leaf topology {
              type string;
            }
          }
        }
      }
    }
  }

  grouping firewall-addr-simple-object {
    uses apply-group;
    uses apply-macro;
    leaf address {
      type ipv4prefix;
    }
  }

  grouping inet-service-filter {
    leaf name {
      type string;
    }
    uses apply-group;
    uses apply-macro;
    list term {
      key "name";
      ordered-by user;
      leaf name {
        type string;
      }
      uses apply-group;
      uses apply-macro;
      container from {
        uses apply-group;
        uses apply-macro;
        choice choice-3 {
          leaf-list interface-group {
            type string;
            ordered-by user;
          }
          leaf-list interface-group-except {
            type string;
            ordered-by user;
          }
        }
        list source-address {
          key "name";
          ordered-by user;
          uses firewall-addr-object;
        }
        list destination-address {
          key "name";
          ordered-by user;
          uses firewall-addr-object;
        }
        list address {
          key "name";
          ordered-by user;
          uses firewall-addr-object;
        }
        list source-prefix-list {
          key "name";
          ordered-by user;
          uses firewall-prefix-list;
        }
        list destination-prefix-list {
          key "name";
          ordered-by user;
          uses firewall-prefix-list;
        }
        list prefix-list {
          key "name";
          ordered-by user;
          uses firewall-prefix-list;
        }
        choice choice-16 {
          leaf-list protocol {
            ordered-by user;
            type string;
          }
          leaf-list protocol-except {
            ordered-by user;
            type string;
          }
        }
        choice choice-17 {
          leaf-list ip-options {
            ordered-by user;
            type string;
          }
          leaf-list ip-options-except {
            ordered-by user;
            type string;
          }
        }
        choice choice-18 {
          leaf-list source-port {
            ordered-by user;
            type string;
          }
          leaf-list source-port-except {
            ordered-by user;
            type string;
          }
        }
        choice choice-19 {
          leaf-list destination-port {
            ordered-by user;
            type string;
          }
          leaf-list destination-port-except {
            ordered-by user;
            type string;
          }
        }
        choice choice-20 {
          leaf-list port {
            ordered-by user;
            type string;
          }
          leaf-list port-except {
            ordered-by user;
            type string;
          }
        }
        choice choice-21 {
          leaf-list esp-spi {
            type string;
            ordered-by user;
          }
          leaf-list esp-spi-except {
            type string;
            ordered-by user;
          }
        }
        leaf is-fragment {
          type empty;
        }
        leaf first-fragment {
          type empty;
        }
        choice choice-26 {
          leaf-list fragment-offset {
            type string;
            ordered-by user;
          }
          leaf-list fragment-offset-except {
            type string;
            ordered-by user;
          }
        }
        leaf fragment-flags {
          type string;
        }
        leaf tcp-flags {
          type string;
        }
        choice choice-31 {
          leaf-list ah-spi {
            type string;
            ordered-by user;
          }
          leaf-list ah-spi-except {
            type string;
            ordered-by user;
          }
        }
        choice choice-32 {
          leaf-list loss-priority {
            ordered-by user;
            type string;
          }
          leaf-list loss-priority-except {
            ordered-by user;
            type string;
          }
        }
      }
      container then {
        uses apply-group;
        uses apply-macro;
        leaf count {
          type string;
        }
        leaf log {
          type empty;
        }
        leaf sample {
          type empty;
        }
        leaf port-mirror {
          type empty;
        }
        choice choice-11 {
          leaf service {
            type empty;
          }
          leaf skip {
            type empty;
          }
        }
      }
    }
  }

  grouping inet-simple-filter {
    leaf name {
      type string;
    }
    uses apply-group;
    uses apply-macro;
    list term {
      key "name";
      ordered-by user;
      leaf name {
        type string;
      }
      uses apply-group;
      uses apply-macro;
      container from {
        uses apply-group;
        uses apply-macro;
        container source-address {
          uses firewall-addr-simple-object;
        }
        container destination-address {
          uses firewall-addr-simple-object;
        }
        choice choice-7 {
          container protocol {
            uses match-simple-protocol-value;
          }
        }
        choice choice-8 {
          container source-port {
            uses match-simple-port-value;
          }
        }
        choice choice-9 {
          container destination-port {
            uses match-simple-port-value;
          }
        }
        choice choice-10 {
          leaf-list forwarding-class {
            type string;
            ordered-by user;
          }
        }
        choice choice-11;
      }
      container then {
        uses apply-group;
        uses apply-macro;
        choice choice-3 {
          leaf policer {
            type string;
          }
          container three-color-policer {
            uses apply-group;
            uses apply-macro;
            choice choice-3 {
              leaf single-rate {
                type string;
              }
              leaf two-rate {
                type string;
              }
            }
          }
        }
        leaf loss-priority {
          type string;
        }
        leaf forwarding-class {
          type string;
        }
        leaf discard {
          type empty;
        }
        leaf accept {
          type empty;
        }
      }
    }
  }

  grouping interface-map-type {
    uses apply-group;
    uses apply-macro;
    leaf file-specification {
      type string;
    }
    leaf collector {
      type interface-device;
    }
    list input_intf_to_cpic_map {
      key "name";
      uses input-intf-to-cpic-map-type;
    }
  }

  grouping input-intf-to-cpic-map-type {
    leaf name {
      type interface-name;
    }
    uses apply-group;
    uses apply-macro;
    leaf file-specification {
      type string;
    }
    leaf collector {
      type interface-device;
    }
  }

  grouping interface-set-type {
    leaf name {
      type string;
    }
    uses apply-group;
    uses apply-macro;
    list interface-list {
      key "name";
      ordered-by user;
      leaf name {
        type interface-wildcard;
      }
      uses apply-group;
      uses apply-macro;
    }
  }

  grouping interface-type {
    leaf name {
      type string;
    }
    uses apply-group;
    uses apply-macro;
    leaf queue-statistics {
      type empty;
    }
    leaf no-queue-statistics {
      type empty;
    }
    leaf traffic-statistics {
      type empty;
    }
    leaf no-traffic-statistics {
      type empty;
    }
    leaf resource-profile {
      type string;
    }
  }

  grouping interfaces-type {
    leaf name {
      type string;
    }
    uses apply-group;
    uses apply-macro;
    leaf description {
      type string;
    }
    container undocumented {
      leaf enable {
        type empty;
      }
    }
    leaf external-model-name {
      type string;
    }
    leaf metadata {
      type string;
    }
    choice choice-5 {
      leaf enable {
        type empty;
      }
      leaf disable {
        type empty;
      }
      leaf enable-disable {
        type string;
      }
    }
    leaf promiscuous-mode {
      type empty;
    }
    leaf port-mirror-instance {
      type string;
    }
    leaf multicast-statistics {
      type empty;
    }
    leaf oam-on-svlan {
      type empty;
    }
    container fabric-options {
      uses apply-group;
      uses apply-macro;
      list member-interfaces {
        key "name";
        leaf name {
          type interface-device;
        }
        uses apply-group;
        uses apply-macro;
      }
      container remote-chassis {
        presence "enable remote-chassis";
        uses apply-group;
        uses apply-macro;
        leaf destination {
          type ipv4addr;
        }
      }
    }
    container traceoptions {
      presence "enable traceoptions";
      uses apply-group;
      uses apply-macro;
      list flag {
        key "name";
        ordered-by user;
        leaf name {
          type string;
        }
      }
    }
    leaf passive-monitor-mode {
      type empty;
    }
    choice choice-16 {
      container keepalives {
        presence "enable keepalives";
        uses keepalives-type;
      }
      leaf no-keepalives {
        type empty;
      }
    }
    leaf traps {
      type empty;
    }
    leaf no-traps {
      type empty;
    }
    leaf interface-mib {
      type empty;
    }
    leaf no-interface-mib {
      type empty;
    }
    leaf accounting-profile {
      type string;
    }
    container anchor-point {
      presence "";
      uses apply-group;
      uses apply-macro;
      leaf interface-name {
        mandatory true;
        type interface-device;
      }
    }
    leaf bypass-queueing-chip {
      type empty;
    }
    leaf no-bypass-queueing-chip {
      type empty;
    }
    choice choice-23 {
      leaf per-unit-scheduler {
        type empty;
      }
      leaf no-per-unit-scheduler {
        type empty;
      }
      leaf shared-scheduler {
        type empty;
      }
      container hierarchical-scheduler {
        presence "enable hierarchical-scheduler";
        leaf maximum-hierarchy-levels {
          type uint32;
        }
        leaf maximum-l2-nodes {
          type uint32;
        }
        leaf maximum-l3-nodes {
          type uint32;
        }
        leaf implicit-hierarchy {
          type empty;
        }
      }
    }
    leaf l2tp-maximum-session {
      type uint32;
    }
    leaf schedulers {
      type uint32;
    }
    leaf interface-transmit-statistics {
      type empty;
    }
    leaf cascade-port {
      type empty;
    }
    leaf dce {
      type empty;
    }
    choice choice-30 {
      leaf vlan-tagging {
        type empty;
      }
      leaf stacked-vlan-tagging {
        type empty;
      }
      leaf flexible-vlan-tagging {
        type empty;
      }
      leaf vlan-vci-tagging {
        type empty;
      }
    }
    leaf native-vlan-id {
      type uint32;
    }
    leaf no-native-vlan-insert {
      type empty;
    }
    leaf vlan-offload {
      type empty;
    }
    leaf input-native-vlan-push {
      type string;
    }
    leaf no-pseudowire-down-on-core-isolation {
      type empty;
    }
    leaf number-of-sub-ports {
      type uint32;
    }
    leaf unused {
      type empty;
    }
    leaf speed {
      type string;
    }
    container forwarding-class-accounting {
      presence "enable forwarding-class-accounting";
      uses apply-group;
      uses apply-macro;
      leaf direction {
        type string;
      }
      container enhanced {
        presence "enable enhanced";
        uses apply-group;
        uses apply-macro;
        leaf traffic-type {
          type string;
        }
        leaf family {
          type string;
        }
        leaf direction {
          type string;
        }
        leaf overhead-bytes {
          type uint32;
        }
      }
    }
    container auto-configure {
      uses auto-configure-vlan-type;
    }
    leaf mtu {
      type uint32;
    }
    container hold-time {
      presence "";
      leaf up {
        type uint32;
      }
      leaf down {
        type uint32;
      }
      container undocumented {
        leaf alternative {
          type empty;
        }
      }
    }
    container damping {
      uses apply-group;
      uses apply-macro;
      leaf half-life {
        units "seconds";
        type uint32;
      }
      leaf max-suppress {
        units "seconds";
        type uint32;
      }
      leaf reuse {
        type uint32;
      }
      leaf suppress {
        type uint32;
      }
      leaf enable {
        type empty;
      }
    }
    container link-degrade-monitor {
      presence "enable link-degrade-monitor";
      uses apply-group;
      uses apply-macro;
      choice choice-link-degrade-monitor-enable {
        leaf link-degrade-monitor-enable {
          type empty;
        }
        leaf no-link-degrade-monitor-enable {
          type empty;
        }
      }
      container actions {
        uses apply-group;
        uses apply-macro;
        leaf media-based {
          type empty;
        }
      }
      container recovery {
        uses apply-group;
        uses apply-macro;
        leaf timer {
          type uint32;
        }
        choice choice-auto {
          leaf auto {
            type empty;
          }
          leaf manual {
            type empty;
          }
        }
      }
      container thresholds {
        uses apply-group;
        uses apply-macro;
        leaf set {
          type string;
        }
        leaf clear {
          type string;
        }
        leaf warning-set {
          type string;
        }
        leaf warning-clear {
          type string;
        }
        leaf interval {
          type uint32;
        }
      }
    }
    container satop-options {
      uses apply-group;
      uses apply-macro;
      leaf idle-pattern {
        type uint32;
      }
      leaf payload-size {
        type uint32;
      }
      container excessive-packet-loss-rate {
        uses apply-group;
        uses apply-macro;
        leaf threshold {
          type uint8;
        }
        leaf sample-period {
          type uint32;
        }
      }
      choice choice-9 {
        leaf jitter-buffer-packets {
          type uint32;
        }
        leaf jitter-buffer-latency {
          type uint32;
        }
        leaf jitter-buffer-auto-adjust {
          type empty;
        }
      }
      leaf bit-rate {
        type uint32;
      }
    }
    container cesopsn-options {
      uses apply-group;
      uses apply-macro;
      leaf idle-pattern {
        type uint32;
      }
      leaf packetization-latency {
        units "microseconds";
        type uint32;
      }
      leaf payload-size {
        type uint32;
      }
      container excessive-packet-loss-rate {
        uses apply-group;
        uses apply-macro;
        leaf threshold {
          type uint8;
        }
        leaf sample-period {
          type uint32;
        }
      }
      choice choice-jitter-buffer-packets {
        leaf jitter-buffer-packets {
          type uint32;
        }
        leaf jitter-buffer-latency {
          units "milliseconds";
          type uint32;
        }
        leaf jitter-buffer-auto-adjust {
          type empty;
        }
      }
      leaf bit-rate {
        type uint32;
      }
    }
    container ima-group-options {
      uses apply-group;
      uses apply-macro;
      leaf frame-length {
        type string;
      }
      leaf symmetry {
        type string;
      }
      leaf transmit-clock {
        type string;
      }
      leaf version {
        type string;
      }
      container minimum-links {
        choice choice-3 {
          leaf symmetrical {
            type uint32;
          }
        }
      }
      container frame-synchronization {
        uses apply-group;
        uses apply-macro;
        leaf alpha {
          type uint32;
        }
        leaf beta {
          type uint32;
        }
        leaf gamma {
          type uint32;
        }
      }
      container test-procedure {
        uses apply-group;
        uses apply-macro;
        leaf period {
          type uint32;
        }
        leaf interface {
          type interface-device;
        }
        leaf pattern {
          type uint32;
        }
      }
      leaf differential-delay {
        type uint32;
      }
    }
    container ima-link-options {
      uses apply-group;
      uses apply-macro;
      leaf group-id {
        type uint32;
      }
    }
    list multi-chassis-protection {
      key "name";
      uses multi-chassis-protection-group;
    }
    container clocking {
      presence "enable clocking";
      choice choice-3 {
        leaf internal {
          type empty;
        }
        container external {
          presence "enable external";
          uses apply-group;
          uses apply-macro;
        }
      }
    }
    leaf link-mode {
      type string;
    }
    leaf media-type {
      type string;
    }
    leaf encapsulation {
      type string;
    }
    leaf network-isolation-profile {
      type string;
    }
    container esi {
      presence "";
      uses apply-group;
      uses apply-macro;
      container apply-advanced {
        uses apply-group;
        uses apply-macro;
      }
      container auto-derive {
        choice esitype {
          case case_1 {
            leaf lacp {
              type empty;
            }
          }
        }
      }
      leaf identifier {
        type string;
      }
      choice choice-single-active {
        leaf single-active {
          type empty;
        }
        leaf all-active {
          type empty;
        }
      }
      container df-election-granularity {
        presence "enable df-election-granularity";
        uses apply-advanced;
        choice mode {
          case case_1 {
            container per-esi {
              presence "enable per-esi";
              uses apply-advanced;
              leaf lacp-oos-on-ndf {
                type empty;
              }
            }
          }
          case case_2 {
            leaf per-esi-vlan {
              type empty;
            }
          }
        }
      }
      container df-election-type {
        presence "enable df-election-type";
        uses apply-advanced;
        choice pref_choice {
          case case_1 {
            container preference {
              presence "enable preference";
              uses apply-advanced;
              leaf value {
                type string;
              }
            }
          }
        }
        choice mod_choice {
          case case_1 {
            container mod {
              presence "enable mod";
            }
          }
        }
      }
      leaf source-bmac {
        type mac-unicast;
      }
    }
    container framing {
      uses apply-group;
      uses apply-macro;
      choice choice-3 {
        leaf lan-phy {
          type empty;
        }
        leaf wan-phy {
          type empty;
        }
        leaf sonet {
          type empty;
        }
        leaf sdh {
          type empty;
        }
      }
      leaf precise-bandwidth {
        type empty;
      }
    }
    leaf unidirectional {
      type empty;
    }
    container lmi {
      uses apply-group;
      uses apply-macro;
      leaf n391dte {
        type uint16;
      }
      leaf n392dce {
        type uint16;
      }
      leaf n392dte {
        type uint16;
      }
      leaf n393dce {
        type uint16;
      }
      leaf n393dte {
        type uint16;
      }
      leaf t391dte {
        type uint16;
      }
      leaf t392dce {
        type uint16;
      }
      leaf lmi-type {
        type string;
      }
    }
    container mlfr-uni-nni-bundle-options {
      uses apply-group;
      uses apply-macro;
      container cisco-interoperability {
        uses apply-group;
        uses apply-macro;
        leaf send-lip-remove-link-for-link-reject {
          type empty;
        }
      }
      leaf mrru {
        type uint16;
      }
      leaf yellow-differential-delay {
        type uint16;
      }
      leaf red-differential-delay {
        type uint16;
      }
      leaf action-red-differential-delay {
        type string;
      }
      leaf fragment-threshold {
        type uint32;
      }
      leaf drop-timeout {
        type uint16;
      }
      leaf link-layer-overhead {
        type unsigned-float;
      }
      leaf lmi-type {
        type string;
      }
      leaf minimum-links {
        type uint16;
      }
      leaf hello-timer {
        type uint16;
      }
      leaf acknowledge-timer {
        type uint16;
      }
      leaf acknowledge-retries {
        type uint16;
      }
      leaf n391 {
        type uint16;
      }
      leaf n392 {
        type uint16;
      }
      leaf n393 {
        type uint16;
      }
      leaf t391 {
        type uint16;
      }
      leaf t392 {
        type uint16;
      }
    }
    leaf mac {
      type mac-unicaset;
    }
    container receive-bucket {
      uses dcd-rx-bucket-config;
    }
    container transmit-bucket {
      uses dcd-tx-bucket-config;
    }
    leaf shared-interface {
      type empty;
    }
    container sonet-options {
      uses sonet-options-type;
    }
    container logical-tunnel-options {
      uses apply-group;
      uses apply-macro;
      container link-protection {
        presence "enable link-protection";
        uses apply-group;
        uses apply-macro;
        leaf revertive {
          type empty;
        }
        leaf non-revertive {
          type empty;
        }
      }
      leaf per-unit-mac-disable {
        type empty;
      }
    }
    container aggregated-sonet-options {
      uses apply-group;
      uses apply-macro;
      leaf minimum-links {
        type uint16;
      }
      leaf link-speed {
        type string;
      }
      leaf minimum-bandwidth {
        type uint64;
      }
    }
    container atm-options {
      uses apply-group;
      uses apply-macro;
      leaf pic-type {
        type string;
      }
      leaf cell-bundle-size {
        type uint32;
      }
      leaf plp-to-clp {
        type empty;
      }
      leaf use-null-cw {
        type empty;
      }
      container promiscuous-mode {
        presence "enable promiscuous-mode";
        uses apply-group;
        uses apply-macro;
        list vpi {
          key "name";
          ordered-by user;
          leaf name {
            type string;
          }
        }
      }
      list vpi {
        key "name";
        ordered-by user;
        leaf name {
          type string;
        }
        uses apply-group;
        uses apply-macro;
        leaf maximum-vcs {
          type uint32;
        }
        container shaping {
          uses dcd-shaping-config;
        }
        container oam-period {
          choice choice-3 {
            leaf oam-period {
              type uint32;
            }
            container disable {
              presence "enable disable";
            }
          }
        }
        container oam-liveness {
          uses apply-group;
          uses apply-macro;
          leaf up-count {
            type uint32;
          }
          leaf down-count {
            type uint32;
          }
        }
      }
      container ilmi {
        presence "enable ilmi";
        uses apply-group;
        uses apply-macro;
      }
      list linear-red-profiles {
        key "name";
        ordered-by user;
        leaf name {
          type string;
        }
        leaf queue-depth {
          type string;
        }
        leaf high-plp-threshold {
          type uint32;
        }
        leaf low-plp-threshold {
          type uint32;
        }
        leaf high-plp-max-threshold {
          type uint32;
        }
        leaf low-plp-max-threshold {
          type uint32;
        }
      }
      list scheduler-maps {
        key "name";
        ordered-by user;
        leaf name {
          type string;
        }
        uses apply-group;
        uses apply-macro;
        leaf vc-cos-mode {
          type string;
        }
        list forwarding-class {
          key "name";
          ordered-by user;
          leaf name {
            type string;
          }
          uses apply-group;
          uses apply-macro;
          leaf priority {
            type string;
          }
          container transmit-weight {
            choice choice-3 {
              leaf percent {
                type uint32;
              }
              leaf cells {
                type string;
              }
            }
          }
          choice choice-7 {
            container epd-threshold {
              presence "";
              uses epd-threshold-config;
            }
            leaf linear-red-profile {
              type string;
            }
          }
        }
      }
      container mpls {
        uses mpls-ifd-options;
      }
      leaf payload-scrambler {
        type empty;
      }
      leaf no-payload-scrambler {
        type empty;
      }
    }
    container multiservice-options {
      uses apply-group;
      uses apply-macro;
      leaf syslog {
        type empty;
      }
      leaf no-syslog {
        type empty;
      }
      leaf core-dump {
        type empty;
      }
      leaf no-core-dump {
        type empty;
      }
      container flow-control-options {
        uses apply-group;
        uses apply-macro;
        leaf dump-on-flow-control {
          type empty;
        }
        leaf reset-on-flow-control {
          type empty;
        }
        leaf down-on-flow-control {
          type empty;
        }
      }
    }
    container ggsn-options {
      uses apply-group;
      uses apply-macro;
      leaf syslog {
        type empty;
      }
      leaf no-syslog {
        type empty;
      }
      leaf core-dump {
        type empty;
      }
      leaf no-core-dump {
        type empty;
      }
    }
    container ppp-options {
      uses ppp-options-type;
    }
    container redundancy-options {
      presence "";
      uses apply-group;
      uses apply-macro;
      container undocumented {
        uses undocumented-redundancy-peer;
      }
      leaf primary {
        type interface-device;
      }
      leaf secondary {
        type interface-device;
      }
    }
    container load-balancing-options {
      uses apply-group;
      uses apply-macro;
      list member-interface {
        key "name";
        leaf name {
          type interface-device;
        }
        uses apply-group;
        uses apply-macro;
      }
      container member-failure-options {
        uses apply-group;
        uses apply-macro;
        choice choice-redistribute-all-traffic {
          container redistribute-all-traffic {
            presence "enable redistribute-all-traffic";
            uses apply-group;
            uses apply-macro;
            leaf enable-rejoin {
              type empty;
            }
          }
          container drop-member-traffic {
            presence "enable drop-member-traffic";
            uses apply-group;
            uses apply-macro;
            leaf rejoin-timeout {
              type uint32;
            }
            leaf enable-rejoin {
              type empty;
            }
          }
        }
      }
      container high-availability-options {
        uses apply-group;
        uses apply-macro;
        choice choice-many-to-one {
          container many-to-one {
            uses apply-group;
            uses apply-macro;
            leaf preferred-backup {
              type interface-device;
            }
          }
          container one-to-one {
            uses apply-group;
            uses apply-macro;
            leaf preferred-backup {
              type interface-device;
            }
          }
        }
      }
    }
    container aggregated-inline-services-options {
      uses apply-group;
      uses apply-macro;
      leaf primary-interface {
        type interface-device;
      }
      leaf secondary-interface {
        type interface-device;
      }
    }
    container anchoring-options {
      presence "";
      uses apply-group;
      uses apply-macro;
      leaf apfe-group-set {
        type string;
      }
      list primary-list {
        key "name";
        leaf name {
          type string;
        }
        uses apply-group;
        uses apply-macro;
      }
      container secondary {
        presence "enable secondary";
        uses apply-group;
        uses apply-macro;
        leaf anchoring-device-name {
          type string;
        }
      }
      leaf warm-standby {
        type empty;
      }
    }
    container lsq-failure-options {
      uses apply-group;
      uses apply-macro;
      list trigger-link-failure {
        key "name";
        ordered-by user;
        leaf name {
          type interface-device;
        }
        uses apply-group;
        uses apply-macro;
      }
      leaf no-termination-request {
        type empty;
      }
      leaf no-no-termination-request {
        type empty;
      }
    }
    container redundancy-group {
      uses apply-group;
      uses apply-macro;
      list member-interface {
        key "name";
        leaf name {
          type interface-device;
        }
        uses apply-group;
        uses apply-macro;
        choice choice-active {
          leaf active {
            type empty;
          }
          leaf backup {
            type empty;
          }
        }
      }
      leaf maximum-links {
        type uint32;
      }
    }
    container services-options {
      uses apply-group;
      uses apply-macro;
      leaf utc-timestamp {
        type empty;
      }
      container syslog {
        uses service-set-syslog-object;
      }
      container jflow-log {
        uses apply-group;
        uses apply-macro;
        leaf message-rate-limit {
          units "messages per second";
          type uint32;
        }
      }
      container deterministic-nat-configuration-log-interval {
        presence "enable deterministic-nat-configuration-log-interval";
        uses apply-group;
        uses apply-macro;
        leaf interval {
          units "seconds";
          type uint32;
        }
      }
      leaf open-timeout {
        units "seconds";
        type uint32;
      }
      leaf close-timeout {
        units "seconds";
        type uint32;
      }
      leaf inactivity-timeout {
        units "seconds";
        type uint32;
      }
      leaf inactivity-tcp-timeout {
        units "seconds";
        type uint32;
      }
      leaf inactivity-asymm-tcp-timeout {
        units "seconds";
        type uint32;
      }
      leaf inactivity-non-tcp-timeout {
        units "seconds";
        type uint32;
      }
      leaf session-timeout {
        units "seconds";
        type uint32;
      }
      leaf disable-global-timeout-override {
        type empty;
      }
      leaf tcp-tickles {
        type uint8;
      }
      container trio-flow-offload {
        presence "enable trio-flow-offload";
        uses apply-group;
        uses apply-macro;
        leaf minimum-bytes {
          type uint32;
        }
      }
      leaf fragment-limit {
        type uint8;
      }
      leaf reassembly-timeout {
        units "seconds";
        type uint8;
      }
      leaf cgn-pic {
        type empty;
      }
      leaf pba-interim-logging-interval {
        units "seconds";
        type uint32;
      }
      container session-limit {
        presence "enable session-limit";
        uses apply-group;
        uses apply-macro;
        leaf maximum {
          type string;
        }
        leaf rate {
          type string;
        }
      }
      leaf enable-subscriber-analysis {
        type empty;
      }
      leaf disable-subscriber-analysis {
        type empty;
      }
      leaf disable-usp-tracing {
        type empty;
      }
      leaf disable-drop-flows {
        type empty;
      }
      container ignore-errors {
        presence "enable ignore-errors";
        leaf tcp {
          type empty;
        }
        leaf alg {
          type empty;
        }
      }
      container capture {
        uses apply-group;
        uses apply-macro;
        leaf capture-size {
          type uint32;
        }
        leaf pkt-size {
          type uint16;
        }
        leaf logs-per-packet {
          type uint16;
        }
        leaf max-log-line-size {
          type uint8;
        }
        container filter {
          presence "enable filter";
          uses apply-group;
          uses apply-macro;
          container source-ip {
            presence "";
            leaf ip {
              mandatory true;
              type ipaddr;
            }
            leaf wildcard {
              type ipaddr;
            }
          }
          container dest-ip {
            presence "";
            leaf ip {
              mandatory true;
              type ipaddr;
            }
            leaf wildcard {
              type ipaddr;
            }
          }
          container sw-sip {
            presence "";
            leaf ip {
              mandatory true;
              type ipv6addr;
            }
            leaf wildcard {
              type ipv6addr;
            }
          }
          container sw-dip {
            presence "";
            leaf ip {
              mandatory true;
              type ipaddr;
            }
            leaf wildcard {
              type ipaddr;
            }
          }
          container sport-range {
            presence "";
            leaf low {
              type uint16;
              mandatory true;
            }
            leaf high {
              type uint16;
              mandatory true;
            }
          }
          container dport-range {
            presence "";
            leaf low {
              type uint16;
              mandatory true;
            }
            leaf high {
              type uint16;
              mandatory true;
            }
          }
          leaf proto {
            type string;
          }
        }
      }
      container flow {
        uses apply-group;
        uses apply-macro;
        container traceoptions {
          uses apply-group;
          uses apply-macro;
        }
      }
      leaf fpc-pic-information {
        type empty;
      }
    }
    container t3-options {
      uses apply-group;
      uses apply-macro;
      leaf loopback {
        type string;
      }
      leaf long-buildout {
        type empty;
      }
      leaf no-long-buildout {
        type empty;
      }
      leaf loop-timing {
        type empty;
      }
      leaf no-loop-timing {
        type empty;
      }
      leaf unframed {
        type empty;
      }
      leaf no-unframed {
        type empty;
      }
      container compatibility-mode {
        choice choice-3 {
          container larscom {
            presence "enable larscom";
            leaf subrate {
              type uint32;
            }
          }
          container verilink {
            presence "enable verilink";
            leaf subrate {
              type uint32;
            }
          }
          container adtran {
            presence "enable adtran";
            leaf subrate {
              type uint32;
            }
          }
          container kentrox {
            presence "enable kentrox";
            leaf subrate {
              type uint32;
            }
          }
          container digital-link {
            presence "enable digital-link";
            leaf subrate {
              type string;
            }
          }
        }
      }
      leaf payload-scrambler {
        type empty;
      }
      leaf no-payload-scrambler {
        type empty;
      }
      leaf cbit-parity {
        type empty;
      }
      leaf no-cbit-parity {
        type empty;
      }
      leaf fcs {
        type string;
      }
      leaf idle-cycle-flag {
        type string;
      }
      leaf start-end-flag {
        type string;
      }
      leaf feac-loop-respond {
        type empty;
      }
      leaf no-feac-loop-respond {
        type empty;
      }
      leaf bert-algorithm {
        type string;
      }
      leaf bert-error-rate {
        type uint32;
      }
      leaf bert-period {
        type uint32;
      }
      leaf buildout {
        type uint32;
      }
      leaf atm-encapsulation {
        type string;
      }
    }
    container e3-options {
      uses apply-group;
      uses apply-macro;
      leaf loopback {
        type string;
      }
      leaf unframed {
        type empty;
      }
      leaf no-unframed {
        type empty;
      }
      container compatibility-mode {
        choice choice-3 {
          leaf larscom {
            type empty;
          }
          container digital-link {
            presence "enable digital-link";
            leaf subrate {
              type string;
            }
          }
          container kentrox {
            presence "enable kentrox";
            leaf subrate {
              type uint32;
            }
          }
        }
      }
      leaf payload-scrambler {
        type empty;
      }
      leaf no-payload-scrambler {
        type empty;
      }
      leaf fcs {
        type string;
      }
      leaf idle-cycle-flag {
        type string;
      }
      leaf invert-data {
        type empty;
      }
      leaf start-end-flag {
        type string;
      }
      leaf bert-algorithm {
        type string;
      }
      leaf bert-error-rate {
        type uint32;
      }
      leaf bert-period {
        type uint32;
      }
      leaf buildout {
        type uint32;
      }
      leaf atm-encapsulation {
        type string;
      }
      leaf framing {
        type string;
      }
    }
    container e1-options {
      uses apply-group;
      uses apply-macro;
      leaf timeslots {
        type string;
      }
      leaf loopback {
        type string;
      }
      leaf framing {
        type string;
      }
      leaf fcs {
        type string;
      }
      leaf invert-data {
        type empty;
      }
      leaf idle-cycle-flag {
        type string;
      }
      leaf start-end-flag {
        type string;
      }
      leaf bert-algorithm {
        type string;
      }
      leaf bert-error-rate {
        type uint32;
      }
      leaf bert-period {
        type uint32;
      }
    }
    container t1-options {
      uses apply-group;
      uses apply-macro;
      leaf timeslots {
        type string;
      }
      leaf voice-timeslots {
        type string;
      }
      leaf loopback {
        type string;
      }
      leaf buildout {
        type string;
      }
      leaf byte-encoding {
        type string;
      }
      leaf line-encoding {
        type string;
      }
      leaf invert-data {
        type empty;
      }
      leaf framing {
        type string;
      }
      leaf fcs {
        type string;
      }
      leaf idle-cycle-flag {
        type string;
      }
      leaf start-end-flag {
        type string;
      }
      leaf bert-algorithm {
        type string;
      }
      leaf bert-error-rate {
        type uint32;
      }
      leaf bert-period {
        type uint32;
      }
      leaf remote-loopback-respond {
        type empty;
      }
      leaf crc-major-alarm-threshold {
        type string;
      }
      leaf crc-minor-alarm-threshold {
        type string;
      }
    }
    container ds0-options {
      uses apply-group;
      uses apply-macro;
      leaf loopback {
        type string;
      }
      leaf byte-encoding {
        type string;
      }
      leaf invert-data {
        type empty;
      }
      leaf fcs {
        type string;
      }
      leaf idle-cycle-flag {
        type string;
      }
      leaf start-end-flag {
        type string;
      }
      leaf bert-algorithm {
        type string;
      }
      leaf bert-error-rate {
        type uint32;
      }
      leaf bert-period {
        type uint32;
      }
    }
    container serial-options {
      uses apply-group;
      uses apply-macro;
      leaf line-protocol {
        type string;
      }
      choice choice-5 {
        container dte-options {
          uses apply-group;
          uses apply-macro;
          leaf ignore-all {
            type empty;
          }
          container dtr {
            choice choice-3 {
              leaf assert {
                type empty;
              }
              leaf de-assert {
                type empty;
              }
              leaf normal {
                type empty;
              }
              container auto-synchronize {
                presence "enable auto-synchronize";
                uses apply-group;
                uses apply-macro;
                leaf duration {
                  type uint16;
                }
                leaf interval {
                  type uint16;
                }
              }
            }
          }
          leaf control-signal {
            type string;
          }
          leaf rts {
            type string;
          }
          leaf dcd {
            type string;
          }
          leaf dsr {
            type string;
          }
          leaf cts {
            type string;
          }
          leaf indication {
            type string;
          }
          leaf tm {
            type string;
          }
        }
        container dce-options {
          uses apply-group;
          uses apply-macro;
          leaf ignore-all {
            type empty;
          }
          leaf dtr {
            type string;
          }
          leaf rts {
            type string;
          }
          leaf dcd {
            type string;
          }
          leaf dsr {
            type string;
          }
          leaf cts {
            type string;
          }
          leaf tm {
            type string;
          }
          leaf dce-loopback-override {
            type empty;
          }
        }
      }
      leaf dtr-circuit {
        type string;
      }
      leaf dtr-polarity {
        type string;
      }
      leaf rts-polarity {
        type string;
      }
      leaf control-polarity {
        type string;
      }
      leaf dcd-polarity {
        type string;
      }
      leaf dsr-polarity {
        type string;
      }
      leaf cts-polarity {
        type string;
      }
      leaf indication-polarity {
        type string;
      }
      leaf tm-polarity {
        type string;
      }
      leaf clocking-mode {
        type string;
      }
      leaf transmit-clock {
        type string;
      }
      leaf clock-rate {
        type string;
      }
      leaf loopback {
        type string;
      }
      leaf encoding {
        type string;
      }
      leaf idle-cycle-flag {
        type string;
      }
    }
    choice gratuitous-arp-reply-choice {
      leaf gratuitous-arp-reply {
        type empty;
      }
      leaf no-gratuitous-arp-reply {
        type empty;
      }
    }
    choice no-gratuitous-arp-request-choice {
      leaf no-gratuitous-arp-request {
        type empty;
      }
      leaf no-no-gratuitous-arp-request {
        type empty;
      }
    }
    leaf arp-l2-validate {
      type empty;
    }
    container ether-options {
      uses apply-group;
      uses apply-macro;
      choice loopback-choice {
        leaf loopback {
          type empty;
        }
        leaf no-loopback {
          type empty;
        }
      }
      leaf loopback-remote {
        type empty;
      }
      choice source-filtering-choice {
        leaf source-filtering {
          type empty;
        }
        leaf no-source-filtering {
          type empty;
        }
      }
      container ethernet-switch-profile {
        uses apply-group;
        uses apply-macro;
        leaf-list tag-protocol-id {
          type string;
          ordered-by user;
        }
        container ethernet-policer-profile {
          uses apply-group;
          uses apply-macro;
          container input-priority-map {
            uses cos-policer-input-priority-map;
          }
          container output-priority-map {
            uses cos-policer-output-priority-map;
          }
          list policer {
            key "name";
            ordered-by user;
            uses cos-policer;
          }
        }
        container storm-control {
          presence "";
          uses apply-group;
          uses apply-macro;
          leaf profile-name {
            type string;
          }
        }
        container recovery-timeout {
          leaf time-in-seconds {
            units "seconds";
            type uint32;
          }
        }
        leaf mac-learn-enable {
          type empty;
        }
        leaf no-mac-learn-enable {
          type empty;
        }
      }
      leaf asynchronous-notification {
        type empty;
      }
      list source-address-filter {
        key "name";
        leaf name {
          type mac-addr;
        }
      }
      choice auto-negotiation-choice {
        leaf auto-negotiation {
          type empty;
        }
        leaf no-auto-negotiation {
          type empty;
        }
      }
      choice flow-control-choice {
        leaf flow-control {
          type empty;
        }
        leaf no-flow-control {
          type empty;
        }
      }
      container configured-flow-control {
        presence "";
        uses apply-group;
        uses apply-macro;
        leaf rx-buffers {
          mandatory true;
          type string;
        }
        leaf tx-buffers {
          mandatory true;
          type string;
        }
      }
      leaf link-mode {
        type string;
      }
      container mpls {
        uses mpls-ifd-options;
      }
      leaf ignore-l3-incompletes {
        type empty;
      }
      leaf no-auto-mdix {
        type empty;
      }
      leaf fec {
        type string;
      }
      container speed {
        choice choice-3 {
          container auto-negotiation {
            presence "enable auto-negotiation";
            leaf auto-negotiate-10-100 {
              type empty;
            }
          }
          leaf ethernet-10m {
            type empty;
          }
          leaf ethernet-100m {
            type empty;
          }
          leaf ethernet-1g {
            type empty;
          }
          leaf ethernet-10g {
            type empty;
          }
        }
      }
      container ieee-802.3ad {
        uses apply-group;
        uses apply-macro;
        container lacp {
          uses apply-group;
          uses apply-macro;
          leaf force-up {
            type empty;
          }
          leaf port-priority {
            type uint16;
          }
        }
        leaf bundle {
          type interface-device;
        }
        choice choice-7 {
          leaf primary {
            type empty;
          }
          leaf backup {
            type empty;
          }
        }
      }
      leaf ieee-802-3az-eee {
        type empty;
      }
      leaf mdi-mode {
        type string;
      }
      container redundant-parent {
        presence "";
        uses apply-group;
        uses apply-macro;
        leaf parent {
          mandatory true;
          type interface-device;
        }
      }
      leaf autostate-exclude {
        type empty;
      }
    }
    container fibrechannel-options {
      uses apply-group;
      uses apply-macro;
      choice loopback-choice {
        leaf loopback {
          type empty;
        }
        leaf no-loopback {
          type empty;
        }
      }
      leaf bb-sc-n {
        type uint16;
      }
      leaf speed {
        type string;
      }
    }
    container gigether-options {
      uses apply-group;
      uses apply-macro;
      choice loopback-choice {
        leaf loopback {
          type empty;
        }
        leaf no-loopback {
          type empty;
        }
      }
      leaf loopback-remote {
        type empty;
      }
      choice flow-control-choice {
        leaf flow-control {
          type empty;
        }
        leaf no-flow-control {
          type empty;
        }
      }
      choice source-filtering-choice {
        leaf source-filtering {
          type empty;
        }
        leaf no-source-filtering {
          type empty;
        }
      }
      choice choice-15 {
        leaf no-auto-negotiation {
          type empty;
        }
        container auto-negotiation {
          presence "enable auto-negotiation";
          leaf remote-fault {
            type string;
          }
        }
      }
      leaf mac-mode {
        type string;
      }
      leaf asynchronous-notification {
        type empty;
      }
      list source-address-filter {
        key "name";
        leaf name {
          type mac-addr;
        }
      }
      leaf pad-to-minimum-frame-size {
        type empty;
      }
      container redundant-parent {
        presence "";
        uses apply-group;
        uses apply-macro;
        leaf parent {
          type interface-device;
        }
      }
      container ieee-802.3ad {
        uses apply-group;
        uses apply-macro;
        container lacp {
          uses apply-group;
          uses apply-macro;
          leaf port-priority {
            type uint16;
          }
        }
        leaf bundle {
          type interface-device;
        }
        leaf link-index {
          type uint16;
        }
        choice choice-9 {
          leaf primary {
            type empty;
          }
          leaf backup {
            type empty;
          }
        }
        leaf distribution-list {
          type string;
        }
      }
      container ethernet-switch-profile {
        uses apply-group;
        uses apply-macro;
        leaf-list tag-protocol-id {
          type string;
          ordered-by user;
        }
        container ethernet-policer-profile {
          uses apply-group;
          uses apply-macro;
          container ieee802.1-priority-map {
            presence "enable ieee802.1-priority-map";
            uses apply-group;
            uses apply-macro;
            leaf-list premium {
              ordered-by user;
              type uint32;
            }
          }
          container input-priority-map {
            uses cos-policer-input-priority-map;
          }
          container output-priority-map {
            uses cos-policer-output-priority-map;
          }
          list policer {
            key "name";
            ordered-by user;
            uses cos-policer;
          }
        }
        container accept-from {
          uses apply-group;
          uses apply-macro;
          list mac-address {
            key "name";
            uses mac-list;
          }
        }
        leaf reject-the-rest {
          type empty;
        }
        leaf no-reject-the-rest {
          type empty;
        }
        leaf mac-learn-enable {
          type empty;
        }
        leaf no-mac-learn-enable {
          type empty;
        }
      }
      container mpls {
        uses mpls-ifd-options;
      }
      leaf ignore-l3-incompletes {
        type empty;
      }
      leaf no-auto-mdix {
        type empty;
      }
      leaf ieee-802-3az-eee {
        type empty;
      }
      leaf mru {
        type uint32;
      }
      leaf fec {
        type string;
      }
      leaf speed {
        type string;
      }
    }
    uses optics-options-grouping;
    container otn-options {
      uses otn-options-type;
    }
    container fastether-options {
      uses apply-group;
      uses apply-macro;
      choice loopback-choice {
        leaf loopback {
          type empty;
        }
        leaf no-loopback {
          type empty;
        }
      }
      choice source-filtering-choice {
        leaf source-filtering {
          type empty;
        }
        leaf no-source-filtering {
          type empty;
        }
      }
      choice auto-negotiation-choice {
        leaf auto-negotiation {
          type empty;
        }
        leaf no-auto-negotiation {
          type empty;
        }
      }
      choice flow-control-choice {
        leaf flow-control {
          type empty;
        }
        leaf no-flow-control {
          type empty;
        }
      }
      leaf ingress-rate-limit {
        type uint32;
      }
      list source-address-filter {
        key "name";
        ordered-by user;
        leaf name {
          type mac-addr;
        }
      }
      container redundant-parent {
        presence "";
        uses apply-group;
        uses apply-macro;
        leaf parent {
          type interface-device;
        }
      }
      container ieee-802.3ad {
        uses apply-group;
        uses apply-macro;
        container lacp {
          uses apply-group;
          uses apply-macro;
          leaf port-priority {
            type uint16;
          }
        }
        leaf bundle {
          type interface-device;
        }
        choice choice-7 {
          leaf primary {
            type empty;
          }
          leaf backup {
            type empty;
          }
        }
      }
      container mpls {
        uses mpls-ifd-options;
      }
      leaf ignore-l3-incompletes {
        type empty;
      }
    }
    container redundant-ether-options {
      presence "";
      uses apply-group;
      uses apply-macro;
      leaf redundancy-group {
        type uint16;
      }
      choice loopback-choice {
        leaf loopback {
          type empty;
        }
        leaf no-loopback {
          type empty;
        }
      }
      choice flow-control-choice {
        leaf flow-control {
          type empty;
        }
        leaf no-flow-control {
          type empty;
        }
      }
      choice source-filtering-choice {
        leaf source-filtering {
          type empty;
        }
        leaf no-source-filtering {
          type empty;
        }
      }
      list source-address-filter {
        key "name";
        ordered-by user;
        leaf name {
          type mac-addr;
        }
      }
      leaf link-speed {
        type string;
      }
      leaf minimum-links {
        type uint16;
      }
      container lacp {
        uses apply-group;
        uses apply-macro;
        choice choice-3 {
          leaf active {
            type empty;
          }
          leaf passive {
            type empty;
          }
        }
        leaf periodic {
          type string;
        }
      }
    }
    container aggregated-ether-options {
      uses apply-group;
      uses apply-macro;
      choice loopback-choice {
        leaf loopback {
          type empty;
        }
        leaf no-loopback {
          type empty;
        }
      }
      choice flow-control-choice {
        leaf flow-control {
          type empty;
        }
        leaf no-flow-control {
          type empty;
        }
      }
      choice source-filtering-choice {
        leaf source-filtering {
          type empty;
        }
        leaf no-source-filtering {
          type empty;
        }
      }
      leaf autostate-exclude {
        type empty;
      }
      container link-protection {
        presence "enable link-protection";
        uses apply-group;
        uses apply-macro;
        leaf revertive {
          type empty;
        }
        leaf non-revertive {
          type empty;
        }
        leaf backup-state {
          type string;
        }
        container rtg-config {
          presence "enable rtg-config";
          uses apply-group;
          uses apply-macro;
          leaf preempt-cutover-timer {
            type uint32;
          }
        }
      }
      leaf no-link-protection {
        type empty;
      }
      leaf fcoe-lag {
        type empty;
      }
      leaf no-fcoe-lag {
        type empty;
      }
      list source-address-filter {
        key "name";
        ordered-by user;
        leaf name {
          type mac-addr;
        }
      }
      container configured-flow-control {
        presence "";
        uses apply-group;
        uses apply-macro;
        leaf rx-buffers {
          type string;
        }
        leaf tx-buffers {
          type string;
        }
      }
      container load-balance {
        uses aggregate-load-balance;
      }
      container bfd-liveness-detection {
        presence "";
        uses apply-group;
        uses apply-macro;
        leaf version {
          type string;
        }
        leaf minimum-interval {
          units "milliseconds";
          type uint32;
        }
        leaf minimum-transmit-interval {
          units "milliseconds";
          type uint32;
        }
        leaf minimum-receive-interval {
          units "milliseconds";
          type uint32;
        }
        leaf multiplier {
          type uint32;
        }
        leaf no-adaptation {
          type empty;
        }
        container transmit-interval {
          uses apply-group;
          uses apply-macro;
          leaf minimum-interval {
            units "milliseconds";
            type uint32;
          }
          leaf threshold {
            type uint32;
            units "milliseconds";
          }
        }
        container detection-time {
          uses apply-group;
          uses apply-macro;
          leaf threshold {
            type uint32;
            units "milliseconds";
          }
        }
        container authentication {
          uses apply-group;
          uses apply-macro;
          leaf key-chain {
            type string;
          }
          leaf algorithm {
            type string;
          }
          leaf loose-check {
            type empty;
          }
        }
        leaf neighbor {
          type ipaddr;
        }
        leaf local-address {
          type ipaddr;
        }
        leaf holddown-interval {
          units "milliseconds";
          type uint32;
        }
      }
      leaf minimum-links {
        type uint16;
      }
      container minimum-bandwidth {
        presence "enable minimum-bandwidth";
        uses apply-group;
        uses apply-macro;
        leaf bw-value {
          type uint64;
        }
        leaf bw-unit {
          type string;
        }
      }
      container targeted-options {
        presence "enable targeted-options";
        uses apply-advanced;
        leaf type {
          type string;
        }
        choice redundancy_choice {
          case case_1 {
            leaf logical-interface-fpc-redundancy {
              type empty;
            }
          }
          case case_2 {
            leaf logical-interface-chassis-redundancy {
              type empty;
            }
          }
        }
        container rebalance-periodic {
          presence "enable rebalance-periodic";
          uses apply-advanced;
          leaf start-time {
            type time-of-day;
          }
          leaf interval {
            type string;
          }
        }
        leaf rebalance-subscriber-granularity {
          type string;
        }
      }
      choice choice-logical-interface-fpc-redundancy {
        leaf logical-interface-fpc-redundancy {
          type empty;
        }
        leaf logical-interface-chassis-redundancy {
          type empty;
        }
      }
      container rebalance-periodic {
        presence "";
        uses apply-group;
        uses apply-macro;
        leaf start-time {
          type time;
        }
        leaf interval {
          type uint32;
        }
      }
      leaf pad-to-minimum-frame-size {
        type empty;
      }
      leaf link-speed {
        type string;
      }
      container lacp {
        uses apply-group;
        uses apply-macro;
        choice choice-3 {
          leaf active {
            type empty;
          }
          leaf passive {
            type empty;
          }
        }
        leaf periodic {
          type string;
        }
        leaf fast-failover {
          type empty;
        }
        container link-protection {
          presence "enable link-protection";
          uses apply-group;
          uses apply-macro;
          leaf disable {
            type empty;
          }
          choice choice-5 {
            leaf revertive {
              type empty;
            }
            leaf non-revertive {
              type empty;
            }
          }
        }
        leaf accept-data {
          type empty;
        }
        leaf system-priority {
          type string;
        }
        leaf system-id {
          type mac-addr;
        }
        leaf admin-key {
          type uint16;
        }
        container hold-time {
          presence "";
          leaf up {
            mandatory true;
            units "seconds";
            type uint16;
          }
        }
        leaf aggregate-wait-time {
          units "seconds";
          type uint16;
        }
        leaf force-up {
          type empty;
        }
      }
      container ethernet-switch-profile {
        uses apply-group;
        uses apply-macro;
        leaf-list tag-protocol-id {
          type string;
          ordered-by user;
        }
      }
      container mc-ae {
        presence "";
        uses apply-group;
        uses apply-macro;
        leaf mc-ae-id {
          type uint16;
        }
        leaf redundancy-group {
          type uint32;
        }
        leaf chassis-id {
          type uint16;
        }
        leaf mode {
          type string;
        }
        leaf status-control {
          type string;
        }
        leaf switchover-mode {
          type string;
        }
        leaf revert-time {
          units "minute";
          type uint32;
        }
        leaf init-delay-time {
          units "seconds";
          type uint16;
        }
        leaf recovery-delay-time {
          units "seconds";
          type uint16;
        }
        container events {
          presence "enable events";
          uses apply-group;
          uses apply-macro;
          container iccp-peer-down {
            presence "enable iccp-peer-down";
            uses apply-group;
            uses apply-macro;
            leaf force-icl-down {
              type empty;
            }
            leaf prefer-status-control-active {
              type empty;
            }
          }
        }
      }
    }
    container es-options {
      uses apply-group;
      uses apply-macro;
      leaf backup-interface {
        type interface-device;
      }
    }
    container dsl-options {
      uses apply-group;
      uses apply-macro;
      leaf operating-mode {
        type string;
      }
    }
    container vdsl-options {
      uses apply-group;
      uses apply-macro;
      leaf vdsl-profile {
        type string;
      }
    }
    container shdsl-options {
      uses apply-group;
      uses apply-macro;
      leaf annex {
        type string;
      }
      leaf line-rate {
        type string;
      }
      leaf loopback {
        type string;
      }
      container snr-margin {
        presence "enable snr-margin";
        uses apply-group;
        uses apply-macro;
        leaf current {
          type string;
        }
        leaf snext {
          type string;
        }
      }
    }
    container data-input {
      uses apply-group;
      uses apply-macro;
      choice choice-3 {
        leaf system {
          type empty;
        }
        leaf interface {
          type interface-device;
        }
      }
    }
    container switch-options {
      uses apply-group;
      uses apply-macro;
      list switch-port {
        key "name";
        leaf name {
          type string;
        }
        uses apply-group;
        uses apply-macro;
        leaf auto-negotiation {
          type empty;
        }
        leaf no-auto-negotiation {
          type empty;
        }
        leaf link-mode {
          type string;
        }
        leaf speed {
          type string;
        }
        leaf vlan-id {
          type uint32;
        }
        leaf cascade-port {
          type empty;
        }
      }
    }
    container container-options {
      uses apply-group;
      uses apply-macro;
      container container-type {
        presence "enable container-type";
        uses apply-group;
        uses apply-macro;
        choice choice-3 {
          container aps {
            presence "enable aps";
            uses aps-type;
          }
        }
      }
      container member-interface-type {
        uses apply-group;
        uses apply-macro;
        choice choice-3 {
          container sonet {
            presence "";
            uses apply-group;
            uses apply-macro;
            leaf member-interface-speed {
              type string;
            }
          }
          container atm {
            presence "";
            uses apply-group;
            uses apply-macro;
            leaf member-interface-speed {
              type string;
            }
          }
        }
      }
      container redundancy {
        uses apply-group;
        uses apply-macro;
        container hold-time {
          presence "";
          leaf up {
            type uint32;
          }
          leaf down {
            type uint32;
          }
        }
      }
      leaf-list container-list {
        type interface-device;
        ordered-by user;
      }
      leaf primary {
        type empty;
      }
      leaf standby {
        type empty;
      }
      leaf allow-configuration-override {
        type empty;
      }
    }
    container layer2-policer {
      uses apply-group;
      uses apply-macro;
      leaf input-hierarchical-policer {
        type string;
      }
    }
    list unit {
      key "name";
      leaf name {
        type string;
      }
      uses apply-group;
      uses apply-macro;
      container policer-overhead {
        uses apply-group;
        uses apply-macro;
        leaf policer-overhead-value {
          units "bytes";
          type int32;
        }
        leaf ingress {
          units "bytes";
          type int32;
        }
        leaf egress {
          units "bytes";
          type int32;
        }
      }
      leaf alias {
        type string;
      }
      leaf enhanced-convergence {
        type empty;
      }
      leaf proxy-macip-advertisement {
        type empty;
      }
      leaf virtual-gateway-accept-data {
        type empty;
      }
      container undocumented {
        leaf enable {
          type empty;
        }
        leaf routing-services {
          type empty;
        }
      }
      container peer-psd {
        presence "";
        leaf psd-name {
          type string;
        }
      }
      container peer-interface {
        presence "enable peer-interface";
        uses apply-group;
        uses apply-macro;
        leaf interface-name {
          type interface-unit;
        }
      }
      container interface-shared-with {
        presence "";
        uses apply-group;
        uses apply-macro;
        leaf psd-name {
          type string;
        }
      }
      leaf enable-disable {
        type string;
      }
      choice choice-9 {
        leaf disable {
          type empty;
        }
      }
      leaf passive-monitor-mode {
        type empty;
      }
      leaf per-session-scheduler {
        type empty;
      }
      container account-layer2-overhead {
        presence "enable account-layer2-overhead";
        uses apply-group;
        uses apply-macro;
        leaf overhead-value {
          units "bytes";
          type int8;
        }
        leaf ingress {
          units "bytes";
          type int8;
        }
        leaf egress {
          units "bytes";
          type int8;
        }
      }
      container forwarding-class-accounting {
        presence "enable forwarding-class-accounting";
        uses apply-group;
        uses apply-macro;
        leaf direction {
          type string;
        }
        container enhanced {
          presence "enable enhanced";
          uses apply-group;
          uses apply-macro;
          leaf traffic-type {
            type string;
          }
          leaf family {
            type string;
          }
          leaf direction {
            type string;
          }
          leaf overhead-bytes {
            type uint32;
          }
        }
      }
      leaf clear-dont-fragment-bit {
        type empty;
      }
      leaf packet-inject-enable {
        type empty;
      }
      leaf reassemble-packets {
        type empty;
      }
      container services-options {
        uses apply-group;
        uses apply-macro;
      }
      container rpm {
        uses apply-group;
        uses apply-macro;
        choice choice-3 {
          leaf client {
            type empty;
          }
          leaf server {
            type empty;
          }
          leaf client-delegate-probes {
            type empty;
          }
          leaf twamp-server {
            type empty;
          }
          leaf twamp-client {
            type empty;
          }
        }
      }
      leaf description {
        type string;
      }
      leaf metadata {
        type string;
      }
      container dial-options {
        uses apply-group;
        uses apply-macro;
        choice choice-3 {
          leaf l2tp-interface-id {
            type string;
          }
          leaf ipsec-interface-id {
            type string;
          }
        }
        choice choice-4 {
          leaf dedicated {
            type empty;
          }
          leaf shared {
            type empty;
          }
        }
      }
      container actual-transit-statistics {
        presence "enable actual-transit-statistics";
        uses apply-group;
        uses apply-macro;
      }
      leaf-list demux-source {
        ordered-by user;
        type string;
      }
      leaf-list demux-destination {
        ordered-by user;
        type string;
      }
      container demux {
        uses apply-group;
        uses apply-macro;
        container inet {
          presence "";
          uses apply-group;
          uses apply-macro;
          leaf address {
            mandatory true;
            type string;
          }
          container auto-configure {
            uses dynamic-ipv4-type;
          }
        }
        container inet6 {
          presence "";
          uses apply-group;
          uses apply-macro;
          leaf address {
            mandatory true;
            type string;
          }
          container auto-configure {
            uses dynamic-ipv6-type;
          }
        }
      }
      leaf encapsulation {
        type string;
      }
      leaf gre {
        type empty;
      }
      leaf mtu {
        type uint32;
      }
      choice choice-32 {
        leaf point-to-point {
          type empty;
        }
        leaf multipoint {
          type empty;
        }
      }
      leaf bandwidth {
        type string;
      }
      leaf global-layer2-domainid {
        type uint32;
      }
      container radio-router {
        presence "enable radio-router";
        uses dynamic-ifbw-parms-type;
      }
      leaf traps {
        type empty;
      }
      leaf no-traps {
        type empty;
      }
      leaf routing-services {
        type empty;
      }
      leaf no-routing-services {
        type empty;
      }
      container routing-service {
        presence "";
        uses apply-group;
        uses apply-macro;
        leaf enable-disable {
          type string;
        }
        leaf enable {
          type empty;
        }
      }
      container arp-resp {
        presence "enable arp-resp";
        choice choice-3 {
          leaf unrestricted {
            type empty;
          }
          leaf restricted {
            type empty;
          }
        }
      }
      container proxy-arp {
        presence "enable proxy-arp";
        choice choice-3 {
          leaf unrestricted {
            type empty;
          }
          leaf restricted {
            type empty;
          }
        }
      }
      choice choice-45 {
        leaf vlan-id {
          type string;
        }
        leaf vlan-id-range {
          type string;
        }
        leaf-list vlan-id-list {
          type string;
        }
        container vlan-tags {
          presence "";
          leaf outer {
            type string;
          }
          choice choice-5 {
            leaf inner {
              type string;
            }
            leaf inner-range {
              type string;
            }
            leaf-list inner-list {
              type string;
            }
          }
        }
      }
      leaf deep-vlan-qualified-learning {
        type uint32;
      }
      leaf native-inner-vlan-id {
        type uint32;
      }
      container inner-vlan-id-range {
        presence "";
        leaf start {
          type uint32;
        }
        leaf end {
          type uint32;
        }
      }
      container accept-source-mac {
        uses apply-group;
        uses apply-macro;
        list mac-address {
          key "name";
          uses mac-list;
        }
      }
      container input-vlan-map {
        uses vlan-map;
      }
      container output-vlan-map {
        uses vlan-map;
      }
      leaf swap-by-poppush {
        type empty;
      }
      leaf receive-lsp {
        type string;
      }
      leaf transmit-lsp {
        type string;
      }
      leaf dlci {
        type uint32;
      }
      leaf multicast-dlci {
        type uint32;
      }
      choice choice-64 {
        leaf vci {
          type atm-vci;
        }
        leaf allow-any-vci {
          type empty;
        }
        leaf vpi {
          type uint32;
        }
        leaf trunk-id {
          type uint32;
        }
      }
      leaf no-vpivci-swapping {
        type empty;
      }
      choice choice-psn-vci {
        leaf psn-vci {
          type atm-vci;
        }
        leaf psn-vpi {
          type uint32;
        }
      }
      container atm-l2circuit-mode {
        choice choice-3 {
          leaf cell {
            type empty;
          }
          leaf aal5 {
            type empty;
          }
        }
      }
      container vci-range {
        presence "";
        leaf start {
          type uint16;
        }
        leaf end {
          type uint16;
        }
      }
      leaf trunk-bandwidth {
        type string;
      }
      leaf multicast-vci {
        type atm-vci;
      }
      container shaping {
        uses dcd-shaping-config;
      }
      container oam-period {
        choice choice-3 {
          leaf oam-period {
            type uint32;
          }
          container disable {
            presence "enable disable";
          }
        }
      }
      container oam-liveness {
        uses apply-group;
        uses apply-macro;
        leaf up-count {
          type uint32;
        }
        leaf down-count {
          type uint32;
        }
      }
      container ppp-options {
        uses ppp-options-type;
      }
      container pppoe-options {
        presence "";
        uses pppoe-options-type;
      }
      container pppoe-underlying-options {
        uses pppoe-underlying-options-type;
      }
      container advisory-options {
        uses advisory-options-type;
      }
      container auto-configure {
        uses auto-configure-vlan-type;
      }
      container demux-options {
        presence "";
        uses demux-options-type;
      }
      container targeted-distribution {
        presence "enable targeted-distribution";
        uses apply-group;
        uses apply-macro;
        leaf primary-list {
          type string;
        }
        leaf backup-list {
          type string;
        }
        leaf standby-list {
          type string;
        }
      }
      container targeted-options {
        presence "enable targeted-options";
        uses apply-group;
        uses apply-macro;
        leaf primary {
          type interface-device;
        }
        leaf backup {
          type interface-device;
        }
        leaf group {
          type string;
        }
        leaf weight {
          type uint32;
        }
      }
      choice choice-87 {
        container keepalives {
          presence "enable keepalives";
          uses keepalives-type;
        }
        leaf no-keepalives {
          type empty;
        }
      }
      leaf inverse-arp {
        type empty;
      }
      leaf transmit-weight {
        type uint16;
      }
      container epd-threshold {
        presence "";
        uses epd-threshold-config;
      }
      leaf cell-bundle-size {
        type uint32;
      }
      leaf cell-bundle-timeout {
        units "microseconds";
        type uint32;
      }
      leaf plp-to-clp {
        type empty;
      }
      leaf atm-scheduler-map {
        type string;
      }
      leaf mrru {
        type uint16;
      }
      leaf short-sequence {
        type empty;
      }
      leaf fragment-threshold {
        type uint32;
      }
      leaf drop-timeout {
        type uint16;
      }
      leaf disable-mlppp-inner-ppp-pfc {
        type empty;
      }
      leaf minimum-links {
        type uint16;
      }
      leaf multilink-max-classes {
        type uint16;
      }
      container compression {
        presence "enable compression";
        uses apply-group;
        uses apply-macro;
        container rtp {
          presence "enable rtp";
          uses apply-group;
          uses apply-macro;
          leaf f-max-period {
            type uint32;
          }
          leaf-list queues {
            ordered-by user;
            type string;
          }
          container port {
            presence "";
            leaf minimum {
              type uint32;
            }
            leaf maximum {
              type uint32;
            }
          }
          container maximum-contexts {
            leaf number {
              type uint32;
            }
          }
        }
      }
      leaf interleave-fragments {
        type empty;
      }
      leaf link-layer-overhead {
        type unsigned-float;
      }
      leaf accounting-profile {
        type string;
      }
      leaf peer-unit {
        type uint32;
      }
      container tunnel {
        presence "";
        uses apply-group;
        uses apply-macro;
        container encapsulation {
          presence "enable encapsulation";
          uses apply-group;
          uses apply-macro;
          container vxlan-gpe {
            presence "";
            uses apply-group;
            uses apply-macro;
            container source {
              presence "enable source";
              uses apply-group;
              uses apply-macro;
              leaf address {
                type ipv4addr;
              }
              leaf interface {
                type interface-name;
              }
            }
            container destination {
              presence "enable destination";
              uses apply-group;
              uses apply-macro;
              leaf address {
                type ipv4addr;
              }
            }
            leaf tunnel-endpoint {
              mandatory true;
              type string;
            }
            leaf destination-udp-port {
              mandatory true;
              type uint32;
            }
            leaf vni {
              mandatory true;
              type uint32;
            }
          }
          container gre {
            presence "enable gre";
            uses apply-advanced;
            container tunnel-termination {
              presence "enable tunnel-termination";
            }
            leaf key {
              type string;
            }
            container source {
              uses apply-advanced;
              leaf address {
                type ipprefix-optional;
              }
            }
            container destination {
              presence "enable destination";
              uses apply-advanced;
              leaf address {
                type ipaddr;
              }
            }
            container tunnel-routing-instance {
              presence "enable tunnel-routing-instance";
              uses apply-advanced;
              leaf routing-instance {
                type string;
              }
            }
            leaf bypass-loopback {
              type empty;
            }
            leaf allow-fragmentation {
              type empty;
            }
            leaf ttl {
              type string;
            }
          }
        }
        leaf source {
          type ipv4addr;
        }
        leaf destination {
          type ipv4addr;
        }
        leaf key {
          type uint32;
        }
        leaf backup-destination {
          type ipv4addr;
        }
        choice choice-11 {
          leaf allow-fragmentation {
            type empty;
          }
          leaf do-not-fragment {
            type empty;
          }
        }
        leaf ttl {
          type uint32;
        }
        leaf traffic-class {
          type uint32;
        }
        leaf flow-label {
          type uint32;
        }
        leaf path-mtu-discovery {
          type empty;
        }
        leaf no-path-mtu-discovery {
          type empty;
        }
        container routing-instance {
          uses apply-group;
          uses apply-macro;
          leaf destination {
            type string;
          }
        }
      }
      leaf compression-device {
        type interface-unit;
      }
      container atm-policer {
        uses apply-group;
        uses apply-macro;
        leaf input-atm-policer {
          type string;
        }
      }
      container layer2-policer {
        uses apply-group;
        uses apply-macro;
        choice choice-3 {
          leaf input-policer {
            type string;
          }
          leaf input-hierarchical-policer {
            type string;
          }
          leaf input-three-color {
            type string;
          }
        }
        choice choice-4 {
          leaf output-policer {
            type string;
          }
          leaf output-three-color {
            type string;
          }
        }
      }
      container filter {
        uses apply-group;
        uses apply-macro;
        container input {
          presence "";
          leaf filter-name {
            type string;
            mandatory true;
          }
          leaf shared-name {
            type string;
          }
          leaf precedence {
            type uint32;
          }
        }
        container output {
          presence "";
          leaf filter-name {
            type string;
            mandatory true;
          }
          leaf shared-name {
            type string;
          }
          leaf precedence {
            type uint32;
          }
        }
      }
      list multi-chassis-protection {
        key "name";
        uses multi-chassis-protection-group;
      }
      leaf statistics {
        type empty;
      }
      container esi {
        presence "";
        uses apply-group;
        uses apply-macro;
        container apply-advanced {
          uses apply-group;
          uses apply-macro;
        }
        leaf identifier {
          mandatory true;
          type string;
        }
        choice choice-single-active {
          leaf single-active {
            type empty;
          }
          leaf all-active {
            type empty;
          }
        }
        container df-election-type {
          presence "enable df-election-type";
          uses apply-advanced;
          choice pref_choice {
            case case_1 {
              container preference {
                presence "enable preference";
                uses apply-advanced;
                leaf value {
                  type string;
                }
              }
            }
          }
          choice mod_choice {
            case case_1 {
              container mod {
                presence "enable mod";
              }
            }
          }
        }
      }
      choice virtual-gateway {
        case case_1 {
          leaf no-auto-virtual-gateway-esi {
            type empty;
          }
        }
        case case_2 {
          container virtual-gateway-esi {
            uses apply-advanced;
            leaf identifier {
              type esi;
            }
            choice mode {
              case case_1 {
                leaf single-active {
                  type empty;
                }
              }
              case case_2 {
                leaf all-active {
                  type empty;
                }
              }
            }
          }
        }
      }
      container family {
        uses apply-group;
        uses apply-macro;
        container inet {
          presence "enable inet";
          uses apply-group;
          uses apply-macro;
          container dhcp {
            presence "enable dhcp";
            uses dhcp-client-type;
          }
          container dhcp-client {
            presence "enable dhcp-client";
            uses dhcp-client-type;
          }
          container targeted-broadcast {
            presence "enable targeted-broadcast";
            uses apply-group;
            uses apply-macro;
            choice choice-3 {
              leaf forward-and-send-to-re {
                type empty;
              }
              leaf forward-only {
                type empty;
              }
            }
          }
          leaf destination-class-usage {
            type empty;
          }
          leaf transit-options-packets {
            type empty;
          }
          leaf transit-ttl-exceeded {
            type empty;
          }
          leaf receive-options-packets {
            type empty;
          }
          leaf receive-ttl-exceeded {
            type empty;
          }
          container accounting {
            uses apply-group;
            uses apply-macro;
            container source-class-usage {
              uses apply-group;
              uses apply-macro;
              leaf input {
                type empty;
              }
              leaf output {
                type empty;
              }
            }
            leaf destination-class-usage {
              type empty;
            }
          }
          leaf mac-validate {
            type string;
          }
          container rpf-check {
            presence "enable rpf-check";
            uses apply-group;
            uses apply-macro;
            leaf fail-filter {
              type string;
            }
            container mode {
              leaf loose {
                type empty;
              }
            }
          }
          leaf mtu {
            type string;
          }
          leaf tcp-mss {
            type uint32;
          }
          leaf no-redirects {
            type empty;
          }
          leaf no-neighbor-learn {
            type empty;
          }
          leaf unconditional-src-learn {
            type empty;
          }
          leaf multicast-only {
            type empty;
          }
          leaf primary {
            type empty;
          }
          leaf ipsec-sa {
            type string;
          }
          list demux-source {
            key "name";
            ordered-by user;
            leaf name {
              type string;
            }
            uses apply-group;
            uses apply-macro;
          }
          list demux-destination {
            key "name";
            ordered-by user;
            leaf name {
              type string;
            }
            uses apply-group;
            uses apply-macro;
          }
          container filter {
            uses apply-group;
            uses apply-macro;
            choice choice-3 {
              container input {
                presence "";
                leaf filter-name {
                  type string;
                }
                leaf shared-name {
                  type string;
                }
                leaf precedence {
                  type uint32;
                }
              }
              leaf-list input-list {
                type string;
                ordered-by user;
              }
            }
            choice choice-4 {
              container output {
                presence "";
                leaf filter-name {
                  type string;
                }
                leaf shared-name {
                  type string;
                }
                leaf precedence {
                  type uint32;
                }
              }
              leaf-list output-list {
                type string;
                ordered-by user;
              }
            }
            leaf-list input-chain {
              ordered-by user;
              type string;
            }
            leaf-list output-chain {
              ordered-by user;
              type string;
            }
            container adf {
              presence "";
              uses apply-group;
              uses apply-macro;
              list rule {
                key "name";
                ordered-by user;
                leaf name {
                  type string;
                }
                uses apply-group;
                uses apply-macro;
              }
              leaf counter {
                type empty;
              }
              leaf input-precedence {
                type uint32;
              }
              leaf not-mandatory {
                type empty;
              }
              leaf output-precedence {
                type uint32;
              }
            }
            leaf group {
              type uint32;
            }
          }
          container simple-filter {
            uses apply-group;
            uses apply-macro;
            leaf input {
              type string;
            }
          }
          leaf input-hierarchical-policer {
            type string;
          }
          container policer {
            uses apply-group;
            uses apply-macro;
            leaf arp {
              type string;
            }
            leaf input {
              type string;
            }
            leaf output {
              type string;
            }
            container undocumented {
              leaf disable-arp-policer {
                type empty;
              }
            }
          }
          container sampling {
            uses apply-group;
            uses apply-macro;
            leaf input {
              type empty;
            }
            leaf output {
              type empty;
            }
          }
          container service {
            uses apply-group;
            uses apply-macro;
            container input {
              uses apply-group;
              uses apply-macro;
              list service-set {
                key "name";
                ordered-by user;
                leaf name {
                  type string;
                }
                uses apply-group;
                uses apply-macro;
                leaf service-filter {
                  type string;
                }
              }
              leaf post-service-filter {
                type string;
              }
            }
            container output {
              uses apply-group;
              uses apply-macro;
              list service-set {
                key "name";
                ordered-by user;
                leaf name {
                  type string;
                }
                uses apply-group;
                uses apply-macro;
                leaf service-filter {
                  type string;
                }
              }
            }
          }
          list next-hop-tunnel {
            key "name";
            ordered-by user;
            leaf name {
              type string;
            }
            uses apply-group;
            uses apply-macro;
            leaf ipsec-vpn {
              type string;
            }
          }
          list address {
            key "name";
            ordered-by user;
            leaf name {
              type ipv4prefix;
            }
            uses apply-group;
            uses apply-macro;
            leaf destination {
              type ipv4addr;
            }
            leaf destination-profile {
              type string;
            }
            leaf broadcast {
              type ipv4addr;
            }
            leaf primary {
              type empty;
            }
            leaf preferred {
              type empty;
            }
            leaf master-only {
              type empty;
            }
            list multipoint-destination {
              key "name";
              ordered-by user;
              leaf name {
                type ipv4addr;
              }
              uses apply-group;
              uses apply-macro;
              choice choice-3 {
                leaf dlci {
                  type uint32;
                }
                leaf vci {
                  type atm-vci;
                }
              }
              container shaping {
                uses dcd-shaping-config;
              }
              container oam-period {
                choice choice-3 {
                  leaf oam_period {
                    type uint32;
                  }
                  container disable {
                    presence "enable disable";
                  }
                }
              }
              container oam-liveness {
                uses apply-group;
                uses apply-macro;
                leaf up-count {
                  type uint32;
                }
                leaf down-count {
                  type uint32;
                }
              }
              leaf inverse-arp {
                type empty;
              }
              leaf transmit-weight {
                type uint16;
              }
              container epd-threshold {
                presence "";
                uses epd-threshold-config;
              }
            }
            list arp {
              key "name";
              ordered-by user;
              leaf name {
                type ipv4addr;
              }
              leaf l2-interface {
                type interface-name;
              }
              choice choice-5 {
                leaf mac {
                  type mac-unicaset;
                }
                leaf multicast-mac {
                  type mac-multicast;
                }
              }
              leaf publish {
                type empty;
              }
            }
            container web-authentication {
              uses apply-group;
              uses apply-macro;
              leaf http {
                type empty;
              }
              leaf https {
                type empty;
              }
              leaf redirect-to-https {
                type empty;
              }
            }
            list vrrp-group {
              key "name";
              ordered-by user;
              uses vrrp-group;
            }
            leaf virtual-gateway-address {
              type ipv4addr;
            }
          }
          container unnumbered-address {
            presence "";
            leaf source {
              type interface-unit;
            }
            leaf preferred-source-address {
              type string;
            }
            leaf destination {
              type ipv4addr;
            }
            leaf destination-profile {
              type string;
            }
          }
          container location-pool-address {
            presence "enable location-pool-address";
            uses apply-group;
            uses apply-macro;
            leaf pool-name {
              type string;
            }
          }
          leaf negotiate-address {
            type empty;
          }
        }
        container iso {
          presence "enable iso";
          uses apply-group;
          uses apply-macro;
          list address {
            key "name";
            ordered-by user;
            leaf name {
              type isoaddr;
            }
            uses apply-group;
            uses apply-macro;
          }
          leaf mtu {
            type uint32;
          }
        }
        container inet6 {
          presence "enable inet6";
          uses apply-group;
          uses apply-macro;
          container dhcpv6-client {
            presence "";
            uses apply-group;
            uses apply-macro;
            leaf client-type {
              mandatory true;
              type string;
            }
            list client-ia-type {
              key "name";
              ordered-by user;
              leaf name {
                type string;
              }
              uses apply-group;
              uses apply-macro;
            }
            container rapid-commit {
              presence "enable rapid-commit";
              uses apply-group;
              uses apply-macro;
            }
            container prefix-delegating {
              uses apply-group;
              uses apply-macro;
              leaf preferred-prefix-length {
                type uint32;
              }
              leaf sub-prefix-length {
                type uint32;
              }
            }
            container client-identifier {
              leaf duid-type {
                type string;
              }
            }
            leaf vendor-id {
              type string;
            }
            list req-option {
              key "name";
              ordered-by user;
              leaf name {
                type string;
              }
              uses apply-group;
              uses apply-macro;
            }
            leaf retransmission-attempt {
              type uint32;
            }
            container no-dns-install {
              presence "enable no-dns-install";
              uses apply-group;
              uses apply-macro;
            }
            container update-router-advertisement {
              uses apply-group;
              uses apply-macro;
              list interface {
                key "name";
                ordered-by user;
                leaf name {
                  type interface-name;
                }
                uses apply-group;
                uses apply-macro;
                leaf managed-configuration {
                  type empty;
                }
                leaf no-managed-configuration {
                  type empty;
                }
                leaf other-stateful-configuration {
                  type empty;
                }
                leaf no-other-stateful-configuration {
                  type empty;
                }
                leaf max-advertisement-interval {
                  units "seconds";
                  type uint32;
                }
                leaf min-advertisement-interval {
                  units "seconds";
                  type uint32;
                }
                leaf enable-recursive-dns-server-option {
                  type empty;
                }
                leaf no-enable-recursive-dns-server-option {
                  type empty;
                }
              }
            }
            leaf update-server {
              type empty;
            }
          }
          container rpf-check {
            presence "enable rpf-check";
            uses apply-group;
            uses apply-macro;
            leaf fail-filter {
              type string;
            }
            container mode {
              leaf loose {
                type empty;
              }
            }
          }
          container accounting {
            uses apply-group;
            uses apply-macro;
            container source-class-usage {
              uses apply-group;
              uses apply-macro;
              leaf input {
                type empty;
              }
              leaf output {
                type empty;
              }
            }
            leaf destination-class-usage {
              type empty;
            }
          }
          leaf mtu {
            type string;
          }
          leaf tcp-mss {
            type uint32;
          }
          leaf nd6-stale-time {
            units "seconds";
            type uint32;
          }
          leaf no-neighbor-learn {
            type empty;
          }
          leaf slaac-enable {
            type empty;
          }
          container ndp-proxy {
            uses apply-group;
            uses apply-macro;
            leaf interface-restricted {
              type empty;
            }
          }
          container dad-proxy {
            uses apply-group;
            uses apply-macro;
            leaf interface-restricted {
              type empty;
            }
          }
          leaf nd6-max-cache {
            type uint32;
          }
          leaf nd6-new-hold-limit {
            type uint32;
          }
          leaf no-redirects {
            type empty;
          }
          leaf allow-filter-on-re {
            type empty;
          }
          container filter {
            uses apply-group;
            uses apply-macro;
            choice choice-3 {
              container input {
                presence "";
                leaf filter-name {
                  type string;
                }
                leaf shared-name {
                  type string;
                }
                leaf precedence {
                  type uint32;
                }
              }
              leaf-list input-list {
                type string;
                ordered-by user;
              }
            }
            choice choice-4 {
              container output {
                presence "";
                leaf filter-name {
                  type string;
                }
                leaf shared-name {
                  type string;
                }
                leaf precedence {
                  type uint32;
                }
              }
              leaf-list output-list {
                type string;
                ordered-by user;
              }
            }
            leaf-list input-chain {
              ordered-by user;
              type string;
            }
            leaf-list output-chain {
              ordered-by user;
              type string;
            }
            container adf {
              presence "";
              uses apply-group;
              uses apply-macro;
              list rule {
                key "name";
                ordered-by user;
                leaf name {
                  type string;
                }
                uses apply-group;
                uses apply-macro;
              }
              leaf counter {
                type empty;
              }
              leaf input-precedence {
                type uint32;
              }
              leaf not-mandatory {
                type empty;
              }
              leaf output-precedence {
                type uint32;
              }
            }
            leaf group {
              type uint32;
            }
          }
          container ingress-queuing-filter {
            presence "";
            leaf filter-name {
              type string;
              mandatory true;
            }
          }
          leaf input-hierarchical-policer {
            type string;
          }
          container policer {
            uses apply-group;
            uses apply-macro;
            leaf input {
              type string;
            }
            leaf output {
              type string;
            }
          }
          container sampling {
            uses apply-group;
            uses apply-macro;
            leaf input {
              type empty;
            }
            leaf output {
              type empty;
            }
          }
          container service {
            uses apply-group;
            uses apply-macro;
            container input {
              uses apply-group;
              uses apply-macro;
              list service-set {
                key "name";
                ordered-by user;
                leaf name {
                  type string;
                }
                uses apply-group;
                uses apply-macro;
                leaf service-filter {
                  type string;
                }
              }
              leaf post-service-filter {
                type string;
              }
            }
            container output {
              uses apply-group;
              uses apply-macro;
              list service-set {
                key "name";
                ordered-by user;
                leaf name {
                  type string;
                }
                uses apply-group;
                uses apply-macro;
                leaf service-filter {
                  type string;
                }
              }
            }
          }
          list address {
            key "name";
            ordered-by user;
            leaf name {
              type ipv6prefix;
            }
            uses apply-group;
            uses apply-macro;
            leaf destination {
              type ipv6addr;
            }
            leaf eui-64 {
              type empty;
            }
            leaf primary {
              type empty;
            }
            leaf preferred {
              type empty;
            }
            leaf master-only {
              type empty;
            }
            list ndp {
              key "name";
              ordered-by user;
              leaf name {
                type ipv6addr;
              }
              leaf l2-interface {
                type interface-name;
              }
              choice choice-5 {
                leaf mac {
                  type mac-unicaset;
                }
                leaf multicast-mac {
                  type mac-multicast;
                }
              }
              leaf publish {
                type empty;
              }
            }
            list vrrp-inet6-group {
              key "name";
              ordered-by user;
              uses vrrp-group;
            }
            container web-authentication {
              uses apply-group;
              uses apply-macro;
              leaf http {
                type empty;
              }
              leaf https {
                type empty;
              }
              leaf redirect-to-https {
                type empty;
              }
            }
            leaf virtual-gateway-address {
              type ipv6addr;
            }
            leaf subnet-router-anycast {
              type empty;
            }
          }
          list demux-source {
            key "name";
            ordered-by user;
            leaf name {
              type string;
            }
            uses apply-group;
            uses apply-macro;
          }
          list demux-destination {
            key "name";
            ordered-by user;
            leaf name {
              type string;
            }
            uses apply-group;
            uses apply-macro;
          }
          container unnumbered-address {
            presence "";
            leaf source {
              type interface-unit;
            }
            leaf preferred-source-address {
              type string;
            }
          }
          leaf dad-disable {
            type empty;
          }
          leaf no-dad-disable {
            type empty;
          }
          leaf negotiate-address {
            type empty;
          }
        }
        container mpls {
          presence "enable mpls";
          uses apply-group;
          uses apply-macro;
          leaf mtu {
            type uint32;
          }
          leaf maximum-labels {
            type uint32;
          }
          container filter {
            uses apply-group;
            uses apply-macro;
            choice choice-3 {
              leaf input {
                type string;
              }
              leaf-list input-list {
                type string;
                ordered-by user;
              }
            }
            choice choice-4 {
              leaf output {
                type string;
              }
              leaf-list output-list {
                type string;
                ordered-by user;
              }
            }
            leaf group {
              type uint32;
            }
          }
          leaf input-hierarchical-policer {
            type string;
          }
          container policer {
            uses apply-group;
            uses apply-macro;
            leaf input {
              type string;
            }
            leaf output {
              type string;
            }
          }
        }
        container mlppp {
          presence "";
          uses apply-group;
          uses apply-macro;
          leaf bundle {
            type interface-unit;
          }
        }
        container mlfr-end-to-end {
          presence "";
          uses apply-group;
          uses apply-macro;
          leaf bundle {
            type interface-unit;
          }
        }
        container mlfr-uni-nni {
          presence "";
          uses apply-group;
          uses apply-macro;
          leaf bundle {
            type interface-unit;
          }
        }
        container ccc {
          presence "enable ccc";
          uses apply-group;
          uses apply-macro;
          leaf mtu {
            type uint32;
          }
          container filter {
            uses apply-group;
            uses apply-macro;
            choice choice-3 {
              leaf input {
                type string;
              }
              leaf-list input-list {
                type string;
                ordered-by user;
              }
            }
            choice choice-4 {
              leaf output {
                type string;
              }
              leaf-list output-list {
                type string;
                ordered-by user;
              }
            }
            leaf group {
              type uint32;
            }
          }
          container policer {
            uses apply-group;
            uses apply-macro;
            leaf input {
              type string;
            }
            leaf output {
              type string;
            }
          }
          leaf translate-fecn-and-becn {
            type empty;
          }
          choice choice-9 {
            leaf translate-discard-eligible {
              type empty;
            }
            leaf translate-plp-control-word-de {
              type empty;
            }
          }
          leaf keep-address-and-control {
            type empty;
          }
        }
        container tcc {
          presence "enable tcc";
          uses apply-group;
          uses apply-macro;
          container policer {
            uses apply-group;
            uses apply-macro;
            leaf input {
              type string;
            }
            leaf output {
              type string;
            }
          }
          container proxy {
            presence "enable proxy";
            uses apply-group;
            uses apply-macro;
            leaf inet-address {
              type ipv4addr;
            }
          }
          container remote {
            presence "enable remote";
            uses apply-group;
            uses apply-macro;
            leaf inet-address {
              type ipv4addr;
            }
            leaf mac-address {
              type mac-addr;
            }
          }
          leaf-list protocols {
            ordered-by user;
            type string;
          }
        }
        container vpls {
          presence "enable vpls";
          uses apply-group;
          uses apply-macro;
          leaf core-facing {
            type empty;
          }
          container filter {
            uses apply-group;
            uses apply-macro;
            choice choice-3 {
              container input {
                presence "";
                leaf filter-name {
                  type string;
                }
                leaf precedence {
                  type uint32;
                }
              }
              leaf-list input-list {
                type string;
                ordered-by user;
              }
            }
            choice choice-4 {
              container output {
                presence "";
                leaf filter-name {
                  type string;
                }
                leaf precedence {
                  type uint32;
                }
              }
              leaf-list output-list {
                type string;
                ordered-by user;
              }
            }
            container adf {
              presence "";
              uses apply-group;
              uses apply-macro;
              list rule {
                key "name";
                ordered-by user;
                leaf name {
                  type string;
                }
                uses apply-group;
                uses apply-macro;
              }
              leaf counter {
                type empty;
              }
              leaf input-precedence {
                type uint32;
              }
              leaf output-precedence {
                type uint32;
              }
            }
            leaf group {
              type uint32;
            }
          }
          container policer {
            uses apply-group;
            uses apply-macro;
            leaf input {
              type string;
            }
            leaf output {
              type string;
            }
          }
        }
        container bridge {
          presence "enable bridge";
          uses apply-group;
          uses apply-macro;
          leaf core-facing {
            type empty;
          }
          container filter {
            uses apply-group;
            uses apply-macro;
            choice choice-3 {
              container input {
                presence "";
                leaf filter-name {
                  type string;
                }
                leaf precedence {
                  type uint32;
                }
              }
              leaf-list input-list {
                type string;
                ordered-by user;
              }
            }
            choice choice-4 {
              container output {
                presence "";
                leaf filter-name {
                  type string;
                }
                leaf precedence {
                  type uint32;
                }
              }
              leaf-list output-list {
                type string;
                ordered-by user;
              }
            }
            container adf {
              presence "";
              uses apply-group;
              uses apply-macro;
              list rule {
                key "name";
                ordered-by user;
                leaf name {
                  type string;
                }
                uses apply-group;
                uses apply-macro;
              }
              leaf counter {
                type empty;
              }
              leaf input-precedence {
                type uint32;
              }
              leaf output-precedence {
                type uint32;
              }
            }
            leaf group {
              type uint32;
            }
          }
          container policer {
            uses apply-group;
            uses apply-macro;
            leaf input {
              type string;
            }
            leaf output {
              type string;
            }
          }
          leaf interface-mode {
            type string;
          }
          leaf bridge-domain-type {
            type string;
          }
          choice choice-13 {
            leaf vlan-id {
              type uint32;
            }
            leaf-list vlan-id-list {
              type string;
              ordered-by user;
            }
            leaf-list inner-vlan-id-list {
              type string;
              ordered-by user;
            }
          }
          container vlan-rewrite {
            uses apply-group;
            uses apply-macro;
            list translate {
              key "name";
              ordered-by user;
              leaf name {
                type string;
              }
              leaf to-vlan-id {
                type uint32;
              }
            }
          }
          choice choice-16 {
            leaf isid-list {
              type string;
            }
          }
          container storm-control {
            presence "";
            uses apply-group;
            uses apply-macro;
            leaf profile-name {
              type string;
              mandatory true;
            }
          }
        }
        container ethernet-switching {
          presence "enable ethernet-switching";
          uses ethernet-switching-type;
        }
        container fibre-channel {
          presence "enable fibre-channel";
          uses fibre-channel-type;
        }
        container pppoe {
          presence "enable pppoe";
          uses pppoe-underlying-options-type;
        }
        container any {
          presence "enable any";
          uses apply-group;
          uses apply-macro;
          container filter {
            uses apply-group;
            uses apply-macro;
            leaf input {
              type string;
            }
            leaf group {
              type uint32;
            }
          }
        }
      }
      leaf service-domain {
        type string;
      }
      leaf copy-tos-to-outer-ip-header {
        type empty;
      }
      leaf copy-tos-to-outer-ip-header-transit {
        type empty;
      }
      leaf force-control-packets-on-transit-path {
        type empty;
      }
      container load-balancing-options {
        uses apply-group;
        uses apply-macro;
        leaf preferred-active {
          type interface-device;
        }
        leaf disable-hash {
          type empty;
        }
        container hash-keys {
          uses apply-group;
          uses apply-macro;
          leaf-list ingress-key {
            ordered-by user;
            type string;
          }
          leaf-list egress-key {
            ordered-by user;
            type string;
          }
          leaf ipv6-source-prefix-length {
            type string;
          }
        }
      }
      leaf mac {
        type mac-unicast;
      }
      leaf virtual-gateway-v4-mac {
        type mac-unicast;
      }
      leaf virtual-gateway-v6-mac {
        type mac-unicast;
      }
      container forwarding-options {
        uses apply-group;
        uses apply-macro;
        container load-balance-stateful {
          presence "";
          uses apply-group;
          uses apply-macro;
          leaf per-flow {
            mandatory true;
            type empty;
          }
          leaf rebalance {
            units "per minute";
            type uint32;
          }
          leaf load-type {
            type string;
          }
        }
      }
      leaf etree-ac-role {
        type string;
      }
      container dialer-options {
        presence "";
        uses apply-group;
        uses apply-macro;
        leaf pool {
          mandatory true;
          type string;
        }
        leaf-list dial-string {
          ordered-by user;
          type string;
        }
        container incoming-map {
          uses apply-group;
          uses apply-macro;
          choice choice-caller {
            list caller {
              key "name";
              ordered-by user;
              leaf name {
                type string;
              }
            }
            leaf accept-all {
              type empty;
            }
          }
        }
        leaf callback {
          type empty;
        }
        leaf callback-wait-period {
          units "seconds";
          type uint32;
        }
        leaf redial-delay {
          units "seconds";
          type uint32;
        }
        leaf idle-timeout {
          units "seconds";
          type uint32;
        }
        list watch-list {
          key "name";
          leaf name {
            type ipprefix-only;
          }
          uses apply-group;
          uses apply-macro;
        }
        leaf load-threshold {
          type uint32;
        }
        leaf load-interval {
          units "seconds";
          type uint32;
        }
        leaf activation-delay {
          units "seconds";
          type uint32;
        }
        leaf deactivation-delay {
          units "seconds";
          type uint32;
        }
        leaf initial-route-check {
          units "seconds";
          type uint16;
        }
        leaf-list route {
          type ipprefix;
          ordered-by user;
        }
        leaf always-on {
          type empty;
        }
      }
      container backup-options {
        uses apply-group;
        uses apply-macro;
        leaf interface {
          type interface-name;
        }
      }
      container dynamic-call-admission-control {
        presence "";
        uses apply-group;
        uses apply-macro;
        leaf bearer-bandwidth-limit {
          mandatory true;
          units "kilobits per second";
          type uint16;
        }
        leaf activation-priority {
          type uint8;
        }
      }
    }
    container no-partition {
      leaf interface-type {
        type string;
      }
    }
    list partition {
      key "name";
      ordered-by user;
      leaf name {
        type string;
      }
      leaf oc-slice {
        type string;
      }
      leaf timeslots {
        type string;
      }
      leaf interface-type {
        type string;
      }
    }
    container dialer-options {
      presence "enable dialer-options";
      uses apply-group;
      uses apply-macro;
      list pool {
        key "name";
        leaf name {
          type key-attribute-string-type;
        }
        leaf priority {
          type uint32;
        }
      }
    }
    container cellular-options {
      presence "enable cellular-options";
      uses apply-group;
      uses apply-macro;
      container gsm-options {
        presence "enable gsm-options";
        uses apply-group;
        uses apply-macro;
        container select-profile {
          presence "";
          leaf profile-id {
            type uint32;
          }
        }
        leaf encrypted-sim-unlock-code {
          type unreadable;
        }
      }
    }
  }

  grouping ipr-profile-object {
    leaf name {
      type key-attribute-string-type;
    }
    uses apply-group;
    uses apply-macro;
    leaf timeout {
      type int32;
    }
    leaf max-reassembly-pending-packets {
      type int32;
    }
  }

  grouping ipr-rule-object {
    leaf name {
      type key-attribute-string-type;
    }
    uses apply-group;
    uses apply-macro;
    leaf match-direction {
      mandatory true;
      type string;
    }
  }

  grouping ipsec-services-traceoptions {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping ipsec-vpn-rule-object {
    leaf name {
      type key-attribute-string-type;
    }
    uses apply-group;
    uses apply-macro;
    list term {
      key "name";
      ordered-by user;
      leaf name {
        type key-attribute-string-type;
      }
      uses apply-group;
      uses apply-macro;
      container from {
        uses ipsec-vpn-match-object;
      }
      container then {
        presence "";
        uses apply-group;
        uses apply-macro;
        leaf syslog {
          type empty;
        }
        leaf remote-gateway {
          type ipaddr;
        }
        leaf backup-remote-gateway {
          type ipaddr;
        }
        choice choice-manual {
          container manual {
            uses apply-group;
            uses apply-macro;
            list direction {
              key "name";
              ordered-by user;
              leaf name {
                type string;
              }
              uses apply-group;
              uses apply-macro;
              leaf protocol {
                type string;
              }
              leaf spi {
                type uint32;
              }
              leaf auxiliary-spi {
                type uint32;
              }
              container authentication {
                presence "";
                uses apply-group;
                uses apply-macro;
                leaf algorithm {
                  type string;
                }
                container key {
                  choice choice-ascii-text {
                    leaf ascii-text {
                      type string;
                    }
                    leaf hexadecimal {
                      type string;
                    }
                  }
                }
              }
              container encryption {
                presence "";
                uses apply-group;
                uses apply-macro;
                leaf algorithm {
                  type string;
                }
                container key {
                  choice choice-ascii-text {
                    leaf ascii-text {
                      type string;
                    }
                    leaf hexadecimal {
                      type string;
                    }
                  }
                }
              }
            }
          }
          container dynamic {
            presence "";
            uses apply-group;
            uses apply-macro;
            leaf ike-policy {
              type string;
            }
            leaf ipsec-policy {
              type string;
            }
          }
        }
        leaf clear-dont-fragment-bit {
          type empty;
        }
        leaf copy-dont-fragment-bit {
          type empty;
        }
        leaf set-dont-fragment-bit {
          type empty;
        }
        leaf no-anti-replay {
          type empty;
        }
        leaf tunnel-mtu {
          type uint32;
        }
        leaf initiate-dead-peer-detection {
          type empty;
        }
        container dead-peer-detection {
          presence "";
          uses apply-group;
          uses apply-macro;
          leaf interval {
            units "seconds";
            type uint32;
          }
          leaf threshold {
            type uint32;
          }
        }
        leaf anti-replay-window-size {
          type uint32;
        }
      }
    }
    leaf match-direction {
      type string;
    }
  }

  grouping ipsec-vpn-match-object {
    uses apply-group;
    uses apply-macro;
    list source-address {
      key "name";
      ordered-by user;
      uses ipsec-vpn-addr-object;
    }
    list destination-address {
      key "name";
      ordered-by user;
      uses ipsec-vpn-addr-object;
    }
    leaf ipsec-inside-interface {
      type interface-unit;
    }
  }

  grouping ipsec-vpn-addr-object {
    leaf name {
      type ipprefix-only;
    }
    uses apply-group;
    uses apply-macro;
  }

  grouping ip-monitoring-address-type {
    leaf name {
      type ipv4addr;
    }
    uses apply-group;
    uses apply-macro;
    leaf weight {
      type uint16;
    }
    list interface {
      key "logical-interface-name secondary-ip-address";
      ordered-by user;
      leaf logical-interface-name {
        type interface-name;
      }
      leaf secondary-ip-address {
        type ipv4addr;
      }
      uses apply-group;
      uses apply-macro;
    }
  }

  grouping jsrc-partition-definition {
    uses apply-group;
    uses apply-macro;
    list partition {
      key "name";
      ordered-by user;
      leaf name {
        type key-attribute-string-type;
      }
      uses apply-group;
      uses apply-macro;
      leaf diameter-instance {
        type string;
      }
      leaf destination-realm {
        type string;
      }
      leaf destination-host {
        type string;
      }
    }
  }

  grouping juniper-access-options {
    uses apply-group;
    uses apply-macro;
    list radius-server {
      key "name";
      ordered-by user;
      uses access-radius-server-object;
    }
    leaf radius-disconnect-port {
      type uint16;
    }
    list radius-disconnect {
      key "name";
      ordered-by user;
      uses radius-disconnect-object;
    }
    list address-pool {
      key "name";
      ordered-by user;
      uses address-pool-object;
    }
    list group-profile {
      key "name";
      ordered-by user;
      uses group-profile-object;
    }
    list profile {
      key "name";
      ordered-by user;
      leaf name {
        type key-attribute-string-type;
      }
      uses apply-group;
      uses apply-macro;
      leaf-list accounting-order {
        ordered-by user;
        type string;
      }
      leaf-list authentication-order {
        ordered-by user;
        type string;
      }
      leaf-list authorization-order {
        ordered-by user;
        type string;
      }
      leaf provisioning-order {
        type string;
      }
      list domain-name-server {
        key "name";
        ordered-by user;
        leaf name {
          type ipv4addr;
        }
        uses apply-group;
        uses apply-macro;
      }
      list domain-name-server-inet {
        key "name";
        ordered-by user;
        leaf name {
          type ipv4addr;
        }
        uses apply-group;
        uses apply-macro;
      }
      list domain-name-server-inet6 {
        key "name";
        ordered-by user;
        leaf name {
          type ipv6addr;
        }
        uses apply-group;
        uses apply-macro;
      }
      list client {
        key "name";
        uses access-client-object;
      }
      container address-assignment {
        uses apply-group;
        uses apply-macro;
        leaf pool {
          type string;
        }
      }
      container radius {
        uses apply-group;
        uses apply-macro;
        leaf-list authentication-server {
          type ipv4addr;
          ordered-by user;
        }
        leaf-list accounting-server {
          type ipv4addr;
          ordered-by user;
        }
        leaf-list preauthentication-server {
          type ipv4addr;
          ordered-by user;
        }
        container options {
          uses apply-group;
          uses apply-macro;
          leaf ethernet-port-type-virtual {
            type empty;
          }
          container interface-description-format {
            uses apply-group;
            uses apply-macro;
            leaf exclude-sub-interface {
              type empty;
            }
            leaf exclude-adapter {
              type empty;
            }
          }
          leaf nas-identifier {
            type string;
          }
          container nas-port-extended-format {
            uses apply-group;
            uses apply-macro;
            leaf slot-width {
              type uint32;
            }
            leaf adapter-width {
              type uint32;
            }
            leaf port-width {
              type uint32;
            }
            leaf stacked-vlan-width {
              type uint32;
            }
            leaf vlan-width {
              type uint32;
            }
          }
          leaf nas-port-id-delimiter {
            type string;
          }
          container nas-port-id-format {
            uses apply-group;
            uses apply-macro;
            leaf nas-identifier {
              type empty;
            }
            leaf interface-description {
              type empty;
            }
            leaf agent-circuit-id {
              type empty;
            }
            leaf agent-remote-id {
              type empty;
            }
            leaf postpend-vlan-tags {
              type empty;
            }
            leaf interface-text-description {
              type empty;
            }
            leaf-list order {
              ordered-by user;
              type string;
            }
          }
          container nas-port-type {
            uses apply-group;
            uses apply-macro;
            leaf ethernet {
              type string;
            }
          }
          leaf calling-station-id-delimiter {
            type string;
          }
          container calling-station-id-format {
            uses apply-group;
            uses apply-macro;
            leaf nas-identifier {
              type empty;
            }
            leaf interface-description {
              type empty;
            }
            leaf agent-circuit-id {
              type empty;
            }
            leaf agent-remote-id {
              type empty;
            }
            leaf interface-text-description {
              type empty;
            }
            leaf stacked-vlan {
              type empty;
            }
            leaf vlan {
              type empty;
            }
            container undocumented {
              leaf mac-address {
                type empty;
              }
            }
          }
          leaf remote-circuit-id-delimiter {
            type string;
          }
          container remote-circuit-id-format {
            uses apply-group;
            uses apply-macro;
            leaf agent-circuit-id {
              type empty;
            }
            leaf agent-remote-id {
              type empty;
            }
          }
          leaf remote-circuit-id-fallback {
            type string;
          }
          container override {
            uses apply-group;
            uses apply-macro;
            container calling-station-id {
              leaf remote-circuit-id {
                type empty;
              }
            }
            leaf nas-port {
              type string;
            }
            leaf nas-port-type {
              type string;
            }
            leaf nas-ip-address {
              type string;
            }
          }
          leaf accounting-session-id-format {
            type string;
          }
          leaf revert-interval {
            type uint32;
          }
          leaf vlan-nas-port-stacked-format {
            type empty;
          }
          leaf client-authentication-algorithm {
            type string;
          }
          leaf client-accounting-algorithm {
            type string;
          }
          leaf juniper-access-line-attributes {
            type empty;
          }
          container ip-address-change-notify {
            presence "enable ip-address-change-notify";
            leaf message {
              type string;
            }
          }
          leaf coa-dynamic-variable-validation {
            type empty;
          }
          leaf chap-challenge-in-request-authenticator {
            type empty;
          }
          container service-activation {
            uses apply-group;
            uses apply-macro;
            leaf extensible-service {
              type string;
            }
            leaf dynamic-profile {
              type string;
            }
          }
          leaf accounting-username-original {
            type empty;
          }
        }
        container attributes {
          uses apply-group;
          uses apply-macro;
          container ignore {
            uses apply-group;
            uses apply-macro;
            leaf output-filter {
              type empty;
            }
            leaf input-filter {
              type empty;
            }
            leaf framed-ip-netmask {
              type empty;
            }
            leaf logical-system-routing-instance {
              type empty;
            }
            leaf dynamic-iflset-name {
              type empty;
            }
            leaf idle-timeout {
              type empty;
            }
            leaf session-timeout {
              type empty;
            }
            leaf-list standard-attribute {
              ordered-by user;
              type uint32;
            }
            list vendor-id {
              key "name";
              ordered-by user;
              leaf name {
                type key-attribute-ulong-type;
              }
              uses apply-group;
              uses apply-macro;
              leaf-list vendor-attribute {
                ordered-by user;
                type uint32;
              }
            }
          }
          container exclude {
            uses apply-group;
            uses apply-macro;
            list standard-attribute {
              key "name";
              ordered-by user;
              leaf name {
                type key-attribute-ulong-type;
              }
              uses apply-group;
              uses apply-macro;
              leaf-list packet-type {
                ordered-by user;
                type string;
              }
            }
            list vendor-id {
              key "name";
              ordered-by user;
              leaf name {
                type key-attribute-ulong-type;
              }
              uses apply-group;
              uses apply-macro;
              list vendor-attribute {
                key "name";
                ordered-by user;
                leaf name {
                  type key-attribute-ulong-type;
                }
                uses apply-group;
                uses apply-macro;
                leaf-list packet-type {
                  ordered-by user;
                  type string;
                }
              }
            }
            leaf-list accounting-authentic {
              ordered-by user;
              type string;
            }
            leaf-list accounting-delay-time {
              ordered-by user;
              type string;
            }
            leaf-list accounting-session-id {
              ordered-by user;
              type string;
            }
            leaf-list accounting-terminate-cause {
              ordered-by user;
              type string;
            }
            leaf-list called-station-id {
              ordered-by user;
              type string;
            }
            leaf-list calling-station-id {
              ordered-by user;
              type string;
            }
            leaf-list class {
              ordered-by user;
              type string;
            }
            leaf-list delegated-ipv6-prefix {
              ordered-by user;
              type string;
            }
            leaf-list dhcp-options {
              ordered-by user;
              type string;
            }
            leaf-list dhcp-gi-address {
              ordered-by user;
              type string;
            }
            leaf-list dhcp-mac-address {
              ordered-by user;
              type string;
            }
            leaf-list output-filter {
              ordered-by user;
              type string;
            }
            leaf-list event-time-stamp {
              ordered-by user;
              type string;
            }
            leaf-list filter-id {
              ordered-by user;
              type string;
            }
            leaf-list framed-ip-address {
              ordered-by user;
              type string;
            }
            leaf-list framed-ip-netmask {
              ordered-by user;
              type string;
            }
            leaf-list framed-ip-route {
              ordered-by user;
              type string;
            }
            leaf-list framed-ipv6-address {
              ordered-by user;
              type string;
            }
            leaf-list framed-ipv6-pool {
              ordered-by user;
              type string;
            }
            leaf-list framed-ipv6-prefix {
              ordered-by user;
              type string;
            }
            leaf-list framed-ipv6-route {
              ordered-by user;
              type string;
            }
            leaf-list framed-pool {
              ordered-by user;
              type string;
            }
            leaf-list input-filter {
              ordered-by user;
              type string;
            }
            leaf-list input-gigapackets {
              ordered-by user;
              type string;
            }
            leaf-list input-gigawords {
              ordered-by user;
              type string;
            }
            leaf-list input-ipv6-packets {
              ordered-by user;
              type string;
            }
            leaf-list input-ipv6-gigawords {
              ordered-by user;
              type string;
            }
            leaf-list input-ipv6-octets {
              ordered-by user;
              type string;
            }
            leaf-list interface-description {
              ordered-by user;
              type string;
            }
            leaf-list nas-identifier {
              ordered-by user;
              type string;
            }
            leaf-list nas-port {
              ordered-by user;
              type string;
            }
            leaf-list nas-port-id {
              ordered-by user;
              type string;
            }
            leaf-list nas-port-type {
              ordered-by user;
              type string;
            }
            leaf-list output-gigapackets {
              ordered-by user;
              type string;
            }
            leaf-list output-gigawords {
              ordered-by user;
              type string;
            }
            leaf-list output-ipv6-packets {
              ordered-by user;
              type string;
            }
            leaf-list output-ipv6-gigawords {
              ordered-by user;
              type string;
            }
            leaf-list output-ipv6-octets {
              ordered-by user;
              type string;
            }
            leaf-list dynamic-iflset-name {
              ordered-by user;
              type string;
            }
            leaf-list dsl-forum-attributes {
              ordered-by user;
              type string;
            }
            leaf-list l2c-upstream-data {
              ordered-by user;
              type string;
            }
            leaf-list l2c-downstream-data {
              ordered-by user;
              type string;
            }
            leaf-list acc-loop-cir-id {
              ordered-by user;
              type string;
            }
            leaf-list acc-aggr-cir-id-bin {
              ordered-by user;
              type string;
            }
            leaf-list acc-aggr-cir-id-asc {
              ordered-by user;
              type string;
            }
            leaf-list act-data-rate-up {
              ordered-by user;
              type string;
            }
            leaf-list act-data-rate-dn {
              ordered-by user;
              type string;
            }
            leaf-list min-data-rate-up {
              ordered-by user;
              type string;
            }
            leaf-list min-data-rate-dn {
              ordered-by user;
              type string;
            }
            leaf-list att-data-rate-up {
              ordered-by user;
              type string;
            }
            leaf-list att-data-rate-dn {
              ordered-by user;
              type string;
            }
            leaf-list max-data-rate-up {
              ordered-by user;
              type string;
            }
            leaf-list max-data-rate-dn {
              ordered-by user;
              type string;
            }
            leaf-list min-lp-data-rate-up {
              ordered-by user;
              type string;
            }
            leaf-list min-lp-data-rate-dn {
              ordered-by user;
              type string;
            }
            leaf-list max-interlv-delay-up {
              ordered-by user;
              type string;
            }
            leaf-list act-interlv-delay-up {
              ordered-by user;
              type string;
            }
            leaf-list max-interlv-delay-dn {
              ordered-by user;
              type string;
            }
            leaf-list act-interlv-delay-dn {
              ordered-by user;
              type string;
            }
            leaf-list dsl-line-state {
              ordered-by user;
              type string;
            }
            leaf-list dsl-type {
              ordered-by user;
              type string;
            }
            leaf-list downstream-calculated-qos-rate {
              ordered-by user;
              type string;
            }
            leaf-list upstream-calculated-qos-rate {
              ordered-by user;
              type string;
            }
            leaf-list cos-shaping-rate {
              ordered-by user;
              type string;
            }
            leaf-list framed-interface-id {
              ordered-by user;
              type string;
            }
            leaf-list chargeable-user-identity {
              ordered-by user;
              type string;
            }
            leaf-list l2tp-tx-connect-speed {
              ordered-by user;
              type string;
            }
            leaf-list l2tp-rx-connect-speed {
              ordered-by user;
              type string;
            }
            leaf-list tunnel-type {
              ordered-by user;
              type string;
            }
            leaf-list tunnel-medium-type {
              ordered-by user;
              type string;
            }
            leaf-list tunnel-client-endpoint {
              ordered-by user;
              type string;
            }
            leaf-list tunnel-server-endpoint {
              ordered-by user;
              type string;
            }
            leaf-list tunnel-assignment-id {
              ordered-by user;
              type string;
            }
            leaf-list tunnel-client-auth-id {
              ordered-by user;
              type string;
            }
            leaf-list tunnel-server-auth-id {
              ordered-by user;
              type string;
            }
            leaf-list acct-tunnel-connection {
              ordered-by user;
              type string;
            }
            leaf-list acc-loop-remote-id {
              ordered-by user;
              type string;
            }
            leaf-list acc-loop-encap {
              ordered-by user;
              type string;
            }
            leaf-list pppoe-description {
              ordered-by user;
              type string;
            }
            leaf-list virtual-router {
              ordered-by user;
              type string;
            }
            leaf-list first-relay-ipv4-address {
              ordered-by user;
              type string;
            }
            leaf-list first-relay-ipv6-address {
              ordered-by user;
              type string;
            }
            leaf-list dhcpv6-options {
              ordered-by user;
              type string;
            }
            leaf-list dhcp-header {
              ordered-by user;
              type string;
            }
            leaf-list dhcpv6-header {
              ordered-by user;
              type string;
            }
            leaf-list acct-request-reason {
              ordered-by user;
              type string;
            }
          }
        }
      }
      container session-options {
        uses apply-group;
        uses apply-macro;
        leaf-list client-group {
          type string;
          ordered-by user;
        }
        leaf client-idle-timeout {
          type uint32;
        }
        leaf client-session-timeout {
          type uint32;
        }
      }
      container client-name-filter {
        uses access-client-name-filter-object;
      }
      container ldap-options {
        presence "";
        uses access-ldap-options;
      }
      list ldap-server {
        key "name";
        ordered-by user;
        uses ldap-server-object;
      }
      list radius-server {
        key "name";
        ordered-by user;
        uses profile-radius-server-object;
      }
      container radius-options {
        uses access-radius-options;
      }
      container accounting {
        presence "";
        uses apply-group;
        uses apply-macro;
        leaf-list order {
          ordered-by user;
          type string;
        }
        leaf accounting-stop-on-failure {
          type empty;
        }
        leaf accounting-stop-on-access-deny {
          type empty;
        }
        leaf immediate-update {
          type empty;
        }
        leaf coa-immediate-update {
          type empty;
        }
        leaf address-change-immediate-update {
          type empty;
        }
        leaf update-interval {
          type uint32;
        }
        leaf statistics {
          type string;
        }
        leaf wait-for-acct-on-ack {
          type empty;
        }
        leaf send-acct-status-on-config-change {
          type empty;
        }
        leaf duplication {
          type empty;
        }
        leaf-list duplication-filter {
          ordered-by user;
          type string;
        }
        container duplication-vrf {
          presence "";
          uses apply-group;
          uses apply-macro;
          leaf vrf-name {
            mandatory true;
            type string;
          }
          leaf-list access-profile-name {
            ordered-by user;
            type string;
          }
        }
        leaf-list duplication-attribute-format {
          ordered-by user;
          type string;
        }
        leaf ancp-speed-change-immediate-update {
          type empty;
        }
        leaf family-state-change-immediate-update {
          type empty;
        }
      }
    }
    container address-assignment {
      uses address-assignment-type;
    }
    list tunnel-profile {
      key "name";
      ordered-by user;
      leaf name {
        type key-attribute-string-type;
      }
      uses apply-group;
      uses apply-macro;
      list tunnel {
        key "name";
        ordered-by user;
        leaf name {
          type string;
        }
        uses apply-group;
        uses apply-macro;
        leaf preference {
          type uint32;
        }
        container remote-gateway {
          presence "";
          uses apply-group;
          uses apply-macro;
          leaf address {
            type ipv4addr;
          }
          leaf gateway-name {
            type string;
          }
        }
        container source-gateway {
          uses apply-group;
          uses apply-macro;
          leaf address {
            type ipv4addr;
          }
          leaf gateway-name {
            type string;
          }
        }
        choice choice-9 {
          leaf routing-instance {
            type string;
          }
          list logical-system {
            key "name";
            ordered-by user;
            leaf name {
              type string;
            }
            uses apply-group;
            uses apply-macro;
            leaf routing-instance {
              type string;
            }
          }
        }
        leaf secret {
          type unreadable;
        }
        leaf medium {
          type string;
        }
        leaf tunnel-type {
          type string;
        }
        leaf identification {
          type string;
        }
        leaf max-sessions {
          type uint32;
        }
      }
    }
    list tunnel-switch-profile {
      key "name";
      ordered-by user;
      leaf name {
        type key-attribute-string-type;
      }
      uses apply-group;
      uses apply-macro;
      container avp {
        uses apply-group;
        uses apply-macro;
        leaf calling-number {
          type string;
        }
        leaf bearer-type {
          type string;
        }
        leaf cisco-nas-port-info {
          type string;
        }
      }
      leaf tunnel-profile {
        type string;
      }
    }
    container domain {
      uses domain-map-type;
    }
    container ppp-options {
      presence "enable ppp-options";
      uses apply-group;
      uses apply-macro;
      container compliance {
        uses apply-group;
        uses apply-macro;
        leaf-list rfc {
          ordered-by user;
          type string;
        }
      }
    }
    container pcrf {
      uses pcrf-definition;
    }
    list aaa-options {
      key "name";
      ordered-by user;
      leaf name {
        type key-attribute-string-type;
      }
      uses apply-group;
      uses apply-macro;
      leaf access-profile {
        type string;
      }
      leaf aaa-context {
        type string;
      }
      leaf subscriber-context {
        type string;
      }
    }
    container radius-options {
      uses access-radius-options;
    }
    container ldap-options {
      presence "";
      uses access-ldap-options;
    }
    list ldap-server {
      key "name";
      ordered-by user;
      uses ldap-server-object;
    }
    list securid-server {
      key "name";
      ordered-by user;
      uses securid-server-object;
    }
    container firewall-authentication {
      uses apply-group;
      uses apply-macro;
      container pass-through {
        presence "";
        uses apply-group;
        uses apply-macro;
        leaf default-profile {
          type string;
        }
        container ftp {
          uses banner-object;
        }
        container telnet {
          uses banner-object;
        }
        container http {
          uses banner-object;
        }
      }
      container web-authentication {
        presence "";
        uses apply-group;
        uses apply-macro;
        leaf default-profile {
          type string;
        }
        container banner {
          uses apply-group;
          uses apply-macro;
          leaf success {
            type string;
          }
        }
      }
      container traceoptions {
        uses apply-group;
        uses apply-macro;
        leaf no-remote-trace {
          type empty;
        }
        container file {
          leaf filename {
            type string;
          }
          leaf size {
            type string;
          }
          leaf files {
            type uint32;
          }
          leaf world-readable {
            type empty;
          }
          leaf no-world-readable {
            type empty;
          }
          leaf match {
            type regular-expression;
          }
        }
        list flag {
          key "name";
          ordered-by user;
          leaf name {
            type string;
          }
        }
      }
    }
  }

  grouping access-client-name-filter-object {
    uses apply-group;
    uses apply-macro;
    leaf domain-name {
      type string;
    }
    leaf separator {
      type string;
    }
    leaf count {
      type uint8;
    }
  }

  grouping access-client-object {
    leaf name {
      type string;
    }
    uses apply-group;
    uses apply-macro;
    leaf no-rfc2486 {
      type empty;
    }
    leaf chap-secret {
      type unreadable;
    }
    leaf pap-password {
      type unreadable;
    }
    choice choice-9 {
      container ppp {
        presence "enable ppp";
        uses apply-group;
        uses apply-macro;
        leaf framed-pool {
          type string;
        }
        leaf idle-timeout {
          type uint32;
        }
        leaf keepalive {
          type uint16;
        }
        leaf primary-dns {
          type string;
        }
        leaf secondary-dns {
          type string;
        }
        leaf primary-wins {
          type string;
        }
        leaf secondary-wins {
          type string;
        }
        leaf encapsulation-overhead {
          type int8;
        }
        leaf cell-overhead {
          type empty;
        }
        leaf interface-id {
          type string;
        }
        leaf framed-ip-address {
          type ipv4prefix;
        }
        leaf keepalive-retries {
          type uint16;
        }
      }
      container l2tp {
        presence "";
        uses apply-group;
        uses apply-macro;
        leaf maximum-sessions {
          type uint32;
        }
        leaf maximum-sessions-per-tunnel {
          type uint16;
        }
        leaf service-profile {
          type string;
        }
        leaf interface-id {
          type string;
        }
        leaf lcp-renegotiation {
          type empty;
        }
        leaf local-chap {
          type empty;
        }
        container override-result-code {
          uses apply-group;
          uses apply-macro;
          leaf session-out-of-resource {
            type empty;
          }
        }
        leaf aaa-access-profile {
          type string;
        }
        container multilink {
          presence "enable multilink";
          uses multilink-object;
        }
        leaf session-limit-group {
          type string;
        }
        leaf ppp-authentication {
          type string;
        }
        leaf shared-secret {
          type unreadable;
        }
        leaf ppp-profile {
          type string;
        }
        leaf dynamic-profile {
          type string;
        }
      }
      container ike {
        presence "";
        uses apply-group;
        uses apply-macro;
        list allowed-proxy-pair {
          key "local remote";
          ordered-by user;
          leaf local {
            type ipprefix-only;
          }
          leaf remote {
            type ipprefix-only;
          }
          uses apply-group;
          uses apply-macro;
        }
        leaf initiate-dead-peer-detection {
          type empty;
        }
        container dead-peer-detection {
          presence "enable dead-peer-detection";
          uses apply-group;
          uses apply-macro;
          leaf interval {
            units "seconds";
            type uint32;
          }
          leaf threshold {
            type uint32;
          }
        }
        choice choice-pre-shared-key {
          container pre-shared-key {
            choice choice-ascii-text {
              leaf ascii-text {
                type unreadable;
              }
              leaf hexadecimal {
                type unreadable;
              }
            }
          }
          leaf ike-policy {
            type string;
          }
        }
        leaf ipsec-policy {
          type string;
        }
        container reverse-route {
          presence "enable reverse-route";
          uses apply-group;
          uses apply-macro;
          container preference {
            presence "";
            leaf metric-value {
              type uint32;
              mandatory true;
            }
          }
        }
        leaf interface-id {
          mandatory true;
          type string;
        }
      }
    }
    leaf group-profile {
      type string;
    }
    leaf user-group-profile {
      type string;
    }
    container xauth {
      uses apply-group;
      uses apply-macro;
      leaf ip-address {
        type ipv4prefix;
      }
    }
    leaf-list client-group {
      type string;
      ordered-by user;
    }
    container firewall-user {
      uses apply-group;
      uses apply-macro;
      leaf password {
        type string;
      }
    }
  }

  grouping access-ldap-options {
    uses apply-group;
    uses apply-macro;
    leaf revert-interval {
      type uint32;
    }
    leaf base-distinguished-name {
      type string;
    }
    choice choice-7 {
      container assemble {
        presence "enable assemble";
        uses apply-group;
        uses apply-macro;
        leaf common-name {
          type string;
        }
      }
      container search {
        presence "";
        uses apply-group;
        uses apply-macro;
        leaf search-filter {
          type string;
        }
        container admin-search {
          presence "";
          uses apply-group;
          uses apply-macro;
          leaf distinguished-name {
            type string;
          }
          leaf password {
            type unreadable;
          }
        }
      }
    }
  }

  grouping access-radius-options {
    uses apply-group;
    uses apply-macro;
    leaf revert-interval {
      type uint32;
    }
    leaf timeout-grace {
      units "seconds";
      type uint32;
    }
    leaf request-rate {
      type uint32;
    }
    leaf interim-rate {
      type uint32;
    }
    leaf interim-update-tolerance {
      units "seconds";
      type uint32;
    }
    container unique-nas-port {
      presence "enable unique-nas-port";
      uses apply-group;
      uses apply-macro;
      leaf chassis-id {
        type uint32;
      }
      leaf chassis-id-width {
        units "bits";
        type uint32;
      }
    }
  }

  grouping access-radius-server-object {
    leaf name {
      type ipv4addr;
    }
    uses apply-group;
    uses apply-macro;
    leaf port {
      type uint16;
    }
    leaf preauthentication-port {
      type uint16;
    }
    leaf accounting-port {
      type uint16;
    }
    leaf dynamic-request-port {
      type uint16;
    }
    leaf secret {
      type unreadable;
    }
    leaf preauthentication-secret {
      type unreadable;
    }
    leaf timeout {
      type uint32;
    }
    leaf retry {
      type uint32;
    }
    leaf accounting-timeout {
      units "seconds";
      type uint32;
    }
    leaf accounting-retry {
      type uint32;
    }
    leaf max-outstanding-requests {
      type uint32;
    }
    leaf source-address {
      type ipv4addr;
    }
    leaf routing-instance {
      type string;
    }
    leaf radsec-destination {
      type uint32;
    }
  }

  grouping address-assignment-type {
    uses apply-group;
    uses apply-macro;
    container neighbor-discovery-router-advertisement {
      leaf ndra-name {
        type string;
      }
    }
    leaf high-utilization {
      type uint16;
    }
    leaf abated-utilization {
      type uint16;
    }
    leaf high-utilization-v6 {
      type uint16;
    }
    leaf abated-utilization-v6 {
      type uint16;
    }
    list pool {
      key "name";
      ordered-by user;
      leaf name {
        type key-attribute-string-type;
      }
      uses apply-group;
      uses apply-macro;
      leaf link {
        type string;
      }
      container family {
        presence "enable family";
        uses apply-group;
        uses apply-macro;
        choice choice-3 {
          container inet {
            presence "";
            uses apply-group;
            uses apply-macro;
            leaf network {
              type ipv4prefix;
            }
            list range {
              key "name";
              ordered-by user;
              leaf name {
                type key-attribute-string-type;
              }
              uses apply-group;
              uses apply-macro;
              leaf low {
                type ipv4addr;
              }
              leaf high {
                type ipv4addr;
              }
            }
            container dhcp-attributes {
              uses dhcp-attribute-type;
            }
            container xauth-attributes {
              uses apply-group;
              uses apply-macro;
              leaf primary-dns {
                type ipv4prefix;
              }
              leaf secondary-dns {
                type ipv4prefix;
              }
              leaf primary-wins {
                type ipv4prefix;
              }
              leaf secondary-wins {
                type ipv4prefix;
              }
            }
            list host {
              key "name";
              ordered-by user;
              leaf name {
                type key-attribute-string-type;
              }
              uses apply-group;
              uses apply-macro;
              leaf hardware-address {
                type mac-addr;
              }
              leaf ip-address {
                type ipv4addr;
              }
            }
            container undocumented {
              leaf mask-length {
                type uint32;
              }
            }
          }
          container inet6 {
            presence "";
            uses apply-group;
            uses apply-macro;
            leaf prefix {
              type ipv6prefix-mandatory;
            }
            list range {
              key "name";
              ordered-by user;
              leaf name {
                type key-attribute-string-type;
              }
              uses apply-group;
              uses apply-macro;
              leaf low {
                type ipv6prefix-mandatory;
              }
              leaf high {
                type ipv6prefix-mandatory;
              }
              leaf prefix-length {
                type uint32;
              }
            }
            container dhcp-attributes {
              uses dhcp-attribute-type;
            }
          }
        }
      }
    }
    list location-pool {
      key "name";
      ordered-by user;
      leaf name {
        type key-attribute-string-type;
      }
      uses apply-group;
      uses apply-macro;
      container family {
        presence "enable family";
        uses apply-group;
        uses apply-macro;
        container inet {
          uses apply-group;
          uses apply-macro;
          list location {
            key "name";
            leaf name {
              type string;
            }
            uses apply-group;
            uses apply-macro;
            leaf address {
              type ipv4prefix;
            }
          }
        }
      }
    }
    list mobile-pools {
      key "name";
      ordered-by user;
      uses sm-ippool-pool;
    }
    list mobile-pool-groups {
      key "name";
      ordered-by user;
      uses sm-ippool-group;
    }
    list address-pools {
      key "name";
      ordered-by user;
      uses sm-ippool-pool;
    }
  }

  grouping address-pool-object {
    leaf name {
      type key-attribute-string-type;
    }
    uses apply-group;
    uses apply-macro;
    choice choice-3 {
      leaf address {
        type ipv4prefix;
      }
      container address-range {
        presence "enable address-range";
        leaf low {
          type ipv4addr;
        }
        leaf high {
          type ipv4addr;
        }
        leaf mask {
          type ipv4addr;
        }
      }
    }
    leaf primary-dns {
      type hostname;
    }
    leaf secondary-dns {
      type hostname;
    }
    leaf primary-wins {
      type hostname;
    }
    leaf secondary-wins {
      type hostname;
    }
  }

  grouping banner-object {
    uses apply-group;
    uses apply-macro;
    container banner {
      uses apply-group;
      uses apply-macro;
      leaf login {
        type string;
      }
      leaf success {
        type string;
      }
      leaf fail {
        type string;
      }
    }
  }

  grouping dhcp-attribute-type {
    uses apply-group;
    uses apply-macro;
    container option-match {
      uses apply-group;
      uses apply-macro;
      container option-82 {
        uses apply-group;
        uses apply-macro;
        list circuit-id {
          key "name";
          ordered-by user;
          leaf name {
            type string;
          }
          leaf range {
            type string;
          }
        }
        list remote-id {
          key "name";
          ordered-by user;
          leaf name {
            type string;
          }
          leaf range {
            type string;
          }
        }
      }
    }
    leaf maximum-lease-time {
      type string;
    }
    leaf server-identifier {
      type ipv4addr;
    }
    leaf grace-period {
      type uint32;
    }
    leaf domain-name {
      type string;
    }
    list name-server {
      key "name";
      ordered-by user;
      leaf name {
        type ipv4addr;
      }
      uses apply-group;
      uses apply-macro;
    }
    list wins-server {
      key "name";
      ordered-by user;
      leaf name {
        type ipv4addr;
      }
      uses apply-group;
      uses apply-macro;
    }
    list router {
      key "name";
      ordered-by user;
      leaf name {
        type ipv4addr;
      }
      uses apply-group;
      uses apply-macro;
    }
    leaf boot-file {
      type string;
    }
    leaf boot-server {
      type string;
    }
    leaf tftp-server {
      type ipv4addr;
    }
    leaf netbios-node-type {
      type string;
    }
    leaf sip-server-domain-name {
      type string;
    }
    list sip-server-address {
      key "name";
      ordered-by user;
      leaf name {
        type ipv6addr;
      }
      uses apply-group;
      uses apply-macro;
    }
    list dns-server {
      key "name";
      ordered-by user;
      leaf name {
        type ipv6addr;
      }
      uses apply-group;
      uses apply-macro;
    }
    leaf propagate-settings {
      type string;
    }
    leaf-list propagate-ppp-settings {
      type interface-name;
      ordered-by user;
    }
    list option {
      key "name";
      ordered-by user;
      leaf name {
        type uint32;
      }
      choice choice-3 {
        leaf flag {
          type string;
        }
        leaf byte {
          type uint8;
        }
        leaf short {
          type int16;
        }
        leaf unsigned-short {
          type uint16;
        }
        leaf integer {
          type int32;
        }
        leaf unsigned-integer {
          type uint32;
        }
        leaf string {
          type string;
        }
        leaf ip-address {
          type ipv4addr;
        }
        leaf ipv6-address {
          type ipv6addr;
        }
        container array {
          presence "enable array";
          uses apply-group;
          uses apply-macro;
          choice choice-3 {
            leaf-list flag {
              ordered-by user;
              type string;
            }
            leaf-list byte {
              type uint8;
              ordered-by user;
            }
            leaf-list short {
              type int16;
              ordered-by user;
            }
            leaf-list unsigned-short {
              type uint16;
              ordered-by user;
            }
            leaf-list integer {
              type int32;
              ordered-by user;
            }
            leaf-list unsigned-integer {
              type uint32;
              ordered-by user;
            }
            leaf-list string {
              ordered-by user;
              type string;
            }
            leaf-list ip-address {
              type ipv4addr;
              ordered-by user;
            }
            leaf-list ipv6-address {
              type ipv6addr;
              ordered-by user;
            }
          }
        }
      }
    }
    leaf valid-lifetime {
      units "seconds";
      type string;
    }
    leaf preferred-lifetime {
      units "seconds";
      type string;
    }
    leaf t1-percentage {
      units "percent";
      type uint32;
    }
    leaf t2-percentage {
      units "percent";
      type uint32;
    }
    leaf exclude-prefix-len {
      type uint32;
    }
    leaf t1-renewal-time {
      type uint32;
      units "seconds";
    }
    leaf t2-rebinding-time {
      type uint32;
      units "seconds";
    }
  }

  grouping domain-map-type {
    uses apply-group;
    uses apply-macro;
    list map {
      key "name";
      ordered-by user;
      leaf name {
        type key-attribute-string-type;
      }
      uses apply-group;
      uses apply-macro;
      choice choice-3 {
        leaf aaa-routing-instance {
          type string;
        }
        list aaa-logical-system {
          key "name";
          ordered-by user;
          leaf name {
            type string;
          }
          uses apply-group;
          uses apply-macro;
          leaf aaa-routing-instance {
            type string;
          }
        }
      }
      leaf access-profile {
        type string;
      }
      leaf address-pool {
        type string;
      }
      leaf dynamic-profile {
        type string;
      }
      list padn {
        key "name";
        ordered-by user;
        leaf name {
          type ipv4addr;
        }
        uses apply-group;
        uses apply-macro;
        leaf mask {
          type ipv4addr;
        }
        leaf metric {
          type uint16;
        }
      }
      choice choice-12 {
        leaf target-routing-instance {
          type string;
        }
        list target-logical-system {
          key "name";
          ordered-by user;
          leaf name {
            type string;
          }
          uses apply-group;
          uses apply-macro;
          leaf target-routing-instance {
            type string;
          }
        }
      }
      leaf strip-domain {
        type empty;
      }
      leaf tunnel-profile {
        type string;
      }
    }
    container delimiter {
      leaf characters {
        type string;
      }
    }
    container parse-direction {
      choice choice-3 {
        leaf left-to-right {
          type empty;
        }
        leaf right-to-left {
          type empty;
        }
      }
    }
  }

  grouping pcrf-definition {
    uses apply-advanced;
    list partition {
      key "name";
      ordered-by user;
      leaf name {
        type string;
      }
      uses apply-advanced;
      container undocumented {
        leaf report-ex-rule-name {
          type empty;
        }
      }
      leaf accept-sdr {
        type empty;
      }
      leaf destination-realm {
        type string;
      }
      leaf destination-host {
        type string;
      }
      leaf diameter-instance {
        type string;
      }
      leaf draining {
        type empty;
      }
      leaf draining-response-timeout {
        units "seconds";
        type string;
      }
      leaf ip-can-type {
        type string;
      }
      container local-decision {
        uses apply-advanced;
        choice permission {
          case case_1 {
            leaf grant {
              type empty;
            }
          }
          case case_2 {
            leaf deny {
              type empty;
            }
          }
        }
        leaf reinit-on-failure {
          type empty;
        }
        leaf reinit-on-rar {
          type empty;
        }
        leaf reinit-timeout {
          units "seconds";
          type string;
        }
        leaf timeout {
          units "seconds";
          type string;
        }
      }
      leaf logout-response-timeout {
        units "seconds";
        type string;
      }
      leaf max-outstanding-requests {
        type string;
      }
      leaf report-local-rule {
        type empty;
      }
      leaf report-resource-allocation {
        type empty;
      }
      leaf report-successful-resource-allocation {
        type empty;
      }
      leaf send-dyn-subscription-indicator {
        type empty;
      }
      leaf send-network-family-indicator {
        type empty;
      }
      leaf send-origin-state-id {
        type empty;
      }
      leaf subscription-id-type {
        type string;
      }
      container subscription-id-data-include {
        uses apply-advanced;
        leaf delimiter {
          type string;
        }
        leaf domain-name {
          type string;
        }
        leaf interface-name {
          type empty;
        }
        leaf vlan-tags {
          type empty;
        }
        leaf base-interface-name {
          type empty;
        }
        leaf mac-address {
          type empty;
        }
        leaf nas-port-id {
          type empty;
        }
        leaf origin-host {
          type empty;
        }
        leaf origin-realm {
          type empty;
        }
        leaf user-prefix {
          type string;
        }
        leaf user-name {
          type empty;
        }
      }
      leaf use-session-stamp {
        type empty;
      }
      leaf update-response-timeout {
        units "seconds";
        type string;
      }
    }
    container global {
      uses apply-advanced;
      list rule-param {
        key "name";
        ordered-by user;
        leaf name {
          type string;
        }
        uses apply-advanced;
        leaf param-name {
          type string;
        }
        leaf log-name {
          type string;
        }
      }
    }
  }

  grouping group-profile-object {
    leaf name {
      type key-attribute-string-type;
    }
    uses apply-group;
    uses apply-macro;
    container ppp {
      presence "enable ppp";
      uses apply-group;
      uses apply-macro;
      leaf framed-pool {
        type string;
      }
      leaf idle-timeout {
        type uint32;
      }
      leaf keepalive {
        type uint16;
      }
      leaf primary-dns {
        type string;
      }
      leaf secondary-dns {
        type string;
      }
      leaf primary-wins {
        type string;
      }
      leaf secondary-wins {
        type string;
      }
      leaf encapsulation-overhead {
        type int8;
      }
      leaf cell-overhead {
        type empty;
      }
      leaf interface-id {
        type string;
      }
      container ppp-options {
        presence "enable ppp-options";
        uses apply-group;
        uses apply-macro;
        leaf pap {
          type empty;
        }
        leaf chap {
          type empty;
        }
        leaf mru {
          type uint32;
        }
        leaf mtu {
          type string;
        }
        container initiate-ncp {
          uses apply-group;
          uses apply-macro;
          leaf ip {
            type empty;
          }
          leaf ipv6 {
            type empty;
          }
          leaf dual-stack-passive {
            type empty;
          }
        }
        leaf peer-ip-address-optional {
          type empty;
        }
        leaf ipcp-suggest-dns-option {
          type empty;
        }
        leaf aaa-options {
          type string;
        }
      }
    }
    container l2tp {
      presence "";
      uses apply-group;
      uses apply-macro;
      leaf maximum-sessions-per-tunnel {
        type uint16;
      }
      leaf interface-id {
        type string;
      }
      leaf lcp-renegotiation {
        type empty;
      }
      leaf local-chap {
        type empty;
      }
      container multilink {
        presence "enable multilink";
        uses multilink-object;
      }
    }
  }

  grouping juniper-bridge-domains {
    leaf name {
      type string;
    }
    uses apply-group;
    uses apply-macro;
    leaf description {
      type string;
    }
    leaf domain-type {
      type string;
    }
    choice choice-7 {
      leaf vlan-id {
        type string;
      }
      container vlan-tags {
        presence "";
        leaf outer {
          type string;
        }
        leaf inner {
          type string;
        }
      }
      leaf-list vlan-id-list {
        type string;
      }
    }
    leaf service-id {
      type uint32;
    }
    leaf no-local-switching {
      type empty;
    }
    leaf mcae-mac-synchronize {
      type empty;
    }
    leaf mcae-mac-flush {
      type empty;
    }
    leaf no-irb-layer-2-copy {
      type empty;
    }
    leaf enable-mac-move-action {
      type empty;
    }
    list interface {
      key "name";
      ordered-by user;
      leaf name {
        type string;
      }
      uses apply-group;
      uses apply-macro;
    }
    leaf routing-interface {
      type interface-unit;
    }
    container forwarding-options {
      uses juniper-bridge-forwarding-options;
    }
    container multicast-snooping-options {
      uses juniper-multicast-snooping-options;
    }
    container bridge-options {
      uses juniper-protocols-bd;
    }
    container protocols {
      presence "enable protocols";
      uses apply-group;
      uses apply-macro;
      container igmp-snooping {
        presence "enable igmp-snooping";
        uses juniper-protocols-igmp-snooping;
      }
      container mld-snooping {
        presence "enable mld-snooping";
        uses juniper-bd-protocols-mld-snooping;
      }
    }
    container vxlan {
      presence "";
      uses apply-group;
      uses apply-macro;
      leaf ovsdb-managed {
        type empty;
      }
      leaf vni {
        type string;
      }
      leaf multicast-group {
        type ipv4addr;
      }
      leaf encapsulate-inner-vlan {
        type empty;
      }
      leaf decapsulate-accept-inner-vlan {
        type empty;
      }
      leaf unreachable-vtep-aging-timer {
        units "seconds";
        type string;
      }
      leaf destination-udp-port {
        type string;
      }
      leaf ingress-node-replication {
        type empty;
      }
    }
    container proxy-mac {
      uses apply-advanced;
      leaf irb {
        type empty;
      }
      leaf proxy-mac-address {
        type mac-unicast;
      }
    }
  }

  grouping juniper-bd-protocols-mld-snooping {
    uses apply-advanced;
    container traceoptions {
      uses apply-advanced;
      container file {
        leaf filename {
          type string;
        }
        leaf replace {
          status deprecated;
          type empty;
        }
        leaf size {
          type string;
        }
        leaf files {
          type string;
        }
        leaf no-stamp {
          status deprecated;
          type empty;
        }
        choice world-readable-choice {
          leaf world-readable {
            type empty;
          }
          leaf no-world-readable {
            type empty;
          }
        }
      }
      list flag {
        key "name";
        ordered-by user;
        leaf name {
          type string;
        }
        leaf send {
          type empty;
        }
        leaf receive {
          type empty;
        }
        leaf detail {
          type empty;
        }
        leaf disable {
          type empty;
        }
      }
    }
    leaf query-interval {
      units "seconds";
      type string;
    }
    container l2-querier {
      uses apply-advanced;
      leaf source-address {
        type ipv6addr;
      }
    }
    leaf query-response-interval {
      units "seconds";
      type string;
    }
    leaf query-last-member-interval {
      units "seconds";
      type string;
    }
    leaf robust-count {
      type string;
    }
    leaf immediate-leave {
      type empty;
    }
    leaf evpn-ssm-reports-only {
      type empty;
    }
    container proxy {
      uses apply-advanced;
      leaf source-address {
        type ipv6addr;
      }
      leaf irb {
        type empty;
      }
    }
    list interface {
      key "name";
      ordered-by user;
      leaf name {
        type string;
      }
      uses apply-advanced;
      leaf multicast-router-interface {
        type empty;
      }
      leaf immediate-leave {
        type empty;
      }
      leaf host-only-interface {
        type empty;
      }
      leaf group-limit {
        type string;
      }
      container static {
        uses apply-advanced;
        list group {
          key "name";
          ordered-by user;
          leaf name {
            type ipv6addr;
          }
          uses apply-advanced;
          list source {
            key "name";
            ordered-by user;
            leaf name {
              type ipv6addr;
            }
            uses apply-advanced;
          }
        }
      }
    }
    list pseudowire-remote-address {
      key "name";
      ordered-by user;
      leaf name {
        type ipv4addr;
      }
      uses apply-advanced;
      leaf multicast-router-interface {
        type empty;
      }
      leaf immediate-leave {
        type empty;
      }
    }
    list vlan {
      key "name";
      ordered-by user;
      leaf name {
        type string;
      }
      uses apply-advanced;
      leaf query-interval {
        units "seconds";
        type string;
      }
      leaf query-response-interval {
        units "seconds";
        type string;
      }
      leaf query-last-member-interval {
        units "seconds";
        type string;
      }
      leaf robust-count {
        type string;
      }
      leaf immediate-leave {
        type empty;
      }
      container proxy {
        uses apply-advanced;
        leaf source-address {
          type ipv6addr;
        }
      }
      leaf evpn-ssm-reports-only {
        type empty;
      }
      list interface {
        key "name";
        ordered-by user;
        leaf name {
          type string;
        }
        uses apply-advanced;
        leaf multicast-router-interface {
          type empty;
        }
        leaf immediate-leave {
          type empty;
        }
        leaf host-only-interface {
          type empty;
        }
        leaf group-limit {
          type string;
        }
        container static {
          uses apply-advanced;
          list group {
            key "name";
            ordered-by user;
            leaf name {
              type ipv6addr;
            }
            uses apply-advanced;
            list source {
              key "name";
              ordered-by user;
              leaf name {
                type ipv6addr;
              }
              uses apply-advanced;
            }
          }
        }
      }
      list pseudowire-remote-address {
        key "name";
        ordered-by user;
        leaf name {
          type ipv4addr;
        }
        uses apply-advanced;
        leaf multicast-router-interface {
          type empty;
        }
        leaf immediate-leave {
          type empty;
        }
      }
      list qualified-vlan {
        key "name";
        ordered-by user;
        leaf name {
          type string;
        }
        uses apply-advanced;
        leaf query-interval {
          units "seconds";
          type string;
        }
        leaf query-response-interval {
          units "seconds";
          type string;
        }
        leaf query-last-member-interval {
          units "seconds";
          type string;
        }
        leaf robust-count {
          type string;
        }
        leaf immediate-leave {
          type empty;
        }
        container proxy {
          uses apply-advanced;
          leaf source-address {
            type ipv6addr;
          }
        }
        leaf evpn-ssm-reports-only {
          type empty;
        }
        list interface {
          key "name";
          ordered-by user;
          leaf name {
            type string;
          }
          uses apply-advanced;
          leaf multicast-router-interface {
            type empty;
          }
          leaf immediate-leave {
            type empty;
          }
          leaf host-only-interface {
            type empty;
          }
          leaf group-limit {
            type string;
          }
          container static {
            uses apply-advanced;
            list group {
              key "name";
              ordered-by user;
              leaf name {
                type ipv6addr;
              }
              uses apply-advanced;
              list source {
                key "name";
                ordered-by user;
                leaf name {
                  type ipv6addr;
                }
                uses apply-advanced;
              }
            }
          }
        }
        list pseudowire-remote-address {
          key "name";
          ordered-by user;
          leaf name {
            type ipv4addr;
          }
          uses apply-advanced;
          leaf multicast-router-interface {
            type empty;
          }
          leaf immediate-leave {
            type empty;
          }
        }
      }
    }
  }

  grouping juniper-bridge-forwarding-options {
    uses apply-group;
    uses apply-macro;
    container filter {
      uses apply-group;
      uses apply-macro;
      leaf input {
        type string;
      }
    }
    container flood {
      uses apply-group;
      uses apply-macro;
      leaf input {
        type string;
      }
    }
    container dhcp-relay {
      uses jdhcp-relay-type;
    }
  }

  grouping jdhcp-relay-type {
    uses apply-group;
    uses apply-macro;
    container traceoptions {
      uses jdhcp-traceoptions-type;
    }
    container persistent-storage {
      leaf automatic {
        type empty;
      }
    }
    leaf duplicate-clients-on-interface {
      type empty;
    }
    container duplicate-clients-in-subnet {
      uses jdhcp-duplicate-clients-in-subnet-type;
    }
    container interface-traceoptions {
      uses jdhcp-interface-traceoptions-type;
    }
    container dhcpv6 {
      uses dhcpv6-relay-type;
    }
    leaf arp-inspection {
      type empty;
    }
    container forward-snooped-clients {
      choice choice-configured-interfaces {
        leaf configured-interfaces {
          type empty;
        }
        leaf non-configured-interfaces {
          type empty;
        }
        leaf all-interfaces {
          type empty;
        }
      }
    }
    container authentication {
      uses authentication-type;
    }
    container liveness-detection {
      presence "";
      uses dhcp-liveness-detection-type;
    }
    container dynamic-profile {
      presence "";
      uses dynamic-profile-type;
    }
    leaf service-profile {
      type string;
    }
    leaf access-profile {
      type string;
    }
    container short-cycle-protection {
      leaf lockout-min-time {
        type uint32;
      }
      leaf lockout-max-time {
        type uint32;
      }
    }
    container overrides {
      presence "enable overrides";
      uses override-type;
    }
    container relay-option {
      presence "enable relay-option";
      uses dhcp-generic-v4-option;
    }
    container server-match {
      uses apply-group;
      uses apply-macro;
      container default-action {
        presence "enable default-action";
        uses server-match-action-choice;
      }
      list address {
        key "name";
        ordered-by user;
        leaf name {
          type ipv4prefix;
        }
        uses apply-group;
        uses apply-macro;
        choice choice-forward-only {
          leaf forward-only {
            type empty;
          }
          leaf create-relay-entry {
            type empty;
          }
        }
      }
    }
    container relay-option-60 {
      presence "enable relay-option-60";
      uses relay-option-60-type-top;
    }
    container relay-option-82 {
      presence "enable relay-option-82";
      uses relay-option-82-type;
    }
    container forward-only {
      presence "enable forward-only";
      uses forward-only-to-rc-type;
    }
    leaf description {
      type string;
    }
    leaf maximum-hop-count {
      type uint32;
    }
    leaf minimum-wait-time {
      type uint32;
    }
    leaf client-response-ttl {
      type uint32;
    }
    leaf source-ip-change {
      type empty;
    }
    leaf forward-only-replies {
      type empty;
    }
    container server-group {
      uses server-group-type;
    }
    container active-server-group {
      uses dhcpv4-gbl-active-sg-type;
    }
    container route-suppression {
      uses dhcp-route-suppression-type;
    }
    list group {
      key "name";
      ordered-by user;
      uses dhcp-group;
    }
    list dual-stack-group {
      key "name";
      uses dhcp-dual-stack-group;
    }
    leaf no-snoop {
      type empty;
    }
    leaf server-response-time {
      type uint32;
    }
    container lease-time-validation {
      presence "enable lease-time-validation";
      uses apply-group;
      uses apply-macro;
      leaf lease-time-threshold {
        units "seconds";
        type uint32;
      }
      container violation-action {
        leaf drop {
          type empty;
        }
      }
    }
    container leasequery {
      presence "enable leasequery";
      uses relay-leasequery-type;
    }
    container bulk-leasequery {
      presence "enable bulk-leasequery";
      uses relay-bulk-leasequery-v4-type;
    }
    container remote-id-mismatch {
      presence "";
      uses dhcp-remote-id-mismatch-type;
    }
  }

  grouping authentication-type {
    uses apply-group;
    uses apply-macro;
    leaf password {
      type string;
    }
    container username-include {
      uses apply-group;
      uses apply-macro;
      leaf delimiter {
        type string;
      }
      leaf domain-name {
        type string;
      }
      leaf user-prefix {
        type string;
      }
      leaf mac-address {
        type empty;
      }
      container option-82 {
        presence "enable option-82";
        leaf circuit-id {
          type empty;
        }
        leaf remote-id {
          type empty;
        }
      }
      leaf logical-system-name {
        type empty;
      }
      leaf routing-instance-name {
        type empty;
      }
      leaf option-60 {
        type empty;
      }
      leaf circuit-type {
        type empty;
      }
      leaf interface-name {
        type empty;
      }
      leaf interface-description {
        type string;
      }
    }
  }

  grouping dhcp-dual-stack-group {
    leaf name {
      type key-attribute-string-type;
    }
    uses apply-group;
    uses apply-macro;
    container authentication {
      uses dual-stack-authentication-type;
    }
    leaf service-profile {
      type string;
    }
    leaf access-profile {
      type string;
    }
    container dynamic-profile {
      presence "";
      uses dynamic-profile-type;
    }
    container liveness-detection {
      presence "";
      uses dhcp-liveness-detection-dualstack-type;
    }
    container relay-agent-interface-id {
      presence "enable relay-agent-interface-id";
      uses v6-relay-option-interface-id-type;
    }
    container relay-agent-remote-id {
      presence "enable relay-agent-remote-id";
      uses v6-relay-option-remote-id-type;
    }
    container classification-key {
      uses classification-types;
    }
    leaf dual-stack-interface-client-limit {
      type uint32;
    }
    container protocol-master {
      uses jdhcp-dual-stack-protocol-mstr-type;
    }
    container short-cycle-protection {
      leaf lockout-min-time {
        type uint32;
      }
      leaf lockout-max-time {
        type uint32;
      }
    }
    container undocumented {
      container renegotiation-master {
        leaf inet {
          type empty;
        }
      }
    }
  }

  grouping classification-types {
    uses apply-group;
    uses apply-macro;
    leaf mac-address {
      type empty;
    }
    leaf circuit-id {
      type empty;
    }
    leaf remote-id {
      type empty;
    }
  }

  grouping dhcp-generic-v4-option {
    uses apply-group;
    uses apply-macro;
    leaf option-number {
      type string;
    }
    container equals {
      uses relay-v4-option-ascii-hex;
    }
    container default-action {
      uses dhcp-v4-option-default-action;
    }
    container starts-with {
      uses relay-v4-option-ascii-hex;
    }
    container option-60 {
      presence "enable option-60";
      uses dhcp-generic-v4-option-type;
    }
    container option-77 {
      presence "enable option-77";
      uses dhcp-generic-v4-option-type;
    }
    list option-order {
      key "name";
      ordered-by user;
      leaf name {
        type string;
      }
      uses apply-group;
      uses apply-macro;
    }
  }

  grouping dhcp-generic-v4-option-type {
    uses apply-group;
    uses apply-macro;
    container equals {
      uses relay-v4-option-ascii-hex;
    }
    container default-action {
      uses dhcp-v4-option-default-action;
    }
    container starts-with {
      uses relay-v4-option-ascii-hex;
    }
  }

  grouping dhcp-group {
    leaf name {
      type key-attribute-string-type;
    }
    uses apply-group;
    uses apply-macro;
    leaf active-server-group {
      type string;
    }
    container authentication {
      uses authentication-type;
    }
    container dynamic-profile {
      presence "";
      uses dynamic-profile-type;
    }
    container overrides {
      presence "enable overrides";
      uses override-type;
      container undocumented {
        leaf renegotiation-lockout {
          type string;
        }
      }
    }
    container relay-option-60 {
      presence "enable relay-option-60";
      uses relay-option-60-type-group;
    }
    container relay-option-82 {
      presence "enable relay-option-82";
      uses relay-option-82-type;
    }
    container forward-only {
      presence "enable forward-only";
      uses forward-only-to-rc-type;
    }
    container route-suppression {
      uses dhcp-route-suppression-type;
    }
    leaf description {
      type string;
    }
    leaf maximum-hop-count {
      type uint32;
    }
    leaf minimum-wait-time {
      type uint32;
    }
    leaf client-response-ttl {
      type uint32;
    }
    leaf source-ip-change {
      type empty;
    }
    list interface {
      key "name";
      leaf name {
        type interface-name;
      }
      uses apply-group;
      uses apply-macro;
      leaf upto {
        type interface-name;
      }
      leaf exclude {
        type empty;
      }
      leaf trace {
        type empty;
      }
      container overrides {
        uses override-type;
      }
    }
  }

  grouping dhcp-liveness-detection-dualstack-type {
    uses apply-group;
    uses apply-macro;
    container failure-action {
      uses dhcp-liveness-detection-failure-action-type;
    }
    container method {
      uses apply-group;
      uses apply-macro;
      container layer2-liveness-detection {
        uses dhcp-arp-nud-liveness-detection-type;
      }
    }
  }

  grouping dhcpv4-gp-active-sg-type {
    uses apply-group;
    uses apply-macro;
    leaf active-server-group {
      type string;
    }
    leaf allow-server-change {
      type empty;
    }
  }

  grouping dhcpv6-relay-type {
    uses apply-group;
    uses apply-macro;
    container authentication {
      uses dhcpv6-authentication-type;
    }
    container persistent-storage {
      leaf automatic {
        type empty;
      }
    }
    container liveness-detection {
      presence "";
      uses dhcpv6-liveness-detection-type;
    }
    container dynamic-profile {
      presence "";
      uses dynamic-profile-type;
    }
    leaf service-profile {
      type string;
    }
    leaf access-profile {
      type string;
    }
    container short-cycle-protection {
      leaf lockout-min-time {
        type string;
      }
      leaf lockout-max-time {
        type string;
      }
    }
    container overrides {
      presence "enable overrides";
      uses dhcpv6-override-relay-type;
    }
    container relay-option {
      presence "enable relay-option";
      uses dhcp-generic-v6-option;
    }
    leaf exclude-relay-agent-identifier {
      type empty;
    }
    container server-match {
      uses apply-advanced;
      container default-action {
        uses server-match-action-choice;
      }
      container duid {
        uses apply-advanced;
        container equals {
          uses server-match-v6-ascii-hex;
        }
        container starts-with {
          uses server-match-v6-ascii-hex;
        }
      }
      list address {
        key "name";
        ordered-by user;
        leaf name {
          type ipv6prefix;
        }
        uses apply-advanced;
        choice server-match-action-choice {
          case case_1 {
            leaf forward-only {
              type empty;
            }
          }
          case case_2 {
            leaf create-relay-entry {
              type empty;
            }
          }
        }
      }
    }
    leaf relay-agent-option-79 {
      type empty;
    }
    container vendor-specific-information {
      uses jdhcp-vendor-specific-type;
    }
    container forward-only {
      presence "enable forward-only";
      uses forward-only-to-rc-type;
    }
    leaf forward-only-replies {
      type empty;
    }
    container forward-snooped-clients {
      choice interface-type {
        case case_1 {
          leaf configured-interfaces {
            type empty;
          }
        }
        case case_2 {
          leaf non-configured-interfaces {
            type empty;
          }
        }
        case case_3 {
          leaf all-interfaces {
            type empty;
          }
        }
      }
    }
    container route-suppression {
      uses dhcpv6-route-suppression-type;
    }
    list group {
      key "name";
      ordered-by user;
      uses dhcpv6-relay-group;
    }
    container relay-agent-interface-id {
      presence "enable relay-agent-interface-id";
      uses v6-relay-option-interface-id-type;
    }
    container relay-agent-remote-id {
      presence "enable relay-agent-remote-id";
      uses v6-relay-option-remote-id-type;
    }
    container server-group {
      uses v6-server-group-type;
    }
    leaf active-server-group {
      type string;
    }
    leaf server-response-time {
      type string;
    }
    container lease-time-validation {
      presence "enable lease-time-validation";
      uses apply-group;
      uses apply-macro;
      leaf lease-time-threshold {
        units "seconds";
        type uint32;
      }
      container violation-action {
        leaf drop {
          type empty;
        }
      }
    }
    leaf no-snoop {
      type empty;
    }
    container leasequery {
      presence "enable leasequery";
      uses relay-leasequery-type;
    }
    container bulk-leasequery {
      presence "enable bulk-leasequery";
      uses relay-bulk-leasequery-v6-type;
    }
    container active-leasequery {
      presence "enable active-leasequery";
      uses relay-active-leasequery-v6-type;
    }
    container remote-id-mismatch {
      presence "enable remote-id-mismatch";
      uses dhcp-remote-id-mismatch-type;
    }
    container duplicate-clients {
      uses dhcpv6-duplicate-clients-type;
    }
  }

  grouping dhcp-generic-v6-option {
    uses apply-group;
    uses apply-macro;
    leaf option-number {
      type string;
    }
    container equals {
      uses relay-v6-option-ascii-hex;
    }
    container default-action {
      uses dhcp-v6-option-default-action;
    }
    container starts-with {
      uses relay-v6-option-ascii-hex;
    }
    container option-15 {
      presence "enable option-15";
      uses dhcp-generic-v6-option-type;
    }
    container option-16 {
      presence "enable option-16";
      uses dhcp-generic-v6-option-type;
    }
    list option-order {
      key "name";
      ordered-by user;
      leaf name {
        type string;
      }
      uses apply-group;
      uses apply-macro;
    }
  }

  grouping dhcp-generic-v6-option-type {
    uses apply-group;
    uses apply-macro;
    container equals {
      uses relay-v6-option-ascii-hex;
    }
    container default-action {
      uses dhcp-v6-option-default-action;
    }
    container starts-with {
      uses relay-v6-option-ascii-hex;
    }
  }

  grouping dhcp-v6-option-default-action {
    uses apply-group;
    uses apply-macro;
    choice choice-relay-server-group {
      leaf relay-server-group {
        type string;
      }
      leaf drop {
        type empty;
      }
      leaf forward-only {
        type empty;
      }
    }
  }

  grouping dhcpv6-authentication-type {
    uses apply-group;
    uses apply-macro;
    leaf password {
      type string;
    }
    container username-include {
      uses apply-group;
      uses apply-macro;
      leaf delimiter {
        type string;
      }
      leaf domain-name {
        type string;
      }
      leaf user-prefix {
        type string;
      }
      leaf mac-address {
        type empty;
      }
      leaf client-id {
        type empty;
      }
      container relay-agent-remote-id {
        presence "enable relay-agent-remote-id";
        uses apply-group;
        uses apply-macro;
        choice choice-enterprise-id {
          leaf enterprise-id {
            type empty;
          }
          leaf remote-id {
            type empty;
          }
        }
      }
      leaf logical-system-name {
        type empty;
      }
      leaf routing-instance-name {
        type empty;
      }
      leaf relay-agent-subscriber-id {
        type empty;
      }
      leaf relay-agent-interface-id {
        type empty;
      }
      leaf circuit-type {
        type empty;
      }
      leaf interface-name {
        type empty;
      }
      leaf interface-description {
        type string;
      }
    }
  }

  grouping dhcpv6-duplicate-clients-type {
    choice distinguish-with {
      case case_1 {
        leaf incoming-interface {
          type empty;
        }
      }
    }
  }

  grouping dhcpv6-gbl-active-sg-type {
    uses apply-group;
    uses apply-macro;
    leaf active-server-group {
      type string;
    }
  }

  grouping dhcpv6-liveness-detection-type {
    uses apply-group;
    uses apply-macro;
    container failure-action {
      uses dhcp-liveness-detection-failure-action-type;
    }
    container method {
      uses apply-group;
      uses apply-macro;
      container bfd {
        uses dhcp-bfd-liveness-detection-type;
      }
    }
  }

  grouping dhcpv6-override-relay-type {
    uses apply-group;
    uses apply-macro;
    leaf allow-snooped-clients {
      type empty;
    }
    leaf no-allow-snooped-clients {
      type empty;
    }
    leaf delay-authentication {
      type empty;
    }
    leaf interface-client-limit {
      type uint32;
    }
    leaf dual-stack {
      type string;
    }
    leaf no-bind-on-request {
      type empty;
    }
    container client-negotiation-match {
      leaf incoming-interface {
        type empty;
      }
    }
    leaf send-release-on-delete {
      type empty;
    }
    leaf always-process-option-request-option {
      type empty;
    }
    leaf relay-source {
      type interface-name;
    }
    leaf delete-binding-on-renegotiation {
      type empty;
    }
    leaf asymmetric-lease-time {
      units "seconds";
      type uint32;
    }
    leaf asymmetric-prefix-lease-time {
      units "seconds";
      type uint32;
    }
  }

  grouping dhcpv6-relay-group {
    leaf name {
      type key-attribute-string-type;
    }
    uses apply-group;
    uses apply-macro;
    leaf active-server-group {
      type string;
    }
    list dual-stack-group {
      key "name";
      uses dhcp-dual-stack-group;
    }
    container authentication {
      uses dhcpv6-authentication-type;
    }
    container liveness-detection {
      presence "";
      uses dhcpv6-liveness-detection-type;
    }
    container dynamic-profile {
      presence "";
      uses dynamic-profile-type;
    }
    leaf service-profile {
      type string;
    }
    leaf access-profile {
      type string;
    }
    container short-cycle-protection {
      leaf lockout-min-time {
        type uint32;
      }
      leaf lockout-max-time {
        type uint32;
      }
    }
    container overrides {
      presence "enable overrides";
      uses dhcpv6-override-relay-type;
      container undocumented {
        leaf renegotiation-lockout {
          type string;
        }
      }
    }
    container relay-option {
      presence "enable relay-option";
      uses dhcp-generic-v6-option;
    }
    container vendor-specific-information {
      uses jdhcp-vendor-specific-type;
    }
    container forward-only {
      presence "enable forward-only";
      uses forward-only-to-rc-type;
    }
    container relay-agent-interface-id {
      presence "enable relay-agent-interface-id";
      uses v6-relay-option-interface-id-type;
    }
    container relay-agent-remote-id {
      presence "enable relay-agent-remote-id";
      uses v6-relay-option-remote-id-type;
    }
    container route-suppression {
      uses dhcpv6-route-suppression-type;
    }
    leaf relay-agent-option-79 {
      type empty;
    }
    list interface {
      key "name";
      leaf name {
        type interface-name;
      }
      uses apply-group;
      uses apply-macro;
      leaf upto {
        type interface-name;
      }
      leaf exclude {
        type empty;
      }
      leaf trace {
        type empty;
      }
      container overrides {
        uses dhcpv6-override-relay-type;
      }
      container dynamic-profile {
        presence "";
        uses dynamic-profile-type;
      }
      leaf service-profile {
        type string;
      }
      leaf access-profile {
        type string;
      }
      container short-cycle-protection {
        leaf lockout-min-time {
          type uint32;
        }
        leaf lockout-max-time {
          type uint32;
        }
      }
    }
    container lease-time-validation {
      presence "enable lease-time-validation";
      uses apply-group;
      uses apply-macro;
      leaf lease-time-threshold {
        units "seconds";
        type uint32;
      }
      container violation-action {
        leaf drop {
          type empty;
        }
      }
    }
    container remote-id-mismatch {
      presence "";
      uses dhcp-remote-id-mismatch-type;
    }
    container server-match {
      uses apply-group;
      uses apply-macro;
      container default-action {
        uses server-match-action-choice;
      }
      container duid {
        uses apply-group;
        uses apply-macro;
        container equals {
          uses server-match-v6-ascii-hex;
        }
        container starts-with {
          uses server-match-v6-ascii-hex;
        }
      }
      list address {
        key "name";
        ordered-by user;
        leaf name {
          type ipv6prefix;
        }
        uses apply-group;
        uses apply-macro;
        choice choice-forward-only {
          leaf forward-only {
            type empty;
          }
          leaf create-relay-entry {
            type empty;
          }
        }
      }
    }
  }

  grouping dhcpv6-gp-active-sg-type {
    uses apply-group;
    uses apply-macro;
    leaf active-server-group {
      type string;
    }
  }

  grouping dhcpv6-route-suppression-type {
    uses apply-group;
    uses apply-macro;
    leaf access {
      type empty;
    }
    leaf access-internal {
      type empty;
    }
  }

  grouping dual-stack-authentication-type {
    uses apply-group;
    uses apply-macro;
    leaf password {
      type string;
    }
    container username-include {
      uses apply-group;
      uses apply-macro;
      leaf delimiter {
        type string;
      }
      leaf domain-name {
        type string;
      }
      leaf user-prefix {
        type string;
      }
      leaf mac-address {
        type empty;
      }
      leaf relay-agent-remote-id {
        type empty;
      }
      leaf logical-system-name {
        type empty;
      }
      leaf routing-instance-name {
        type empty;
      }
      leaf relay-agent-interface-id {
        type empty;
      }
      leaf interface-name {
        type empty;
      }
      leaf interface-description {
        type string;
      }
      leaf circuit-type {
        type empty;
      }
      leaf vlan-tags {
        type empty;
      }
    }
  }

  grouping dynamic-profile-type {
    uses apply-group;
    uses apply-macro;
    leaf dynamic-profile {
      type string;
    }
    choice choice-5 {
      leaf use-primary {
        type string;
      }
      container aggregate-clients {
        presence "enable aggregate-clients";
        uses apply-group;
        uses apply-macro;
        choice choice-3 {
          leaf merge {
            type empty;
          }
          leaf replace {
            type empty;
          }
        }
      }
    }
  }

  grouping forward-only-to-rc-type {
    uses apply-group;
    uses apply-macro;
    leaf logical-system {
      type string;
    }
    leaf routing-instance {
      type string;
    }
  }

  grouping jdhcp-dual-stack-protocol-mstr-type {
    uses apply-group;
    uses apply-macro;
    choice choice-inet {
      leaf inet {
        type empty;
      }
      leaf inet6 {
        type empty;
      }
    }
  }

  grouping jdhcp-duplicate-clients-in-subnet-type {
    uses apply-group;
    uses apply-macro;
    choice choice-incoming-interface {
      leaf incoming-interface {
        type empty;
      }
      leaf option-82 {
        type empty;
      }
    }
  }

  grouping jdhcp-interface-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    list flag {
      key "name";
      ordered-by user;
      leaf name {
        type string;
      }
    }
  }

  grouping jdhcp-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    list flag {
      key "name";
      ordered-by user;
      leaf name {
        type string;
      }
    }
  }

  grouping dynamic-profile-option-object {
    uses apply-group;
    uses apply-macro;
    container apply-advanced {
      uses apply-group;
      uses apply-macro;
    }
    leaf versioning {
      mandatory true;
      type empty;
    }
  }

  grouping jdhcp-interface-traceoptions-level-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping jdhcp-traceoptions-level-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping jdhcp-vendor-specific-type {
    uses apply-group;
    uses apply-macro;
    leaf host-name {
      type empty;
    }
    leaf location {
      type empty;
    }
  }

  grouping juniper-cdr-profiles {
    leaf name {
      type key-attribute-string-type;
    }
    uses apply-group;
    uses apply-macro;
    leaf description {
      type string;
    }
    leaf enable-reduced-partial-cdrs {
      type empty;
    }
    leaf report-requested-apn {
      type empty;
    }
    container exclude-attributes {
      uses apply-group;
      uses apply-macro;
      leaf apn-ni {
        type empty;
      }
      leaf apn-selection-mode {
        type empty;
      }
      leaf cc-selection-mode {
        type empty;
      }
      leaf dynamic-address {
        type empty;
      }
      leaf pgw-plmn-identifier {
        type empty;
      }
      leaf list-of-traffic-volumes {
        type empty;
      }
      leaf list-of-service-data {
        type empty;
      }
      leaf lrsn {
        type empty;
      }
      leaf ms-time-zone {
        type empty;
      }
      leaf network-initiation {
        type empty;
      }
      leaf node-id {
        type empty;
      }
      leaf pdn-connection-id {
        type empty;
      }
      leaf pdppdn-type {
        type empty;
      }
      leaf rat-type {
        type empty;
      }
      leaf record-sequence-number {
        type empty;
      }
      leaf served-imeisv {
        type empty;
      }
      leaf served-msisdn {
        type empty;
      }
      leaf served-pdppdn-address {
        type empty;
      }
      leaf serving-node-plmn-identifier {
        type empty;
      }
      leaf start-time {
        type empty;
      }
      leaf stop-time {
        type empty;
      }
      leaf user-location-information {
        type empty;
      }
      leaf sgw-change {
        type empty;
      }
      leaf pgw-address-used {
        type empty;
      }
      leaf ps-furnish-info {
        type empty;
      }
      leaf served-pdp-address-extension {
        type empty;
      }
    }
    leaf node-id {
      type string;
    }
  }

  grouping juniper-charged-configuraton {
    uses apply-group;
    uses apply-macro;
    container file-age {
      presence "enable file-age";
      leaf age {
        units "minutes";
        type uint16;
      }
      leaf disable {
        type empty;
      }
    }
    container file-size {
      presence "enable file-size";
      leaf size {
        units "megabytes";
        type uint32;
      }
      leaf disable {
        type empty;
      }
    }
    leaf cdrs-per-file {
      type uint32;
    }
    leaf user-name {
      type string;
    }
    leaf disable-replication {
      type empty;
    }
    leaf world-readable {
      type empty;
    }
    leaf file-format {
      type string;
    }
    leaf file-name-private-extension {
      type string;
    }
    leaf file-creation-policy {
      type string;
    }
    container disk-space-policy {
      presence "enable disk-space-policy";
      uses apply-group;
      uses apply-macro;
      container water-mark-level1 {
        presence "enable water-mark-level1";
        uses apply-group;
        uses apply-macro;
        leaf percentage {
          type uint8;
        }
        leaf notification-level {
          type string;
        }
      }
      container water-mark-level2 {
        presence "enable water-mark-level2";
        uses apply-group;
        uses apply-macro;
        leaf percentage {
          type uint8;
        }
        leaf notification-level {
          type string;
        }
      }
      container water-mark-level3 {
        presence "enable water-mark-level3";
        uses apply-group;
        uses apply-macro;
        leaf percentage {
          type uint8;
        }
        leaf notification-level {
          type string;
        }
      }
    }
    container traceoptions {
      uses charged-traceoptions-type;
    }
  }

  grouping charged-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping juniper-charging-profiles {
    leaf name {
      type key-attribute-string-type;
    }
    uses apply-group;
    uses apply-macro;
    leaf description {
      type string;
    }
    leaf profile-id {
      type uint16;
    }
    leaf default-service-id {
      type uint32;
    }
    leaf default-rating-group {
      type uint32;
    }
    container transport-profile {
      uses apply-group;
      uses apply-macro;
      leaf transport-profile-name {
        type string;
      }
    }
    container cdr-profile {
      uses apply-group;
      uses apply-macro;
      leaf cdr-profile-name {
        type string;
      }
    }
    container diameter-avp-profile {
      uses apply-group;
      uses apply-macro;
      leaf diameter-avp-profile-name {
        type string;
      }
    }
    list trigger-profile {
      key "name";
      leaf name {
        type key-attribute-string-type;
      }
      uses apply-group;
      uses apply-macro;
      leaf-list rating-group {
        ordered-by user;
        type uint32;
      }
    }
    leaf service-mode {
      type string;
    }
  }

  grouping juniper-class-of-service-options {
    uses apply-group;
    uses apply-macro;
    container undocumented {
      leaf copy-plp {
        type empty;
      }
      leaf rate-limit-burst {
        type uint32;
      }
    }
    container forwarding-policy {
      uses apply-group;
      uses apply-macro;
      list next-hop-map {
        key "name";
        ordered-by user;
        leaf name {
          type string;
        }
        uses apply-group;
        uses apply-macro;
        list forwarding-class {
          key "name";
          ordered-by user;
          leaf name {
            type string;
          }
          uses apply-group;
          uses apply-macro;
          leaf-list next-hop {
            type ipaddr-or-interface;
            ordered-by user;
          }
          leaf-list lsp-next-hop {
            type string;
            ordered-by user;
          }
          leaf non-lsp-next-hop {
            type empty;
          }
          leaf-list static-lsp-next-hop {
            type string;
            ordered-by user;
          }
          leaf discard {
            type empty;
          }
        }
        container forwarding-class-default {
          uses apply-group;
          uses apply-macro;
          leaf-list next-hop {
            type ipaddr-or-interface;
            ordered-by user;
          }
          leaf-list lsp-next-hop {
            type string;
            ordered-by user;
          }
          leaf non-lsp-next-hop {
            type empty;
          }
          leaf discard {
            type empty;
          }
        }
      }
      list class {
        key "name";
        ordered-by user;
        leaf name {
          type string;
        }
        uses apply-group;
        uses apply-macro;
        container classification-override {
          uses apply-group;
          uses apply-macro;
          leaf forwarding-class {
            type string;
          }
        }
      }
    }
    container classifiers {
      uses apply-group;
      uses apply-macro;
      list dscp {
        key "name";
        ordered-by user;
        leaf name {
          type string;
        }
        uses apply-group;
        uses apply-macro;
        leaf import {
          type string;
        }
        list forwarding-class {
          key "name";
          ordered-by user;
          leaf name {
            type string;
          }
          uses apply-group;
          uses apply-macro;
          list loss-priority {
            key "name";
            ordered-by user;
            leaf name {
              type string;
            }
            leaf-list code-points {
              type string;
              ordered-by user;
            }
          }
        }
      }
      list dscp-ipv6 {
        key "name";
        ordered-by user;
        leaf name {
          type string;
        }
        uses apply-group;
        uses apply-macro;
        leaf import {
          type string;
        }
        list forwarding-class {
          key "name";
          ordered-by user;
          leaf name {
            type string;
          }
          uses apply-group;
          uses apply-macro;
          list loss-priority {
            key "name";
            ordered-by user;
            leaf name {
              type string;
            }
            leaf-list code-points {
              type string;
              ordered-by user;
            }
          }
        }
      }
      list exp {
        key "name";
        ordered-by user;
        leaf name {
          type string;
        }
        uses apply-group;
        uses apply-macro;
        leaf import {
          type string;
        }
        list forwarding-class {
          key "name";
          ordered-by user;
          leaf name {
            type string;
          }
          uses apply-group;
          uses apply-macro;
          list loss-priority {
            key "name";
            ordered-by user;
            leaf name {
              type string;
            }
            leaf-list code-points {
              type string;
              ordered-by user;
            }
          }
        }
      }
      list ieee-802.1 {
        key "name";
        ordered-by user;
        leaf name {
          type string;
        }
        uses apply-group;
        uses apply-macro;
        leaf import {
          type string;
        }
        list forwarding-class {
          key "name";
          ordered-by user;
          leaf name {
            type string;
          }
          uses apply-group;
          uses apply-macro;
          list loss-priority {
            key "name";
            ordered-by user;
            leaf name {
              type string;
            }
            leaf-list code-points {
              type string;
              ordered-by user;
            }
          }
        }
      }
      list inet-precedence {
        key "name";
        ordered-by user;
        leaf name {
          type string;
        }
        uses apply-group;
        uses apply-macro;
        leaf import {
          type string;
        }
        list forwarding-class {
          key "name";
          ordered-by user;
          leaf name {
            type string;
          }
          uses apply-group;
          uses apply-macro;
          list loss-priority {
            key "name";
            ordered-by user;
            leaf name {
              type string;
            }
            leaf-list code-points {
              type string;
              ordered-by user;
            }
          }
        }
      }
      list ieee-802.1ad {
        key "name";
        ordered-by user;
        leaf name {
          type string;
        }
        uses apply-group;
        uses apply-macro;
        leaf import {
          type string;
        }
        list forwarding-class {
          key "name";
          ordered-by user;
          leaf name {
            type string;
          }
          uses apply-group;
          uses apply-macro;
          list loss-priority {
            key "name";
            ordered-by user;
            leaf name {
              type string;
            }
            leaf-list code-points {
              type string;
              ordered-by user;
            }
          }
        }
      }
    }
    container traffic-class-map {
      uses apply-group;
      uses apply-macro;
      list inet-precedence {
        key "name";
        ordered-by user;
        leaf name {
          type key-attribute-string-type;
        }
        uses apply-group;
        uses apply-macro;
        list traffic-class {
          key "name";
          ordered-by user;
          leaf name {
            mandatory true;
            type string;
          }
          leaf-list code-points {
            type string;
            ordered-by user;
          }
        }
      }
      list dscp {
        key "name";
        ordered-by user;
        leaf name {
          type key-attribute-string-type;
        }
        uses apply-group;
        uses apply-macro;
        list traffic-class {
          key "name";
          ordered-by user;
          leaf name {
            mandatory true;
            type string;
          }
          leaf-list code-points {
            type string;
            ordered-by user;
          }
        }
      }
      list exp {
        key "name";
        ordered-by user;
        leaf name {
          type key-attribute-string-type;
        }
        uses apply-group;
        uses apply-macro;
        list traffic-class {
          key "name";
          ordered-by user;
          leaf name {
            mandatory true;
            type string;
          }
          leaf-list code-points {
            type string;
            ordered-by user;
          }
        }
      }
      list ieee-802.1 {
        key "name";
        ordered-by user;
        leaf name {
          type key-attribute-string-type;
        }
        uses apply-group;
        uses apply-macro;
        list traffic-class {
          key "name";
          ordered-by user;
          leaf name {
            mandatory true;
            type string;
          }
          leaf-list code-points {
            type string;
            ordered-by user;
          }
        }
      }
      list ieee-802.1ad {
        key "name";
        ordered-by user;
        leaf name {
          type key-attribute-string-type;
        }
        uses apply-group;
        uses apply-macro;
        list traffic-class {
          key "name";
          ordered-by user;
          leaf name {
            mandatory true;
            type string;
          }
          leaf-list code-points {
            type string;
            ordered-by user;
          }
        }
      }
    }
    list policy-map {
      key "name";
      ordered-by user;
      leaf name {
        type key-attribute-string-type;
      }
      uses apply-group;
      uses apply-macro;
      list inet-precedence {
        key "name";
        ordered-by user;
        leaf name {
          mandatory true;
          type string;
        }
        leaf code-point {
          type string;
          mandatory true;
        }
      }
      list dscp {
        key "name";
        ordered-by user;
        leaf name {
          mandatory true;
          type string;
        }
        leaf code-point {
          type string;
          mandatory true;
        }
      }
      list dscp-ipv6 {
        key "name";
        ordered-by user;
        leaf name {
          mandatory true;
          type string;
        }
        leaf code-point {
          type string;
          mandatory true;
        }
      }
      list exp {
        key "name";
        ordered-by user;
        leaf name {
          mandatory true;
          type string;
        }
        leaf code-point {
          type string;
          mandatory true;
        }
      }
      list ieee-802.1 {
        key "name";
        ordered-by user;
        leaf name {
          mandatory true;
          type string;
        }
        leaf code-point {
          type string;
          mandatory true;
        }
      }
      list ieee-802.1ad {
        key "name";
        ordered-by user;
        leaf name {
          mandatory true;
          type string;
        }
        leaf code-point {
          type string;
          mandatory true;
        }
      }
    }
    list forwarding-class-map {
      key "name";
      ordered-by user;
      leaf name {
        type key-attribute-string-type;
      }
      uses apply-group;
      uses apply-macro;
      list class {
        key "name";
        ordered-by user;
        leaf name {
          type key-attribute-string-type;
        }
        leaf queue-num {
          type uint32;
        }
        leaf restricted-queue {
          type uint32;
        }
      }
    }
    container loss-priority-maps {
      uses apply-group;
      uses apply-macro;
      list frame-relay-de {
        key "name";
        ordered-by user;
        leaf name {
          type string;
        }
        uses apply-group;
        uses apply-macro;
        list loss-priority {
          key "name";
          ordered-by user;
          leaf name {
            type string;
          }
          leaf-list code-points {
            type string;
            ordered-by user;
          }
        }
      }
    }
    container loss-priority-rewrites {
      uses apply-group;
      uses apply-macro;
      list frame-relay-de {
        key "name";
        ordered-by user;
        leaf name {
          type key-attribute-string-type;
        }
        uses apply-group;
        uses apply-macro;
        list loss-priority {
          key "name";
          ordered-by user;
          leaf name {
            type string;
          }
          leaf code-point {
            type string;
          }
        }
      }
    }
    container code-point-aliases {
      uses apply-group;
      uses apply-macro;
      list dscp {
        key "name";
        ordered-by user;
        leaf name {
          type string;
        }
        leaf bits {
          type string;
        }
      }
      list dscp-ipv6 {
        key "name";
        ordered-by user;
        leaf name {
          type string;
        }
        leaf bits {
          type string;
        }
      }
      list exp {
        key "name";
        ordered-by user;
        leaf name {
          type string;
        }
        leaf bits {
          type string;
        }
      }
      list ieee-802.1 {
        key "name";
        ordered-by user;
        leaf name {
          type string;
        }
        leaf bits {
          type string;
        }
      }
      list inet-precedence {
        key "name";
        ordered-by user;
        leaf name {
          type string;
        }
        leaf bits {
          type string;
        }
      }
      list ieee-802.1ad {
        key "name";
        ordered-by user;
        leaf name {
          type string;
        }
        leaf bits {
          type string;
        }
      }
      list inet6-precedence {
        key "name";
        ordered-by user;
        leaf name {
          type string;
        }
        leaf bits {
          type string;
          mandatory true;
        }
      }
    }
    container translation-table {
      uses apply-group;
      uses apply-macro;
      list to-802.1p-from-dscp {
        key "name";
        ordered-by user;
        leaf name {
          type string;
        }
        uses apply-group;
        uses apply-macro;
        list to-code-point {
          key "name";
          ordered-by user;
          leaf name {
            type string;
          }
          leaf-list from-code-points {
            type string;
            ordered-by user;
          }
        }
      }
      list to-inet-precedence-from-inet-precedence {
        key "name";
        ordered-by user;
        leaf name {
          type string;
        }
        uses apply-group;
        uses apply-macro;
        list to-code-point {
          key "name";
          ordered-by user;
          leaf name {
            type string;
          }
          leaf-list from-code-points {
            type string;
            ordered-by user;
          }
        }
      }
      list to-dscp-from-dscp {
        key "name";
        ordered-by user;
        leaf name {
          type string;
        }
        uses apply-group;
        uses apply-macro;
        list to-code-point {
          key "name";
          ordered-by user;
          leaf name {
            type string;
          }
          leaf-list from-code-points {
            type string;
            ordered-by user;
          }
        }
      }
      list to-dscp-ipv6-from-dscp-ipv6 {
        key "name";
        ordered-by user;
        leaf name {
          type string;
        }
        uses apply-group;
        uses apply-macro;
        list to-code-point {
          key "name";
          ordered-by user;
          leaf name {
            type string;
          }
          leaf-list from-code-points {
            type string;
            ordered-by user;
          }
        }
      }
      list to-exp-from-exp {
        key "name";
        ordered-by user;
        leaf name {
          type string;
        }
        uses apply-group;
        uses apply-macro;
        list to-code-point {
          key "name";
          ordered-by user;
          leaf name {
            type string;
          }
          leaf-list from-code-points {
            type string;
            ordered-by user;
          }
        }
      }
    }
    container host-outbound-traffic {
      uses apply-group;
      uses apply-macro;
      leaf forwarding-class {
        type string;
      }
      leaf dscp-code-point {
        type string;
      }
      leaf override-firewall {
        type empty;
      }
      container translation-table {
        presence "";
        leaf to-802.1p-from-dscp {
          type string;
        }
      }
      container tcp {
        presence "enable tcp";
        uses apply-group;
        uses apply-macro;
        leaf raise-internet-control-priority {
          type empty;
        }
      }
      container ieee-802.1 {
        presence "enable ieee-802.1";
        uses apply-group;
        uses apply-macro;
        leaf rewrite-rules {
          type empty;
        }
        leaf default {
          type string;
        }
      }
      container protocol {
        uses apply-group;
        uses apply-macro;
        container isis-over-gre {
          uses apply-group;
          uses apply-macro;
          leaf dscp-code-point {
            type string;
          }
        }
      }
    }
    list drop-profiles {
      key "name";
      ordered-by user;
      leaf name {
        type string;
      }
      uses apply-group;
      uses apply-macro;
      list fill-level {
        key "name";
        ordered-by user;
        leaf name {
          type string;
        }
        leaf drop-probability {
          type uint32;
        }
      }
      container interpolate {
        presence "";
        uses apply-group;
        uses apply-macro;
        leaf-list fill-level {
          ordered-by user;
          type uint32;
        }
        leaf-list drop-probability {
          ordered-by user;
          type uint32;
        }
      }
    }
    list adaptive-shapers {
      key "name";
      ordered-by user;
      leaf name {
        type string;
      }
      uses apply-group;
      uses apply-macro;
      list trigger {
        key "name";
        ordered-by user;
        leaf name {
          type string;
        }
        container shaping-rate {
          choice choice-3 {
            leaf absolute-rate {
              type string;
            }
            leaf percent {
              type uint32;
            }
          }
        }
      }
    }
    list virtual-channels {
      key "name";
      ordered-by user;
      leaf name {
        type string;
      }
      uses apply-group;
      uses apply-macro;
    }
    list virtual-channel-groups {
      key "name";
      ordered-by user;
      leaf name {
        type string;
      }
      uses apply-group;
      uses apply-macro;
      list channel {
        key "name";
        ordered-by user;
        leaf name {
          type string;
        }
        uses apply-group;
        uses apply-macro;
        leaf scheduler-map {
          type string;
        }
        container shaping-rate {
          choice choice-3 {
            leaf absolute-rate {
              type string;
            }
            leaf percent {
              type uint32;
            }
          }
        }
        leaf default {
          type empty;
        }
      }
    }
    leaf copy-plp-all {
      type empty;
    }
    leaf tri-color {
      type empty;
    }
    container shared-buffer {
      uses apply-group;
      uses apply-macro;
      leaf percent {
        type uint32;
      }
      container ingress {
        uses apply-group;
        uses apply-macro;
        leaf percent {
          type string;
        }
        list buffer-partition {
          key "name";
          ordered-by user;
          leaf name {
            type string;
          }
          uses apply-group;
          uses apply-macro;
          leaf percent {
            type string;
          }
          leaf dynamic-threshold {
            type string;
          }
        }
      }
      container egress {
        uses apply-group;
        uses apply-macro;
        leaf percent {
          type string;
        }
        list buffer-partition {
          key "name";
          ordered-by user;
          leaf name {
            type string;
          }
          uses apply-group;
          uses apply-macro;
          leaf percent {
            type string;
          }
          leaf dynamic-threshold {
            type string;
          }
        }
      }
      list node-group {
        key "name";
        leaf name {
          type key-attribute-string-type;
        }
        uses apply-group;
        uses apply-macro;
        container ingress {
          uses apply-group;
          uses apply-macro;
          leaf percent {
            type uint32;
          }
          list buffer-partition {
            key "name";
            ordered-by user;
            leaf name {
              type string;
            }
            uses apply-group;
            uses apply-macro;
            leaf percent {
              type uint32;
            }
          }
        }
        container egress {
          uses apply-group;
          uses apply-macro;
          leaf percent {
            type uint32;
          }
          list buffer-partition {
            key "name";
            ordered-by user;
            leaf name {
              type string;
            }
            uses apply-group;
            uses apply-macro;
            leaf percent {
              type uint32;
            }
          }
        }
      }
    }
    container forwarding-classes {
      uses apply-group;
      uses apply-macro;
      list class {
        key "name";
        ordered-by user;
        leaf name {
          type string;
        }
        leaf queue-num {
          type uint32;
        }
        leaf priority {
          type string;
        }
        leaf policing-priority {
          type string;
        }
        leaf no-loss {
          type empty;
        }
        leaf spu-priority {
          type string;
        }
      }
      list queue {
        key "name";
        ordered-by user;
        leaf name {
          type string;
        }
        leaf class-name {
          type string;
        }
        leaf priority {
          type string;
        }
        leaf policing-priority {
          type string;
        }
      }
    }
    container restricted-queues {
      uses apply-group;
      uses apply-macro;
      list forwarding-class {
        key "name";
        ordered-by user;
        leaf name {
          type string;
        }
        leaf rqueue-num {
          type uint32;
        }
      }
    }
    list traffic-control-profiles {
      key "name";
      ordered-by user;
      leaf name {
        type key-attribute-string-type;
      }
      uses apply-group;
      uses apply-macro;
      leaf scheduler-map {
        type string;
      }
      leaf strict-priority-scheduler {
        type empty;
      }
      leaf atm-service {
        type string;
      }
      leaf peak-rate {
        type string;
        units "cps";
      }
      leaf sustained-rate {
        type string;
        units "cps";
      }
      leaf max-burst-size {
        units "cells";
        type uint64;
      }
      container shaping-rate {
        choice choice-3 {
          leaf rate {
            type string;
          }
          leaf percent {
            type uint32;
          }
        }
        leaf burst-size {
          type string;
        }
      }
      container overhead-accounting {
        leaf mode {
          type string;
        }
        leaf bytes {
          type string;
        }
        leaf frame-mode-bytes {
          type int32;
        }
        leaf cell-mode-bytes {
          type int32;
        }
      }
      container shaping-rate-priority-strict-high {
        leaf rate {
          type string;
          units "bits per second";
        }
        leaf burst-size {
          type string;
          units "bytes";
        }
      }
      container shaping-rate-priority-high {
        leaf rate {
          type string;
        }
        leaf burst-size {
          type string;
        }
      }
      container shaping-rate-priority-medium {
        leaf rate {
          type string;
        }
        leaf burst-size {
          type string;
        }
      }
      container shaping-rate-priority-medium-low {
        leaf rate {
          type string;
          units "bits per second";
        }
        leaf burst-size {
          type string;
          units "bytes";
        }
      }
      container shaping-rate-priority-low {
        leaf rate {
          type string;
        }
        leaf burst-size {
          type string;
        }
      }
      container shaping-rate-excess-high {
        leaf rate {
          type string;
        }
        leaf burst-size {
          type string;
        }
      }
      container shaping-rate-excess-low {
        leaf rate {
          type string;
        }
        leaf burst-size {
          type string;
        }
      }
      container shaping-rate-excess-medium-high {
        leaf rate {
          type string;
          units "bits per second";
        }
        leaf burst-size {
          type string;
          units "bytes";
        }
      }
      container shaping-rate-excess-medium-low {
        leaf rate {
          type string;
          units "bits per second";
        }
        leaf burst-size {
          type string;
          units "bytes";
        }
      }
      container guaranteed-rate {
        choice choice-3 {
          leaf rate {
            type string;
          }
          leaf percent {
            type uint32;
          }
        }
        leaf burst-size {
          type string;
        }
      }
      container excess-rate {
        choice choice-3 {
          leaf proportion {
            type string;
          }
          leaf percent {
            type uint32;
          }
        }
      }
      container excess-rate-high {
        choice choice-proportion {
          leaf proportion {
            type uint32;
          }
          leaf percent {
            type uint32;
          }
        }
      }
      container excess-rate-medium-high {
        choice choice-proportion {
          leaf proportion {
            type uint32;
          }
          leaf percent {
            type uint32;
          }
        }
      }
      container excess-rate-low {
        choice choice-proportion {
          leaf proportion {
            type uint32;
          }
          leaf percent {
            type uint32;
          }
        }
      }
      container excess-rate-medium-low {
        choice choice-proportion {
          leaf proportion {
            type uint32;
          }
          leaf percent {
            type uint32;
          }
        }
      }
      choice choice-23 {
        container delay-buffer-rate {
          choice choice-3 {
            leaf rate {
              type string;
            }
            leaf percent {
              type uint32;
            }
            leaf cps {
              type string;
              units "cells per second";
            }
          }
        }
      }
      container adjust-minimum {
        leaf rate {
          type string;
          units "bits per second";
        }
      }
      container undocumented {
        container huge-buffer-temporal {
          leaf temporal {
            type string;
          }
        }
      }
    }
    list forwarding-class-sets {
      key "name";
      ordered-by user;
      leaf name {
        type string;
      }
      uses apply-group;
      uses apply-macro;
      list class {
        key "name";
        ordered-by user;
        leaf name {
          type string;
        }
        uses apply-group;
        uses apply-macro;
      }
    }
    list congestion-notification-profile {
      key "name";
      ordered-by user;
      leaf name {
        type string;
      }
      uses apply-group;
      uses apply-macro;
      container input {
        presence "";
        uses apply-group;
        uses apply-macro;
        leaf cable-length {
          type string;
          units "metre";
        }
        container ieee-802.1 {
          uses apply-group;
          uses apply-macro;
          list code-point {
            key "name";
            ordered-by user;
            leaf name {
              type string;
            }
            uses apply-group;
            uses apply-macro;
            leaf pfc {
              type empty;
            }
            leaf mru {
              type string;
              units "bytes";
            }
            choice choice-5 {
              leaf qfc {
                type empty;
              }
              container qcn {
                presence "enable qcn";
                uses apply-group;
                uses apply-macro;
                container defense-mode-edge {
                  presence "";
                  uses apply-group;
                  uses apply-macro;
                  container alternate-priority {
                    presence "";
                    uses apply-group;
                    uses apply-macro;
                    leaf bits {
                      type string;
                    }
                  }
                }
              }
            }
          }
        }
        container dscp {
          uses apply-group;
          uses apply-macro;
          list code-point {
            key "name";
            ordered-by user;
            leaf name {
              mandatory true;
              type string;
            }
            uses apply-group;
            uses apply-macro;
            leaf pfc {
              type empty;
            }
            leaf mru {
              type string;
              units "bytes";
            }
          }
        }
      }
      container output {
        uses apply-group;
        uses apply-macro;
        list class {
          key "name";
          ordered-by user;
          leaf name {
            type string;
          }
          uses apply-group;
          uses apply-macro;
          leaf remove-cntag {
            type empty;
          }
          leaf qcn {
            type empty;
          }
        }
        container ieee-802.1 {
          uses apply-group;
          uses apply-macro;
          list code-point {
            key "name";
            ordered-by user;
            leaf name {
              type string;
            }
            uses apply-group;
            uses apply-macro;
            leaf-list flow-control-queue {
              ordered-by user;
              type uint32;
            }
          }
        }
      }
    }
    list scheduler-map-forwarding-class-sets {
      key "name";
      ordered-by user;
      leaf name {
        type key-attribute-string-type;
      }
      uses apply-group;
      uses apply-macro;
      list forwarding-class-set {
        key "name";
        ordered-by user;
        leaf name {
          type key-attribute-string-type;
        }
        leaf scheduler {
          type string;
        }
      }
    }
    container system-defaults {
      uses apply-group;
      uses apply-macro;
      container classifiers {
        uses apply-group;
        uses apply-macro;
        container exp {
          leaf classifier-name {
            type string;
          }
        }
      }
    }
    container dynamic-class-of-service-options {
      uses apply-group;
      uses apply-macro;
      list vendor-specific-tags {
        key "name";
        ordered-by user;
        leaf name {
          type string;
        }
        uses apply-group;
        uses apply-macro;
      }
    }
    container interfaces {
      uses apply-group;
      uses apply-macro;
      list interface-set {
        key "name";
        ordered-by user;
        leaf name {
          type string;
        }
        uses apply-group;
        uses apply-macro;
        leaf internal-node {
          type empty;
        }
        container input-excess-bandwidth-share {
          choice choice-3 {
            leaf proportional {
              type string;
            }
            leaf equal {
              type empty;
            }
          }
        }
        container excess-bandwidth-share {
          choice choice-3 {
            leaf proportional {
              type string;
            }
            leaf equal {
              type empty;
            }
          }
        }
        container input-traffic-control-profile {
          leaf profile-name {
            type string;
          }
        }
        container input-traffic-control-profile-remaining {
          leaf profile-name {
            type string;
          }
        }
        container output-traffic-control-profile {
          leaf profile-name {
            type string;
          }
        }
        container output-traffic-control-profile-remaining {
          leaf profile-name {
            type string;
          }
        }
      }
      list interface {
        key "name";
        uses cos-interfaces-type;
      }
    }
    list routing-instances {
      key "name";
      ordered-by user;
      leaf name {
        type string;
      }
      uses apply-group;
      uses apply-macro;
      container classifiers {
        uses apply-group;
        uses apply-macro;
        leaf no-default {
          type empty;
        }
        container exp {
          leaf classifier-name {
            type string;
          }
        }
        container ieee-802.1 {
          presence "";
          leaf classifier-name {
            type string;
          }
          leaf encapsulated {
            type empty;
          }
          leaf vlan-tag {
            type string;
          }
        }
        container dscp {
          leaf classifier-name {
            type string;
          }
        }
        container dscp-ipv6 {
          leaf classifier-name {
            type string;
          }
        }
      }
      container rewrite-rules {
        uses apply-group;
        uses apply-macro;
        choice choice-3 {
          container ieee-802.1 {
            presence "";
            leaf rewrite-rule-name {
              type string;
            }
            leaf encapsulated {
              type empty;
            }
            leaf vlan-tag {
              type string;
            }
          }
          container ieee-802.1ad {
            presence "";
            leaf rewrite-rule-name {
              type string;
            }
            leaf encapsulated {
              type empty;
            }
            leaf vlan-tag {
              type string;
            }
          }
        }
      }
      container policy-map {
        leaf policy-map-name {
          type string;
        }
      }
    }
    container rewrite-rules {
      uses apply-group;
      uses apply-macro;
      list dscp {
        key "name";
        ordered-by user;
        leaf name {
          type string;
        }
        uses apply-group;
        uses apply-macro;
        leaf import {
          type string;
        }
        list forwarding-class {
          key "name";
          ordered-by user;
          leaf name {
            type string;
          }
          uses apply-group;
          uses apply-macro;
          list loss-priority {
            key "name";
            ordered-by user;
            leaf name {
              type string;
            }
            leaf code-point {
              type string;
            }
          }
        }
      }
      list dscp-ipv6 {
        key "name";
        ordered-by user;
        leaf name {
          type string;
        }
        uses apply-group;
        uses apply-macro;
        leaf import {
          type string;
        }
        list forwarding-class {
          key "name";
          ordered-by user;
          leaf name {
            type string;
          }
          uses apply-group;
          uses apply-macro;
          list loss-priority {
            key "name";
            ordered-by user;
            leaf name {
              type string;
            }
            leaf code-point {
              type string;
            }
          }
        }
      }
      list exp {
        key "name";
        ordered-by user;
        leaf name {
          type string;
        }
        uses apply-group;
        uses apply-macro;
        leaf import {
          type string;
        }
        list forwarding-class {
          key "name";
          ordered-by user;
          leaf name {
            type string;
          }
          uses apply-group;
          uses apply-macro;
          list loss-priority {
            key "name";
            ordered-by user;
            leaf name {
              type string;
            }
            leaf code-point {
              type string;
            }
          }
        }
      }
      list ieee-802.1 {
        key "name";
        ordered-by user;
        leaf name {
          type string;
        }
        uses apply-group;
        uses apply-macro;
        leaf import {
          type string;
        }
        list forwarding-class {
          key "name";
          ordered-by user;
          leaf name {
            type string;
          }
          uses apply-group;
          uses apply-macro;
          list loss-priority {
            key "name";
            ordered-by user;
            leaf name {
              type string;
            }
            leaf code-point {
              type string;
            }
          }
        }
      }
      list inet-precedence {
        key "name";
        ordered-by user;
        leaf name {
          type string;
        }
        uses apply-group;
        uses apply-macro;
        leaf import {
          type string;
        }
        list forwarding-class {
          key "name";
          ordered-by user;
          leaf name {
            type string;
          }
          uses apply-group;
          uses apply-macro;
          list loss-priority {
            key "name";
            ordered-by user;
            leaf name {
              type string;
            }
            leaf code-point {
              type string;
            }
          }
        }
      }
      list frame-relay-de {
        key "name";
        ordered-by user;
        leaf name {
          type string;
        }
        uses apply-group;
        uses apply-macro;
        leaf import {
          type string;
        }
        list forwarding-class {
          key "name";
          ordered-by user;
          leaf name {
            type string;
          }
          uses apply-group;
          uses apply-macro;
          list loss-priority {
            key "name";
            ordered-by user;
            leaf name {
              type string;
            }
            leaf code-point {
              type string;
            }
          }
        }
      }
      list ieee-802.1ad {
        key "name";
        ordered-by user;
        leaf name {
          type string;
        }
        uses apply-group;
        uses apply-macro;
        leaf import {
          type string;
        }
        list forwarding-class {
          key "name";
          ordered-by user;
          leaf name {
            type string;
          }
          uses apply-group;
          uses apply-macro;
          list loss-priority {
            key "name";
            ordered-by user;
            leaf name {
              type string;
            }
            leaf code-point {
              type string;
            }
          }
        }
      }
    }
    container fabric {
      uses apply-group;
      uses apply-macro;
      container scheduler-map {
        uses apply-group;
        uses apply-macro;
        list priority {
          key "name";
          ordered-by user;
          leaf name {
            type string;
          }
          leaf scheduler {
            type string;
          }
        }
      }
    }
    list scheduler-maps {
      key "name";
      ordered-by user;
      leaf name {
        type key-attribute-string-type;
      }
      uses apply-group;
      uses apply-macro;
      list forwarding-class {
        key "name";
        ordered-by user;
        leaf name {
          type key-attribute-string-type;
        }
        leaf scheduler {
          type string;
        }
      }
    }
    list fragmentation-maps {
      key "name";
      ordered-by user;
      leaf name {
        type string;
      }
      uses apply-group;
      uses apply-macro;
      list forwarding-class {
        key "name";
        ordered-by user;
        leaf name {
          type string;
        }
        uses apply-group;
        uses apply-macro;
        choice choice-3 {
          leaf fragment-threshold {
            type uint16;
          }
          leaf no-fragmentation {
            type empty;
          }
        }
        leaf multilink-class {
          type uint16;
        }
        leaf drop-timeout {
          type uint16;
        }
      }
    }
    list schedulers {
      key "name";
      ordered-by user;
      leaf name {
        type key-attribute-string-type;
      }
      uses apply-group;
      uses apply-macro;
      container transmit-rate {
        choice choice-3 {
          leaf rate {
            type string;
          }
          leaf percent {
            type string;
          }
          container remainder {
            presence "enable remainder";
            uses apply-group;
            uses apply-macro;
            leaf percent {
              type uint32;
            }
          }
        }
        choice choice-4 {
          leaf exact {
            type empty;
          }
          leaf rate-limit {
            type empty;
          }
        }
      }
      container excess-rate {
        choice choice-3 {
          leaf percent {
            type uint32;
          }
          leaf proportion {
            type uint32;
          }
        }
      }
      container shaping-rate {
        choice choice-3 {
          leaf rate {
            type string;
          }
          leaf percent {
            type uint32;
          }
        }
        leaf burst-size {
          type string;
          units "bytes";
        }
      }
      container buffer-size {
        choice choice-3 {
          leaf percent {
            type uint32;
          }
          container remainder {
            presence "enable remainder";
            uses apply-group;
            uses apply-macro;
            leaf percent {
              type uint32;
            }
          }
          leaf temporal {
            type string;
          }
        }
        choice choice-4 {
          leaf exact {
            type empty;
          }
        }
      }
      container shared-buffer {
        uses apply-group;
        uses apply-macro;
        container maximum {
          presence "enable maximum";
          uses apply-group;
          uses apply-macro;
          leaf percent {
            type uint32;
          }
          container multicast {
            presence "enable multicast";
            uses apply-group;
            uses apply-macro;
            leaf percent {
              type uint32;
            }
          }
        }
      }
      leaf priority {
        type string;
      }
      leaf excess-priority {
        type string;
      }
      list drop-profile-map {
        key "loss-priority protocol";
        ordered-by user;
        leaf loss-priority {
          type string;
        }
        leaf protocol {
          type string;
        }
        leaf drop-profile {
          type string;
        }
      }
      leaf explicit-congestion-notification {
        type empty;
      }
      container drop-profile-map-set {
        presence "";
        uses apply-group;
        uses apply-macro;
        leaf profile-name {
          type string;
        }
        leaf profile-type {
          type string;
        }
      }
      leaf adjust-percent {
        units "percent";
        type uint32;
      }
      leaf adjust-minimum {
        type string;
        units "bits per second";
      }
    }
    list adjustment-control-profiles {
      key "name";
      leaf name {
        type key-attribute-string-type;
      }
      uses apply-group;
      uses apply-macro;
      list application {
        key "name";
        ordered-by user;
        leaf name {
          type string;
        }
        leaf priority {
          type uint32;
        }
        leaf algorithm {
          type string;
        }
      }
    }
    container traceoptions {
      uses apply-group;
      uses apply-macro;
      leaf no-remote-trace {
        type empty;
      }
      container file {
        leaf filename {
          type string;
        }
        leaf size {
          type string;
        }
        leaf files {
          type uint32;
        }
        leaf world-readable {
          type empty;
        }
        leaf no-world-readable {
          type empty;
        }
        leaf match {
          type regular-expression;
        }
      }
      list flag {
        key "name";
        ordered-by user;
        leaf name {
          type string;
        }
      }
    }
    container multi-destination {
      uses apply-group;
      uses apply-macro;
      leaf scheduler-map {
        type string;
      }
      container family {
        uses apply-group;
        uses apply-macro;
        container ethernet {
          uses apply-group;
          uses apply-macro;
          leaf broadcast {
            type string;
          }
        }
        container inet {
          uses apply-group;
          uses apply-macro;
          container classifier {
            uses apply-group;
            uses apply-macro;
            container dscp {
              leaf classifier-name {
                type string;
              }
            }
            container inet-precedence {
              leaf classifier-name {
                type string;
              }
            }
          }
        }
        container inet6 {
          uses apply-group;
          uses apply-macro;
          container classifier {
            uses apply-group;
            uses apply-macro;
            container dscp-ipv6 {
              leaf classifier-name {
                type string;
              }
            }
          }
        }
      }
      container classifiers {
        uses apply-group;
        uses apply-macro;
        container ieee-802.1 {
          leaf classifier-name {
            type string;
          }
        }
        container dscp {
          leaf classifier-name {
            type string;
          }
        }
      }
    }
    container application-traffic-control {
      presence "enable application-traffic-control";
      uses apply-group;
      uses apply-macro;
      container traceoptions {
        uses appqos-traceoptions-type;
      }
      list rate-limiters {
        key "name";
        ordered-by user;
        leaf name {
          type key-attribute-string-type;
        }
        uses apply-group;
        uses apply-macro;
        leaf bandwidth-limit {
          units "kbps";
          type uint32;
        }
        leaf burst-size-limit {
          units "bytes";
          type uint32;
        }
      }
      list rule-sets {
        key "name";
        ordered-by user;
        leaf name {
          type key-attribute-string-type;
        }
        uses apply-group;
        uses apply-macro;
        list rule {
          key "name";
          ordered-by user;
          uses appqos-rule-type;
        }
      }
    }
  }

  grouping appqos-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    list flag {
      key "name";
      ordered-by user;
      leaf name {
        type string;
      }
    }
    leaf level {
      type string;
    }
  }

  grouping appqos-rule-type {
    leaf name {
      type key-attribute-string-type;
    }
    uses apply-group;
    uses apply-macro;
    container match {
      uses apply-group;
      uses apply-macro;
      leaf application-any {
        type empty;
      }
      leaf application-unknown {
        type empty;
      }
      leaf application-known {
        type empty;
      }
      leaf-list application {
        type string;
        ordered-by user;
      }
      leaf-list application-group {
        type string;
        ordered-by user;
      }
    }
    container then {
      uses apply-group;
      uses apply-macro;
      leaf forwarding-class {
        type string;
      }
      leaf dscp-code-point {
        type string;
      }
      leaf loss-priority {
        type string;
      }
      container rate-limit {
        uses apply-group;
        uses apply-macro;
        leaf client-to-server {
          type string;
        }
        leaf server-to-client {
          type string;
        }
      }
      leaf log {
        type empty;
      }
    }
  }

  grouping cos-interfaces-type {
    leaf name {
      type interface-device-wildcard;
    }
    uses apply-group;
    uses apply-macro;
    list forwarding-class-set {
      key "name";
      ordered-by user;
      leaf name {
        type string;
      }
      uses apply-group;
      uses apply-macro;
      container output-traffic-control-profile {
        leaf profile-name {
          type string;
        }
      }
    }
    leaf congestion-notification-profile {
      type string;
    }
    leaf scheduler-map-forwarding-class-set {
      type string;
    }
    leaf scheduler-map {
      type string;
    }
    leaf input-scheduler-map {
      type string;
    }
    leaf scheduler-map-chassis {
      type string;
    }
    leaf output-forwarding-class-map {
      type string;
    }
    leaf logical-interface-aggregate-statistics {
      type empty;
    }
    container shaping-rate {
      leaf rate {
        type string;
      }
    }
    container input-excess-bandwidth-share {
      choice choice-3 {
        leaf proportional {
          type string;
        }
        leaf equal {
          type empty;
        }
      }
    }
    container excess-bandwidth-share {
      choice choice-3 {
        leaf proportional {
          type string;
        }
        leaf equal {
          type empty;
        }
      }
    }
    container input-shaping-rate {
      presence "";
      leaf rate {
        type string;
      }
    }
    container input-traffic-control-profile {
      presence "";
      leaf profile-name {
        type string;
      }
    }
    container input-traffic-control-profile-remaining {
      presence "";
      leaf profile-name {
        type string;
      }
    }
    container output-traffic-control-profile {
      presence "";
      leaf profile-name {
        type string;
      }
    }
    container output-traffic-control-profile-remaining {
      presence "";
      leaf profile-name {
        type string;
      }
    }
    container member-link-scheduler {
      choice choice-3 {
        leaf scale {
          type empty;
        }
        leaf replicate {
          type empty;
        }
      }
    }
    list unit {
      key "name";
      leaf name {
        type string;
      }
      uses apply-group;
      uses apply-macro;
      leaf output-forwarding-class-map {
        type string;
      }
      leaf forwarding-class {
        type string;
      }
      leaf virtual-channel-group {
        type string;
      }
      leaf vc-shared-scheduler {
        type empty;
      }
      leaf scheduler-map {
        type string;
      }
      leaf input-scheduler-map {
        type string;
      }
      leaf fragmentation-map {
        type string;
      }
      leaf adaptive-shaper {
        type string;
      }
      container shaping-rate {
        presence "enable shaping-rate";
        choice choice-3 {
          leaf rate {
            type string;
          }
          leaf percent {
            type uint32;
          }
        }
      }
      container input-shaping-rate {
        choice choice-3 {
          leaf rate {
            type string;
          }
          leaf percent {
            type uint32;
          }
        }
      }
      container input-traffic-control-profile {
        presence "";
        leaf profile-name {
          type string;
        }
        leaf shared-instance {
          type string;
        }
      }
      container output-traffic-control-profile {
        presence "";
        leaf profile-name {
          type string;
        }
        leaf shared-instance {
          type string;
        }
      }
      container output-traffic-control-profile-remaining {
        presence "";
        leaf profile-name {
          type string;
        }
      }
      container classifiers {
        uses apply-group;
        uses apply-macro;
        leaf no-default {
          type empty;
        }
        list dscp {
          key "name";
          ordered-by user;
          leaf name {
            type string;
          }
          uses apply-group;
          uses apply-macro;
          leaf-list family {
            type string;
            ordered-by user;
          }
        }
        list dscp-ipv6 {
          key "name";
          ordered-by user;
          leaf name {
            type string;
          }
          uses apply-group;
          uses apply-macro;
          leaf-list family {
            type string;
            ordered-by user;
          }
        }
        container exp {
          leaf classifier-name {
            type string;
          }
        }
        container ieee-802.1 {
          presence "";
          leaf classifier-name {
            type string;
          }
          leaf vlan-tag {
            type string;
          }
        }
        container inet-precedence {
          leaf classifier-name {
            type string;
          }
        }
        container ieee-802.1ad {
          presence "";
          leaf classifier-name {
            type string;
          }
          leaf vlan-tag {
            type string;
          }
        }
      }
      container ingress-rewrite-rules {
        uses apply-group;
        uses apply-macro;
        list dscp {
          key "name";
          ordered-by user;
          leaf name {
            type string;
          }
        }
        container dscp-ipv6 {
          leaf rewrite-rule-name {
            type string;
          }
        }
        list inet-precedence {
          key "name";
          ordered-by user;
          leaf name {
            type string;
          }
        }
      }
      container loss-priority-maps {
        uses apply-group;
        uses apply-macro;
        container frame-relay-de {
          leaf lpmap-name {
            type string;
          }
        }
      }
      container rewrite-rules {
        uses apply-group;
        uses apply-macro;
        list dscp {
          key "name";
          ordered-by user;
          leaf name {
            type string;
          }
          leaf-list protocol {
            ordered-by user;
            type string;
          }
        }
        list dscp-ipv6 {
          key "name";
          ordered-by user;
          leaf name {
            type string;
          }
          leaf-list protocol {
            ordered-by user;
            type string;
          }
        }
        list exp {
          key "name";
          ordered-by user;
          leaf name {
            type string;
          }
          leaf-list protocol {
            ordered-by user;
            type string;
          }
        }
        container ieee-802.1 {
          presence "";
          leaf rewrite-rule-name {
            type string;
          }
          leaf vlan-tag {
            type string;
          }
        }
        list inet-precedence {
          key "name";
          ordered-by user;
          leaf name {
            type string;
          }
          leaf-list protocol {
            ordered-by user;
            type string;
          }
        }
        container exp-swap-push-push {
          choice choice-3 {
            leaf default {
              type empty;
            }
          }
        }
        container exp-push-push-push {
          choice choice-3 {
            leaf default {
              type empty;
            }
          }
        }
        container frame-relay-de {
          leaf rewrite-rule-name {
            type string;
          }
        }
        container ieee-802.1ad {
          presence "";
          uses apply-group;
          uses apply-macro;
          leaf rewrite-rule-name {
            type string;
          }
          leaf vlan-tag {
            type string;
          }
        }
      }
      container loss-priority-rewrites {
        uses apply-group;
        uses apply-macro;
        container frame-relay-de {
          leaf lprewrite-name {
            type string;
          }
        }
      }
      container translation-table {
        uses apply-group;
        uses apply-macro;
        container to-inet-precedence-from-inet-precedence {
          leaf translation-table-name {
            type string;
          }
        }
        container to-dscp-from-dscp {
          leaf translation-table-name {
            type string;
          }
        }
        container to-dscp-ipv6-from-dscp-ipv6 {
          leaf translation-table-name {
            type string;
          }
        }
        container to-exp-from-exp {
          leaf translation-table-name {
            type string;
          }
        }
      }
      container policy-map {
        leaf policy-map-name {
          type string;
        }
      }
      container undocumented {
        container burst-size {
          leaf size {
            type string;
            units "bytes";
          }
        }
      }
    }
    container classifiers {
      uses apply-group;
      uses apply-macro;
      list dscp {
        key "name";
        ordered-by user;
        leaf name {
          type string;
        }
        uses apply-group;
        uses apply-macro;
      }
      list dscp-ipv6 {
        key "name";
        ordered-by user;
        leaf name {
          type string;
        }
        uses apply-group;
        uses apply-macro;
      }
      container ieee-802.1 {
        presence "";
        leaf classifier-name {
          type string;
        }
        leaf vlan-tag {
          type string;
        }
      }
      container inet-precedence {
        leaf classifier-name {
          type string;
        }
      }
    }
    leaf forwarding-class {
      type string;
    }
    container rewrite-rules {
      uses apply-group;
      uses apply-macro;
      list dscp {
        key "name";
        ordered-by user;
        leaf name {
          type string;
        }
      }
      list dscp-ipv6 {
        key "name";
        ordered-by user;
        leaf name {
          type string;
        }
      }
      container ieee-802.1 {
        presence "";
        leaf rewrite-rule-name {
          type string;
        }
      }
      list inet-precedence {
        key "name";
        ordered-by user;
        leaf name {
          type string;
        }
      }
    }
  }

  grouping juniper-def-rtb-switch-options {
    uses apply-group;
    uses apply-macro;
    container mac-table-size {
      presence "enable mac-table-size";
      uses apply-group;
      uses apply-macro;
      leaf limit {
        type uint32;
      }
      leaf packet-action {
        type string;
      }
    }
    container interface-mac-limit {
      presence "enable interface-mac-limit";
      uses apply-group;
      uses apply-macro;
      leaf limit {
        type uint32;
      }
      leaf packet-action {
        type string;
      }
    }
    container mac-notification {
      presence "enable mac-notification";
      uses apply-group;
      uses apply-macro;
      leaf notification-interval {
        units "seconds";
        type uint32;
      }
    }
    leaf mac-table-aging-time {
      units "seconds";
      type uint32;
    }
    leaf no-mac-learning {
      type empty;
    }
    leaf mac-statistics {
      type empty;
    }
    leaf service-id {
      type uint32;
    }
    leaf ovsdb-managed {
      type empty;
    }
    leaf vtep-source-interface {
      type interface-unit;
    }
    container voip {
      uses apply-group;
      uses apply-macro;
      list interface {
        key "name";
        ordered-by user;
        leaf name {
          type string;
        }
        uses apply-group;
        uses apply-macro;
        leaf vlan {
          type string;
        }
        leaf forwarding-class {
          type string;
        }
      }
    }
    container unknown-unicast-forwarding {
      uses apply-group;
      uses apply-macro;
      list vlan {
        key "name";
        leaf name {
          type string;
        }
        uses apply-group;
        uses apply-macro;
        leaf interface {
          type interface-name;
        }
      }
    }
    list authentication-whitelist {
      key "name";
      ordered-by user;
      leaf name {
        type mac-addr-prefix;
      }
      uses apply-group;
      uses apply-macro;
      leaf vlan-assignment {
        type string;
      }
      leaf bridge-domain-assignment {
        type string;
      }
      leaf interface {
        type interface-name;
      }
    }
    container route-distinguisher {
      leaf rd-type {
        type string;
      }
    }
    leaf-list vrf-import {
      type policy-algebra;
      ordered-by user;
    }
    leaf-list vrf-export {
      type policy-algebra;
      ordered-by user;
    }
    container vrf-target {
      uses apply-group;
      uses apply-macro;
      leaf community {
        type string;
      }
      leaf import {
        type string;
      }
      leaf export {
        type string;
      }
      leaf auto {
        type empty;
      }
    }
    container vtep-remote-interface {
      uses apply-group;
      uses apply-macro;
      list remote-ip {
        key "name";
        ordered-by user;
        leaf name {
          type ipv4addr;
        }
        uses apply-group;
        uses apply-macro;
        leaf dynamic-profile {
          type string;
        }
      }
      container default {
        uses apply-group;
        uses apply-macro;
        leaf dynamic-profile {
          type string;
        }
      }
    }
    list interface {
      key "name";
      ordered-by user;
      leaf name {
        type interface-name;
      }
      uses apply-group;
      uses apply-macro;
      container interface-mac-limit {
        presence "enable interface-mac-limit";
        uses apply-group;
        uses apply-macro;
        leaf limit {
          type uint32;
        }
        leaf packet-action {
          type string;
        }
      }
      leaf no-mac-learning {
        type empty;
      }
      leaf persistent-learning {
        type empty;
      }
      leaf no-mac-notification {
        type empty;
      }
    }
    leaf-list remote-vtep-list {
      type ipaddr;
    }
    container redundant-trunk-group {
      uses apply-group;
      uses apply-macro;
      list group {
        key "name";
        ordered-by user;
        leaf name {
          type key-attribute-string-type;
        }
        uses apply-group;
        uses apply-macro;
        leaf preempt-cutover-timer {
          units "seconds";
          type uint16;
        }
        leaf description {
          type string;
        }
        list interface {
          key "name";
          leaf name {
            type interface-name;
          }
          uses apply-group;
          uses apply-macro;
          leaf primary {
            type empty;
          }
        }
      }
    }
  }

  grouping juniper-diameter-avp-profiles {
    leaf name {
      type key-attribute-string-type;
    }
    uses apply-group;
    uses apply-macro;
    leaf description {
      type string;
    }
    container exclude-avp-options {
      uses apply-group;
      uses apply-macro;
      leaf ps-information {
        type empty;
      }
      leaf user-location-3gpp {
        type empty;
      }
      leaf framed-v4-address {
        type empty;
      }
      leaf gprs-negotiated-qos {
        type empty;
      }
      leaf username {
        type empty;
      }
      leaf user-equip-info {
        type empty;
      }
      leaf all-3gpp-avps {
        type empty;
      }
      leaf qos-information {
        type empty;
      }
      leaf pdn-connection-id {
        type empty;
      }
      leaf dynamic-address-flag {
        type empty;
      }
      leaf serving-node-type {
        type empty;
      }
      leaf charging-charact-select-mode {
        type empty;
      }
      leaf start-time {
        type empty;
      }
      leaf stop-time {
        type empty;
      }
    }
  }

  grouping esp-trace-file-type {
    uses apply-group;
    uses apply-macro;
    leaf filename {
      type string;
    }
    leaf replace {
      type empty;
    }
    leaf size {
      type string;
    }
    leaf files {
      type uint32;
    }
    leaf no-stamp {
      type empty;
    }
    leaf world-readable {
      type empty;
    }
    leaf no-world-readable {
      type empty;
    }
  }

  grouping juniper-dynamic-profile-object {
    leaf name {
      type key-attribute-string-type;
    }
    uses apply-group;
    uses apply-macro;
    list variables {
      key "name";
      ordered-by user;
      uses juniper-dynamic-variable-object;
    }
    container predefined-variable-defaults {
      uses apply-group;
      uses apply-macro;
      container cos-excess-rate {
        uses apply-group;
        uses apply-macro;
        leaf proportion {
          type uint32;
        }
        leaf percent {
          type uint32;
        }
      }
      container cos-scheduler-tx {
        uses apply-group;
        uses apply-macro;
        leaf rate {
          type string;
        }
        leaf percent {
          type uint32;
        }
      }
      container cos-scheduler-bs {
        uses apply-group;
        uses apply-macro;
        leaf percent {
          type uint32;
        }
        leaf temporal {
          type uint32;
        }
      }
      container cos-scheduler-shaping-rate {
        uses apply-group;
        uses apply-macro;
        leaf rate {
          type string;
        }
        leaf percent {
          type uint32;
        }
      }
      list other-variables {
        key "name";
        ordered-by user;
        uses base-default-variable-object;
      }
    }
    container routing-instances {
      uses apply-group;
      uses apply-macro;
      list instance {
        key "name";
        ordered-by user;
        leaf name {
          type string;
        }
        uses apply-group;
        uses apply-macro;
        list interface {
          key "name";
          leaf name {
            type string;
          }
          uses apply-group;
          uses apply-macro;
          choice choice-3 {
            leaf any {
              type empty;
            }
            leaf unicast {
              type empty;
            }
            leaf multicast {
              type empty;
            }
          }
        }
        container routing-options {
          uses apply-group;
          uses apply-macro;
          list rib {
            key "name";
            ordered-by user;
            leaf name {
              type string;
            }
            uses apply-group;
            uses apply-macro;
            container static {
              uses apply-group;
              uses apply-macro;
              leaf rib-group {
                type string;
              }
              container defaults {
                uses apply-group;
                uses apply-macro;
                leaf retain {
                  type empty;
                }
                leaf no-retain {
                  type empty;
                }
                leaf install {
                  type empty;
                }
                leaf no-install {
                  type empty;
                }
                leaf readvertise {
                  type empty;
                }
                leaf no-readvertise {
                  type empty;
                }
                leaf resolve {
                  type empty;
                }
                leaf no-resolve {
                  type empty;
                }
                choice choice-19 {
                  leaf active {
                    type empty;
                  }
                  leaf passive {
                    type empty;
                  }
                }
                container metric {
                  presence "";
                  uses rib-static-metric-type;
                }
                container metric2 {
                  presence "";
                  uses rib-static-metric-type;
                }
                container metric3 {
                  presence "";
                  uses rib-static-metric-type;
                }
                container metric4 {
                  presence "";
                  uses rib-static-metric-type;
                }
                container tag {
                  presence "";
                  uses rib-static-metric-type;
                }
                container tag2 {
                  presence "";
                  uses rib-static-metric-type;
                }
                container preference {
                  presence "";
                  uses rib-static-metric-type;
                }
                container preference2 {
                  presence "";
                  uses rib-static-metric-type;
                }
                container color {
                  presence "";
                  uses rib-static-metric-type;
                }
                container color2 {
                  presence "";
                  uses rib-static-metric-type;
                }
                leaf-list community {
                  type community;
                  ordered-by user;
                }
                container as-path {
                  uses apply-group;
                  uses apply-macro;
                  leaf path {
                    type string;
                  }
                  leaf origin {
                    type string;
                  }
                  leaf atomic-aggregate {
                    type empty;
                  }
                  container aggregator {
                    presence "";
                    uses apply-group;
                    uses apply-macro;
                    leaf as-number {
                      type string;
                    }
                    leaf address {
                      type ipv4addr;
                    }
                  }
                }
              }
              list route {
                key "name";
                ordered-by user;
                leaf name {
                  type ipprefix;
                }
                uses apply-group;
                uses apply-macro;
                choice choice-3 {
                  leaf-list next-hop {
                    type ipaddr-or-interface;
                    ordered-by user;
                  }
                  leaf reject {
                    type empty;
                  }
                  leaf discard {
                    type empty;
                  }
                  leaf receive {
                    type empty;
                  }
                  leaf next-table {
                    type string;
                  }
                }
                list qualified-next-hop {
                  key "name";
                  ordered-by user;
                  uses qualified-nh-obj;
                }
                list lsp-next-hop {
                  key "name";
                  ordered-by user;
                  uses lsp-nh-obj;
                }
                list static-lsp-next-hop {
                  key "name";
                  ordered-by user;
                  uses lsp-nh-obj;
                }
                list p2mp-lsp-next-hop {
                  key "name";
                  ordered-by user;
                  uses lsp-nh-obj;
                }
                leaf backup-pe-group {
                  type string;
                }
                container bfd-liveness-detection {
                  uses apply-group;
                  uses apply-macro;
                  leaf version {
                    type string;
                  }
                  leaf minimum-interval {
                    type uint32;
                  }
                  leaf minimum-receive-interval {
                    type uint32;
                  }
                  leaf multiplier {
                    type uint32;
                  }
                  choice choice-11 {
                    leaf no-adaptation {
                      type empty;
                    }
                  }
                  container transmit-interval {
                    uses apply-group;
                    uses apply-macro;
                    leaf minimum-interval {
                      type uint32;
                    }
                    leaf threshold {
                      type uint32;
                    }
                  }
                  container detection-time {
                    uses apply-group;
                    uses apply-macro;
                    leaf threshold {
                      type uint32;
                    }
                  }
                  container authentication {
                    uses apply-group;
                    uses apply-macro;
                    leaf key-chain {
                      type string;
                    }
                    leaf algorithm {
                      type string;
                    }
                    leaf loose-check {
                      type empty;
                    }
                  }
                  leaf neighbor {
                    type ipaddr;
                  }
                  leaf local-address {
                    type ipaddr;
                  }
                  leaf holddown-interval {
                    type uint32;
                  }
                  leaf minimum-receive-ttl {
                    type uint8;
                  }
                }
                leaf retain {
                  type empty;
                }
                leaf no-retain {
                  type empty;
                }
                leaf install {
                  type empty;
                }
                leaf no-install {
                  type empty;
                }
                leaf readvertise {
                  type empty;
                }
                leaf no-readvertise {
                  type empty;
                }
                leaf resolve {
                  type empty;
                }
                leaf no-resolve {
                  type empty;
                }
                choice choice-32 {
                  leaf active {
                    type empty;
                  }
                  leaf passive {
                    type empty;
                  }
                }
                container metric {
                  presence "";
                  uses rib-static-metric-type;
                }
                container metric2 {
                  presence "";
                  uses rib-static-metric-type;
                }
                container metric3 {
                  presence "";
                  uses rib-static-metric-type;
                }
                container metric4 {
                  presence "";
                  uses rib-static-metric-type;
                }
                container tag {
                  presence "";
                  uses rib-static-metric-type;
                }
                container tag2 {
                  presence "";
                  uses rib-static-metric-type;
                }
                container preference {
                  presence "";
                  uses rib-static-metric-type;
                }
                container preference2 {
                  presence "";
                  uses rib-static-metric-type;
                }
                container color {
                  presence "";
                  uses rib-static-metric-type;
                }
                container color2 {
                  presence "";
                  uses rib-static-metric-type;
                }
                leaf-list community {
                  type community;
                  ordered-by user;
                }
                container as-path {
                  uses apply-group;
                  uses apply-macro;
                  leaf path {
                    type string;
                  }
                  leaf origin {
                    type string;
                  }
                  leaf atomic-aggregate {
                    type empty;
                  }
                  container aggregator {
                    presence "";
                    uses apply-group;
                    uses apply-macro;
                    leaf as-number {
                      type string;
                    }
                    leaf address {
                      type ipv4addr;
                    }
                  }
                }
              }
              list iso-route {
                key "name";
                ordered-by user;
                leaf name {
                  type isoprefix;
                }
                uses apply-group;
                uses apply-macro;
                choice choice-3 {
                  leaf-list next-hop {
                    type ipaddr-or-interface;
                    ordered-by user;
                  }
                  leaf reject {
                    type empty;
                  }
                  leaf discard {
                    type empty;
                  }
                  leaf receive {
                    type empty;
                  }
                  leaf next-table {
                    type string;
                  }
                }
                list qualified-next-hop {
                  key "name";
                  ordered-by user;
                  uses qualified-nh-obj;
                }
                list lsp-next-hop {
                  key "name";
                  ordered-by user;
                  uses lsp-nh-obj;
                }
                list static-lsp-next-hop {
                  key "name";
                  ordered-by user;
                  uses lsp-nh-obj;
                }
                list p2mp-lsp-next-hop {
                  key "name";
                  ordered-by user;
                  uses lsp-nh-obj;
                }
                leaf backup-pe-group {
                  type string;
                }
                container bfd-liveness-detection {
                  uses apply-group;
                  uses apply-macro;
                  leaf version {
                    type string;
                  }
                  leaf minimum-interval {
                    type uint32;
                  }
                  leaf minimum-receive-interval {
                    type uint32;
                  }
                  leaf multiplier {
                    type uint32;
                  }
                  choice choice-11 {
                    leaf no-adaptation {
                      type empty;
                    }
                  }
                  container transmit-interval {
                    uses apply-group;
                    uses apply-macro;
                    leaf minimum-interval {
                      type uint32;
                    }
                    leaf threshold {
                      type uint32;
                    }
                  }
                  container detection-time {
                    uses apply-group;
                    uses apply-macro;
                    leaf threshold {
                      type uint32;
                    }
                  }
                  container authentication {
                    uses apply-group;
                    uses apply-macro;
                    leaf key-chain {
                      type string;
                    }
                    leaf algorithm {
                      type string;
                    }
                    leaf loose-check {
                      type empty;
                    }
                  }
                  leaf neighbor {
                    type ipaddr;
                  }
                  leaf local-address {
                    type ipaddr;
                  }
                  leaf holddown-interval {
                    type uint32;
                  }
                  leaf minimum-receive-ttl {
                    type uint8;
                  }
                }
                leaf retain {
                  type empty;
                }
                leaf no-retain {
                  type empty;
                }
                leaf install {
                  type empty;
                }
                leaf no-install {
                  type empty;
                }
                leaf readvertise {
                  type empty;
                }
                leaf no-readvertise {
                  type empty;
                }
                leaf resolve {
                  type empty;
                }
                leaf no-resolve {
                  type empty;
                }
                choice choice-32 {
                  leaf active {
                    type empty;
                  }
                  leaf passive {
                    type empty;
                  }
                }
                container metric {
                  presence "";
                  uses rib-static-metric-type;
                }
                container metric2 {
                  presence "";
                  uses rib-static-metric-type;
                }
                container metric3 {
                  presence "";
                  uses rib-static-metric-type;
                }
                container metric4 {
                  presence "";
                  uses rib-static-metric-type;
                }
                container tag {
                  presence "";
                  uses rib-static-metric-type;
                }
                container tag2 {
                  presence "";
                  uses rib-static-metric-type;
                }
                container preference {
                  presence "";
                  uses rib-static-metric-type;
                }
                container preference2 {
                  presence "";
                  uses rib-static-metric-type;
                }
                container color {
                  presence "";
                  uses rib-static-metric-type;
                }
                container color2 {
                  presence "";
                  uses rib-static-metric-type;
                }
                leaf-list community {
                  type community;
                  ordered-by user;
                }
                container as-path {
                  uses apply-group;
                  uses apply-macro;
                  leaf path {
                    type string;
                  }
                  leaf origin {
                    type string;
                  }
                  leaf atomic-aggregate {
                    type empty;
                  }
                  container aggregator {
                    presence "";
                    uses apply-group;
                    uses apply-macro;
                    leaf as-number {
                      type string;
                    }
                    leaf address {
                      type ipv4addr;
                    }
                  }
                }
              }
            }
            list martians {
              key "address key2 key2-arg";
              ordered-by user;
              uses martian-type;
            }
            container aggregate {
              uses rib-aggregate-type;
            }
            container generate {
              uses rib-aggregate-type;
            }
            choice choice-11 {
              container maximum-paths {
                presence "";
                leaf limit {
                  type uint32;
                }
                choice choice-5 {
                  leaf threshold {
                    type uint32;
                  }
                  leaf log-only {
                    type empty;
                  }
                }
                leaf log-interval {
                  type uint32;
                }
              }
            }
            container maximum-prefixes {
              presence "";
              leaf limit {
                type uint32;
              }
              choice choice-5 {
                leaf threshold {
                  type uint32;
                }
                leaf log-only {
                  type empty;
                }
              }
              leaf log-interval {
                type uint32;
              }
            }
            container multipath {
              presence "enable multipath";
              uses apply-group;
              uses apply-macro;
              container vpn-unequal-cost {
                presence "enable vpn-unequal-cost";
                leaf equal-external-internal {
                  type empty;
                }
              }
              leaf as-path-compare {
                type empty;
              }
            }
            container label {
              presence "enable label";
              uses apply-group;
              uses apply-macro;
              leaf-list allocation {
                type policy-algebra;
                ordered-by user;
              }
              leaf-list substitution {
                type policy-algebra;
                ordered-by user;
              }
            }
            container access {
              uses apply-group;
              uses apply-macro;
              list route {
                key "name";
                ordered-by user;
                leaf name {
                  type ipprefix;
                }
                uses apply-group;
                uses apply-macro;
                leaf-list next-hop {
                  type ipaddr-or-interface;
                  ordered-by user;
                }
                list qualified-next-hop {
                  key "name";
                  ordered-by user;
                  uses qualified-nh-obj;
                }
                leaf metric {
                  type string;
                }
                leaf preference {
                  type string;
                }
                leaf tag {
                  type string;
                }
              }
            }
            container access-internal {
              uses apply-group;
              uses apply-macro;
              list route {
                key "name";
                ordered-by user;
                leaf name {
                  type ipprefix;
                }
                uses apply-group;
                uses apply-macro;
                leaf-list next-hop {
                  type ipaddr-or-interface;
                  ordered-by user;
                }
                list qualified-next-hop {
                  key "name";
                  ordered-by user;
                  uses qualified-nh-obj;
                }
              }
            }
          }
          container access {
            uses apply-group;
            uses apply-macro;
            list route {
              key "name";
              ordered-by user;
              leaf name {
                type ipprefix;
              }
              uses apply-group;
              uses apply-macro;
              leaf-list next-hop {
                type ipaddr-or-interface;
                ordered-by user;
              }
              list qualified-next-hop {
                key "name";
                ordered-by user;
                uses qualified-nh-obj;
              }
              leaf metric {
                type string;
              }
              leaf preference {
                type string;
              }
              leaf tag {
                type string;
              }
            }
          }
          container access-internal {
            uses apply-group;
            uses apply-macro;
            list route {
              key "name";
              ordered-by user;
              leaf name {
                type ipprefix;
              }
              uses apply-group;
              uses apply-macro;
              leaf-list next-hop {
                type ipaddr-or-interface;
                ordered-by user;
              }
              list qualified-next-hop {
                key "name";
                ordered-by user;
                uses qualified-nh-obj;
              }
            }
          }
          container multicast {
            uses apply-group;
            uses apply-macro;
            container traceoptions {
              uses apply-group;
              uses apply-macro;
              container file {
                presence "";
                uses trace-file-type;
              }
              list flag {
                key "name";
                ordered-by user;
                leaf name {
                  type string;
                }
                leaf disable {
                  type empty;
                }
              }
            }
            list scope {
              key "name";
              ordered-by user;
              leaf name {
                type string;
              }
              uses apply-group;
              uses apply-macro;
              leaf prefix {
                type ipprefix;
              }
              leaf-list interface {
                type interface-name;
                ordered-by user;
              }
            }
            leaf-list scope-policy {
              type policy-algebra;
              ordered-by user;
            }
            list flow-map {
              key "name";
              ordered-by user;
              leaf name {
                type string;
              }
              uses apply-group;
              uses apply-macro;
              leaf-list policy {
                type policy-algebra;
                ordered-by user;
              }
              container bandwidth {
                presence "enable bandwidth";
                leaf bandwidth-value {
                  type string;
                }
                leaf adaptive {
                  type empty;
                }
              }
              leaf-list redundant-sources {
                type ipaddr;
                ordered-by user;
              }
              container forwarding-cache {
                presence "";
                uses apply-group;
                uses apply-macro;
                container timeout {
                  choice choice-3 {
                    leaf timeout-value {
                      type uint32;
                    }
                    container never {
                      presence "enable never";
                      uses apply-group;
                      uses apply-macro;
                      leaf non-discard-entry-only {
                        type empty;
                      }
                    }
                  }
                }
              }
            }
            leaf-list ssm-groups {
              type ipprefix;
              ordered-by user;
            }
            leaf asm-override-ssm {
              type empty;
            }
            leaf-list rpf-check-policy {
              type policy-algebra;
              ordered-by user;
            }
            container pim-to-igmp-proxy {
              presence "";
              uses apply-group;
              uses apply-macro;
              leaf-list upstream-interface {
                type interface-name;
                ordered-by user;
              }
            }
            container pim-to-mld-proxy {
              presence "";
              uses apply-group;
              uses apply-macro;
              leaf-list upstream-interface {
                type interface-name;
                ordered-by user;
              }
            }
            container forwarding-cache {
              uses apply-group;
              uses apply-macro;
              container threshold {
                uses apply-group;
                uses apply-macro;
                leaf suppress {
                  type uint32;
                }
                leaf reuse {
                  type uint32;
                }
              }
              leaf timeout {
                type uint32;
              }
            }
            list interface {
              key "name";
              ordered-by user;
              uses multicast-interface-options-type;
            }
            list ssm-map {
              key "name";
              ordered-by user;
              leaf name {
                type string;
              }
              uses apply-group;
              uses apply-macro;
              leaf-list policy {
                type policy-algebra;
                ordered-by user;
              }
              leaf-list source {
                type ipaddr;
                ordered-by user;
              }
            }
            list backup-pe-group {
              key "name";
              ordered-by user;
              leaf name {
                type string;
              }
              uses apply-group;
              uses apply-macro;
              leaf-list backups {
                type ipaddr;
                ordered-by user;
              }
              leaf local-address {
                type ipaddr;
              }
            }
          }
        }
      }
    }
    container telemetry {
      uses apply-advanced;
      container service-statistics {
        presence "enable service-statistics";
      }
      container subscriber-statistics {
        presence "enable subscriber-statistics";
      }
      container queue-statistics {
        uses apply-advanced;
        list interface {
          key "name";
          ordered-by user;
          leaf name {
            type string;
          }
          uses apply-advanced;
          leaf refresh {
            type string;
          }
          leaf queues {
            type string;
          }
        }
        list interface-set {
          key "name";
          ordered-by user;
          leaf name {
            type string;
          }
          uses apply-advanced;
          leaf refresh {
            type string;
          }
          leaf queues {
            type string;
          }
        }
      }
    }
    container interfaces {
      uses apply-group;
      uses apply-macro;
      list pic-set {
        key "name";
        ordered-by user;
        leaf name {
          type key-attribute-string-type;
        }
        uses apply-group;
        uses apply-macro;
        list interface {
          key "name";
          ordered-by user;
          leaf name {
            type key-attribute-string-type;
          }
          uses apply-group;
          uses apply-macro;
        }
        list fpc {
          key "name";
          ordered-by user;
          leaf name {
            type string;
          }
          uses apply-group;
          uses apply-macro;
          list pic {
            key "name";
            ordered-by user;
            leaf name {
              type string;
            }
            uses apply-group;
            uses apply-macro;
          }
        }
      }
      list interface-set {
        key "name";
        ordered-by user;
        leaf name {
          type string;
        }
        uses apply-group;
        uses apply-macro;
        list interface {
          key "name";
          ordered-by user;
          leaf name {
            type interface-device;
          }
          uses apply-group;
          uses apply-macro;
          list unit {
            key "name";
            leaf name {
              type string;
            }
            uses apply-group;
            uses apply-macro;
          }
          list vlan-tags-outer {
            key "name";
            leaf name {
              type string;
            }
            uses apply-group;
            uses apply-macro;
          }
        }
      }
      container traceoptions {
        uses apply-group;
        uses apply-macro;
        leaf no-remote-trace {
          type empty;
        }
        container file {
          leaf filename {
            type string;
          }
          leaf size {
            type string;
          }
          leaf files {
            type uint32;
          }
          leaf world-readable {
            type empty;
          }
          leaf no-world-readable {
            type empty;
          }
          leaf match {
            type regular-expression;
          }
        }
        list flag {
          key "name";
          leaf name {
            type string;
          }
          leaf disable {
            type empty;
          }
        }
      }
      list interface-range {
        key "name";
        ordered-by user;
        leaf name {
          type key-attribute-string-type;
        }
        uses apply-group;
        uses apply-macro;
        list member {
          key "name";
          ordered-by user;
          leaf name {
            type interface-range-wild;
          }
          uses apply-group;
          uses apply-macro;
        }
        list member-range {
          key "name";
          ordered-by user;
          leaf name {
            type interface-device;
          }
          leaf end-range {
            type interface-device;
          }
        }
        leaf description {
          type string;
        }
        choice choice-9 {
          leaf disable {
            type empty;
          }
        }
        leaf promiscuous-mode {
          type empty;
        }
        leaf multicast-statistics {
          type empty;
        }
        container fabric-options {
          uses apply-group;
          uses apply-macro;
          list member-interfaces {
            key "name";
            leaf name {
              type interface-device;
            }
            uses apply-group;
            uses apply-macro;
          }
        }
        container traceoptions {
          presence "enable traceoptions";
          uses apply-group;
          uses apply-macro;
          list flag {
            key "name";
            ordered-by user;
            leaf name {
              type string;
            }
          }
        }
        leaf passive-monitor-mode {
          type empty;
        }
        choice choice-20 {
          container keepalives {
            presence "enable keepalives";
            uses keepalives-type;
          }
          leaf no-keepalives {
            type empty;
          }
        }
        leaf traps {
          type empty;
        }
        leaf no-traps {
          type empty;
        }
        leaf accounting-profile {
          type string;
        }
        choice choice-27 {
          leaf per-unit-scheduler {
            type empty;
          }
          leaf shared-scheduler {
            type empty;
          }
          container hierarchical-scheduler {
            presence "enable hierarchical-scheduler";
            leaf maximum-hierarchy-levels {
              type uint32;
            }
            leaf maximum-l2-nodes {
              type uint32;
            }
            leaf implicit-hierarchy {
              type empty;
            }
          }
        }
        leaf schedulers {
          type uint32;
        }
        leaf interface-transmit-statistics {
          type empty;
        }
        leaf dce {
          type empty;
        }
        choice choice-34 {
          leaf vlan-tagging {
            type empty;
          }
          leaf stacked-vlan-tagging {
            type empty;
          }
          leaf flexible-vlan-tagging {
            type empty;
          }
          leaf vlan-vci-tagging {
            type empty;
          }
        }
        leaf native-vlan-id {
          type uint32;
        }
        leaf speed {
          type string;
        }
        container auto-configure {
          uses auto-configure-vlan-type;
        }
        leaf mtu {
          type uint32;
        }
        container hold-time {
          presence "";
          leaf up {
            type uint32;
          }
          leaf down {
            type uint32;
          }
        }
        container satop-options {
          uses apply-group;
          uses apply-macro;
          leaf idle-pattern {
            type uint32;
          }
          leaf payload-size {
            type uint32;
          }
          container excessive-packet-loss-rate {
            uses apply-group;
            uses apply-macro;
            leaf threshold {
              type uint8;
            }
            leaf sample-period {
              type uint32;
            }
          }
          choice choice-9 {
            leaf jitter-buffer-packets {
              type uint32;
            }
            leaf jitter-buffer-latency {
              type uint32;
            }
            leaf jitter-buffer-auto-adjust {
              type empty;
            }
          }
          leaf bit-rate {
            type uint32;
          }
        }
        container cesopsn-options {
          uses apply-group;
          uses apply-macro;
          leaf idle-pattern {
            type uint32;
          }
          leaf packetization-latency {
            units "microseconds";
            type uint32;
          }
          container excessive-packet-loss-rate {
            uses apply-group;
            uses apply-macro;
            leaf threshold {
              type uint8;
            }
            leaf sample-period {
              type uint32;
            }
          }
          choice choice-jitter-buffer-packets {
            leaf jitter-buffer-packets {
              type uint32;
            }
            leaf jitter-buffer-latency {
              units "milliseconds";
              type uint32;
            }
            leaf jitter-buffer-auto-adjust {
              type empty;
            }
          }
          leaf bit-rate {
            type uint32;
          }
        }
        container ima-group-options {
          uses apply-group;
          uses apply-macro;
          leaf frame-length {
            type string;
          }
          leaf symmetry {
            type string;
          }
          leaf transmit-clock {
            type string;
          }
          leaf version {
            type string;
          }
          container minimum-links {
            choice choice-3 {
              leaf symmetrical {
                type uint32;
              }
            }
          }
          container frame-synchronization {
            uses apply-group;
            uses apply-macro;
            leaf alpha {
              type uint32;
            }
            leaf beta {
              type uint32;
            }
            leaf gamma {
              type uint32;
            }
          }
          container test-procedure {
            uses apply-group;
            uses apply-macro;
            leaf period {
              type uint32;
            }
            leaf interface {
              type interface-device;
            }
            leaf pattern {
              type uint32;
            }
          }
          leaf differential-delay {
            type uint32;
          }
        }
        container ima-link-options {
          uses apply-group;
          uses apply-macro;
          leaf group-id {
            type uint32;
          }
        }
        container clocking {
          presence "enable clocking";
          choice choice-3 {
            leaf internal {
              type empty;
            }
            container external {
              presence "enable external";
              uses apply-group;
              uses apply-macro;
            }
          }
        }
        leaf link-mode {
          type string;
        }
        leaf media-type {
          type string;
        }
        leaf encapsulation {
          type string;
        }
        container esi {
          presence "";
          uses apply-group;
          uses apply-macro;
          container apply-advanced {
            uses apply-group;
            uses apply-macro;
          }
          leaf identifier {
            mandatory true;
            type string;
          }
          choice choice-single-active {
            leaf single-active {
              type empty;
            }
            leaf all-active {
              type empty;
            }
          }
        }
        container framing {
          uses apply-group;
          uses apply-macro;
          choice choice-3 {
            leaf lan-phy {
              type empty;
            }
            leaf wan-phy {
              type empty;
            }
            leaf sonet {
              type empty;
            }
            leaf sdh {
              type empty;
            }
          }
        }
        leaf unidirectional {
          type empty;
        }
        container lmi {
          uses apply-group;
          uses apply-macro;
          leaf n391dte {
            type uint16;
          }
          leaf n392dce {
            type uint16;
          }
          leaf n392dte {
            type uint16;
          }
          leaf n393dce {
            type uint16;
          }
          leaf n393dte {
            type uint16;
          }
          leaf t391dte {
            type uint16;
          }
          leaf t392dce {
            type uint16;
          }
          leaf lmi-type {
            type string;
          }
        }
        container mlfr-uni-nni-bundle-options {
          uses apply-group;
          uses apply-macro;
          container cisco-interoperability {
            uses apply-group;
            uses apply-macro;
            leaf send-lip-remove-link-for-link-reject {
              type empty;
            }
          }
          leaf mrru {
            type uint16;
          }
          leaf yellow-differential-delay {
            type uint16;
          }
          leaf red-differential-delay {
            type uint16;
          }
          leaf action-red-differential-delay {
            type string;
          }
          leaf fragment-threshold {
            type uint32;
          }
          leaf drop-timeout {
            type uint16;
          }
          leaf link-layer-overhead {
            type unsigned-float;
          }
          leaf lmi-type {
            type string;
          }
          leaf minimum-links {
            type uint16;
          }
          leaf hello-timer {
            type uint16;
          }
          leaf acknowledge-timer {
            type uint16;
          }
          leaf acknowledge-retries {
            type uint16;
          }
          leaf n391 {
            type uint16;
          }
          leaf n392 {
            type uint16;
          }
          leaf n393 {
            type uint16;
          }
          leaf t391 {
            type uint16;
          }
          leaf t392 {
            type uint16;
          }
        }
        leaf mac {
          type mac-unicaset;
        }
        container receive-bucket {
          uses dcd-rx-bucket-config;
        }
        container transmit-bucket {
          uses dcd-tx-bucket-config;
        }
        leaf shared-interface {
          type empty;
        }
        container sonet-options {
          uses sonet-options-type;
        }
        container aggregated-sonet-options {
          uses apply-group;
          uses apply-macro;
          leaf minimum-links {
            type uint16;
          }
          leaf link-speed {
            type string;
          }
          leaf minimum-bandwidth {
            type uint64;
          }
        }
        container atm-options {
          uses apply-group;
          uses apply-macro;
          leaf pic-type {
            type string;
          }
          leaf cell-bundle-size {
            type uint32;
          }
          leaf plp-to-clp {
            type empty;
          }
          leaf use-null-cw {
            type empty;
          }
          container promiscuous-mode {
            presence "enable promiscuous-mode";
            uses apply-group;
            uses apply-macro;
            list vpi {
              key "name";
              ordered-by user;
              leaf name {
                type string;
              }
            }
          }
          list vpi {
            key "name";
            ordered-by user;
            leaf name {
              type string;
            }
            uses apply-group;
            uses apply-macro;
            leaf maximum-vcs {
              type uint32;
            }
            container shaping {
              uses dcd-shaping-config;
            }
            container oam-period {
              choice choice-3 {
                leaf oam-period {
                  type uint32;
                }
                container disable {
                  presence "enable disable";
                }
              }
            }
            container oam-liveness {
              uses apply-group;
              uses apply-macro;
              leaf up-count {
                type uint32;
              }
              leaf down-count {
                type uint32;
              }
            }
          }
          container ilmi {
            presence "enable ilmi";
            uses apply-group;
            uses apply-macro;
          }
          list linear-red-profiles {
            key "name";
            ordered-by user;
            leaf name {
              type string;
            }
            leaf queue-depth {
              type string;
            }
            leaf high-plp-threshold {
              type uint32;
            }
            leaf low-plp-threshold {
              type uint32;
            }
            leaf high-plp-max-threshold {
              type uint32;
            }
            leaf low-plp-max-threshold {
              type uint32;
            }
          }
          list scheduler-maps {
            key "name";
            ordered-by user;
            leaf name {
              type string;
            }
            uses apply-group;
            uses apply-macro;
            leaf vc-cos-mode {
              type string;
            }
            list forwarding-class {
              key "name";
              ordered-by user;
              leaf name {
                type string;
              }
              uses apply-group;
              uses apply-macro;
              leaf priority {
                type string;
              }
              container transmit-weight {
                choice choice-3 {
                  leaf percent {
                    type uint32;
                  }
                  leaf cells {
                    type string;
                  }
                }
              }
              choice choice-7 {
                container epd-threshold {
                  presence "";
                  uses epd-threshold-config;
                }
                leaf linear-red-profile {
                  type string;
                }
              }
            }
          }
          container mpls {
            uses mpls-ifd-options;
          }
          leaf payload-scrambler {
            type empty;
          }
          leaf no-payload-scrambler {
            type empty;
          }
        }
        container multiservice-options {
          uses apply-group;
          uses apply-macro;
          leaf syslog {
            type empty;
          }
          leaf no-syslog {
            type empty;
          }
          leaf core-dump {
            type empty;
          }
          leaf no-core-dump {
            type empty;
          }
          container flow-control-options {
            uses apply-group;
            uses apply-macro;
            leaf dump-on-flow-control {
              type empty;
            }
            leaf reset-on-flow-control {
              type empty;
            }
            leaf down-on-flow-control {
              type empty;
            }
          }
        }
        container ggsn-options {
          uses apply-group;
          uses apply-macro;
          leaf syslog {
            type empty;
          }
          leaf no-syslog {
            type empty;
          }
          leaf core-dump {
            type empty;
          }
          leaf no-core-dump {
            type empty;
          }
        }
        container ppp-options {
          uses ppp-options-type;
        }
        container redundancy-options {
          presence "";
          uses apply-group;
          uses apply-macro;
          container undocumented {
            uses undocumented-redundancy-peer;
          }
          leaf primary {
            type interface-device;
          }
          leaf secondary {
            type interface-device;
          }
        }
        container lsq-failure-options {
          uses apply-group;
          uses apply-macro;
          list trigger-link-failure {
            key "name";
            ordered-by user;
            leaf name {
              type interface-device;
            }
            uses apply-group;
            uses apply-macro;
          }
          leaf no-termination-request {
            type empty;
          }
          leaf no-no-termination-request {
            type empty;
          }
        }
        container redundancy-group {
          uses apply-group;
          uses apply-macro;
          list member-interface {
            key "name";
            leaf name {
              type interface-device;
            }
            uses apply-group;
            uses apply-macro;
            choice choice-active {
              leaf active {
                type empty;
              }
              leaf backup {
                type empty;
              }
            }
          }
          leaf maximum-links {
            type uint32;
          }
        }
        container services-options {
          uses apply-group;
          uses apply-macro;
          container syslog {
            uses service-set-syslog-object;
          }
          leaf open-timeout {
            units "seconds";
            type uint32;
          }
          leaf close-timeout {
            units "seconds";
            type uint32;
          }
          leaf inactivity-timeout {
            units "seconds";
            type uint32;
          }
          leaf inactivity-tcp-timeout {
            units "seconds";
            type uint32;
          }
          leaf inactivity-asymm-tcp-timeout {
            units "seconds";
            type uint32;
          }
          leaf inactivity-non-tcp-timeout {
            units "seconds";
            type uint32;
          }
          leaf session-timeout {
            units "seconds";
            type uint32;
          }
          leaf disable-global-timeout-override {
            type empty;
          }
          leaf tcp-tickles {
            type uint8;
          }
          container trio-flow-offload {
            presence "enable trio-flow-offload";
            uses apply-group;
            uses apply-macro;
            leaf minimum-bytes {
              type uint32;
            }
          }
          leaf fragment-limit {
            type uint8;
          }
          leaf reassembly-timeout {
            units "seconds";
            type uint8;
          }
          leaf cgn-pic {
            type empty;
          }
          leaf pba-interim-logging-interval {
            units "seconds";
            type uint32;
          }
          container session-limit {
            presence "enable session-limit";
            uses apply-group;
            uses apply-macro;
            leaf maximum {
              type string;
            }
            leaf rate {
              type string;
            }
          }
          container ignore-errors {
            presence "enable ignore-errors";
            leaf tcp {
              type empty;
            }
            leaf alg {
              type empty;
            }
          }
        }
        container t3-options {
          uses apply-group;
          uses apply-macro;
          leaf loopback {
            type string;
          }
          leaf long-buildout {
            type empty;
          }
          leaf no-long-buildout {
            type empty;
          }
          leaf loop-timing {
            type empty;
          }
          leaf no-loop-timing {
            type empty;
          }
          container compatibility-mode {
            choice choice-3 {
              container larscom {
                presence "enable larscom";
                leaf subrate {
                  type uint32;
                }
              }
              container verilink {
                presence "enable verilink";
                leaf subrate {
                  type uint32;
                }
              }
              container adtran {
                presence "enable adtran";
                leaf subrate {
                  type uint32;
                }
              }
              container kentrox {
                presence "enable kentrox";
                leaf subrate {
                  type uint32;
                }
              }
              container digital-link {
                presence "enable digital-link";
                leaf subrate {
                  type string;
                }
              }
            }
          }
          leaf payload-scrambler {
            type empty;
          }
          leaf no-payload-scrambler {
            type empty;
          }
          leaf cbit-parity {
            type empty;
          }
          leaf no-cbit-parity {
            type empty;
          }
          leaf fcs {
            type string;
          }
          leaf idle-cycle-flag {
            type string;
          }
          leaf start-end-flag {
            type string;
          }
          leaf feac-loop-respond {
            type empty;
          }
          leaf no-feac-loop-respond {
            type empty;
          }
          leaf bert-algorithm {
            type string;
          }
          leaf bert-error-rate {
            type uint32;
          }
          leaf bert-period {
            type uint32;
          }
          leaf buildout {
            type uint32;
          }
          leaf atm-encapsulation {
            type string;
          }
        }
        container e3-options {
          uses apply-group;
          uses apply-macro;
          leaf loopback {
            type string;
          }
          leaf unframed {
            type empty;
          }
          leaf no-unframed {
            type empty;
          }
          container compatibility-mode {
            choice choice-3 {
              leaf larscom {
                type empty;
              }
              container digital-link {
                presence "enable digital-link";
                leaf subrate {
                  type string;
                }
              }
              container kentrox {
                presence "enable kentrox";
                leaf subrate {
                  type uint32;
                }
              }
            }
          }
          leaf payload-scrambler {
            type empty;
          }
          leaf no-payload-scrambler {
            type empty;
          }
          leaf fcs {
            type string;
          }
          leaf idle-cycle-flag {
            type string;
          }
          leaf invert-data {
            type empty;
          }
          leaf start-end-flag {
            type string;
          }
          leaf bert-algorithm {
            type string;
          }
          leaf bert-error-rate {
            type uint32;
          }
          leaf bert-period {
            type uint32;
          }
          leaf buildout {
            type uint32;
          }
          leaf atm-encapsulation {
            type string;
          }
          leaf framing {
            type string;
          }
        }
        container e1-options {
          uses apply-group;
          uses apply-macro;
          leaf timeslots {
            type string;
          }
          leaf loopback {
            type string;
          }
          leaf framing {
            type string;
          }
          leaf fcs {
            type string;
          }
          leaf invert-data {
            type empty;
          }
          leaf idle-cycle-flag {
            type string;
          }
          leaf start-end-flag {
            type string;
          }
          leaf bert-algorithm {
            type string;
          }
          leaf bert-error-rate {
            type uint32;
          }
          leaf bert-period {
            type uint32;
          }
        }
        container t1-options {
          uses apply-group;
          uses apply-macro;
          leaf timeslots {
            type string;
          }
          leaf voice-timeslots {
            type string;
          }
          leaf loopback {
            type string;
          }
          leaf buildout {
            type string;
          }
          leaf byte-encoding {
            type string;
          }
          leaf line-encoding {
            type string;
          }
          leaf invert-data {
            type empty;
          }
          leaf framing {
            type string;
          }
          leaf fcs {
            type string;
          }
          leaf idle-cycle-flag {
            type string;
          }
          leaf start-end-flag {
            type string;
          }
          leaf bert-algorithm {
            type string;
          }
          leaf bert-error-rate {
            type uint32;
          }
          leaf bert-period {
            type uint32;
          }
          leaf remote-loopback-respond {
            type empty;
          }
          leaf crc-major-alarm-threshold {
            type string;
          }
          leaf crc-minor-alarm-threshold {
            type string;
          }
        }
        container ds0-options {
          uses apply-group;
          uses apply-macro;
          leaf loopback {
            type string;
          }
          leaf byte-encoding {
            type string;
          }
          leaf invert-data {
            type empty;
          }
          leaf fcs {
            type string;
          }
          leaf idle-cycle-flag {
            type string;
          }
          leaf start-end-flag {
            type string;
          }
          leaf bert-algorithm {
            type string;
          }
          leaf bert-error-rate {
            type uint32;
          }
          leaf bert-period {
            type uint32;
          }
        }
        container serial-options {
          uses apply-group;
          uses apply-macro;
          leaf line-protocol {
            type string;
          }
          choice choice-5 {
            container dte-options {
              uses apply-group;
              uses apply-macro;
              leaf ignore-all {
                type empty;
              }
              container dtr {
                choice choice-3 {
                  leaf assert {
                    type empty;
                  }
                  leaf de-assert {
                    type empty;
                  }
                  leaf normal {
                    type empty;
                  }
                  container auto-synchronize {
                    presence "enable auto-synchronize";
                    uses apply-group;
                    uses apply-macro;
                    leaf duration {
                      type uint16;
                    }
                    leaf interval {
                      type uint16;
                    }
                  }
                }
              }
              leaf control-signal {
                type string;
              }
              leaf rts {
                type string;
              }
              leaf dcd {
                type string;
              }
              leaf dsr {
                type string;
              }
              leaf cts {
                type string;
              }
              leaf indication {
                type string;
              }
              leaf tm {
                type string;
              }
            }
            container dce-options {
              uses apply-group;
              uses apply-macro;
              leaf ignore-all {
                type empty;
              }
              leaf dtr {
                type string;
              }
              leaf rts {
                type string;
              }
              leaf dcd {
                type string;
              }
              leaf dsr {
                type string;
              }
              leaf cts {
                type string;
              }
              leaf tm {
                type string;
              }
              leaf dce-loopback-override {
                type empty;
              }
            }
          }
          leaf dtr-circuit {
            type string;
          }
          leaf dtr-polarity {
            type string;
          }
          leaf rts-polarity {
            type string;
          }
          leaf control-polarity {
            type string;
          }
          leaf dcd-polarity {
            type string;
          }
          leaf dsr-polarity {
            type string;
          }
          leaf cts-polarity {
            type string;
          }
          leaf indication-polarity {
            type string;
          }
          leaf tm-polarity {
            type string;
          }
          leaf clocking-mode {
            type string;
          }
          leaf transmit-clock {
            type string;
          }
          leaf clock-rate {
            type string;
          }
          leaf loopback {
            type string;
          }
          leaf encoding {
            type string;
          }
          leaf idle-cycle-flag {
            type string;
          }
        }
        choice gratuitous-arp-reply-choice {
          leaf gratuitous-arp-reply {
            type empty;
          }
          leaf no-gratuitous-arp-reply {
            type empty;
          }
        }
        choice no-gratuitous-arp-request-choice {
          leaf no-gratuitous-arp-request {
            type empty;
          }
          leaf no-no-gratuitous-arp-request {
            type empty;
          }
        }
        leaf arp-l2-validate {
          type empty;
        }
        container ether-options {
          uses apply-group;
          uses apply-macro;
          choice loopback-choice {
            leaf loopback {
              type empty;
            }
            leaf no-loopback {
              type empty;
            }
          }
          leaf loopback-remote {
            type empty;
          }
          choice source-filtering-choice {
            leaf source-filtering {
              type empty;
            }
            leaf no-source-filtering {
              type empty;
            }
          }
          container ethernet-switch-profile {
            uses apply-group;
            uses apply-macro;
            leaf-list tag-protocol-id {
              type string;
              ordered-by user;
            }
            container ethernet-policer-profile {
              uses apply-group;
              uses apply-macro;
              container input-priority-map {
                uses cos-policer-input-priority-map;
              }
              container output-priority-map {
                uses cos-policer-output-priority-map;
              }
              list policer {
                key "name";
                ordered-by user;
                uses cos-policer;
              }
            }
            container storm-control {
              presence "";
              uses apply-group;
              uses apply-macro;
              leaf profile-name {
                type string;
              }
            }
            container recovery-timeout {
              leaf time-in-seconds {
                units "seconds";
                type uint32;
              }
            }
            leaf mac-learn-enable {
              type empty;
            }
            leaf no-mac-learn-enable {
              type empty;
            }
          }
          leaf asynchronous-notification {
            type empty;
          }
          list source-address-filter {
            key "name";
            leaf name {
              type mac-addr;
            }
          }
          choice auto-negotiation-choice {
            leaf auto-negotiation {
              type empty;
            }
            leaf no-auto-negotiation {
              type empty;
            }
          }
          choice flow-control-choice {
            leaf flow-control {
              type empty;
            }
            leaf no-flow-control {
              type empty;
            }
          }
          container configured-flow-control {
            presence "";
            uses apply-group;
            uses apply-macro;
            leaf rx-buffers {
              type string;
            }
            leaf tx-buffers {
              type string;
            }
          }
          leaf link-mode {
            type string;
          }
          container mpls {
            uses mpls-ifd-options;
          }
          leaf ignore-l3-incompletes {
            type empty;
          }
          leaf no-auto-mdix {
            type empty;
          }
          container speed {
            choice choice-3 {
              container auto-negotiation {
                presence "enable auto-negotiation";
                leaf auto-negotiate-10-100 {
                  type empty;
                }
              }
              leaf ethernet-10m {
                type empty;
              }
              leaf ethernet-100m {
                type empty;
              }
              leaf ethernet-1g {
                type empty;
              }
              leaf ethernet-10g {
                type empty;
              }
            }
          }
          container ieee-802.3ad {
            uses apply-group;
            uses apply-macro;
            container lacp {
              uses apply-group;
              uses apply-macro;
              leaf force-up {
                type empty;
              }
              leaf port-priority {
                type uint16;
              }
            }
            leaf bundle {
              type interface-device;
            }
            choice choice-7 {
              leaf primary {
                type empty;
              }
              leaf backup {
                type empty;
              }
            }
          }
          leaf ieee-802-3az-eee {
            type empty;
          }
          leaf mdi-mode {
            type string;
          }
        }
        container gigether-options {
          uses apply-group;
          uses apply-macro;
          choice loopback-choice {
            leaf loopback {
              type empty;
            }
            leaf no-loopback {
              type empty;
            }
          }
          choice flow-control-choice {
            leaf flow-control {
              type empty;
            }
            leaf no-flow-control {
              type empty;
            }
          }
          choice source-filtering-choice {
            leaf source-filtering {
              type empty;
            }
            leaf no-source-filtering {
              type empty;
            }
          }
          choice choice-15 {
            leaf no-auto-negotiation {
              type empty;
            }
            container auto-negotiation {
              presence "enable auto-negotiation";
              leaf remote-fault {
                type string;
              }
            }
          }
          leaf mac-mode {
            type string;
          }
          leaf asynchronous-notification {
            type empty;
          }
          list source-address-filter {
            key "name";
            leaf name {
              type mac-addr;
            }
          }
          container redundant-parent {
            presence "";
            uses apply-group;
            uses apply-macro;
            leaf parent {
              type interface-device;
            }
          }
          container ieee-802.3ad {
            uses apply-group;
            uses apply-macro;
            container lacp {
              uses apply-group;
              uses apply-macro;
              leaf port-priority {
                type uint16;
              }
            }
            leaf bundle {
              type interface-device;
            }
            leaf link-index {
              type uint16;
            }
            choice choice-9 {
              leaf primary {
                type empty;
              }
              leaf backup {
                type empty;
              }
            }
          }
          container ethernet-switch-profile {
            uses apply-group;
            uses apply-macro;
            leaf-list tag-protocol-id {
              type string;
              ordered-by user;
            }
            container ethernet-policer-profile {
              uses apply-group;
              uses apply-macro;
              container input-priority-map {
                uses cos-policer-input-priority-map;
              }
              container output-priority-map {
                uses cos-policer-output-priority-map;
              }
              list policer {
                key "name";
                ordered-by user;
                uses cos-policer;
              }
            }
            leaf mac-learn-enable {
              type empty;
            }
            leaf no-mac-learn-enable {
              type empty;
            }
          }
          container mpls {
            uses mpls-ifd-options;
          }
          leaf ignore-l3-incompletes {
            type empty;
          }
          leaf no-auto-mdix {
            type empty;
          }
        }
        uses optics-options-grouping;
        container otn-options {
          uses otn-options-type;
        }
        container fastether-options {
          uses apply-group;
          uses apply-macro;
          choice loopback-choice {
            leaf loopback {
              type empty;
            }
            leaf no-loopback {
              type empty;
            }
          }
          choice source-filtering-choice {
            leaf source-filtering {
              type empty;
            }
            leaf no-source-filtering {
              type empty;
            }
          }
          choice auto-negotiation-choice {
            leaf auto-negotiation {
              type empty;
            }
            leaf no-auto-negotiation {
              type empty;
            }
          }
          choice flow-control-choice {
            leaf flow-control {
              type empty;
            }
            leaf no-flow-control {
              type empty;
            }
          }
          leaf ingress-rate-limit {
            type uint32;
          }
          list source-address-filter {
            key "name";
            ordered-by user;
            leaf name {
              type mac-addr;
            }
          }
          container redundant-parent {
            presence "";
            uses apply-group;
            uses apply-macro;
            leaf parent {
              type interface-device;
            }
          }
          container ieee-802.3ad {
            uses apply-group;
            uses apply-macro;
            container lacp {
              uses apply-group;
              uses apply-macro;
              leaf port-priority {
                type uint16;
              }
            }
            leaf bundle {
              type interface-device;
            }
            choice choice-7 {
              leaf primary {
                type empty;
              }
              leaf backup {
                type empty;
              }
            }
          }
          container mpls {
            uses mpls-ifd-options;
          }
          leaf ignore-l3-incompletes {
            type empty;
          }
        }
        container redundant-ether-options {
          presence "";
          uses apply-group;
          uses apply-macro;
          leaf redundancy-group {
            type uint16;
          }
          choice loopback-choice {
            leaf loopback {
              type empty;
            }
            leaf no-loopback {
              type empty;
            }
          }
          choice flow-control-choice {
            leaf flow-control {
              type empty;
            }
            leaf no-flow-control {
              type empty;
            }
          }
          choice source-filtering-choice {
            leaf source-filtering {
              type empty;
            }
            leaf no-source-filtering {
              type empty;
            }
          }
          list source-address-filter {
            key "name";
            ordered-by user;
            leaf name {
              type mac-addr;
            }
          }
          leaf link-speed {
            type string;
          }
          leaf minimum-links {
            type uint16;
          }
          container lacp {
            uses apply-group;
            uses apply-macro;
            choice choice-3 {
              leaf active {
                type empty;
              }
              leaf passive {
                type empty;
              }
            }
            leaf periodic {
              type string;
            }
          }
        }
        container aggregated-ether-options {
          uses apply-group;
          uses apply-macro;
          choice loopback-choice {
            leaf loopback {
              type empty;
            }
            leaf no-loopback {
              type empty;
            }
          }
          choice flow-control-choice {
            leaf flow-control {
              type empty;
            }
            leaf no-flow-control {
              type empty;
            }
          }
          choice source-filtering-choice {
            leaf source-filtering {
              type empty;
            }
            leaf no-source-filtering {
              type empty;
            }
          }
          leaf autostate-exclude {
            type empty;
          }
          container link-protection {
            presence "enable link-protection";
            uses apply-group;
            uses apply-macro;
            leaf revertive {
              type empty;
            }
            leaf non-revertive {
              type empty;
            }
            leaf backup-state {
              type string;
            }
            container rtg-config {
              presence "enable rtg-config";
              uses apply-group;
              uses apply-macro;
              leaf preempt-cutover-timer {
                type uint32;
              }
            }
          }
          leaf no-link-protection {
            type empty;
          }
          list source-address-filter {
            key "name";
            ordered-by user;
            leaf name {
              type mac-addr;
            }
          }
          leaf minimum-links {
            type uint16;
          }
          leaf link-speed {
            type string;
          }
          container lacp {
            uses apply-group;
            uses apply-macro;
            choice choice-3 {
              leaf active {
                type empty;
              }
              leaf passive {
                type empty;
              }
            }
            leaf periodic {
              type string;
            }
            leaf fast-failover {
              type empty;
            }
            container link-protection {
              presence "enable link-protection";
              uses apply-group;
              uses apply-macro;
              leaf disable {
                type empty;
              }
              choice choice-5 {
                leaf revertive {
                  type empty;
                }
                leaf non-revertive {
                  type empty;
                }
              }
            }
            leaf accept-data {
              type empty;
            }
            leaf system-priority {
              type string;
            }
            leaf system-id {
              type mac-addr;
            }
            leaf admin-key {
              type uint16;
            }
            container hold-time {
              presence "";
              leaf up {
                mandatory true;
                units "seconds";
                type uint16;
              }
            }
            leaf aggregate-wait-time {
              units "seconds";
              type uint16;
            }
            leaf force-up {
              type empty;
            }
          }
          container ethernet-switch-profile {
            uses apply-group;
            uses apply-macro;
            leaf-list tag-protocol-id {
              type string;
              ordered-by user;
            }
          }
          container mc-ae {
            presence "";
            uses apply-group;
            uses apply-macro;
            leaf mc-ae-id {
              type uint16;
            }
            leaf redundancy-group {
              type uint32;
            }
            leaf chassis-id {
              type uint16;
            }
            leaf mode {
              type string;
            }
            leaf status-control {
              type string;
            }
            leaf switchover-mode {
              type string;
            }
            leaf revert-time {
              units "minute";
              type uint32;
            }
            leaf init-delay-time {
              units "seconds";
              type uint16;
            }
            leaf recovery-delay-time {
              units "seconds";
              type uint16;
            }
            container events {
              presence "enable events";
              uses apply-group;
              uses apply-macro;
              container iccp-peer-down {
                presence "enable iccp-peer-down";
                uses apply-group;
                uses apply-macro;
                leaf force-icl-down {
                  type empty;
                }
                leaf prefer-status-control-active {
                  type empty;
                }
              }
            }
          }
        }
        container es-options {
          uses apply-group;
          uses apply-macro;
          leaf backup-interface {
            type interface-device;
          }
        }
        container dsl-options {
          uses apply-group;
          uses apply-macro;
          leaf operating-mode {
            type string;
          }
        }
        container vdsl-options {
          uses apply-group;
          uses apply-macro;
          leaf vdsl-profile {
            type string;
          }
        }
        container shdsl-options {
          uses apply-group;
          uses apply-macro;
          leaf annex {
            type string;
          }
          leaf line-rate {
            type string;
          }
          leaf loopback {
            type string;
          }
          container snr-margin {
            presence "enable snr-margin";
            uses apply-group;
            uses apply-macro;
            leaf current {
              type string;
            }
            leaf snext {
              type string;
            }
          }
        }
        container data-input {
          uses apply-group;
          uses apply-macro;
          choice choice-3 {
            leaf system {
              type empty;
            }
            leaf interface {
              type interface-device;
            }
          }
        }
        container switch-options {
          uses apply-group;
          uses apply-macro;
          list switch-port {
            key "name";
            leaf name {
              type string;
            }
            uses apply-group;
            uses apply-macro;
            leaf auto-negotiation {
              type empty;
            }
            leaf no-auto-negotiation {
              type empty;
            }
            leaf link-mode {
              type string;
            }
            leaf speed {
              type string;
            }
            leaf vlan-id {
              type uint32;
            }
            leaf cascade-port {
              type empty;
            }
          }
        }
        container container-options {
          uses apply-group;
          uses apply-macro;
          container container-type {
            presence "enable container-type";
            uses apply-group;
            uses apply-macro;
            choice choice-3 {
              container aps {
                presence "enable aps";
                uses aps-type;
              }
            }
          }
          container member-interface-type {
            uses apply-group;
            uses apply-macro;
            choice choice-3 {
              container sonet {
                presence "";
                uses apply-group;
                uses apply-macro;
                leaf member-interface-speed {
                  type string;
                }
              }
              container atm {
                presence "";
                uses apply-group;
                uses apply-macro;
                leaf member-interface-speed {
                  type string;
                }
              }
            }
          }
          container redundancy {
            uses apply-group;
            uses apply-macro;
            container hold-time {
              presence "";
              leaf up {
                type uint32;
              }
              leaf down {
                type uint32;
              }
            }
          }
          leaf-list container-list {
            type interface-device;
            ordered-by user;
          }
          leaf primary {
            type empty;
          }
          leaf standby {
            type empty;
          }
          leaf allow-configuration-override {
            type empty;
          }
        }
        container layer2-policer {
          uses apply-group;
          uses apply-macro;
          leaf input-hierarchical-policer {
            type string;
          }
        }
        list unit {
          key "name";
          leaf name {
            type string;
          }
          uses apply-group;
          uses apply-macro;
          container peer-psd {
            presence "";
            leaf psd-name {
              type string;
            }
          }
          container peer-interface {
            presence "enable peer-interface";
            uses apply-group;
            uses apply-macro;
            leaf interface-name {
              type interface-unit;
            }
          }
          container interface-shared-with {
            presence "";
            uses apply-group;
            uses apply-macro;
            leaf psd-name {
              type string;
            }
          }
          choice choice-9 {
            leaf disable {
              type empty;
            }
          }
          leaf passive-monitor-mode {
            type empty;
          }
          leaf per-session-scheduler {
            type empty;
          }
          leaf clear-dont-fragment-bit {
            type empty;
          }
          leaf reassemble-packets {
            type empty;
          }
          container rpm {
            uses apply-group;
            uses apply-macro;
            choice choice-3 {
              leaf client {
                type empty;
              }
              leaf server {
                type empty;
              }
              leaf twamp-server {
                type empty;
              }
            }
          }
          leaf description {
            type string;
          }
          container dial-options {
            uses apply-group;
            uses apply-macro;
            choice choice-3 {
              leaf l2tp-interface-id {
                type string;
              }
              leaf ipsec-interface-id {
                type string;
              }
            }
            choice choice-4 {
              leaf dedicated {
                type empty;
              }
              leaf shared {
                type empty;
              }
            }
          }
          leaf-list demux-source {
            ordered-by user;
            type string;
          }
          leaf-list demux-destination {
            ordered-by user;
            type string;
          }
          leaf encapsulation {
            type string;
          }
          leaf mtu {
            type uint32;
          }
          choice choice-32 {
            leaf point-to-point {
              type empty;
            }
            leaf multipoint {
              type empty;
            }
          }
          leaf bandwidth {
            type string;
          }
          container radio-router {
            presence "enable radio-router";
            uses dynamic-ifbw-parms-type;
          }
          leaf traps {
            type empty;
          }
          leaf no-traps {
            type empty;
          }
          container arp-resp {
            presence "enable arp-resp";
            choice choice-3 {
              leaf unrestricted {
                type empty;
              }
              leaf restricted {
                type empty;
              }
            }
          }
          container proxy-arp {
            presence "enable proxy-arp";
            choice choice-3 {
              leaf unrestricted {
                type empty;
              }
              leaf restricted {
                type empty;
              }
            }
          }
          choice choice-45 {
            leaf vlan-id {
              type string;
            }
            leaf vlan-id-range {
              type string;
            }
            leaf-list vlan-id-list {
              type string;
            }
            container vlan-tags {
              presence "";
              leaf outer {
                type string;
              }
              choice choice-5 {
                leaf inner {
                  type string;
                }
                leaf inner-range {
                  type string;
                }
                leaf-list inner-list {
                  type string;
                }
              }
            }
          }
          leaf native-inner-vlan-id {
            type uint32;
          }
          container inner-vlan-id-range {
            presence "";
            leaf start {
              type uint32;
            }
            leaf end {
              type uint32;
            }
          }
          container accept-source-mac {
            uses apply-group;
            uses apply-macro;
            list mac-address {
              key "name";
              uses mac-list;
            }
          }
          container input-vlan-map {
            uses vlan-map;
          }
          container output-vlan-map {
            uses vlan-map;
          }
          leaf receive-lsp {
            type string;
          }
          leaf transmit-lsp {
            type string;
          }
          leaf dlci {
            type uint32;
          }
          leaf multicast-dlci {
            type uint32;
          }
          choice choice-64 {
            leaf vci {
              type atm-vci;
            }
            leaf allow-any-vci {
              type empty;
            }
            leaf vpi {
              type uint32;
            }
            leaf trunk-id {
              type uint32;
            }
          }
          container atm-l2circuit-mode {
            choice choice-3 {
              leaf cell {
                type empty;
              }
              leaf aal5 {
                type empty;
              }
            }
          }
          container vci-range {
            presence "";
            leaf start {
              type uint16;
            }
            leaf end {
              type uint16;
            }
          }
          leaf trunk-bandwidth {
            type string;
          }
          leaf multicast-vci {
            type atm-vci;
          }
          container shaping {
            uses dcd-shaping-config;
          }
          container oam-period {
            choice choice-3 {
              leaf oam-period {
                type uint32;
              }
              container disable {
                presence "enable disable";
              }
            }
          }
          container oam-liveness {
            uses apply-group;
            uses apply-macro;
            leaf up-count {
              type uint32;
            }
            leaf down-count {
              type uint32;
            }
          }
          container ppp-options {
            uses ppp-options-type;
          }
          container pppoe-options {
            presence "";
            uses pppoe-options-type;
          }
          container pppoe-underlying-options {
            uses pppoe-underlying-options-type;
          }
          container demux-options {
            presence "";
            uses demux-options-type;
          }
          choice choice-87 {
            container keepalives {
              presence "enable keepalives";
              uses keepalives-type;
            }
            leaf no-keepalives {
              type empty;
            }
          }
          leaf inverse-arp {
            type empty;
          }
          leaf transmit-weight {
            type uint16;
          }
          container epd-threshold {
            presence "";
            uses epd-threshold-config;
          }
          leaf cell-bundle-size {
            type uint32;
          }
          leaf plp-to-clp {
            type empty;
          }
          leaf atm-scheduler-map {
            type string;
          }
          leaf mrru {
            type uint16;
          }
          leaf short-sequence {
            type empty;
          }
          leaf fragment-threshold {
            type uint32;
          }
          leaf drop-timeout {
            type uint16;
          }
          leaf disable-mlppp-inner-ppp-pfc {
            type empty;
          }
          leaf minimum-links {
            type uint16;
          }
          leaf multilink-max-classes {
            type uint16;
          }
          container compression {
            presence "enable compression";
            uses apply-group;
            uses apply-macro;
            container rtp {
              presence "enable rtp";
              uses apply-group;
              uses apply-macro;
              leaf f-max-period {
                type uint32;
              }
              leaf-list queues {
                ordered-by user;
                type string;
              }
              container port {
                presence "";
                leaf minimum {
                  type uint32;
                }
                leaf maximum {
                  type uint32;
                }
              }
              container maximum-contexts {
                leaf number {
                  type uint32;
                }
              }
            }
          }
          leaf interleave-fragments {
            type empty;
          }
          leaf link-layer-overhead {
            type unsigned-float;
          }
          leaf accounting-profile {
            type string;
          }
          leaf peer-unit {
            type uint32;
          }
          container tunnel {
            presence "";
            uses apply-group;
            uses apply-macro;
            leaf source {
              type ipv4addr;
            }
            leaf destination {
              type ipv4addr;
            }
            leaf key {
              type uint32;
            }
            leaf backup-destination {
              type ipv4addr;
            }
            choice choice-11 {
              leaf allow-fragmentation {
                type empty;
              }
              leaf do-not-fragment {
                type empty;
              }
            }
            leaf ttl {
              type uint32;
            }
            leaf path-mtu-discovery {
              type empty;
            }
            leaf no-path-mtu-discovery {
              type empty;
            }
            container routing-instance {
              uses apply-group;
              uses apply-macro;
              leaf destination {
                type string;
              }
            }
          }
          leaf compression-device {
            type interface-unit;
          }
          container layer2-policer {
            uses apply-group;
            uses apply-macro;
            choice choice-3 {
              leaf input-policer {
                type string;
              }
              leaf input-hierarchical-policer {
                type string;
              }
              leaf input-three-color {
                type string;
              }
            }
            choice choice-4 {
              leaf output-policer {
                type string;
              }
              leaf output-three-color {
                type string;
              }
            }
          }
          container filter {
            uses apply-group;
            uses apply-macro;
            leaf input {
              type string;
            }
            leaf output {
              type string;
            }
          }
          leaf statistics {
            type empty;
          }
          container esi {
            presence "";
            uses apply-group;
            uses apply-macro;
            container apply-advanced {
              uses apply-group;
              uses apply-macro;
            }
            leaf identifier {
              mandatory true;
              type string;
            }
            choice choice-single-active {
              leaf single-active {
                type empty;
              }
              leaf all-active {
                type empty;
              }
            }
          }
          container family {
            uses apply-group;
            uses apply-macro;
            container inet {
              presence "enable inet";
              uses apply-group;
              uses apply-macro;
              container targeted-broadcast {
                presence "enable targeted-broadcast";
                uses apply-group;
                uses apply-macro;
                choice choice-3 {
                  leaf forward-and-send-to-re {
                    type empty;
                  }
                  leaf forward-only {
                    type empty;
                  }
                }
              }
              leaf receive-options-packets {
                type empty;
              }
              leaf receive-ttl-exceeded {
                type empty;
              }
              container accounting {
                uses apply-group;
                uses apply-macro;
                container source-class-usage {
                  uses apply-group;
                  uses apply-macro;
                  leaf input {
                    type empty;
                  }
                  leaf output {
                    type empty;
                  }
                }
                leaf destination-class-usage {
                  type empty;
                }
              }
              leaf mac-validate {
                type string;
              }
              container rpf-check {
                presence "enable rpf-check";
                uses apply-group;
                uses apply-macro;
                leaf fail-filter {
                  type string;
                }
                container mode {
                  leaf loose {
                    type empty;
                  }
                }
              }
              leaf mtu {
                type uint32;
              }
              leaf no-redirects {
                type empty;
              }
              leaf no-neighbor-learn {
                type empty;
              }
              leaf multicast-only {
                type empty;
              }
              leaf primary {
                type empty;
              }
              leaf ipsec-sa {
                type string;
              }
              list demux-source {
                key "name";
                ordered-by user;
                leaf name {
                  type string;
                }
                uses apply-group;
                uses apply-macro;
              }
              list demux-destination {
                key "name";
                ordered-by user;
                leaf name {
                  type string;
                }
                uses apply-group;
                uses apply-macro;
              }
              container filter {
                uses apply-group;
                uses apply-macro;
                choice choice-3 {
                  container input {
                    presence "";
                    leaf filter-name {
                      type string;
                    }
                    leaf precedence {
                      type uint32;
                    }
                  }
                  leaf-list input-list {
                    type string;
                    ordered-by user;
                  }
                }
                choice choice-4 {
                  container output {
                    presence "";
                    leaf filter-name {
                      type string;
                    }
                    leaf precedence {
                      type uint32;
                    }
                  }
                  leaf-list output-list {
                    type string;
                    ordered-by user;
                  }
                }
                container adf {
                  presence "";
                  uses apply-group;
                  uses apply-macro;
                  list rule {
                    key "name";
                    ordered-by user;
                    leaf name {
                      type string;
                    }
                    uses apply-group;
                    uses apply-macro;
                  }
                  leaf counter {
                    type empty;
                  }
                  leaf input-precedence {
                    type uint32;
                  }
                  leaf output-precedence {
                    type uint32;
                  }
                }
                leaf group {
                  type uint32;
                }
              }
              container simple-filter {
                uses apply-group;
                uses apply-macro;
                leaf input {
                  type string;
                }
              }
              leaf input-hierarchical-policer {
                type string;
              }
              container policer {
                uses apply-group;
                uses apply-macro;
                leaf arp {
                  type string;
                }
                leaf input {
                  type string;
                }
                leaf output {
                  type string;
                }
              }
              container sampling {
                uses apply-group;
                uses apply-macro;
                leaf input {
                  type empty;
                }
                leaf output {
                  type empty;
                }
              }
              list next-hop-tunnel {
                key "name";
                ordered-by user;
                leaf name {
                  type string;
                }
                uses apply-group;
                uses apply-macro;
                leaf ipsec-vpn {
                  type string;
                }
              }
              list address {
                key "name";
                ordered-by user;
                leaf name {
                  type ipv4prefix;
                }
                uses apply-group;
                uses apply-macro;
                leaf destination {
                  type ipv4addr;
                }
                leaf destination-profile {
                  type string;
                }
                leaf broadcast {
                  type ipv4addr;
                }
                leaf primary {
                  type empty;
                }
                leaf preferred {
                  type empty;
                }
                leaf master-only {
                  type empty;
                }
                list multipoint-destination {
                  key "name";
                  ordered-by user;
                  leaf name {
                    type ipv4addr;
                  }
                  uses apply-group;
                  uses apply-macro;
                  choice choice-3 {
                    leaf dlci {
                      type uint32;
                    }
                    leaf vci {
                      type atm-vci;
                    }
                  }
                  container shaping {
                    uses dcd-shaping-config;
                  }
                  container oam-period {
                    choice choice-3 {
                      leaf oam_period {
                        type uint32;
                      }
                      container disable {
                        presence "enable disable";
                      }
                    }
                  }
                  container oam-liveness {
                    uses apply-group;
                    uses apply-macro;
                    leaf up-count {
                      type uint32;
                    }
                    leaf down-count {
                      type uint32;
                    }
                  }
                  leaf inverse-arp {
                    type empty;
                  }
                  leaf transmit-weight {
                    type uint16;
                  }
                  container epd-threshold {
                    presence "";
                    uses epd-threshold-config;
                  }
                }
                list arp {
                  key "name";
                  ordered-by user;
                  leaf name {
                    type ipv4addr;
                  }
                  leaf l2-interface {
                    type interface-name;
                  }
                  choice choice-5 {
                    leaf mac {
                      type mac-unicaset;
                    }
                    leaf multicast-mac {
                      type mac-multicast;
                    }
                  }
                  leaf publish {
                    type empty;
                  }
                }
                container web-authentication {
                  uses apply-group;
                  uses apply-macro;
                  leaf http {
                    type empty;
                  }
                }
                list vrrp-group {
                  key "name";
                  ordered-by user;
                  uses vrrp-group;
                }
              }
              container unnumbered-address {
                presence "";
                leaf source {
                  type interface-unit;
                }
                leaf preferred-source-address {
                  type string;
                }
                leaf destination {
                  type ipv4addr;
                }
                leaf destination-profile {
                  type string;
                }
              }
              container location-pool-address {
                presence "enable location-pool-address";
                uses apply-group;
                uses apply-macro;
                leaf pool-name {
                  type string;
                }
              }
              leaf negotiate-address {
                type empty;
              }
              container dhcp {
                presence "enable dhcp";
                uses apply-group;
                uses apply-macro;
                container client-identifier {
                  choice choice-3 {
                    leaf ascii {
                      type string;
                    }
                    leaf hexadecimal {
                      type string;
                    }
                  }
                }
                leaf lease-time {
                  type string;
                }
                leaf retransmission-attempt {
                  type uint32;
                }
                leaf retransmission-interval {
                  type uint32;
                }
                leaf server-address {
                  type ipv4addr;
                }
                leaf update-server {
                  type empty;
                }
                leaf vendor-id {
                  type string;
                }
              }
            }
            container iso {
              presence "enable iso";
              uses apply-group;
              uses apply-macro;
              list address {
                key "name";
                ordered-by user;
                leaf name {
                  type isoaddr;
                }
                uses apply-group;
                uses apply-macro;
              }
              leaf mtu {
                type uint32;
              }
            }
            container inet6 {
              presence "enable inet6";
              uses apply-group;
              uses apply-macro;
              container rpf-check {
                presence "enable rpf-check";
                uses apply-group;
                uses apply-macro;
                leaf fail-filter {
                  type string;
                }
                container mode {
                  leaf loose {
                    type empty;
                  }
                }
              }
              container accounting {
                uses apply-group;
                uses apply-macro;
                container source-class-usage {
                  uses apply-group;
                  uses apply-macro;
                  leaf input {
                    type empty;
                  }
                  leaf output {
                    type empty;
                  }
                }
                leaf destination-class-usage {
                  type empty;
                }
              }
              leaf mtu {
                type uint32;
              }
              leaf no-neighbor-learn {
                type empty;
              }
              container filter {
                uses apply-group;
                uses apply-macro;
                choice choice-3 {
                  container input {
                    presence "";
                    leaf filter-name {
                      type string;
                    }
                    leaf precedence {
                      type uint32;
                    }
                  }
                  leaf-list input-list {
                    type string;
                    ordered-by user;
                  }
                }
                choice choice-4 {
                  container output {
                    presence "";
                    leaf filter-name {
                      type string;
                    }
                    leaf precedence {
                      type uint32;
                    }
                  }
                  leaf-list output-list {
                    type string;
                    ordered-by user;
                  }
                }
                container adf {
                  presence "";
                  uses apply-group;
                  uses apply-macro;
                  list rule {
                    key "name";
                    ordered-by user;
                    leaf name {
                      type string;
                    }
                    uses apply-group;
                    uses apply-macro;
                  }
                  leaf counter {
                    type empty;
                  }
                  leaf input-precedence {
                    type uint32;
                  }
                  leaf output-precedence {
                    type uint32;
                  }
                }
                leaf group {
                  type uint32;
                }
              }
              leaf input-hierarchical-policer {
                type string;
              }
              container policer {
                uses apply-group;
                uses apply-macro;
                leaf input {
                  type string;
                }
                leaf output {
                  type string;
                }
              }
              container sampling {
                uses apply-group;
                uses apply-macro;
                leaf input {
                  type empty;
                }
                leaf output {
                  type empty;
                }
              }
              list address {
                key "name";
                ordered-by user;
                leaf name {
                  type ipv6prefix;
                }
                uses apply-group;
                uses apply-macro;
                leaf destination {
                  type ipv6addr;
                }
                leaf eui-64 {
                  type empty;
                }
                leaf primary {
                  type empty;
                }
                leaf preferred {
                  type empty;
                }
                leaf master-only {
                  type empty;
                }
                list ndp {
                  key "name";
                  ordered-by user;
                  leaf name {
                    type ipv6addr;
                  }
                  leaf l2-interface {
                    type interface-name;
                  }
                  choice choice-5 {
                    leaf mac {
                      type mac-unicaset;
                    }
                    leaf multicast-mac {
                      type mac-multicast;
                    }
                  }
                  leaf publish {
                    type empty;
                  }
                }
                list vrrp-inet6-group {
                  key "name";
                  ordered-by user;
                  uses vrrp-group;
                }
              }
              list demux-source {
                key "name";
                ordered-by user;
                leaf name {
                  type string;
                }
                uses apply-group;
                uses apply-macro;
              }
              list demux-destination {
                key "name";
                ordered-by user;
                leaf name {
                  type string;
                }
                uses apply-group;
                uses apply-macro;
              }
              container unnumbered-address {
                presence "";
                leaf source {
                  type interface-unit;
                }
                leaf preferred-source-address {
                  type string;
                }
              }
              leaf dad-disable {
                type empty;
              }
              leaf no-dad-disable {
                type empty;
              }
            }
            container mpls {
              presence "enable mpls";
              uses apply-group;
              uses apply-macro;
              leaf mtu {
                type uint32;
              }
              leaf maximum-labels {
                type uint32;
              }
              container filter {
                uses apply-group;
                uses apply-macro;
                choice choice-3 {
                  leaf input {
                    type string;
                  }
                  leaf-list input-list {
                    type string;
                    ordered-by user;
                  }
                }
                choice choice-4 {
                  leaf output {
                    type string;
                  }
                  leaf-list output-list {
                    type string;
                    ordered-by user;
                  }
                }
                leaf group {
                  type uint32;
                }
              }
              leaf input-hierarchical-policer {
                type string;
              }
              container policer {
                uses apply-group;
                uses apply-macro;
                leaf input {
                  type string;
                }
                leaf output {
                  type string;
                }
              }
            }
            container mlppp {
              presence "";
              uses apply-group;
              uses apply-macro;
              leaf bundle {
                type interface-unit;
              }
            }
            container mlfr-end-to-end {
              presence "";
              uses apply-group;
              uses apply-macro;
              leaf bundle {
                type interface-unit;
              }
            }
            container mlfr-uni-nni {
              presence "";
              uses apply-group;
              uses apply-macro;
              leaf bundle {
                type interface-unit;
              }
            }
            container ccc {
              presence "enable ccc";
              uses apply-group;
              uses apply-macro;
              container filter {
                uses apply-group;
                uses apply-macro;
                choice choice-3 {
                  leaf input {
                    type string;
                  }
                  leaf-list input-list {
                    type string;
                    ordered-by user;
                  }
                }
                choice choice-4 {
                  leaf output {
                    type string;
                  }
                  leaf-list output-list {
                    type string;
                    ordered-by user;
                  }
                }
                leaf group {
                  type uint32;
                }
              }
              container policer {
                uses apply-group;
                uses apply-macro;
                leaf input {
                  type string;
                }
                leaf output {
                  type string;
                }
              }
              leaf translate-fecn-and-becn {
                type empty;
              }
              choice choice-9 {
                leaf translate-discard-eligible {
                  type empty;
                }
                leaf translate-plp-control-word-de {
                  type empty;
                }
              }
              leaf keep-address-and-control {
                type empty;
              }
            }
            container tcc {
              presence "enable tcc";
              uses apply-group;
              uses apply-macro;
              container policer {
                uses apply-group;
                uses apply-macro;
                leaf input {
                  type string;
                }
                leaf output {
                  type string;
                }
              }
              container proxy {
                presence "enable proxy";
                uses apply-group;
                uses apply-macro;
                leaf inet-address {
                  type ipv4addr;
                }
              }
              container remote {
                presence "enable remote";
                uses apply-group;
                uses apply-macro;
                leaf inet-address {
                  type ipv4addr;
                }
                leaf mac-address {
                  type mac-addr;
                }
              }
              leaf-list protocols {
                ordered-by user;
                type string;
              }
            }
            container vpls {
              presence "enable vpls";
              uses apply-group;
              uses apply-macro;
              leaf core-facing {
                type empty;
              }
              container filter {
                uses apply-group;
                uses apply-macro;
                choice choice-3 {
                  container input {
                    presence "";
                    leaf filter-name {
                      type string;
                    }
                    leaf precedence {
                      type uint32;
                    }
                  }
                  leaf-list input-list {
                    type string;
                    ordered-by user;
                  }
                }
                choice choice-4 {
                  container output {
                    presence "";
                    leaf filter-name {
                      type string;
                    }
                    leaf precedence {
                      type uint32;
                    }
                  }
                  leaf-list output-list {
                    type string;
                    ordered-by user;
                  }
                }
                container adf {
                  presence "";
                  uses apply-group;
                  uses apply-macro;
                  list rule {
                    key "name";
                    ordered-by user;
                    leaf name {
                      type string;
                    }
                    uses apply-group;
                    uses apply-macro;
                  }
                  leaf counter {
                    type empty;
                  }
                  leaf input-precedence {
                    type uint32;
                  }
                  leaf output-precedence {
                    type uint32;
                  }
                }
                leaf group {
                  type uint32;
                }
              }
              container policer {
                uses apply-group;
                uses apply-macro;
                leaf input {
                  type string;
                }
                leaf output {
                  type string;
                }
              }
            }
            container bridge {
              presence "enable bridge";
              uses apply-group;
              uses apply-macro;
              leaf core-facing {
                type empty;
              }
              container filter {
                uses apply-group;
                uses apply-macro;
                choice choice-3 {
                  container input {
                    presence "";
                    leaf filter-name {
                      type string;
                    }
                    leaf precedence {
                      type uint32;
                    }
                  }
                  leaf-list input-list {
                    type string;
                    ordered-by user;
                  }
                }
                choice choice-4 {
                  container output {
                    presence "";
                    leaf filter-name {
                      type string;
                    }
                    leaf precedence {
                      type uint32;
                    }
                  }
                  leaf-list output-list {
                    type string;
                    ordered-by user;
                  }
                }
                container adf {
                  presence "";
                  uses apply-group;
                  uses apply-macro;
                  list rule {
                    key "name";
                    ordered-by user;
                    leaf name {
                      type string;
                    }
                    uses apply-group;
                    uses apply-macro;
                  }
                  leaf counter {
                    type empty;
                  }
                  leaf input-precedence {
                    type uint32;
                  }
                  leaf output-precedence {
                    type uint32;
                  }
                }
                leaf group {
                  type uint32;
                }
              }
              container policer {
                uses apply-group;
                uses apply-macro;
                leaf input {
                  type string;
                }
                leaf output {
                  type string;
                }
              }
              leaf interface-mode {
                type string;
              }
              leaf bridge-domain-type {
                type string;
              }
              choice choice-13 {
                leaf vlan-id {
                  type uint32;
                }
                leaf-list vlan-id-list {
                  type string;
                  ordered-by user;
                }
                leaf-list inner-vlan-id-list {
                  type string;
                  ordered-by user;
                }
              }
              container vlan-rewrite {
                uses apply-group;
                uses apply-macro;
                list translate {
                  key "name";
                  ordered-by user;
                  leaf name {
                    type string;
                  }
                  leaf to-vlan-id {
                    type uint32;
                  }
                }
              }
              choice choice-16 {
                leaf isid-list {
                  type string;
                }
              }
            }
            container ethernet-switching {
              presence "enable ethernet-switching";
              uses ethernet-switching-type;
            }
            container fibre-channel {
              presence "enable fibre-channel";
              uses fibre-channel-type;
            }
            container any {
              presence "enable any";
              uses apply-group;
              uses apply-macro;
              container filter {
                uses apply-group;
                uses apply-macro;
                leaf input {
                  type string;
                }
                leaf group {
                  type uint32;
                }
              }
            }
          }
          leaf service-domain {
            type string;
          }
          leaf copy-tos-to-outer-ip-header {
            type empty;
          }
        }
        container no-partition {
          leaf interface-type {
            type string;
          }
        }
        list partition {
          key "name";
          ordered-by user;
          leaf name {
            type string;
          }
          leaf oc-slice {
            type string;
          }
          leaf timeslots {
            type string;
          }
          leaf interface-type {
            type string;
          }
        }
        container cellular-options {
          presence "enable cellular-options";
          uses apply-group;
          uses apply-macro;
          container gsm-options {
            presence "enable gsm-options";
            uses apply-group;
            uses apply-macro;
            container select-profile {
              presence "";
              leaf profile-id {
                type uint32;
              }
            }
            leaf encrypted-sim-unlock-code {
              type unreadable;
            }
          }
        }
      }
      list interface {
        key "name";
        uses interfaces-type;
      }
    }
    container protocols {
      uses apply-group;
      uses apply-macro;
      container igmp {
        presence "enable igmp";
        uses apply-group;
        uses apply-macro;
        container traceoptions {
          uses apply-group;
          uses apply-macro;
          container file {
            presence "";
            uses trace-file-type;
          }
          list flag {
            key "name";
            ordered-by user;
            leaf name {
              type string;
            }
            leaf send {
              type empty;
            }
            leaf receive {
              type empty;
            }
            leaf detail {
              type empty;
            }
            leaf disable {
              type empty;
            }
          }
        }
        leaf query-interval {
          type uint32;
        }
        leaf query-response-interval {
          type string;
        }
        leaf query-last-member-interval {
          type string;
        }
        leaf robust-count {
          type uint32;
        }
        leaf maximum-transmit-rate {
          type uint32;
        }
        leaf accounting {
          type empty;
        }
        list interface {
          key "name";
          ordered-by user;
          leaf name {
            type string;
          }
          uses apply-group;
          uses apply-macro;
          choice choice-3 {
            leaf disable {
              type empty;
            }
          }
          leaf version {
            type uint8;
          }
          container static {
            uses apply-group;
            uses apply-macro;
            list group {
              key "name";
              ordered-by user;
              leaf name {
                type ipv4addr;
              }
              uses apply-group;
              uses apply-macro;
              leaf group-increment {
                type ipv4addr;
              }
              leaf group-count {
                type uint32;
              }
              leaf exclude {
                type empty;
              }
              list source {
                key "name";
                ordered-by user;
                leaf name {
                  type ipv4addr;
                }
                uses apply-group;
                uses apply-macro;
                leaf source-increment {
                  type ipv4addr;
                }
                leaf source-count {
                  type uint32;
                }
              }
            }
          }
          leaf ssm-map {
            type string;
          }
          leaf immediate-leave {
            type empty;
          }
          leaf promiscuous-mode {
            type empty;
          }
          leaf accounting {
            type empty;
          }
          leaf no-accounting {
            type empty;
          }
          leaf-list group-policy {
            type policy-algebra;
            ordered-by user;
          }
          leaf group-limit {
            type uint16;
          }
          container passive {
            presence "enable passive";
            leaf allow-receive {
              type empty;
            }
            leaf send-general-query {
              type empty;
            }
            leaf send-group-query {
              type empty;
            }
          }
          leaf-list oif-map {
            type policy-algebra;
            ordered-by user;
          }
        }
      }
      container mld {
        presence "enable mld";
        uses apply-group;
        uses apply-macro;
        container traceoptions {
          uses apply-group;
          uses apply-macro;
          container file {
            presence "";
            uses trace-file-type;
          }
          list flag {
            key "name";
            ordered-by user;
            leaf name {
              type string;
            }
            leaf send {
              type empty;
            }
            leaf receive {
              type empty;
            }
            leaf detail {
              type empty;
            }
            leaf disable {
              type empty;
            }
          }
        }
        leaf query-interval {
          type uint32;
        }
        leaf query-response-interval {
          type string;
        }
        leaf query-last-member-interval {
          type string;
        }
        leaf robust-count {
          type uint32;
        }
        leaf maximum-transmit-rate {
          type uint32;
        }
        leaf accounting {
          type empty;
        }
        list interface {
          key "name";
          ordered-by user;
          leaf name {
            type string;
          }
          uses apply-group;
          uses apply-macro;
          choice choice-3 {
            leaf disable {
              type empty;
            }
          }
          leaf version {
            type uint8;
          }
          container static {
            uses apply-group;
            uses apply-macro;
            list group {
              key "name";
              ordered-by user;
              leaf name {
                type ipv6addr;
              }
              uses apply-group;
              uses apply-macro;
              leaf group-increment {
                type ipv6addr;
              }
              leaf group-count {
                type uint32;
              }
              leaf exclude {
                type empty;
              }
              list source {
                key "name";
                ordered-by user;
                leaf name {
                  type ipv6addr;
                }
                uses apply-group;
                uses apply-macro;
                leaf source-increment {
                  type ipv6addr;
                }
                leaf source-count {
                  type uint32;
                }
              }
            }
          }
          leaf ssm-map {
            type string;
          }
          leaf immediate-leave {
            type empty;
          }
          leaf-list group-policy {
            type policy-algebra;
            ordered-by user;
          }
          leaf group-limit {
            type uint16;
          }
          leaf accounting {
            type empty;
          }
          leaf no-accounting {
            type empty;
          }
          container passive {
            presence "enable passive";
            leaf allow-receive {
              type empty;
            }
            leaf send-general-query {
              type empty;
            }
            leaf send-group-query {
              type empty;
            }
          }
          leaf-list oif-map {
            type policy-algebra;
            ordered-by user;
          }
        }
      }
      container router-advertisement {
        uses apply-group;
        uses apply-macro;
        container traceoptions {
          uses apply-group;
          uses apply-macro;
          container file {
            presence "";
            uses trace-file-type;
          }
          list flag {
            key "name";
            ordered-by user;
            leaf name {
              type string;
            }
          }
        }
        list interface {
          key "name";
          ordered-by user;
          leaf name {
            type string;
          }
          uses apply-group;
          uses apply-macro;
          leaf max-advertisement-interval {
            type uint32;
          }
          leaf min-advertisement-interval {
            type uint32;
          }
          leaf managed-configuration {
            type empty;
          }
          leaf no-managed-configuration {
            type empty;
          }
          leaf other-stateful-configuration {
            type empty;
          }
          leaf no-other-stateful-configuration {
            type empty;
          }
          leaf link-mtu {
            type empty;
          }
          leaf no-link-mtu {
            type empty;
          }
          leaf reachable-time {
            type uint32;
          }
          leaf retransmit-timer {
            type uint32;
          }
          leaf virtual-router-only {
            type empty;
          }
          leaf current-hop-limit {
            type uint32;
          }
          leaf default-lifetime {
            type uint32;
          }
          list prefix {
            key "name";
            ordered-by user;
            leaf name {
              type ipv6prefix;
            }
            uses apply-group;
            uses apply-macro;
            leaf valid-lifetime {
              type uint32;
            }
            leaf on-link {
              type empty;
            }
            leaf no-on-link {
              type empty;
            }
            leaf preferred-lifetime {
              type uint32;
            }
            leaf autonomous {
              type empty;
            }
            leaf no-autonomous {
              type empty;
            }
          }
        }
      }
      container pim {
        list interface {
          key "name";
          ordered-by user;
          leaf name {
            type interface-name;
          }
          leaf mode {
            type string;
          }
        }
      }
    }
    container class-of-service {
      uses juniper-class-of-service-options;
    }
    container routing-options {
      uses apply-group;
      uses apply-macro;
      list rib {
        key "name";
        ordered-by user;
        leaf name {
          type string;
        }
        uses apply-group;
        uses apply-macro;
        container static {
          uses apply-group;
          uses apply-macro;
          leaf rib-group {
            type string;
          }
          container defaults {
            uses apply-group;
            uses apply-macro;
            leaf retain {
              type empty;
            }
            leaf no-retain {
              type empty;
            }
            leaf install {
              type empty;
            }
            leaf no-install {
              type empty;
            }
            leaf readvertise {
              type empty;
            }
            leaf no-readvertise {
              type empty;
            }
            leaf resolve {
              type empty;
            }
            leaf no-resolve {
              type empty;
            }
            choice choice-19 {
              leaf active {
                type empty;
              }
              leaf passive {
                type empty;
              }
            }
            container metric {
              presence "";
              uses rib-static-metric-type;
            }
            container metric2 {
              presence "";
              uses rib-static-metric-type;
            }
            container metric3 {
              presence "";
              uses rib-static-metric-type;
            }
            container metric4 {
              presence "";
              uses rib-static-metric-type;
            }
            container tag {
              presence "";
              uses rib-static-metric-type;
            }
            container tag2 {
              presence "";
              uses rib-static-metric-type;
            }
            container preference {
              presence "";
              uses rib-static-metric-type;
            }
            container preference2 {
              presence "";
              uses rib-static-metric-type;
            }
            container color {
              presence "";
              uses rib-static-metric-type;
            }
            container color2 {
              presence "";
              uses rib-static-metric-type;
            }
            leaf-list community {
              type community;
              ordered-by user;
            }
            container as-path {
              uses apply-group;
              uses apply-macro;
              leaf path {
                type string;
              }
              leaf origin {
                type string;
              }
              leaf atomic-aggregate {
                type empty;
              }
              container aggregator {
                presence "";
                uses apply-group;
                uses apply-macro;
                leaf as-number {
                  type string;
                }
                leaf address {
                  type ipv4addr;
                }
              }
            }
          }
          list route {
            key "name";
            ordered-by user;
            leaf name {
              type ipprefix;
            }
            uses apply-group;
            uses apply-macro;
            choice choice-3 {
              leaf-list next-hop {
                type ipaddr-or-interface;
                ordered-by user;
              }
              leaf reject {
                type empty;
              }
              leaf discard {
                type empty;
              }
              leaf receive {
                type empty;
              }
              leaf next-table {
                type string;
              }
            }
            list qualified-next-hop {
              key "name";
              ordered-by user;
              uses qualified-nh-obj;
            }
            list lsp-next-hop {
              key "name";
              ordered-by user;
              uses lsp-nh-obj;
            }
            list static-lsp-next-hop {
              key "name";
              ordered-by user;
              uses lsp-nh-obj;
            }
            list p2mp-lsp-next-hop {
              key "name";
              ordered-by user;
              uses lsp-nh-obj;
            }
            leaf backup-pe-group {
              type string;
            }
            container bfd-liveness-detection {
              uses apply-group;
              uses apply-macro;
              leaf version {
                type string;
              }
              leaf minimum-interval {
                type uint32;
              }
              leaf minimum-receive-interval {
                type uint32;
              }
              leaf multiplier {
                type uint32;
              }
              choice choice-11 {
                leaf no-adaptation {
                  type empty;
                }
              }
              container transmit-interval {
                uses apply-group;
                uses apply-macro;
                leaf minimum-interval {
                  type uint32;
                }
                leaf threshold {
                  type uint32;
                }
              }
              container detection-time {
                uses apply-group;
                uses apply-macro;
                leaf threshold {
                  type uint32;
                }
              }
              container authentication {
                uses apply-group;
                uses apply-macro;
                leaf key-chain {
                  type string;
                }
                leaf algorithm {
                  type string;
                }
                leaf loose-check {
                  type empty;
                }
              }
              leaf neighbor {
                type ipaddr;
              }
              leaf local-address {
                type ipaddr;
              }
              leaf holddown-interval {
                type uint32;
              }
              leaf minimum-receive-ttl {
                type uint8;
              }
            }
            leaf retain {
              type empty;
            }
            leaf no-retain {
              type empty;
            }
            leaf install {
              type empty;
            }
            leaf no-install {
              type empty;
            }
            leaf readvertise {
              type empty;
            }
            leaf no-readvertise {
              type empty;
            }
            leaf resolve {
              type empty;
            }
            leaf no-resolve {
              type empty;
            }
            choice choice-32 {
              leaf active {
                type empty;
              }
              leaf passive {
                type empty;
              }
            }
            container metric {
              presence "";
              uses rib-static-metric-type;
            }
            container metric2 {
              presence "";
              uses rib-static-metric-type;
            }
            container metric3 {
              presence "";
              uses rib-static-metric-type;
            }
            container metric4 {
              presence "";
              uses rib-static-metric-type;
            }
            container tag {
              presence "";
              uses rib-static-metric-type;
            }
            container tag2 {
              presence "";
              uses rib-static-metric-type;
            }
            container preference {
              presence "";
              uses rib-static-metric-type;
            }
            container preference2 {
              presence "";
              uses rib-static-metric-type;
            }
            container color {
              presence "";
              uses rib-static-metric-type;
            }
            container color2 {
              presence "";
              uses rib-static-metric-type;
            }
            leaf-list community {
              type community;
              ordered-by user;
            }
            container as-path {
              uses apply-group;
              uses apply-macro;
              leaf path {
                type string;
              }
              leaf origin {
                type string;
              }
              leaf atomic-aggregate {
                type empty;
              }
              container aggregator {
                presence "";
                uses apply-group;
                uses apply-macro;
                leaf as-number {
                  type string;
                }
                leaf address {
                  type ipv4addr;
                }
              }
            }
          }
          list iso-route {
            key "name";
            ordered-by user;
            leaf name {
              type isoprefix;
            }
            uses apply-group;
            uses apply-macro;
            choice choice-3 {
              leaf-list next-hop {
                type ipaddr-or-interface;
                ordered-by user;
              }
              leaf reject {
                type empty;
              }
              leaf discard {
                type empty;
              }
              leaf receive {
                type empty;
              }
              leaf next-table {
                type string;
              }
            }
            list qualified-next-hop {
              key "name";
              ordered-by user;
              uses qualified-nh-obj;
            }
            list lsp-next-hop {
              key "name";
              ordered-by user;
              uses lsp-nh-obj;
            }
            list static-lsp-next-hop {
              key "name";
              ordered-by user;
              uses lsp-nh-obj;
            }
            list p2mp-lsp-next-hop {
              key "name";
              ordered-by user;
              uses lsp-nh-obj;
            }
            leaf backup-pe-group {
              type string;
            }
            container bfd-liveness-detection {
              uses apply-group;
              uses apply-macro;
              leaf version {
                type string;
              }
              leaf minimum-interval {
                type uint32;
              }
              leaf minimum-receive-interval {
                type uint32;
              }
              leaf multiplier {
                type uint32;
              }
              choice choice-11 {
                leaf no-adaptation {
                  type empty;
                }
              }
              container transmit-interval {
                uses apply-group;
                uses apply-macro;
                leaf minimum-interval {
                  type uint32;
                }
                leaf threshold {
                  type uint32;
                }
              }
              container detection-time {
                uses apply-group;
                uses apply-macro;
                leaf threshold {
                  type uint32;
                }
              }
              container authentication {
                uses apply-group;
                uses apply-macro;
                leaf key-chain {
                  type string;
                }
                leaf algorithm {
                  type string;
                }
                leaf loose-check {
                  type empty;
                }
              }
              leaf neighbor {
                type ipaddr;
              }
              leaf local-address {
                type ipaddr;
              }
              leaf holddown-interval {
                type uint32;
              }
              leaf minimum-receive-ttl {
                type uint8;
              }
            }
            leaf retain {
              type empty;
            }
            leaf no-retain {
              type empty;
            }
            leaf install {
              type empty;
            }
            leaf no-install {
              type empty;
            }
            leaf readvertise {
              type empty;
            }
            leaf no-readvertise {
              type empty;
            }
            leaf resolve {
              type empty;
            }
            leaf no-resolve {
              type empty;
            }
            choice choice-32 {
              leaf active {
                type empty;
              }
              leaf passive {
                type empty;
              }
            }
            container metric {
              presence "";
              uses rib-static-metric-type;
            }
            container metric2 {
              presence "";
              uses rib-static-metric-type;
            }
            container metric3 {
              presence "";
              uses rib-static-metric-type;
            }
            container metric4 {
              presence "";
              uses rib-static-metric-type;
            }
            container tag {
              presence "";
              uses rib-static-metric-type;
            }
            container tag2 {
              presence "";
              uses rib-static-metric-type;
            }
            container preference {
              presence "";
              uses rib-static-metric-type;
            }
            container preference2 {
              presence "";
              uses rib-static-metric-type;
            }
            container color {
              presence "";
              uses rib-static-metric-type;
            }
            container color2 {
              presence "";
              uses rib-static-metric-type;
            }
            leaf-list community {
              type community;
              ordered-by user;
            }
            container as-path {
              uses apply-group;
              uses apply-macro;
              leaf path {
                type string;
              }
              leaf origin {
                type string;
              }
              leaf atomic-aggregate {
                type empty;
              }
              container aggregator {
                presence "";
                uses apply-group;
                uses apply-macro;
                leaf as-number {
                  type string;
                }
                leaf address {
                  type ipv4addr;
                }
              }
            }
          }
        }
        list martians {
          key "address key2 key2-arg";
          ordered-by user;
          uses martian-type;
        }
        container aggregate {
          uses rib-aggregate-type;
        }
        container generate {
          uses rib-aggregate-type;
        }
        choice choice-11 {
          container maximum-paths {
            presence "";
            leaf limit {
              type uint32;
            }
            choice choice-5 {
              leaf threshold {
                type uint32;
              }
              leaf log-only {
                type empty;
              }
            }
            leaf log-interval {
              type uint32;
            }
          }
        }
        container maximum-prefixes {
          presence "";
          leaf limit {
            type uint32;
          }
          choice choice-5 {
            leaf threshold {
              type uint32;
            }
            leaf log-only {
              type empty;
            }
          }
          leaf log-interval {
            type uint32;
          }
        }
        container multipath {
          presence "enable multipath";
          uses apply-group;
          uses apply-macro;
          container vpn-unequal-cost {
            presence "enable vpn-unequal-cost";
            leaf equal-external-internal {
              type empty;
            }
          }
          leaf as-path-compare {
            type empty;
          }
        }
        container label {
          presence "enable label";
          uses apply-group;
          uses apply-macro;
          leaf-list allocation {
            type policy-algebra;
            ordered-by user;
          }
          leaf-list substitution {
            type policy-algebra;
            ordered-by user;
          }
        }
        container access {
          uses apply-group;
          uses apply-macro;
          list route {
            key "name";
            ordered-by user;
            leaf name {
              type ipprefix;
            }
            uses apply-group;
            uses apply-macro;
            leaf-list next-hop {
              type ipaddr-or-interface;
              ordered-by user;
            }
            list qualified-next-hop {
              key "name";
              ordered-by user;
              uses qualified-nh-obj;
            }
            leaf metric {
              type uint32;
            }
            leaf preference {
              type uint32;
            }
            leaf tag {
              type string;
            }
          }
        }
        container access-internal {
          uses apply-group;
          uses apply-macro;
          list route {
            key "name";
            ordered-by user;
            leaf name {
              type ipprefix;
            }
            uses apply-group;
            uses apply-macro;
            leaf-list next-hop {
              type ipaddr-or-interface;
              ordered-by user;
            }
            list qualified-next-hop {
              key "name";
              ordered-by user;
              uses qualified-nh-obj;
            }
          }
        }
      }
      container access {
        uses apply-group;
        uses apply-macro;
        list route {
          key "name";
          ordered-by user;
          leaf name {
            type ipprefix;
          }
          uses apply-group;
          uses apply-macro;
          leaf-list next-hop {
            type ipaddr-or-interface;
            ordered-by user;
          }
          list qualified-next-hop {
            key "name";
            ordered-by user;
            uses qualified-nh-obj;
          }
          leaf metric {
            type uint32;
          }
          leaf preference {
            type uint32;
          }
          leaf tag {
            type string;
          }
        }
      }
      container access-internal {
        uses apply-group;
        uses apply-macro;
        list route {
          key "name";
          ordered-by user;
          leaf name {
            type ipprefix;
          }
          uses apply-group;
          uses apply-macro;
          leaf-list next-hop {
            type ipaddr-or-interface;
            ordered-by user;
          }
          list qualified-next-hop {
            key "name";
            ordered-by user;
            uses qualified-nh-obj;
          }
        }
      }
      container multicast {
        uses apply-group;
        uses apply-macro;
        container traceoptions {
          uses apply-group;
          uses apply-macro;
          container file {
            presence "";
            uses trace-file-type;
          }
          list flag {
            key "name";
            ordered-by user;
            leaf name {
              type string;
            }
            leaf disable {
              type empty;
            }
          }
        }
        list scope {
          key "name";
          ordered-by user;
          leaf name {
            type string;
          }
          uses apply-group;
          uses apply-macro;
          leaf prefix {
            type ipprefix;
          }
          leaf-list interface {
            type interface-name;
            ordered-by user;
          }
        }
        leaf-list scope-policy {
          type policy-algebra;
          ordered-by user;
        }
        list flow-map {
          key "name";
          ordered-by user;
          leaf name {
            type string;
          }
          uses apply-group;
          uses apply-macro;
          leaf-list policy {
            type policy-algebra;
            ordered-by user;
          }
          container bandwidth {
            presence "enable bandwidth";
            leaf bandwidth-value {
              type string;
            }
            leaf adaptive {
              type empty;
            }
          }
          leaf-list redundant-sources {
            type ipaddr;
            ordered-by user;
          }
          container forwarding-cache {
            presence "";
            uses apply-group;
            uses apply-macro;
            container timeout {
              choice choice-3 {
                leaf timeout-value {
                  type uint32;
                }
                container never {
                  presence "enable never";
                  uses apply-group;
                  uses apply-macro;
                  leaf non-discard-entry-only {
                    type empty;
                  }
                }
              }
            }
          }
        }
        leaf-list ssm-groups {
          type ipprefix;
          ordered-by user;
        }
        leaf asm-override-ssm {
          type empty;
        }
        leaf-list rpf-check-policy {
          type policy-algebra;
          ordered-by user;
        }
        container pim-to-igmp-proxy {
          presence "";
          uses apply-group;
          uses apply-macro;
          leaf-list upstream-interface {
            type interface-name;
            ordered-by user;
          }
        }
        container pim-to-mld-proxy {
          presence "";
          uses apply-group;
          uses apply-macro;
          leaf-list upstream-interface {
            type interface-name;
            ordered-by user;
          }
        }
        container forwarding-cache {
          uses apply-group;
          uses apply-macro;
          container threshold {
            uses apply-group;
            uses apply-macro;
            leaf suppress {
              type uint32;
            }
            leaf reuse {
              type uint32;
            }
          }
          leaf timeout {
            type uint32;
          }
        }
        list interface {
          key "name";
          ordered-by user;
          uses multicast-interface-options-type;
        }
        list ssm-map {
          key "name";
          ordered-by user;
          leaf name {
            type string;
          }
          uses apply-group;
          uses apply-macro;
          leaf-list policy {
            type policy-algebra;
            ordered-by user;
          }
          leaf-list source {
            type ipaddr;
            ordered-by user;
          }
        }
        list backup-pe-group {
          key "name";
          ordered-by user;
          leaf name {
            type string;
          }
          uses apply-group;
          uses apply-macro;
          leaf-list backups {
            type ipaddr;
            ordered-by user;
          }
          leaf local-address {
            type ipaddr;
          }
        }
      }
    }
    container firewall {
      uses apply-group;
      uses apply-macro;
      container family {
        uses apply-group;
        uses apply-macro;
        container inet {
          uses apply-group;
          uses apply-macro;
          list dialer-filter {
            key "name";
            ordered-by user;
            uses inet-dialer-filter;
          }
          list prefix-action {
            key "name";
            ordered-by user;
            uses prefix-action;
          }
          list filter {
            key "name";
            ordered-by user;
            uses inet-filter;
          }
          list simple-filter {
            key "name";
            ordered-by user;
            uses inet-simple-filter;
          }
          list service-filter {
            key "name";
            ordered-by user;
            uses inet-service-filter;
          }
          list fast-update-filter {
            key "name";
            ordered-by user;
            uses inet-fuf;
          }
        }
        container inet6 {
          uses apply-group;
          uses apply-macro;
          list dialer-filter {
            key "name";
            ordered-by user;
            uses inet6-dialer-filter;
          }
          list filter {
            key "name";
            ordered-by user;
            uses inet6-filter;
          }
          list service-filter {
            key "name";
            ordered-by user;
            uses inet6-service-filter;
          }
          list fast-update-filter {
            key "name";
            ordered-by user;
            uses inet6-fuf;
          }
        }
        container mpls {
          uses apply-group;
          uses apply-macro;
          list dialer-filter {
            key "name";
            ordered-by user;
            uses mpls-dialer-filter;
          }
          list filter {
            key "name";
            ordered-by user;
            uses mpls-filter;
          }
        }
        container vpls {
          uses apply-group;
          uses apply-macro;
          list filter {
            key "name";
            ordered-by user;
            uses vpls-filter;
          }
        }
        container bridge {
          uses apply-group;
          uses apply-macro;
          list filter {
            key "name";
            ordered-by user;
            uses bridge-filter;
          }
        }
        container ccc {
          uses apply-group;
          uses apply-macro;
          list filter {
            key "name";
            ordered-by user;
            uses ccc-filter;
          }
        }
        container any {
          uses apply-group;
          uses apply-macro;
          list filter {
            key "name";
            ordered-by user;
            uses any-filter;
          }
        }
        container ethernet-switching {
          uses apply-group;
          uses apply-macro;
          list filter {
            key "name";
            ordered-by user;
            uses es-filter;
          }
        }
      }
      list policer {
        key "name";
        ordered-by user;
        uses firewall-policer;
      }
      list hierarchical-policer {
        key "name";
        ordered-by user;
        uses firewall-hierpolicer;
      }
      list interface-set {
        key "name";
        ordered-by user;
        uses interface-set-type;
      }
      list load-balance-group {
        key "name";
        ordered-by user;
        uses firewall-load-balance-group;
      }
      list three-color-policer {
        key "name";
        ordered-by user;
        uses three-color-policer-type;
      }
      list filter {
        key "name";
        ordered-by user;
        uses inet-filter;
      }
    }
    container services {
      uses apply-group;
      uses apply-macro;
      container aacl {
        uses apply-group;
        uses apply-macro;
        list rule {
          key "name";
          ordered-by user;
          uses aacl-rule-object;
        }
        list rule-set {
          key "name";
          ordered-by user;
          leaf name {
            type key-attribute-string-type;
          }
          uses apply-group;
          uses apply-macro;
          list rule {
            key "name";
            ordered-by user;
            leaf name {
              type string;
            }
            uses apply-group;
            uses apply-macro;
          }
        }
        list aacl-dyn-rule-set {
          key "name";
          ordered-by user;
          leaf name {
            type key-attribute-string-type;
          }
          uses apply-group;
          uses apply-macro;
          list rule {
            key "name";
            ordered-by user;
            leaf name {
              type string;
            }
            uses apply-group;
            uses apply-macro;
          }
        }
      }
      container captive-portal-content-delivery {
        uses apply-group;
        uses apply-macro;
        list rule {
          key "name";
          ordered-by user;
          uses cpcd-rule-object-type;
        }
        list rule-set {
          key "name";
          ordered-by user;
          leaf name {
            type key-attribute-string-type;
          }
          uses apply-group;
          uses apply-macro;
          list rule {
            key "name";
            ordered-by user;
            leaf name {
              type string;
            }
            uses apply-group;
            uses apply-macro;
          }
        }
        list profile {
          key "name";
          ordered-by user;
          leaf name {
            type key-attribute-string-type;
          }
          uses apply-group;
          uses apply-macro;
          container apply-advanced {
            uses apply-group;
            uses apply-macro;
          }
          choice choice-dynamic {
            leaf dynamic {
              type empty;
            }
            list cpcd-rules {
              key "name";
              ordered-by user;
              leaf name {
                type key-attribute-string-type;
              }
              uses apply-group;
              uses apply-macro;
              container apply-advanced {
                uses apply-group;
                uses apply-macro;
              }
            }
            list cpcd-rule-sets {
              key "name";
              ordered-by user;
              leaf name {
                type key-attribute-string-type;
              }
              uses apply-group;
              uses apply-macro;
              container apply-advanced {
                uses apply-group;
                uses apply-macro;
              }
            }
          }
          container ipda-rewrite-options {
            uses apply-group;
            uses apply-macro;
            container apply-advanced {
              uses apply-group;
              uses apply-macro;
            }
            leaf destination-address {
              type ipaddr;
            }
            leaf destination-port {
              type uint16;
            }
          }
          container http-redirect-options {
            presence "";
            uses apply-group;
            uses apply-macro;
            leaf url {
              type string;
              mandatory true;
            }
          }
        }
        container traceoptions {
          uses cpcd-trace-options-type;
        }
      }
    }
  }

  grouping base-default-variable-object {
    leaf name {
      type string;
    }
    uses apply-group;
    uses apply-macro;
    leaf default-value {
      type string;
    }
  }

  grouping juniper-dynamic-variable-object {
    leaf name {
      type string;
    }
    uses apply-group;
    uses apply-macro;
    leaf equals {
      type string;
    }
    leaf default-value {
      type string;
    }
    leaf mandatory {
      type empty;
    }
    leaf uid-reference {
      type empty;
    }
    leaf uid {
      type empty;
    }
  }

  grouping juniper-express-fallback-settings {
    uses apply-group;
    uses apply-macro;
    leaf default {
      type string;
    }
    leaf content-size {
      type string;
    }
    leaf engine-not-ready {
      type string;
    }
    leaf timeout {
      type string;
    }
    leaf out-of-resources {
      type string;
    }
    leaf too-many-requests {
      type string;
    }
  }

  grouping juniper-express-scan-options {
    uses apply-group;
    uses apply-macro;
    leaf intelligent-prescreening {
      type empty;
    }
    leaf no-intelligent-prescreening {
      type empty;
    }
    leaf content-size-limit {
      type string;
    }
    leaf timeout {
      type uint32;
    }
  }

  grouping juniper-fabric-routing-instance {
    leaf name {
      type string;
    }
    uses apply-group;
    uses apply-macro;
    leaf description {
      type string;
    }
    leaf instance-type {
      type string;
    }
    container route-distinguisher {
      leaf rd-type {
        type string;
      }
    }
    container routing-options {
      uses juniper-fabric-routing-options;
    }
  }

  grouping juniper-fabric-routing-options {
    uses apply-group;
    uses apply-macro;
    container traceoptions {
      uses apply-group;
      uses apply-macro;
      container file {
        presence "";
        uses trace-file-type;
      }
      list flag {
        key "name";
        ordered-by user;
        leaf name {
          type string;
        }
        leaf disable {
          type empty;
        }
      }
    }
    container graceful-restart {
      presence "enable graceful-restart";
      uses apply-group;
      uses apply-macro;
      choice choice-3 {
        leaf disable {
          type empty;
        }
      }
      leaf restart-duration {
        type uint32;
      }
    }
    container forwarding-table {
      uses forwarding-table-type;
    }
    container resolution {
      presence "enable resolution";
      uses apply-group;
      uses apply-macro;
      container traceoptions {
        uses apply-group;
        uses apply-macro;
        container file {
          presence "";
          uses trace-file-type;
        }
        list flag {
          key "name";
          ordered-by user;
          leaf name {
            type string;
          }
          leaf send {
            type empty;
          }
          leaf receive {
            type empty;
          }
          leaf detail {
            type empty;
          }
          leaf disable {
            type empty;
          }
        }
      }
    }
    container auto-export {
      presence "enable auto-export";
      uses apply-group;
      uses apply-macro;
      container traceoptions {
        uses apply-group;
        uses apply-macro;
        container file {
          presence "";
          uses trace-file-type;
        }
        list flag {
          key "name";
          ordered-by user;
          leaf name {
            type string;
          }
          leaf send {
            type empty;
          }
          leaf receive {
            type empty;
          }
          leaf detail {
            type empty;
          }
          leaf disable {
            type empty;
          }
        }
      }
    }
    container multicast {
      uses apply-group;
      uses apply-macro;
      leaf l2-root {
        type empty;
      }
      leaf replication {
        type empty;
      }
      leaf no-make-before-break {
        type empty;
      }
      leaf make-before-break-timeout {
        units "seconds";
        type uint32;
      }
    }
  }

  grouping forwarding-table-type {
    uses apply-group;
    uses apply-macro;
    leaf route-origin-proto-tlv {
      type empty;
    }
    leaf remnant-holdtime {
      type uint32;
    }
    leaf send-gr-issu-message {
      type string;
    }
    leaf chain-composite-max-label-count {
      type string;
    }
    leaf krt-nexthop-ack {
      type empty;
    }
    leaf krt-nexthop-ack-timeout {
      type string;
    }
    leaf srv6-chain-merge {
      type empty;
    }
    choice session-id-change-limiter-indirect-choice {
      leaf session-id-change-limiter-indirect {
        type empty;
      }
      leaf no-session-id-change-limiter-indirect {
        type empty;
      }
    }
    container consistency-checking {
      presence "";
      uses apply-group;
      uses apply-macro;
      leaf enable-disable {
        type string;
      }
      leaf period {
        type uint32;
      }
      leaf threshold {
        type uint32;
      }
    }
    leaf-list export {
      type policy-algebra;
      ordered-by user;
    }
    leaf dynamic-list-next-hop {
      type empty;
    }
    container evpn-egress-link-protection {
      presence "enable evpn-egress-link-protection";
      uses apply-advanced;
    }
    leaf vpls-hotstandby-convergence {
      type empty;
    }
    container egress-chaining {
      uses apply-advanced;
      leaf spring-te {
        type empty;
      }
    }
    leaf evpn-aliasing-optimize {
      type empty;
    }
    choice ecmp-fast-reroute-choice {
      leaf ecmp-fast-reroute {
        type empty;
      }
      leaf no-ecmp-fast-reroute {
        type empty;
      }
    }
    choice indirect-next-hop-choice {
      leaf indirect-next-hop {
        type empty;
      }
      leaf no-indirect-next-hop {
        type empty;
      }
    }
    choice indirect-next-hop-change-acknowledgements-choice {
      leaf indirect-next-hop-change-acknowledgements {
        type empty;
      }
      leaf no-indirect-next-hop-change-acknowledgements {
        type empty;
      }
    }
    choice route-ack-converge-choice {
      leaf route-ack-converge {
        type empty;
      }
      leaf no-route-ack-converge {
        type empty;
      }
    }
    leaf long-live-ack-timer-val {
      type string;
    }
    list rib {
      key "name";
      ordered-by user;
      leaf name {
        type string;
      }
    }
    leaf unicast-reverse-path {
      type string;
    }
    container ip-tunnel-rpf-check {
      presence "enable ip-tunnel-rpf-check";
      uses apply-advanced;
      leaf mode {
        type string;
      }
      leaf fail-filter {
        type string;
      }
    }
    list source-class {
      key "name";
      ordered-by user;
      uses source-class-filters;
    }
    list destination-class {
      key "name";
      ordered-by user;
      uses destination-class-filters;
    }
    leaf transit-lsp-statistics-from-route {
      type empty;
    }
    container chained-composite-next-hop {
      uses apply-group;
      uses apply-macro;
      container ingress {
        uses apply-group;
        uses apply-macro;
        leaf l2vpn {
          type empty;
        }
        leaf no-l2vpn {
          type empty;
        }
        leaf l2ckt {
          type empty;
        }
        leaf no-l2ckt {
          type empty;
        }
        leaf fec129-vpws {
          type empty;
        }
        leaf no-fec129-vpws {
          type empty;
        }
        leaf evpn {
          type empty;
        }
        leaf no-evpn {
          type empty;
        }
        container labeled-bgp {
          uses apply-group;
          uses apply-macro;
          choice inet-choice {
            leaf inet {
              type empty;
            }
            leaf no-inet {
              type empty;
            }
          }
          choice inet6-choice {
            leaf inet6 {
              type empty;
            }
            leaf no-inet6 {
              type empty;
            }
          }
        }
        container l3vpn {
          presence "enable l3vpn";
          leaf extended-space {
            type empty;
          }
        }
        choice ldp-choice {
          leaf ldp {
            type empty;
          }
          leaf no-ldp {
            type empty;
          }
        }
      }
      container transit {
        uses apply-group;
        uses apply-macro;
        leaf l2vpn {
          type empty;
        }
        leaf no-l2vpn {
          type empty;
        }
        leaf l3vpn {
          type empty;
        }
        leaf no-l3vpn {
          type empty;
        }
        leaf labeled-bgp {
          type empty;
        }
        leaf no-labeled-bgp {
          type empty;
        }
        leaf static {
          type empty;
        }
        leaf no-static {
          type empty;
        }
        leaf rsvp {
          type empty;
        }
        leaf no-rsvp {
          type empty;
        }
        leaf rsvp-p2mp {
          type empty;
        }
        leaf no-rsvp-p2mp {
          type empty;
        }
        leaf ldp {
          type empty;
        }
        leaf no-ldp {
          type empty;
        }
        leaf ldp-p2mp {
          type empty;
        }
        leaf no-ldp-p2mp {
          type empty;
        }
      }
    }
  }

  grouping destination-class-filters {
    leaf name {
      type string;
    }
    uses apply-advanced;
    container family {
      container inet {
        uses apply-advanced;
        container filter {
          uses apply-advanced;
          leaf filter-name {
            type string;
          }
        }
      }
      container inet6 {
        uses apply-advanced;
        container filter {
          uses apply-advanced;
          leaf filter-name {
            type string;
          }
        }
      }
    }
  }

  grouping source-class-filters {
    leaf name {
      type string;
    }
    uses apply-advanced;
    container family {
      container inet {
        uses apply-advanced;
        container filter {
          uses apply-advanced;
          leaf filter-name {
            type string;
          }
        }
      }
      container inet6 {
        uses apply-advanced;
        container filter {
          uses apply-advanced;
          leaf filter-name {
            type string;
          }
        }
      }
    }
  }

  grouping juniper-forwarding-options {
    uses apply-group;
    uses apply-macro;
    list storm-control-profiles {
      key "name";
      leaf name {
        type key-attribute-string-type;
      }
      uses apply-group;
      uses apply-macro;
      container all {
        presence "enable all";
        uses apply-group;
        uses apply-macro;
        choice choice-bandwidth-percentage {
          leaf bandwidth-percentage {
            type uint32;
          }
          leaf bandwidth-level {
            units "kbps";
            type uint32;
          }
        }
        leaf burst-size {
          units "bytes";
          type string;
        }
        leaf no-broadcast {
          type empty;
        }
        leaf no-unknown-unicast {
          type empty;
        }
        choice choice-no-multicast {
          leaf no-multicast {
            type empty;
          }
          leaf no-registered-multicast {
            type empty;
          }
          leaf no-unregistered-multicast {
            type empty;
          }
        }
      }
      leaf action-shutdown {
        type empty;
      }
    }
    choice choice-3 {
      container sampling {
        uses juniper-sampling-options;
      }
      container packet-capture {
        uses juniper-packet-capture-options;
      }
    }
    list monitoring {
      key "name";
      uses juniper-monitoring-options;
    }
    list accounting {
      key "name";
      uses juniper-packet-accounting-options;
    }
    list analyzer {
      key "name";
      uses smpl-analyzer-type;
    }
    container port-mirroring {
      uses juniper-port-mirror-options;
    }
    container load-balance {
      uses apply-group;
      uses apply-macro;
      container indexed-next-hop {
        presence "enable indexed-next-hop";
        uses apply-group;
        uses apply-macro;
      }
      container indexed-load-balance {
        presence "enable indexed-load-balance";
        uses apply-group;
        uses apply-macro;
      }
      container per-flow {
        presence "";
        uses apply-group;
        uses apply-macro;
        leaf hash-seed {
          type empty;
        }
      }
      container per-prefix {
        presence "enable per-prefix";
        uses apply-group;
        uses apply-macro;
        leaf hash-seed {
          type uint16;
        }
      }
    }
    container hash-key {
      uses junos-hash-key;
    }
    container enhanced-hash-key {
      uses apply-group;
      uses apply-macro;
      leaf use-trunk-max-links {
        type empty;
      }
      leaf ecmp-resilient-hash {
        type empty;
      }
      container fabric-load-balance {
        presence "enable fabric-load-balance";
        uses apply-group;
        uses apply-macro;
        choice choice-flowlet {
          container flowlet {
            presence "enable flowlet";
            uses apply-group;
            uses apply-macro;
            leaf inactivity-interval {
              type string;
            }
          }
          leaf per-packet {
            type empty;
          }
        }
      }
      container hash-mode {
        uses apply-group;
        uses apply-macro;
        choice choice-layer2-header {
          leaf layer2-header {
            type empty;
          }
          leaf layer2-payload {
            type empty;
          }
          leaf gtp-header-offset {
            type uint8;
          }
        }
      }
      container hash-seed {
        presence "enable hash-seed";
        uses apply-group;
        uses apply-macro;
        leaf seed-value {
          type uint32;
        }
      }
      container resilient-hash-seed {
        presence "enable resilient-hash-seed";
        uses apply-group;
        uses apply-macro;
        leaf resilient-seed-value {
          type uint32;
        }
      }
      container layer2 {
        uses apply-group;
        uses apply-macro;
        leaf no-incoming-port {
          type empty;
        }
        leaf no-incoming-device {
          type empty;
        }
        leaf no-source-mac-address {
          type empty;
        }
        leaf source-mac-address {
          type empty;
        }
        leaf no-destination-mac-address {
          type empty;
        }
        leaf destination-mac-address {
          type empty;
        }
        leaf no-ether-type {
          type empty;
        }
        leaf vlan-id {
          type empty;
        }
        leaf no-vlan-id {
          type empty;
        }
        leaf inner-vlan-id {
          type empty;
        }
      }
      container inet {
        uses apply-group;
        uses apply-macro;
        leaf no-incoming-port {
          type empty;
        }
        leaf no-incoming-device {
          type empty;
        }
        leaf no-l4-source-port {
          type empty;
        }
        leaf no-l4-destination-port {
          type empty;
        }
        leaf no-protocol {
          type empty;
        }
        leaf no-ipv4-source-address {
          type empty;
        }
        leaf no-ipv4-destination-address {
          type empty;
        }
        leaf vlan-id {
          type empty;
        }
      }
      container inet6 {
        uses apply-group;
        uses apply-macro;
        leaf no-incoming-port {
          type empty;
        }
        leaf no-incoming-device {
          type empty;
        }
        leaf no-l4-source-port {
          type empty;
        }
        leaf no-l4-destination-port {
          type empty;
        }
        leaf ipv6-flow-label {
          type empty;
        }
        leaf no-next-header {
          type empty;
        }
        leaf no-ipv6-source-address {
          type empty;
        }
        leaf no-ipv6-destination-address {
          type empty;
        }
        leaf vlan-id {
          type empty;
        }
      }
      leaf no-mpls {
        type empty;
      }
      container gre {
        uses apply-group;
        uses apply-macro;
        leaf key {
          type empty;
        }
        leaf protocol {
          type empty;
        }
      }
      leaf vxlan-vnid {
        type empty;
      }
      container services-loadbalancing {
        uses apply-group;
        uses apply-macro;
        container family {
          uses apply-group;
          uses apply-macro;
          container inet {
            uses apply-group;
            uses apply-macro;
            container layer-3-services {
              uses apply-group;
              uses apply-macro;
              leaf source-address {
                type empty;
              }
              leaf destination-address {
                type empty;
              }
              leaf incoming-interface-index {
                type empty;
              }
            }
          }
          container inet6 {
            uses apply-group;
            uses apply-macro;
            container layer-3-services {
              uses apply-group;
              uses apply-macro;
              leaf source-address {
                type empty;
              }
              leaf destination-address {
                type empty;
              }
              leaf incoming-interface-index {
                type empty;
              }
              leaf src-prefix-len {
                units "bits";
                type uint32;
              }
            }
          }
        }
      }
      container source-destination-only-loadbalancing {
        uses apply-group;
        uses apply-macro;
        container family {
          uses apply-group;
          uses apply-macro;
          container inet {
            uses apply-group;
            uses apply-macro;
            leaf prefix-length {
              units "bits";
              type uint32;
            }
          }
          container inet6 {
            uses apply-group;
            uses apply-macro;
            leaf prefix-length {
              units "bits";
              type uint32;
            }
          }
        }
      }
      container family {
        uses apply-group;
        uses apply-macro;
        container inet {
          uses apply-group;
          uses apply-macro;
          leaf incoming-interface-index {
            type empty;
          }
          leaf no-destination-port {
            type empty;
          }
          leaf no-source-port {
            type empty;
          }
          leaf type-of-service {
            type empty;
          }
          leaf gtp-tunnel-endpoint-identifier {
            type empty;
          }
          leaf l2tp-tunnel-session-identifier {
            type empty;
          }
          leaf session-id {
            type empty;
          }
        }
        container inet6 {
          uses apply-group;
          uses apply-macro;
          leaf incoming-interface-index {
            type empty;
          }
          leaf traffic-class {
            type empty;
          }
          leaf no-destination-port {
            type empty;
          }
          leaf no-source-port {
            type empty;
          }
          leaf gtp-tunnel-endpoint-identifier {
            type empty;
          }
          leaf session-id {
            type empty;
          }
        }
        container mpls {
          uses apply-group;
          uses apply-macro;
          leaf label-1-exp {
            type empty;
          }
          leaf incoming-interface-index {
            type empty;
          }
          choice choice-no-ether-pseudowire {
            leaf no-ether-pseudowire {
              type empty;
            }
            container ether-pseudowire {
              leaf zero-control-word {
                type empty;
              }
            }
          }
          leaf no-payload {
            type empty;
          }
        }
        container multiservice {
          uses apply-group;
          uses apply-macro;
          leaf incoming-interface-index {
            type empty;
          }
          leaf outer-priority {
            type empty;
          }
          leaf no-payload {
            type empty;
          }
          leaf no-mac-addresses {
            type empty;
          }
        }
      }
      container hash-function {
        uses apply-group;
        uses apply-macro;
        choice choice-CRC16-CCITT {
          leaf CRC16-CCITT {
            type empty;
          }
          leaf CRC16 {
            type empty;
          }
          leaf CRC16XOR1 {
            type empty;
          }
          leaf CRC16XOR2 {
            type empty;
          }
          leaf CRC16XOR4 {
            type empty;
          }
          leaf CRC16XOR8 {
            type empty;
          }
          leaf CRC32HI {
            type empty;
          }
          leaf CRC32LO {
            type empty;
          }
          container xor {
            presence "enable xor";
            uses apply-group;
            uses apply-macro;
            leaf no-L3-L4-headers {
              type empty;
            }
            leaf no-L4-ports {
              type empty;
            }
            leaf mac-addresses {
              type empty;
            }
            leaf no-mpls-hash {
              type empty;
            }
            leaf no-ipv4-source-address {
              type empty;
            }
            leaf no-ipv4-destination-address {
              type empty;
            }
            leaf no-ipv6-source-address {
              type empty;
            }
            leaf no-ipv6-destination-address {
              type empty;
            }
            leaf no-ip6-flow-label {
              type empty;
            }
            leaf en-ip-over-mpls {
              type empty;
            }
            leaf no-mpls-label0 {
              type empty;
            }
            leaf no-mpls-label1 {
              type empty;
            }
            leaf no-source-mac-address {
              type empty;
            }
            leaf no-destination-mac-address {
              type empty;
            }
            leaf no-l4-source-port {
              type empty;
            }
            leaf no-l4-destination-port {
              type empty;
            }
          }
          leaf ingress-port {
            type empty;
          }
          container crc6 {
            presence "enable crc6";
            uses apply-group;
            uses apply-macro;
            leaf crc6-seed {
              type uint32;
            }
            leaf en-ip-over-mpls {
              type empty;
            }
            leaf no-source-mac-address {
              type empty;
            }
            leaf no-destination-mac-address {
              type empty;
            }
            leaf no-mpls-label0 {
              type empty;
            }
            leaf no-mpls-label1 {
              type empty;
            }
            leaf no-l4-source-port {
              type empty;
            }
            leaf no-l4-destination-port {
              type empty;
            }
            leaf no-ip-source-address {
              type empty;
            }
            leaf no-ip-destination-address {
              type empty;
            }
            leaf no-ip6-flow-label {
              type empty;
            }
          }
          container crc16 {
            presence "enable crc16";
            uses apply-group;
            uses apply-macro;
            leaf crc16-seed {
              type uint32;
            }
            leaf en-ip-over-mpls {
              type empty;
            }
            leaf no-source-mac-address {
              type empty;
            }
            leaf no-destination-mac-address {
              type empty;
            }
            leaf no-mpls-label0 {
              type empty;
            }
            leaf no-mpls-label1 {
              type empty;
            }
            leaf no-l4-source-port {
              type empty;
            }
            leaf no-l4-destination-port {
              type empty;
            }
            leaf no-ip-source-address {
              type empty;
            }
            leaf no-ip-destination-address {
              type empty;
            }
            leaf no-ip6-flow-label {
              type empty;
            }
          }
        }
      }
      leaf symmetric {
        type empty;
      }
    }
    container next-hop {
      uses apply-group;
      uses apply-macro;
      leaf arp-throttle {
        type uint16;
      }
      leaf arp-detect {
        type uint32;
      }
    }
    container multicast {
      uses apply-group;
      uses apply-macro;
      leaf resolve-rate {
        units "per second";
        type uint32;
      }
      leaf mismatch-rate {
        units "per second";
        type uint32;
      }
      container policer {
        presence "";
        uses apply-group;
        uses apply-macro;
        leaf bandwidth-limit {
          type string;
          units "bits per second";
        }
        leaf burst-size-limit {
          type string;
          mandatory true;
          units "bytes";
        }
      }
    }
    container rpf-loose-mode-discard {
      uses apply-group;
      uses apply-macro;
      container family {
        uses apply-group;
        uses apply-macro;
        leaf inet {
          type empty;
        }
        leaf inet6 {
          type empty;
        }
      }
    }
    leaf l2circuit-control-passthrough {
      type empty;
    }
    container explicit-null-cos {
      presence "enable explicit-null-cos";
      uses apply-group;
      uses apply-macro;
      leaf inet {
        type empty;
      }
      leaf inet6 {
        type empty;
      }
    }
    container helpers {
      uses apply-group;
      uses apply-macro;
      container traceoptions {
        uses apply-group;
        uses apply-macro;
        leaf no-remote-trace {
          type empty;
        }
        container file {
          leaf filename {
            type string;
          }
          leaf size {
            type string;
          }
          leaf files {
            type uint32;
          }
          leaf world-readable {
            type empty;
          }
          leaf no-world-readable {
            type empty;
          }
          leaf match {
            type regular-expression;
          }
        }
        leaf level {
          type string;
        }
        list flag {
          key "name";
          ordered-by user;
          leaf name {
            type string;
          }
        }
      }
      container domain {
        uses apply-group;
        uses apply-macro;
        leaf description {
          type string;
        }
        container server {
          leaf address {
            type ipv4addr;
          }
          choice choice-5 {
            container logical-system {
              presence "";
              leaf logical-system-name {
                type string;
              }
              leaf routing-instance {
                type string;
              }
            }
            leaf routing-instance {
              type string;
            }
          }
        }
        list interface {
          key "name";
          ordered-by user;
          leaf name {
            type interface-wildcard;
          }
          uses apply-group;
          uses apply-macro;
          leaf no-listen {
            type empty;
          }
          leaf broadcast {
            type empty;
          }
          leaf description {
            type string;
          }
          container server {
            leaf address {
              type ipv4addr;
            }
            choice choice-5 {
              container logical-system {
                presence "";
                leaf logical-system-name {
                  type string;
                }
                leaf routing-instance {
                  type string;
                }
              }
              leaf routing-instance {
                type string;
              }
            }
          }
        }
      }
      container tftp {
        uses apply-group;
        uses apply-macro;
        leaf description {
          type string;
        }
        container server {
          leaf address {
            type ipv4addr;
          }
          choice choice-5 {
            container logical-system {
              presence "";
              leaf logical-system-name {
                type string;
              }
              leaf routing-instance {
                type string;
              }
            }
            leaf routing-instance {
              type string;
            }
          }
        }
        list interface {
          key "name";
          ordered-by user;
          leaf name {
            type interface-wildcard;
          }
          uses apply-group;
          uses apply-macro;
          leaf no-listen {
            type empty;
          }
          leaf broadcast {
            type empty;
          }
          leaf description {
            type string;
          }
          container server {
            leaf address {
              type ipv4addr;
            }
            choice choice-5 {
              container logical-system {
                presence "";
                leaf logical-system-name {
                  type string;
                }
                leaf routing-instance {
                  type string;
                }
              }
              leaf routing-instance {
                type string;
              }
            }
          }
        }
      }
      container bootp {
        uses apply-group;
        uses apply-macro;
        leaf relay-agent-option {
          type empty;
        }
        container dhcp-option82 {
          presence "enable dhcp-option82";
          uses dhcp-option82-type;
        }
        leaf description {
          type string;
        }
        list server {
          key "name";
          ordered-by user;
          leaf name {
            type ipv4addr;
          }
          uses apply-group;
          uses apply-macro;
          list logical-system {
            key "name";
            ordered-by user;
            leaf name {
              type string;
            }
            leaf-list routing-instance {
              type string;
              ordered-by user;
            }
          }
          leaf-list routing-instance {
            type string;
            ordered-by user;
          }
        }
        leaf maximum-hop-count {
          type uint32;
        }
        leaf minimum-wait-time {
          type uint32;
        }
        leaf client-response-ttl {
          type uint32;
        }
        leaf source-address-giaddr {
          type empty;
        }
        leaf vpn {
          type empty;
        }
        list interface {
          key "name";
          ordered-by user;
          leaf name {
            type interface-wildcard;
          }
          uses apply-group;
          uses apply-macro;
          leaf no-listen {
            type empty;
          }
          leaf broadcast {
            type empty;
          }
          leaf description {
            type string;
          }
          list server {
            key "name";
            ordered-by user;
            leaf name {
              type ipv4addr;
            }
            uses apply-group;
            uses apply-macro;
            list logical-system {
              key "name";
              ordered-by user;
              leaf name {
                type string;
              }
              leaf-list routing-instance {
                type string;
                ordered-by user;
              }
            }
            leaf-list routing-instance {
              type string;
              ordered-by user;
            }
          }
          leaf maximum-hop-count {
            type uint32;
          }
          leaf minimum-wait-time {
            type uint32;
          }
          leaf client-response-ttl {
            type uint32;
          }
          leaf source-address-giaddr {
            type empty;
          }
          leaf vpn {
            type empty;
          }
          container dhcp-option82 {
            presence "enable dhcp-option82";
            uses dhcp-option82-type;
          }
        }
      }
      list port {
        key "name";
        ordered-by user;
        leaf name {
          type string;
        }
        uses apply-group;
        uses apply-macro;
        leaf description {
          type string;
        }
        container server {
          leaf address {
            type ipv4addr;
          }
          choice choice-5 {
            container logical-system {
              presence "";
              leaf logical-system-name {
                type string;
              }
              leaf routing-instance {
                type string;
              }
            }
            leaf routing-instance {
              type string;
            }
          }
        }
        list interface {
          key "name";
          ordered-by user;
          leaf name {
            type interface-wildcard;
          }
          uses apply-group;
          uses apply-macro;
          leaf no-listen {
            type empty;
          }
          leaf broadcast {
            type empty;
          }
          leaf description {
            type string;
          }
          container server {
            leaf address {
              type ipv4addr;
            }
            choice choice-5 {
              container logical-system {
                presence "";
                leaf logical-system-name {
                  type string;
                }
                leaf routing-instance {
                  type string;
                }
              }
              leaf routing-instance {
                type string;
              }
            }
          }
        }
      }
    }
    container family {
      uses apply-group;
      uses apply-macro;
      container inet {
        uses apply-group;
        uses apply-macro;
        container filter {
          uses apply-group;
          uses apply-macro;
          leaf input {
            type string;
          }
          leaf output {
            type string;
          }
        }
      }
      container inet6 {
        uses apply-group;
        uses apply-macro;
        container filter {
          uses apply-group;
          uses apply-macro;
          leaf input {
            type string;
          }
          leaf output {
            type string;
          }
        }
        leaf route-accounting {
          type empty;
        }
      }
      container mpls {
        uses apply-group;
        uses apply-macro;
        container filter {
          uses apply-group;
          uses apply-macro;
          leaf input {
            type string;
          }
          leaf output {
            type string;
          }
        }
      }
      container vpls {
        uses apply-group;
        uses apply-macro;
        container filter {
          uses apply-group;
          uses apply-macro;
          leaf input {
            type string;
          }
        }
        container flood {
          uses apply-group;
          uses apply-macro;
          leaf input {
            type string;
          }
        }
      }
      container evpn {
        uses apply-group;
        uses apply-macro;
        container filter {
          uses apply-group;
          uses apply-macro;
          leaf input {
            type string;
          }
        }
        container flood {
          uses apply-group;
          uses apply-macro;
          leaf input {
            type string;
          }
        }
      }
    }
    list next-hop-group {
      key "name";
      uses juniper-next-hop-group-options;
    }
    container dhcp-relay {
      uses jdhcp-relay-type;
      container undocumented {
        leaf stale-timer {
          type uint32;
        }
      }
    }
    leaf load-balance-label-capability {
      type empty;
    }
    leaf no-load-balance-label-capability {
      type empty;
    }
    leaf fast-reroute-priority {
      type string;
    }
    list ip-options-protocol-queue {
      key "name";
      ordered-by user;
      leaf name {
        type string;
      }
      uses apply-group;
      uses apply-macro;
      leaf protocol-id {
        mandatory true;
        type uint8;
      }
      leaf queue-depth {
        mandatory true;
        type uint32;
      }
    }
    leaf link-layer-broadcast-inet-check {
      type empty;
    }
    leaf cut-through {
      type empty;
    }
    leaf vrf-fallback {
      type empty;
    }
    leaf no-hierarchical-ecmp {
      type empty;
    }
    leaf ipmc-miss-do-l2mc {
      type empty;
    }
    leaf hyper-mode {
      type empty;
    }
    leaf no-hyper-mode {
      type empty;
    }
    leaf ecmp-do-local-lookup {
      type empty;
    }
    container access-security {
      uses jdhcp-access-security-type;
    }
    list forwarding-sandbox {
      key "name";
      uses juniper-forwarding-sandbox-options;
    }
    container vxlan-routing {
      uses apply-group;
      uses apply-macro;
      leaf next-hop {
        type uint32;
      }
      leaf interface-num {
        type uint32;
      }
      leaf overlay-ecmp {
        type empty;
      }
    }
    container satellite {
      uses apply-group;
      uses apply-macro;
      container traceoptions {
        uses apply-group;
        uses apply-macro;
        leaf no-remote-trace {
          type empty;
        }
        container file {
          leaf filename {
            type string;
          }
          leaf size {
            type string;
          }
          leaf files {
            type uint32;
          }
          leaf world-readable {
            type empty;
          }
          leaf no-world-readable {
            type empty;
          }
          leaf match {
            type regular-expression;
          }
        }
        list flag {
          key "name";
          ordered-by user;
          leaf name {
            type string;
          }
        }
      }
      leaf local-replication {
        type empty;
      }
      list fpc {
        key "name";
        leaf name {
          type key-attribute-ulong-type;
        }
        uses apply-group;
        uses apply-macro;
        choice choice-local-switching {
          container local-switching {
            presence "enable local-switching";
            uses apply-group;
            uses apply-macro;
            leaf l3 {
              type empty;
            }
          }
          container selective-vlan-switching {
            uses apply-group;
            uses apply-macro;
            leaf routing-instance {
              type string;
            }
          }
        }
      }
      container vlan-auto-sense {
        uses apply-group;
        uses apply-macro;
        leaf expiry-time {
          units "seconds";
          type uint32;
        }
      }
      container analyzer-vlan {
        uses apply-group;
        uses apply-macro;
        leaf vlan-name {
          type string;
        }
      }
      leaf disable-heartbeat {
        type empty;
      }
      leaf no-disable-heartbeat {
        type empty;
      }
    }
    container evpn-vxlan {
      leaf shared-tunnels {
        type empty;
      }
    }
    leaf vxlan-disable-copy-tos-encap {
      type empty;
    }
    leaf vxlan-disable-copy-tos-decap {
      type empty;
    }
  }

  grouping juniper-ethernet-options {
    uses apply-group;
    uses apply-macro;
    list analyzer {
      key "name";
      ordered-by user;
      uses analyzer-type;
    }
    container secure-access-port {
      uses apply-group;
      uses apply-macro;
      list interface {
        key "name";
        leaf name {
          type interface-name;
        }
        uses apply-group;
        uses apply-macro;
        container mac-limit {
          presence "";
          leaf limit {
            type uint32;
          }
          leaf action {
            type string;
          }
        }
        list static-ip {
          key "name";
          ordered-by user;
          uses juniper-ip-mac-static;
        }
        leaf-list allowed-mac {
          ordered-by user;
          type mac-addr;
        }
        leaf no-allowed-mac-log {
          type empty;
        }
        leaf dhcp-trusted {
          type empty;
        }
        leaf no-dhcp-trusted {
          type empty;
        }
        leaf fcoe-trusted {
          type empty;
        }
        leaf no-fcoe-trusted {
          type empty;
        }
      }
      list vlan {
        key "name";
        leaf name {
          type string;
        }
        uses apply-group;
        uses apply-macro;
        choice choice-3 {
          container arp-inspection {
            presence "enable arp-inspection";
            leaf forwarding-class {
              type string;
            }
          }
          leaf no-arp-inspection {
            type empty;
          }
        }
        choice choice-4 {
          container examine-dhcp {
            presence "enable examine-dhcp";
            leaf forwarding-class {
              type string;
            }
          }
          leaf no-examine-dhcp {
            type empty;
          }
        }
        container examine-fip {
          presence "enable examine-fip";
          uses apply-group;
          uses apply-macro;
          leaf fc-map {
            type string;
          }
        }
        container mac-move-limit {
          presence "";
          leaf limit {
            type uint32;
          }
          leaf action {
            type string;
          }
        }
        leaf ip-source-guard {
          type empty;
        }
        leaf no-ip-source-guard {
          type empty;
        }
        container dhcp-option82 {
          presence "enable dhcp-option82";
          uses dhcp-option82-type;
        }
      }
      container dhcp-snooping-file {
        presence "";
        uses apply-group;
        uses apply-macro;
        leaf location {
          type filename;
        }
        leaf write-interval {
          type uint32;
        }
        leaf timeout {
          type uint32;
        }
      }
    }
    container traceoptions {
      uses apply-group;
      uses apply-macro;
      container file {
        presence "";
        uses esp-trace-file-type;
      }
      list flag {
        key "name";
        ordered-by user;
        leaf name {
          type string;
        }
        leaf disable {
          type empty;
        }
      }
    }
    container voip {
      presence "enable voip";
      uses apply-group;
      uses apply-macro;
      list interface {
        key "name";
        ordered-by user;
        leaf name {
          type string;
        }
        uses apply-group;
        uses apply-macro;
        leaf vlan {
          type string;
        }
        leaf forwarding-class {
          type string;
        }
      }
    }
    container unknown-unicast-forwarding {
      uses apply-group;
      uses apply-macro;
      list vlan {
        key "name";
        leaf name {
          type string;
        }
        uses apply-group;
        uses apply-macro;
        leaf interface {
          type interface-name;
        }
      }
    }
    container dot1q-tunneling {
      uses apply-group;
      uses apply-macro;
      leaf ether-type {
        type string;
      }
    }
    leaf mac-lookup-length {
      type string;
    }
    container mac-notification {
      presence "enable mac-notification";
      uses apply-group;
      uses apply-macro;
      leaf notification-interval {
        type uint32;
      }
    }
    container interfaces {
      uses apply-group;
      uses apply-macro;
      list esw-interface {
        key "name";
        uses esw-interface-type;
      }
    }
    container mac-table-aging-time {
      uses mac-aging-time-config;
    }
    leaf nonstop-bridging {
      type empty;
    }
    leaf uac-policy {
      type empty;
    }
    container port-error-disable {
      uses apply-group;
      uses apply-macro;
      leaf disable-timeout {
        type int32;
      }
    }
    container redundant-trunk-group {
      uses apply-group;
      uses apply-macro;
      list group {
        key "name";
        ordered-by user;
        leaf name {
          type key-attribute-string-type;
        }
        uses apply-group;
        uses apply-macro;
        leaf preempt-cutover-timer {
          type uint16;
        }
        leaf description {
          type string;
        }
        list interface {
          key "name";
          leaf name {
            type interface-name;
          }
          uses apply-group;
          uses apply-macro;
          leaf primary {
            type empty;
          }
        }
      }
    }
    container storm-control {
      uses apply-group;
      uses apply-macro;
      leaf action-shutdown {
        type empty;
      }
      list interface {
        key "name";
        leaf name {
          type string;
        }
        uses apply-group;
        uses apply-macro;
        leaf bandwidth {
          type uint32;
        }
        leaf level {
          type uint32;
        }
        leaf no-broadcast {
          type empty;
        }
        leaf no-unknown-unicast {
          type empty;
        }
        choice choice-9 {
          leaf multicast {
            type empty;
          }
          leaf no-multicast {
            type empty;
          }
          leaf no-registered-multicast {
            type empty;
          }
          leaf no-unregistered-multicast {
            type empty;
          }
        }
      }
    }
    container bpdu-block {
      uses apply-group;
      uses apply-macro;
      list interface {
        key "name";
        leaf name {
          type string;
        }
        uses apply-group;
        uses apply-macro;
      }
      leaf disable-timeout {
        type int32;
      }
    }
    list authentication-whitelist {
      key "name";
      ordered-by user;
      leaf name {
        type mac-addr-prefix;
      }
      uses apply-group;
      uses apply-macro;
      leaf vlan-assignment {
        type string;
      }
      leaf interface {
        type interface-name;
      }
    }
    container static {
      uses apply-group;
      uses apply-macro;
      list vlan {
        key "name";
        ordered-by user;
        leaf name {
          type string;
        }
        uses apply-group;
        uses apply-macro;
        list mac {
          key "name";
          ordered-by user;
          leaf name {
            type mac-addr;
          }
          leaf next-hop {
            type interface-name;
          }
        }
      }
    }
  }

  grouping analyzer-type {
    leaf name {
      type key-attribute-string-type;
    }
    uses apply-group;
    uses apply-macro;
    leaf ratio {
      type uint32;
    }
    leaf loss-priority {
      type string;
    }
    container input {
      uses analyzer-input-type;
    }
    container output {
      uses analyzer-output-type;
    }
  }

  grouping analyzer-input-type {
    uses apply-group;
    uses apply-macro;
    container ingress {
      uses analyzer-ingress-type;
    }
    container egress {
      uses analyzer-egress-type;
    }
  }

  grouping analyzer-egress-type {
    uses apply-group;
    uses apply-macro;
    list interface {
      key "name";
      ordered-by user;
      uses analyzer-egress-interface-type;
    }
    list vlan {
      key "name";
      ordered-by user;
      uses analyzer-vlan-type;
    }
  }

  grouping smpl-analyzer-type {
    leaf name {
      type key-attribute-string-type;
    }
    uses apply-group;
    uses apply-macro;
    container input {
      uses smpl-analyzer-input-type;
    }
    container output {
      uses smpl-analyzer-output-type;
    }
  }

  grouping smpl-analyzer-input-type {
    uses apply-group;
    uses apply-macro;
    leaf rate {
      type uint32;
    }
    leaf maximum-packet-length {
      units "bytes";
      type uint32;
    }
    container ingress {
      uses smpl-analyzer-ingress-type;
    }
    container egress {
      uses smpl-analyzer-egress-type;
    }
  }

  grouping smpl-analyzer-egress-type {
    uses apply-group;
    uses apply-macro;
    list interface {
      key "name";
      ordered-by user;
      uses analyzer-egress-interface-type;
    }
    list routing-instance {
      key "name";
      uses analyzer-egress-routing-instance-type;
    }
    list vlan {
      key "name";
      ordered-by user;
      uses analyzer-egress-vlan-type;
    }
    list bridge-domain {
      key "name";
      ordered-by user;
      uses analyzer-egress-bridge-domain-type;
    }
  }

  grouping analyzer-egress-routing-instance-type {
    leaf name {
      type string;
    }
    uses apply-group;
    uses apply-macro;
    list vlan {
      key "name";
      ordered-by user;
      uses analyzer-egress-vlan-type;
    }
    list bridge-domain {
      key "name";
      ordered-by user;
      uses analyzer-egress-bridge-domain-type;
    }
  }

  grouping analyzer-egress-bridge-domain-type {
    leaf name {
      type string;
    }
    uses apply-group;
    uses apply-macro;
  }

  grouping analyzer-egress-vlan-type {
    leaf name {
      type string;
    }
    uses apply-group;
    uses apply-macro;
  }

  grouping smpl-analyzer-output-type {
    uses apply-group;
    uses apply-macro;
    choice choice-interface {
      leaf interface {
        type interface-name;
      }
      leaf ip-address {
        type ipv4addr;
      }
      leaf next-hop-group {
        type string;
      }
      list routing-instance {
        key "name";
        uses output-routing-instance-type;
      }
      list vlan {
        key "name";
        uses pm-rspan-vlan;
      }
      list bridge-domain {
        key "name";
        uses pm-rspan-bridge-domain;
      }
    }
  }

  grouping output-routing-instance-type {
    leaf name {
      type string;
    }
    uses apply-group;
    uses apply-macro;
    leaf ip-address {
      type ipv4addr;
    }
    list vlan {
      key "name";
      uses pm-rspan-vlan;
    }
    list bridge-domain {
      key "name";
      uses pm-rspan-bridge-domain;
    }
  }

  grouping analyzer-egress-interface-type {
    leaf name {
      type string;
    }
    uses apply-group;
    uses apply-macro;
  }

  grouping smpl-analyzer-ingress-type {
    uses apply-group;
    uses apply-macro;
    list interface {
      key "name";
      ordered-by user;
      uses analyzer-ingress-interface-type;
    }
    list routing-instance {
      key "name";
      uses analyzer-ingress-routing-instance-type;
    }
    list vlan {
      key "name";
      ordered-by user;
      uses analyzer-ingress-vlan-type;
    }
    list bridge-domain {
      key "name";
      ordered-by user;
      uses analyzer-ingress-bridge-domain-type;
    }
  }

  grouping analyzer-ingress-vlan-type {
    leaf name {
      type string;
    }
    uses apply-group;
    uses apply-macro;
  }

  grouping analyzer-ingress-routing-instance-type {
    leaf name {
      type string;
    }
    uses apply-group;
    uses apply-macro;
    list vlan {
      key "name";
      ordered-by user;
      uses analyzer-ingress-vlan-type;
    }
    list bridge-domain {
      key "name";
      ordered-by user;
      uses analyzer-ingress-bridge-domain-type;
    }
  }

  grouping analyzer-ingress-bridge-domain-type {
    leaf name {
      type string;
    }
    uses apply-group;
    uses apply-macro;
  }

  grouping analyzer-ingress-type {
    uses apply-group;
    uses apply-macro;
    list interface {
      key "name";
      ordered-by user;
      uses analyzer-ingress-interface-type;
    }
    list vlan {
      key "name";
      ordered-by user;
      uses analyzer-vlan-type;
    }
  }

  grouping analyzer-ingress-interface-type {
    leaf name {
      type string;
    }
    uses apply-group;
    uses apply-macro;
  }

  grouping analyzer-output-type {
    uses apply-group;
    uses apply-macro;
    list interface {
      key "name";
      ordered-by user;
      leaf name {
        type interface-name;
      }
      uses apply-group;
      uses apply-macro;
    }
    list vlan {
      key "name";
      ordered-by user;
      leaf name {
        type string;
      }
      uses apply-group;
      uses apply-macro;
    }
  }

  grouping analyzer-vlan-type {
    leaf name {
      type string;
    }
    uses apply-group;
    uses apply-macro;
  }

  grouping dhcp-option82-type {
    uses apply-group;
    uses apply-macro;
    leaf disable {
      type empty;
    }
    container circuit-id {
      presence "enable circuit-id";
      uses apply-group;
      uses apply-macro;
      leaf prefix {
        type string;
      }
      leaf use-interface-description {
        type empty;
      }
      leaf use-vlan-id {
        type empty;
      }
    }
    container remote-id {
      presence "enable remote-id";
      uses apply-group;
      uses apply-macro;
      leaf prefix {
        type string;
      }
      leaf use-interface-description {
        type empty;
      }
      leaf use-string {
        type string;
      }
    }
    container vendor-id {
      presence "enable vendor-id";
      uses apply-group;
      uses apply-macro;
      leaf use-string {
        type string;
      }
    }
  }

  grouping jdhcp-access-security-type {
    uses apply-group;
    uses apply-macro;
    container router-advertisement-guard {
      presence "enable router-advertisement-guard";
      uses apply-group;
      uses apply-macro;
      list policy {
        key "name";
        ordered-by user;
        leaf name {
          type key-attribute-string-type;
        }
        uses apply-group;
        uses apply-macro;
        container discard {
          uses apply-group;
          uses apply-macro;
          leaf source-ip-address-list {
            type string;
          }
          leaf source-mac-address-list {
            type string;
          }
          leaf prefix-list-name {
            type string;
          }
        }
        container accept {
          uses apply-group;
          uses apply-macro;
          container match-list {
            uses apply-group;
            uses apply-macro;
            leaf source-ip-address-list {
              type string;
            }
            leaf source-mac-address-list {
              type string;
            }
            leaf prefix-list-name {
              type string;
            }
            leaf match-criteria {
              type string;
            }
          }
          container match-options {
            presence "enable match-options";
            uses apply-group;
            uses apply-macro;
            container hop-limit {
              uses apply-group;
              uses apply-macro;
              leaf maximum {
                type uint32;
              }
              leaf minimum {
                type uint32;
              }
            }
            container route-preference {
              presence "";
              uses apply-group;
              uses apply-macro;
              leaf maximum {
                mandatory true;
                type string;
              }
            }
            leaf managed-config-flag {
              type empty;
            }
            leaf other-config-flag {
              type empty;
            }
          }
        }
      }
      container interface {
        uses apply-group;
        uses apply-macro;
        list intf-config {
          key "name";
          uses interface-policy;
        }
      }
      container vlans {
        uses apply-group;
        uses apply-macro;
        list vlan-config {
          key "name";
          uses vlan-policy;
        }
      }
    }
  }

  grouping interface-policy {
    leaf name {
      type interface-name;
    }
    uses apply-group;
    uses apply-macro;
    container policy {
      uses apply-group;
      uses apply-macro;
      leaf policy-name {
        type string;
      }
      choice choice-stateful {
        leaf stateful {
          type empty;
        }
        leaf stateless {
          type empty;
        }
      }
    }
    container mark-interface {
      uses apply-group;
      uses apply-macro;
      choice choice-trusted {
        leaf trusted {
          type empty;
        }
        leaf block {
          type empty;
        }
      }
    }
  }

  grouping esw-interface-type {
    leaf name {
      type interface-name;
    }
    uses apply-group;
    uses apply-macro;
    leaf no-mac-learning {
      type empty;
    }
  }

  grouping juniper-ip-mac-static {
    leaf name {
      type ipaddr;
    }
    uses apply-group;
    uses apply-macro;
    leaf vlan {
      type string;
    }
    leaf mac {
      type mac-addr;
    }
  }

  grouping juniper-forwarding-sandbox-options {
    leaf name {
      type string;
    }
    uses apply-group;
    uses apply-macro;
    leaf size {
      type string;
    }
    list port {
      key "name";
      uses juniper-forwarding-sandbox-port-options;
    }
  }

  grouping juniper-forwarding-sandbox-port-options {
    leaf name {
      type string;
    }
    uses apply-group;
    uses apply-macro;
    list interface {
      key "name";
      ordered-by user;
      leaf name {
        type interface-device;
      }
      uses apply-group;
      uses apply-macro;
    }
  }

  grouping juniper-logical-system {
    leaf name {
      type string;
    }
    uses apply-group;
    uses apply-macro;
    container interfaces {
      uses apply-group;
      uses apply-macro;
      list interface {
        key "name";
        uses lr-interfaces-type;
      }
    }
    container protocols {
      uses juniper-protocols;
    }
    container policy-options {
      uses juniper-policy-options;
    }
    container routing-instances {
      uses apply-group;
      uses apply-macro;
      list instance {
        key "name";
        uses juniper-routing-instance;
      }
    }
    container routing-options {
      uses juniper-routing-options;
    }
    container forwarding-options {
      uses apply-group;
      uses apply-macro;
      container dhcp-relay {
        uses jdhcp-relay-type;
      }
    }
    container system {
      uses apply-group;
      uses apply-macro;
      container services {
        uses apply-group;
        uses apply-macro;
        container dhcp-local-server {
          uses jdhcp-local-server-type;
        }
        container static-subscribers {
          uses jsscd-static-subscribers-type;
        }
      }
    }
    container access {
      uses apply-group;
      uses apply-macro;
      container address-assignment {
        uses address-assignment-type;
      }
    }
    container access-profile {
      leaf access-profile-name {
        type string;
      }
    }
    container firewall {
      uses apply-group;
      uses apply-macro;
      container family {
        uses apply-group;
        uses apply-macro;
        container inet {
          uses apply-group;
          uses apply-macro;
          list dialer-filter {
            key "name";
            ordered-by user;
            uses inet-dialer-filter;
          }
          list prefix-action {
            key "name";
            ordered-by user;
            uses prefix-action;
          }
          list filter {
            key "name";
            ordered-by user;
            uses inet-filter;
          }
          list simple-filter {
            key "name";
            ordered-by user;
            uses inet-simple-filter;
          }
          list service-filter {
            key "name";
            ordered-by user;
            uses inet-service-filter;
          }
          list fast-update-filter {
            key "name";
            ordered-by user;
            uses inet-fuf;
          }
        }
        container inet6 {
          uses apply-group;
          uses apply-macro;
          list dialer-filter {
            key "name";
            ordered-by user;
            uses inet6-dialer-filter;
          }
          list filter {
            key "name";
            ordered-by user;
            uses inet6-filter;
          }
          list service-filter {
            key "name";
            ordered-by user;
            uses inet6-service-filter;
          }
          list fast-update-filter {
            key "name";
            ordered-by user;
            uses inet6-fuf;
          }
        }
        container mpls {
          uses apply-group;
          uses apply-macro;
          list dialer-filter {
            key "name";
            ordered-by user;
            uses mpls-dialer-filter;
          }
          list filter {
            key "name";
            ordered-by user;
            uses mpls-filter;
          }
        }
        container vpls {
          uses apply-group;
          uses apply-macro;
          list filter {
            key "name";
            ordered-by user;
            uses vpls-filter;
          }
        }
        container bridge {
          uses apply-group;
          uses apply-macro;
          list filter {
            key "name";
            ordered-by user;
            uses bridge-filter;
          }
        }
        container ccc {
          uses apply-group;
          uses apply-macro;
          list filter {
            key "name";
            ordered-by user;
            uses ccc-filter;
          }
        }
        container any {
          uses apply-group;
          uses apply-macro;
          list filter {
            key "name";
            ordered-by user;
            uses any-filter;
          }
        }
        container ethernet-switching {
          uses apply-group;
          uses apply-macro;
          list filter {
            key "name";
            ordered-by user;
            uses es-filter;
          }
        }
      }
      list policer {
        key "name";
        ordered-by user;
        uses firewall-policer;
      }
      list hierarchical-policer {
        key "name";
        ordered-by user;
        uses firewall-hierpolicer;
      }
      list interface-set {
        key "name";
        ordered-by user;
        uses interface-set-type;
      }
      list load-balance-group {
        key "name";
        ordered-by user;
        uses firewall-load-balance-group;
      }
      list three-color-policer {
        key "name";
        ordered-by user;
        uses three-color-policer-type;
      }
      list filter {
        key "name";
        ordered-by user;
        uses inet-filter;
      }
    }
    container services {
      uses apply-group;
      uses apply-macro;
      container mobile-ip {
        presence "enable mobile-ip";
        uses juniper-protocols-mobile-ipv4;
      }
    }
    container bridge-domains {
      uses apply-group;
      uses apply-macro;
      list domain {
        key "name";
        uses juniper-bridge-domains;
      }
    }
    container switch-options {
      uses juniper-def-rtb-switch-options;
    }
    container security {
      uses apply-group;
      uses apply-macro;
      container apply-advanced {
        uses apply-group;
        uses apply-macro;
      }
      container alarms {
        uses apply-group;
        uses apply-macro;
        container apply-advanced {
          uses apply-group;
          uses apply-macro;
        }
        container audible {
          presence "enable audible";
          uses apply-group;
          uses apply-macro;
          container apply-advanced {
            uses apply-group;
            uses apply-macro;
          }
          leaf continuous {
            type empty;
          }
        }
        container potential-violation {
          uses apply-group;
          uses apply-macro;
          container apply-advanced {
            uses apply-group;
            uses apply-macro;
          }
          leaf authentication {
            type uint32;
          }
          leaf cryptographic-self-test {
            type empty;
          }
          container decryption-failures {
            presence "enable decryption-failures";
            uses apply-group;
            uses apply-macro;
          }
          container encryption-failures {
            presence "enable encryption-failures";
            uses apply-group;
            uses apply-macro;
          }
          container ike-phase1-failures {
            presence "enable ike-phase1-failures";
            uses apply-group;
            uses apply-macro;
          }
          container ike-phase2-failures {
            presence "enable ike-phase2-failures";
            uses apply-group;
            uses apply-macro;
          }
          leaf key-generation-self-test {
            type empty;
          }
          leaf non-cryptographic-self-test {
            type empty;
          }
          container policy {
            uses apply-group;
            uses apply-macro;
          }
          container replay-attacks {
            presence "enable replay-attacks";
            uses apply-group;
            uses apply-macro;
            container apply-advanced {
              uses apply-group;
              uses apply-macro;
            }
            leaf threshold {
              type uint32;
            }
          }
          leaf security-log-percent-full {
            type uint8;
          }
          leaf idp {
            type empty;
          }
        }
      }
      container log {
        uses apply-group;
        uses apply-macro;
        container apply-advanced {
          uses apply-group;
          uses apply-macro;
        }
        leaf disable {
          type empty;
        }
        leaf utc-timestamp {
          type empty;
        }
        leaf mode {
          type string;
        }
        leaf event-rate {
          type uint32;
        }
        leaf format {
          type string;
        }
        leaf rate-cap {
          units "logs per second";
          type uint32;
        }
        leaf max-database-record {
          type uint32;
        }
        container report {
          presence "enable report";
          uses apply-group;
          uses apply-macro;
        }
        choice choice-source-address {
          leaf source-address {
            type ipaddr;
          }
          leaf source-interface {
            type interface-name;
          }
        }
        container transport {
          presence "enable transport";
          uses apply-group;
          uses apply-macro;
          container apply-advanced {
            uses apply-group;
            uses apply-macro;
          }
          leaf tcp-connections {
            type uint32;
          }
          leaf protocol {
            type string;
          }
          leaf tls-profile {
            type string;
          }
        }
        leaf facility-override {
          type string;
        }
        list stream {
          key "name";
          ordered-by user;
          leaf name {
            type key-attribute-string-type;
          }
          uses apply-group;
          uses apply-macro;
          leaf severity {
            type string;
          }
          leaf format {
            type string;
          }
          container host {
            presence "";
            uses host-object;
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
        list exclude {
          key "name";
          ordered-by user;
          leaf name {
            type string;
          }
          uses apply-group;
          uses apply-macro;
          container apply-advanced {
            uses apply-group;
            uses apply-macro;
          }
          leaf destination-address {
            type ipaddr;
          }
          leaf destination-port {
            type uint32;
          }
          leaf event-id {
            type string;
          }
          leaf failure {
            type empty;
          }
          leaf interface-name {
            type string;
          }
          leaf policy-name {
            type string;
          }
          leaf process {
            type string;
          }
          leaf protocol {
            type string;
          }
          leaf source-address {
            type ipaddr;
          }
          leaf source-port {
            type uint32;
          }
          leaf success {
            type empty;
          }
          leaf username {
            type string;
          }
        }
        leaf limit {
          type uint32;
        }
        container cache {
          presence "enable cache";
          uses apply-group;
          uses apply-macro;
          container apply-advanced {
            uses apply-group;
            uses apply-macro;
          }
          list exclude {
            key "name";
            ordered-by user;
            leaf name {
              type string;
            }
            uses apply-group;
            uses apply-macro;
            container apply-advanced {
              uses apply-group;
              uses apply-macro;
            }
            leaf destination-address {
              type ipaddr;
            }
            leaf destination-port {
              type uint32;
            }
            leaf event-id {
              type string;
            }
            leaf failure {
              type empty;
            }
            leaf interface-name {
              type string;
            }
            leaf policy-name {
              type string;
            }
            leaf process {
              type string;
            }
            leaf protocol {
              type string;
            }
            leaf source-address {
              type ipaddr;
            }
            leaf source-port {
              type uint32;
            }
            leaf success {
              type empty;
            }
            leaf username {
              type string;
            }
          }
          leaf limit {
            type uint32;
          }
        }
      }
      container certificates {
        uses apply-group;
        uses apply-macro;
        container apply-advanced {
          uses apply-group;
          uses apply-macro;
        }
        list local {
          key "name";
          ordered-by user;
          uses certificate-object;
        }
        leaf path-length {
          type uint32;
        }
        leaf maximum-certificates {
          type uint32;
        }
        leaf cache-size {
          type string;
          units "bytes";
        }
        leaf cache-timeout-negative {
          type uint32;
        }
        leaf enrollment-retry {
          type uint32;
        }
        list certification-authority {
          key "name";
          ordered-by user;
          leaf name {
            type string;
          }
          uses apply-group;
          uses apply-macro;
          container apply-advanced {
            uses apply-group;
            uses apply-macro;
          }
          leaf ca-name {
            type string;
          }
          leaf file {
            type string;
          }
          leaf crl {
            type string;
          }
          leaf enrollment-url {
            type string;
          }
          leaf ldap-url {
            type string;
          }
          leaf encoding {
            type string;
          }
        }
      }
      container ssh-known-hosts {
        uses apply-group;
        uses apply-macro;
        container apply-advanced {
          uses apply-group;
          uses apply-macro;
        }
        list host {
          key "name";
          ordered-by user;
          leaf name {
            type string;
          }
          uses apply-group;
          uses apply-macro;
          container apply-advanced {
            uses apply-group;
            uses apply-macro;
          }
          leaf rsa1-key {
            type string;
          }
          leaf rsa-key {
            type string;
          }
          leaf dsa-key {
            type string;
          }
          leaf ecdsa-key {
            type string;
          }
          leaf ecdsa-sha2-nistp256-key {
            type string;
          }
          leaf ecdsa-sha2-nistp384-key {
            type string;
          }
          leaf ecdsa-sha2-nistp521-key {
            type string;
          }
          leaf ed25519-key {
            type string;
          }
        }
      }
      leaf key-protection {
        type empty;
      }
      container pki {
        presence "enable pki";
        uses security-pki;
      }
      container group-vpn {
        uses security-group-vpn;
      }
      container gprs {
        presence "enable gprs";
        uses apply-group;
        uses apply-macro;
        container gtp {
          presence "enable gtp";
          uses apply-group;
          uses apply-macro;
          leaf enable {
            type empty;
          }
          list profile {
            key "name";
            leaf name {
              type key-attribute-string-type;
            }
            uses apply-group;
            uses apply-macro;
            leaf min-message-length {
              type uint32;
            }
            leaf max-message-length {
              type uint32;
            }
            leaf timeout {
              type uint32;
            }
            leaf rate-limit {
              type uint32;
            }
            container log {
              presence "enable log";
              uses apply-group;
              uses apply-macro;
              leaf forwarded {
                type string;
              }
              leaf state-invalid {
                type string;
              }
              leaf prohibited {
                type string;
              }
              container rate-limited {
                presence "enable rate-limited";
                uses apply-group;
                uses apply-macro;
                choice choice-3 {
                  leaf basic {
                    type empty;
                  }
                  leaf detail {
                    type empty;
                  }
                }
                leaf frequency-number {
                  type uint32;
                }
              }
            }
            leaf remove-r6 {
              type empty;
            }
            container drop {
              presence "enable drop";
              uses apply-group;
              uses apply-macro;
              leaf aa-create-pdp {
                type string;
              }
              leaf aa-delete-pdp {
                type string;
              }
              leaf create-pdp {
                type string;
              }
              leaf data-record {
                type string;
              }
              leaf delete-pdp {
                type string;
              }
              leaf echo {
                type string;
              }
              leaf error-indication {
                type string;
              }
              leaf failure-report {
                type string;
              }
              leaf fwd-relocation {
                type string;
              }
              leaf fwd-srns-context {
                type string;
              }
              leaf g-pdu {
                type string;
              }
              leaf identification {
                type string;
              }
              leaf node-alive {
                type string;
              }
              leaf note-ms-present {
                type string;
              }
              leaf pdu-notification {
                type string;
              }
              leaf ran-info {
                type string;
              }
              leaf redirection {
                type string;
              }
              leaf relocation-cancel {
                type string;
              }
              leaf send-route {
                type string;
              }
              leaf sgsn-context {
                type string;
              }
              leaf supported-extension {
                type string;
              }
              leaf update-pdp {
                type string;
              }
              leaf ver-not-supported {
                type string;
              }
            }
            list apn {
              key "name";
              leaf name {
                type key-attribute-string-type;
              }
              uses apply-group;
              uses apply-macro;
              list mcc-mnc {
                key "name";
                leaf name {
                  type key-attribute-string-type;
                }
                uses apply-group;
                uses apply-macro;
                container action {
                  presence "enable action";
                  uses apply-group;
                  uses apply-macro;
                  choice choice-3 {
                    leaf pass {
                      type empty;
                    }
                    leaf drop {
                      type empty;
                    }
                    container selection {
                      presence "enable selection";
                      uses apply-group;
                      uses apply-macro;
                      leaf ms {
                        type empty;
                      }
                      leaf net {
                        type empty;
                      }
                      leaf vrf {
                        type empty;
                      }
                    }
                  }
                }
              }
            }
            leaf seq-number-validated {
              type empty;
            }
          }
          container traceoptions {
            uses apply-group;
            uses apply-macro;
            leaf no-remote-trace {
              type empty;
            }
            container file {
              leaf filename {
                type string;
              }
              leaf size {
                type string;
              }
              leaf files {
                type uint32;
              }
              leaf world-readable {
                type empty;
              }
              leaf no-world-readable {
                type empty;
              }
              leaf match {
                type regular-expression;
              }
            }
            list flag {
              key "name";
              ordered-by user;
              leaf name {
                type string;
              }
            }
          }
        }
        container sctp {
          presence "enable sctp";
          uses apply-group;
          uses apply-macro;
          list profile {
            key "name";
            leaf name {
              type key-attribute-string-type;
            }
            uses apply-group;
            uses apply-macro;
            leaf association-timeout {
              type uint32;
            }
            leaf handshake-timeout {
              type uint32;
            }
            container drop {
              presence "enable drop";
              uses apply-group;
              uses apply-macro;
              list m3ua-service {
                key "name";
                ordered-by user;
                leaf name {
                  type string;
                }
              }
              list payload-protocol {
                key "name";
                ordered-by user;
                leaf name {
                  type string;
                }
              }
            }
            container limit {
              presence "enable limit";
              uses apply-group;
              uses apply-macro;
              container rate {
                presence "enable rate";
                uses apply-group;
                uses apply-macro;
                leaf sccp {
                  type uint16;
                }
                leaf ssp {
                  type uint16;
                }
                leaf sst {
                  type uint16;
                }
                list address {
                  key "name";
                  ordered-by user;
                  leaf name {
                    type ipv4addr;
                  }
                  uses apply-group;
                  uses apply-macro;
                  leaf sccp {
                    type uint16;
                  }
                  leaf ssp {
                    type uint16;
                  }
                  leaf sst {
                    type uint16;
                  }
                }
              }
            }
          }
          list log {
            key "name";
            ordered-by user;
            leaf name {
              type string;
            }
          }
          container traceoptions {
            uses apply-group;
            uses apply-macro;
            leaf no-remote-trace {
              type empty;
            }
            container file {
              leaf filename {
                type string;
              }
              leaf size {
                type string;
              }
              leaf files {
                type uint32;
              }
              leaf world-readable {
                type empty;
              }
              leaf no-world-readable {
                type empty;
              }
              leaf match {
                type regular-expression;
              }
            }
            list flag {
              key "name";
              ordered-by user;
              leaf name {
                type string;
              }
            }
          }
        }
      }
      container nat {
        uses apply-group;
        uses apply-macro;
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
            leaf syslog {
              type empty;
            }
          }
        }
        container source {
          uses ssg-source-nat-object;
        }
        container destination {
          uses ssg-destination-nat-object;
        }
        container static {
          uses ssg-static-nat-object;
        }
        container proxy-arp {
          uses ssg-proxy-arp-object;
        }
      }
      container screen {
        uses apply-group;
        uses apply-macro;
        list ids-option {
          key "name";
          uses ids-option-type;
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
      }
      container zones {
        uses apply-group;
        uses apply-macro;
        container functional-zone {
          presence "enable functional-zone";
          uses apply-group;
          uses apply-macro;
          container management {
            presence "enable management";
            uses apply-group;
            uses apply-macro;
            list interfaces {
              key "name";
              ordered-by user;
              uses zone-interface-list-type;
            }
            leaf screen {
              type string;
            }
            container host-inbound-traffic {
              uses zone-host-inbound-traffic-t;
            }
          }
        }
        list security-zone {
          key "name";
          ordered-by user;
          uses security-zone-type;
        }
      }
      container policies {
        presence "enable policies";
        uses policy-object-type;
      }
      container traceoptions {
        uses apply-group;
        uses apply-macro;
        container apply-advanced {
          uses apply-group;
          uses apply-macro;
        }
        leaf no-remote-trace {
          type empty;
        }
        container file {
          leaf filename {
            type string;
          }
          leaf size {
            type string;
          }
          leaf files {
            type uint32;
          }
          leaf world-readable {
            type empty;
          }
          leaf no-world-readable {
            type empty;
          }
          leaf match {
            type regular-expression;
          }
        }
        leaf rate-limit {
          type uint32;
        }
        container filter {
          uses apply-group;
          uses apply-macro;
          container apply-advanced {
            uses apply-group;
            uses apply-macro;
          }
          leaf fpc {
            type uint32;
          }
          leaf pic {
            type uint32;
          }
        }
        list flag {
          key "name";
          ordered-by user;
          leaf name {
            type string;
          }
        }
        leaf level {
          type string;
        }
      }
      container ipsec {
        uses security-ipsec;
      }
      list address-book {
        key "name";
        ordered-by user;
        uses named-address-book-type;
      }
      container ike {
        uses security-ike;
      }
      container authentication-key-chains {
        uses security-authentication-key-chains;
      }
      container datapath-debug {
        uses apply-group;
        uses apply-macro;
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
        }
        container capture-file {
          presence "";
          leaf filename {
            type string;
          }
          leaf format {
            type string;
          }
          leaf size {
            type string;
          }
          leaf files {
            type uint32;
          }
          leaf world-readable {
            type empty;
          }
          leaf no-world-readable {
            type empty;
          }
        }
        leaf maximum-capture-size {
          type uint32;
        }
        list action-profile {
          key "name";
          ordered-by user;
          uses e2e-action-profile;
        }
        list packet-filter {
          key "name";
          ordered-by user;
          uses end-to-end-debug-filter;
        }
      }
      container alg {
        uses apply-group;
        uses apply-macro;
        container dns {
          leaf disable {
            type empty;
          }
          leaf maximum-message-length {
            type uint32;
          }
          container traceoptions {
            uses apply-group;
            uses apply-macro;
            list flag {
              key "name";
              ordered-by user;
              leaf name {
                type string;
              }
              choice choice-3 {
                leaf extensive {
                  type empty;
                }
              }
            }
          }
        }
        container ftp {
          leaf disable {
            type empty;
          }
          leaf ftps-extension {
            type empty;
          }
          leaf line-break-extension {
            type empty;
          }
          container traceoptions {
            uses apply-group;
            uses apply-macro;
            list flag {
              key "name";
              ordered-by user;
              leaf name {
                type string;
              }
              choice choice-3 {
                leaf extensive {
                  type empty;
                }
              }
            }
          }
        }
        container h323 {
          presence "enable h323";
          uses apply-group;
          uses apply-macro;
          leaf disable {
            type empty;
          }
          leaf endpoint-registration-timeout {
            type uint32;
          }
          leaf media-source-port-any {
            type empty;
          }
          container application-screen {
            uses apply-group;
            uses apply-macro;
            container unknown-message {
              uses apply-group;
              uses apply-macro;
              leaf permit-nat-applied {
                type empty;
              }
              leaf permit-routed {
                type empty;
              }
            }
            container message-flood {
              uses apply-group;
              uses apply-macro;
              container gatekeeper {
                leaf threshold {
                  type uint32;
                }
              }
            }
          }
          container dscp-rewrite {
            uses apply-group;
            uses apply-macro;
            leaf code-point {
              type string;
            }
          }
          container traceoptions {
            uses apply-group;
            uses apply-macro;
            list flag {
              key "name";
              ordered-by user;
              leaf name {
                type string;
              }
              choice choice-3 {
                leaf terse {
                  type empty;
                }
                leaf detail {
                  type empty;
                }
                leaf extensive {
                  type empty;
                }
              }
            }
          }
        }
        container mgcp {
          presence "enable mgcp";
          uses apply-group;
          uses apply-macro;
          leaf disable {
            type empty;
          }
          leaf inactive-media-timeout {
            type uint32;
          }
          leaf transaction-timeout {
            type uint32;
          }
          leaf maximum-call-duration {
            type uint32;
          }
          container application-screen {
            uses apply-group;
            uses apply-macro;
            container unknown-message {
              uses apply-group;
              uses apply-macro;
              leaf permit-nat-applied {
                type empty;
              }
              leaf permit-routed {
                type empty;
              }
            }
            container message-flood {
              leaf threshold {
                type uint32;
              }
            }
            container connection-flood {
              leaf threshold {
                type uint32;
              }
            }
          }
          container dscp-rewrite {
            uses apply-group;
            uses apply-macro;
            leaf code-point {
              type string;
            }
          }
          container traceoptions {
            uses apply-group;
            uses apply-macro;
            list flag {
              key "name";
              ordered-by user;
              leaf name {
                type string;
              }
              choice choice-3 {
                leaf extensive {
                  type empty;
                }
              }
            }
          }
        }
        container msrpc {
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container sunrpc {
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container real {
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container rsh {
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container rtsp {
          presence "enable rtsp";
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container sccp {
          presence "enable sccp";
          uses apply-group;
          uses apply-macro;
          leaf disable {
            type empty;
          }
          leaf inactive-media-timeout {
            type uint32;
          }
          container application-screen {
            uses apply-group;
            uses apply-macro;
            container unknown-message {
              uses apply-group;
              uses apply-macro;
              leaf permit-nat-applied {
                type empty;
              }
              leaf permit-routed {
                type empty;
              }
            }
            container call-flood {
              leaf threshold {
                type uint32;
              }
            }
          }
          container dscp-rewrite {
            uses apply-group;
            uses apply-macro;
            leaf code-point {
              type string;
            }
          }
          container traceoptions {
            uses apply-group;
            uses apply-macro;
            list flag {
              key "name";
              ordered-by user;
              leaf name {
                type string;
              }
              choice choice-3 {
                leaf extensive {
                  type empty;
                }
              }
            }
          }
        }
        container sip {
          presence "enable sip";
          uses apply-group;
          uses apply-macro;
          leaf disable {
            type empty;
          }
          leaf inactive-media-timeout {
            type uint32;
          }
          leaf maximum-call-duration {
            type uint32;
          }
          leaf t1-interval {
            type uint32;
          }
          leaf t4-interval {
            type uint32;
          }
          leaf c-timeout {
            type uint32;
          }
          leaf retain-hold-resource {
            type empty;
          }
          container application-screen {
            uses apply-group;
            uses apply-macro;
            container unknown-message {
              uses apply-group;
              uses apply-macro;
              leaf permit-nat-applied {
                type empty;
              }
              leaf permit-routed {
                type empty;
              }
            }
            container protect {
              uses apply-group;
              uses apply-macro;
              container deny {
                presence "enable deny";
                uses apply-group;
                uses apply-macro;
                choice choice-3 {
                  list destination-ip {
                    key "name";
                    ordered-by user;
                    leaf name {
                      type ipv4addr;
                    }
                    uses apply-group;
                    uses apply-macro;
                  }
                  leaf all {
                    type empty;
                  }
                }
                leaf timeout {
                  type uint32;
                }
              }
            }
          }
          container dscp-rewrite {
            uses apply-group;
            uses apply-macro;
            leaf code-point {
              type string;
            }
          }
          container traceoptions {
            uses apply-group;
            uses apply-macro;
            list flag {
              key "name";
              ordered-by user;
              leaf name {
                type string;
              }
              choice choice-3 {
                leaf terse {
                  type empty;
                }
                leaf detail {
                  type empty;
                }
                leaf extensive {
                  type empty;
                }
              }
            }
          }
        }
        container sql {
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container talk {
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container tftp {
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container pptp {
          leaf disable {
            type empty;
          }
          container traceoptions {
            uses apply-group;
            uses apply-macro;
            list flag {
              key "name";
              ordered-by user;
              leaf name {
                type string;
              }
              choice choice-3 {
                leaf extensive {
                  type empty;
                }
              }
            }
          }
        }
        container ike-esp-nat {
          uses apply-group;
          uses apply-macro;
          leaf enable {
            type empty;
          }
          leaf esp-gate-timeout {
            type uint32;
          }
          leaf esp-session-timeout {
            type uint32;
          }
          leaf state-timeout {
            type uint32;
          }
          container traceoptions {
            uses apply-group;
            uses apply-macro;
            list flag {
              key "name";
              ordered-by user;
              leaf name {
                type string;
              }
              choice choice-3 {
                leaf extensive {
                  type empty;
                }
              }
            }
          }
        }
      }
      container application-firewall {
        presence "enable application-firewall";
        uses apply-group;
        uses apply-macro;
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
        list profile {
          key "name";
          ordered-by user;
          leaf name {
            type key-attribute-string-type;
          }
          uses apply-group;
          uses apply-macro;
          container block-message {
            presence "";
            uses apply-group;
            uses apply-macro;
            container type {
              uses apply-group;
              uses apply-macro;
              choice choice-custom-text {
                container custom-text {
                  uses apply-group;
                  uses apply-macro;
                  leaf content {
                    type string;
                  }
                }
                container custom-redirect-url {
                  uses apply-group;
                  uses apply-macro;
                  leaf content {
                    type string;
                  }
                }
              }
            }
          }
        }
        list rule-sets {
          key "name";
          ordered-by user;
          leaf name {
            type key-attribute-string-type;
          }
          uses apply-group;
          uses apply-macro;
          list rule {
            key "name";
            ordered-by user;
            uses appfw-rule-type;
          }
          container default-rule {
            presence "enable default-rule";
            uses apply-group;
            uses apply-macro;
            choice choice-permit {
              leaf permit {
                type empty;
              }
              container deny {
                presence "enable deny";
                uses apply-group;
                uses apply-macro;
                leaf block-message {
                  type empty;
                }
              }
              container reject {
                presence "enable reject";
                uses apply-group;
                uses apply-macro;
                leaf block-message {
                  type empty;
                }
              }
            }
          }
          leaf profile {
            type string;
          }
        }
      }
      container forwarding-process {
        presence "";
        uses apply-group;
        uses apply-macro;
        container application-services {
          uses apply-group;
          uses apply-macro;
          leaf maximize-alg-sessions {
            type empty;
          }
          leaf maximize-cp-sessions {
            type empty;
          }
          container maximize-idp-sessions {
            presence "enable maximize-idp-sessions";
            uses apply-group;
            uses apply-macro;
            container weight {
              uses apply-group;
              uses apply-macro;
              choice choice-3 {
                leaf equal {
                  type empty;
                }
                container idp {
                  presence "enable idp";
                  uses apply-group;
                  uses apply-macro;
                }
                leaf firewall {
                  type empty;
                }
              }
            }
            leaf inline-tap {
              type empty;
            }
          }
        }
      }
      container resource-manager {
        uses apply-group;
        uses apply-macro;
        container traceoptions {
          uses apply-group;
          uses apply-macro;
          list flag {
            key "name";
            ordered-by user;
            leaf name {
              type string;
            }
            choice choice-3 {
              leaf terse {
                type empty;
              }
              leaf detail {
                type empty;
              }
              leaf extensive {
                type empty;
              }
            }
          }
        }
      }
      container firewall-authentication {
        uses apply-group;
        uses apply-macro;
        container traceoptions {
          uses apply-group;
          uses apply-macro;
          list flag {
            key "name";
            ordered-by user;
            leaf name {
              type string;
            }
            choice choice-3 {
              leaf terse {
                type empty;
              }
              leaf detail {
                type empty;
              }
              leaf extensive {
                type empty;
              }
            }
          }
        }
      }
      container application-tracking {
        presence "enable application-tracking";
        uses apply-group;
        uses apply-macro;
        choice choice-3 {
          leaf first-update-interval {
            type uint32;
          }
          leaf first-update {
            type empty;
          }
        }
        leaf session-update-interval {
          type uint32;
        }
      }
      container forwarding-options {
        uses apply-group;
        uses apply-macro;
        container family {
          uses apply-group;
          uses apply-macro;
          container inet6 {
            uses apply-group;
            uses apply-macro;
            leaf mode {
              type string;
            }
          }
          container mpls {
            uses apply-group;
            uses apply-macro;
            leaf mode {
              type string;
            }
          }
          container iso {
            uses apply-group;
            uses apply-macro;
            leaf mode {
              type string;
            }
          }
        }
      }
      container flow {
        uses apply-group;
        uses apply-macro;
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
          leaf rate-limit {
            type uint32;
          }
          list packet-filter {
            key "name";
            ordered-by user;
            uses flow-filter-type;
          }
        }
        leaf pending-sess-queue-length {
          type string;
        }
        leaf allow-dns-reply {
          type empty;
        }
        leaf route-change-timeout {
          type uint32;
        }
        leaf syn-flood-protection-mode {
          type string;
        }
        container aging {
          uses apply-group;
          uses apply-macro;
          leaf early-ageout {
            type uint32;
          }
          leaf low-watermark {
            type uint32;
          }
          leaf high-watermark {
            type uint32;
          }
        }
        container bridge {
          uses apply-group;
          uses apply-macro;
          leaf block-non-ip-all {
            type empty;
          }
          leaf bypass-non-ip-unicast {
            type empty;
          }
          container no-packet-flooding {
            presence "enable no-packet-flooding";
            uses apply-group;
            uses apply-macro;
            leaf no-trace-route {
              type empty;
            }
          }
        }
        container tcp-mss {
          uses apply-group;
          uses apply-macro;
          container all-tcp {
            presence "";
            uses apply-group;
            uses apply-macro;
            leaf mss {
              type uint32;
            }
          }
          container ipsec-vpn {
            presence "enable ipsec-vpn";
            uses apply-group;
            uses apply-macro;
            leaf mss {
              type uint32;
            }
          }
          container gre-in {
            presence "enable gre-in";
            uses apply-group;
            uses apply-macro;
            leaf mss {
              type uint32;
            }
          }
          container gre-out {
            presence "enable gre-out";
            uses apply-group;
            uses apply-macro;
            leaf mss {
              type uint32;
            }
          }
        }
        container tcp-session {
          uses apply-group;
          uses apply-macro;
          leaf rst-invalidate-session {
            type empty;
          }
          leaf rst-sequence-check {
            type empty;
          }
          leaf no-syn-check {
            type empty;
          }
          leaf strict-syn-check {
            type empty;
          }
          leaf no-syn-check-in-tunnel {
            type empty;
          }
          leaf no-sequence-check {
            type empty;
          }
          leaf tcp-initial-timeout {
            type uint32;
          }
          container time-wait-state {
            presence "enable time-wait-state";
            uses apply-group;
            uses apply-macro;
            choice choice-3 {
              leaf session-ageout {
                type empty;
              }
              leaf session-timeout {
                type uint32;
              }
            }
          }
        }
      }
      container utm {
        uses apply-group;
        uses apply-macro;
        container traceoptions {
          uses utm-traceoptions;
        }
        container application-proxy {
          uses apply-group;
          uses apply-macro;
          container traceoptions {
            uses utm-apppxy-traceoptions;
          }
        }
        container ipc {
          uses apply-group;
          uses apply-macro;
          container traceoptions {
            uses utm-ipc-traceoptions;
          }
        }
        container custom-objects {
          uses apply-group;
          uses apply-macro;
          list mime-pattern {
            key "name";
            ordered-by user;
            uses mime-list-type;
          }
          list filename-extension {
            key "name";
            ordered-by user;
            uses extension-list-type;
          }
          list url-pattern {
            key "name";
            ordered-by user;
            uses url-list-type;
          }
          list custom-url-category {
            key "name";
            ordered-by user;
            uses category-list-type;
          }
          list protocol-command {
            key "name";
            ordered-by user;
            uses command-list-type;
          }
        }
        container feature-profile {
          uses apply-group;
          uses apply-macro;
          container anti-virus {
            uses anti-virus-feature;
          }
          container web-filtering {
            uses webfilter-feature;
          }
          container anti-spam {
            uses anti-spam-feature;
          }
          container content-filtering {
            uses content-filtering-feature;
          }
        }
        list utm-policy {
          key "name";
          ordered-by user;
          uses profile-setting;
        }
      }
      container dynamic-vpn {
        presence "";
        uses apply-group;
        uses apply-macro;
        leaf force-upgrade {
          type empty;
        }
        leaf access-profile {
          type string;
        }
        list clients {
          key "name";
          ordered-by user;
          uses clients-object;
        }
      }
      container analysis {
        uses apply-group;
        uses apply-macro;
        leaf no-report {
          type empty;
        }
      }
      container softwires {
        uses apply-group;
        uses apply-macro;
        list softwire-name {
          key "name";
          uses softwire-option-type;
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
      }
      container idp {
        list idp-policy {
          key "name";
          ordered-by user;
          uses idp-policy-type;
        }
        leaf active-policy {
          type string;
        }
        list custom-attack {
          key "name";
          ordered-by user;
          uses custom-attack-type;
        }
        list custom-attack-group {
          key "name";
          ordered-by user;
          uses custom-attack-group-type;
        }
        list dynamic-attack-group {
          key "name";
          ordered-by user;
          uses dynamic-attack-group-type;
        }
        list application-ddos {
          key "name";
          ordered-by user;
          uses application-ddos-type;
        }
        container traceoptions {
          uses idpd-traceoptions-type;
        }
        container security-package {
          uses apply-group;
          uses apply-macro;
          container apply-advanced {
            uses apply-group;
            uses apply-macro;
          }
          leaf url {
            type string;
          }
          leaf source-address {
            type ipv4addr;
          }
          container install {
            presence "enable install";
            uses apply-group;
            uses apply-macro;
            container apply-advanced {
              uses apply-group;
              uses apply-macro;
            }
            leaf ignore-version-check {
              type empty;
            }
          }
          container automatic {
            presence "enable automatic";
            uses apply-group;
            uses apply-macro;
            container apply-advanced {
              uses apply-group;
              uses apply-macro;
            }
            leaf start-time {
              type time;
            }
            leaf interval {
              units "hours";
              type string;
            }
            leaf download-timeout {
              units "minutes";
              type uint32;
            }
            leaf enable-disable {
              type string;
            }
            leaf enable {
              type empty;
            }
          }
        }
        container sensor-configuration {
          container log {
            uses apply-group;
            uses apply-macro;
            container apply-advanced {
              uses apply-group;
              uses apply-macro;
            }
            leaf cache-size {
              type uint32;
            }
            container suppression {
              presence "enable suppression";
              uses apply-group;
              uses apply-macro;
              container apply-advanced {
                uses apply-group;
                uses apply-macro;
              }
              leaf enable-disable {
                type string;
              }
              leaf disable {
                type empty;
              }
              leaf include-destination-address {
                type empty;
              }
              leaf no-include-destination-address {
                type empty;
              }
              leaf start-log {
                type uint32;
              }
              leaf max-logs-operate {
                type uint32;
              }
              leaf max-time-report {
                type uint32;
              }
            }
          }
          container packet-log {
            presence "";
            uses apply-group;
            uses apply-macro;
            container apply-advanced {
              uses apply-group;
              uses apply-macro;
            }
            leaf total-memory {
              type uint32;
            }
            leaf max-sessions {
              type uint32;
            }
            leaf source-address {
              mandatory true;
              type ipv4addr;
            }
            container host {
              presence "";
              uses apply-group;
              uses apply-macro;
              container apply-advanced {
                uses apply-group;
                uses apply-macro;
              }
              leaf ipaddr {
                mandatory true;
                type ipv4addr;
              }
              leaf port {
                type uint16;
                mandatory true;
              }
            }
          }
          container application-identification {
            presence "enable application-identification";
            uses apply-group;
            uses apply-macro;
            container apply-advanced {
              uses apply-group;
              uses apply-macro;
            }
            leaf enable-disable {
              type string;
            }
            leaf disable {
              type empty;
            }
            leaf application-system-cache {
              type empty;
            }
            leaf no-application-system-cache {
              type empty;
            }
            leaf max-tcp-session-packet-memory {
              type uint32;
            }
            leaf max-udp-session-packet-memory {
              type uint32;
            }
            leaf max-sessions {
              type uint32;
            }
            leaf max-packet-memory {
              type uint32;
            }
            leaf application-system-cache-timeout {
              type uint32;
            }
          }
          container flow {
            uses apply-group;
            uses apply-macro;
            container apply-advanced {
              uses apply-group;
              uses apply-macro;
            }
            leaf log-errors {
              type empty;
            }
            leaf no-log-errors {
              type empty;
            }
            leaf reset-on-policy {
              type empty;
            }
            leaf no-reset-on-policy {
              type empty;
            }
            leaf allow-icmp-without-flow {
              type empty;
            }
            leaf no-allow-icmp-without-flow {
              type empty;
            }
            leaf hash-table-size {
              type uint32;
            }
            leaf reject-timeout {
              type uint32;
            }
            leaf max-timers-poll-ticks {
              type uint32;
            }
            leaf fifo-max-size {
              type uint32;
            }
            leaf udp-anticipated-timeout {
              type uint32;
            }
            leaf allow-nonsyn-connection {
              type empty;
            }
          }
          container re-assembler {
            uses apply-group;
            uses apply-macro;
            container apply-advanced {
              uses apply-group;
              uses apply-macro;
            }
            leaf ignore-memory-overflow {
              type empty;
            }
            leaf no-ignore-memory-overflow {
              type empty;
            }
            leaf ignore-reassembly-memory-overflow {
              type empty;
            }
            leaf no-ignore-reassembly-memory-overflow {
              type empty;
            }
            leaf ignore-reassembly-overflow {
              type empty;
            }
            leaf max-packet-mem {
              type uint32;
            }
            leaf max-flow-mem {
              type uint32;
            }
          }
          container ips {
            uses apply-group;
            uses apply-macro;
            container apply-advanced {
              uses apply-group;
              uses apply-macro;
            }
            leaf process-override {
              type empty;
            }
            leaf no-process-override {
              type empty;
            }
            leaf detect-shellcode {
              type empty;
            }
            leaf no-detect-shellcode {
              type empty;
            }
            leaf process-ignore-s2c {
              type empty;
            }
            leaf no-process-ignore-s2c {
              type empty;
            }
            leaf ignore-regular-expression {
              type empty;
            }
            leaf no-ignore-regular-expression {
              type empty;
            }
            leaf process-port {
              type uint32;
            }
            leaf fifo-max-size {
              type uint32;
            }
            leaf log-supercede-min {
              type uint32;
            }
            leaf content-decompression-max-memory-kb {
              type uint32;
            }
            leaf content-decompression-max-ratio {
              type uint32;
            }
          }
          container global {
            uses apply-group;
            uses apply-macro;
            container apply-advanced {
              uses apply-group;
              uses apply-macro;
            }
            leaf enable-packet-pool {
              type empty;
            }
            leaf no-enable-packet-pool {
              type empty;
            }
            leaf enable-all-qmodules {
              type empty;
            }
            leaf no-enable-all-qmodules {
              type empty;
            }
            leaf policy-lookup-cache {
              type empty;
            }
            leaf no-policy-lookup-cache {
              type empty;
            }
            leaf memory-limit-percent {
              type uint32;
            }
            container gtp {
              uses apply-group;
              uses apply-macro;
              container apply-advanced {
                uses apply-group;
                uses apply-macro;
              }
              leaf decapsulation {
                type empty;
              }
              leaf no-decapsulation {
                type empty;
              }
            }
          }
          container detector {
            uses apply-group;
            uses apply-macro;
            container apply-advanced {
              uses apply-group;
              uses apply-macro;
            }
            list protocol-name {
              key "name";
              ordered-by user;
              uses proto-object;
            }
          }
          container ssl-inspection {
            uses apply-group;
            uses apply-macro;
            container apply-advanced {
              uses apply-group;
              uses apply-macro;
            }
            leaf sessions {
              type uint32;
            }
            leaf session-id-cache-timeout {
              units "seconds";
              type uint32;
            }
            leaf maximum-cache-size {
              units "sessions";
              type uint32;
            }
            leaf cache-prune-chunk-size {
              type uint32;
            }
            leaf key-protection {
              type empty;
            }
          }
          container application-ddos {
            uses apply-group;
            uses apply-macro;
            container apply-advanced {
              uses apply-group;
              uses apply-macro;
            }
            container statistics {
              presence "enable statistics";
              uses apply-group;
              uses apply-macro;
              container apply-advanced {
                uses apply-group;
                uses apply-macro;
              }
              leaf interval {
                units "minutes";
                type uint32;
              }
            }
          }
          container high-availability {
            uses apply-group;
            uses apply-macro;
            container apply-advanced {
              uses apply-group;
              uses apply-macro;
            }
            leaf no-policy-cold-synchronization {
              type empty;
            }
          }
        }
        container processes {
          uses apply-group;
          uses apply-macro;
        }
      }
      container macsec {
        uses security-macsec;
      }
    }
    container applications {
      uses apply-group;
      uses apply-macro;
      list application {
        key "name";
        ordered-by user;
        uses application-object;
      }
      list application-set {
        key "name";
        ordered-by user;
        uses application-set-object;
      }
    }
  }

  grouping jdhcp-local-server-type {
    uses apply-group;
    uses apply-macro;
    container traceoptions {
      uses jdhcp-traceoptions-type;
    }
    container interface-traceoptions {
      uses jdhcp-interface-traceoptions-type;
    }
    container dhcpv6 {
      uses dhcpv6-local-server-type;
    }
    list pool-match-order {
      key "name";
      ordered-by user;
      leaf name {
        type string;
      }
      uses apply-group;
      uses apply-macro;
    }
    leaf duplicate-clients-on-interface {
      type empty;
    }
    container forward-snooped-clients {
      choice choice-3 {
        leaf configured-interfaces {
          type empty;
        }
        leaf non-configured-interfaces {
          type empty;
        }
        leaf all-interfaces {
          type empty;
        }
      }
    }
    container authentication {
      uses authentication-type;
    }
    container reconfigure {
      presence "enable reconfigure";
      uses reconfigure-type;
    }
    container overrides {
      presence "enable overrides";
      uses override-local-server-type;
    }
    container dynamic-profile {
      presence "";
      uses dynamic-profile-type;
    }
    list group {
      key "name";
      ordered-by user;
      uses dhcp-local-server-group;
    }
    container persistent-storage {
      leaf automatic {
        type empty;
      }
    }
  }

  grouping dhcp-local-server-group {
    leaf name {
      type key-attribute-string-type;
    }
    uses apply-group;
    uses apply-macro;
    container authentication {
      uses authentication-type;
    }
    container reconfigure {
      presence "enable reconfigure";
      uses reconfigure-type;
    }
    container overrides {
      presence "enable overrides";
      uses override-local-server-type;
    }
    container dynamic-profile {
      presence "";
      uses dynamic-profile-type;
    }
    list interface {
      key "name";
      leaf name {
        type interface-name;
      }
      uses apply-group;
      uses apply-macro;
      leaf upto {
        type interface-name;
      }
      leaf exclude {
        type empty;
      }
      leaf trace {
        type empty;
      }
      container overrides {
        uses override-local-server-type;
      }
    }
  }

  grouping dhcpv6-local-server-type {
    uses apply-group;
    uses apply-macro;
    container authentication {
      uses dhcpv6-authentication-type;
    }
    container reconfigure {
      presence "enable reconfigure";
      uses dhcpv6-reconfigure-type;
    }
    container dynamic-profile {
      presence "";
      uses dynamic-profile-type;
    }
    container overrides {
      presence "enable overrides";
      uses dhcpv6-override-local-server-type;
    }
    list group {
      key "name";
      ordered-by user;
      uses dhcpv6-local-server-group;
    }
  }

  grouping dhcpv6-local-server-group {
    leaf name {
      type key-attribute-string-type;
    }
    uses apply-group;
    uses apply-macro;
    container authentication {
      uses dhcpv6-authentication-type;
    }
    container reconfigure {
      presence "enable reconfigure";
      uses dhcpv6-reconfigure-type;
    }
    container dynamic-profile {
      presence "";
      uses dynamic-profile-type;
    }
    container overrides {
      presence "enable overrides";
      uses dhcpv6-override-local-server-type;
    }
    list interface {
      key "name";
      leaf name {
        type interface-name;
      }
      uses apply-group;
      uses apply-macro;
      leaf upto {
        type interface-name;
      }
      leaf exclude {
        type empty;
      }
      leaf trace {
        type empty;
      }
      container overrides {
        uses dhcpv6-override-local-server-type;
      }
    }
  }

  grouping dhcpv6-override-local-server-type {
    uses apply-group;
    uses apply-macro;
    leaf interface-client-limit {
      type uint32;
    }
    leaf rapid-commit {
      type empty;
    }
    container client-negotiation-match {
      leaf incoming-interface {
        type empty;
      }
    }
    container process-inform {
      presence "enable process-inform";
      uses apply-group;
      uses apply-macro;
      leaf pool {
        type string;
      }
    }
    container delay-advertise {
      presence "";
      uses dhcpv6-filter-option;
    }
    leaf delegated-pool {
      type string;
    }
    leaf multi-address-embedded-option-response {
      type empty;
    }
    leaf always-process-option-request-option {
      type empty;
    }
    leaf delete-binding-on-renegotiation {
      type empty;
    }
    leaf top-level-status-code {
      type empty;
    }
    leaf always-add-option-dns-server {
      type empty;
    }
    leaf asymmetric-lease-time {
      units "seconds";
      type uint32;
    }
    leaf asymmetric-prefix-lease-time {
      units "seconds";
      type uint32;
    }
    leaf protocol-attributes {
      type string;
    }
    leaf dual-stack {
      type string;
    }
  }

  grouping dhcpv6-filter-option {
    uses apply-group;
    uses apply-macro;
    leaf delay-time {
      units "seconds";
      type uint32;
    }
    container based-on {
      uses apply-group;
      uses apply-macro;
      container option-18 {
        presence "enable option-18";
        uses apply-group;
        uses apply-macro;
        container equals {
          uses server-v6-option-ascii-hex;
        }
        container not-equals {
          uses server-v6-option-ascii-hex;
        }
        container starts-with {
          uses server-v6-option-ascii-hex;
        }
      }
      container option-37 {
        presence "enable option-37";
        uses apply-group;
        uses apply-macro;
        container equals {
          uses server-v6-option-ascii-hex;
        }
        container not-equals {
          uses server-v6-option-ascii-hex;
        }
        container starts-with {
          uses server-v6-option-ascii-hex;
        }
      }
      container option-15 {
        presence "enable option-15";
        uses apply-group;
        uses apply-macro;
        container equals {
          uses server-v6-option-ascii-hex;
        }
        container not-equals {
          uses server-v6-option-ascii-hex;
        }
        container starts-with {
          uses server-v6-option-ascii-hex;
        }
      }
      container option-16 {
        presence "enable option-16";
        uses apply-group;
        uses apply-macro;
        container equals {
          uses server-v6-option-ascii-hex;
        }
        container not-equals {
          uses server-v6-option-ascii-hex;
        }
        container starts-with {
          uses server-v6-option-ascii-hex;
        }
      }
    }
  }

  grouping dhcpv6-reconfigure-type {
    uses apply-group;
    uses apply-macro;
    leaf strict {
      type empty;
    }
    leaf clear-on-abort {
      type empty;
    }
    leaf attempts {
      type uint32;
    }
    leaf timeout {
      type uint32;
    }
    leaf token {
      type string;
    }
    container trigger {
      uses reconfigure-trigger-type;
    }
  }

  grouping jsscd-static-subscribers-type {
    uses apply-group;
    uses apply-macro;
    container access-profile {
      uses jsscd-access-profile-type;
    }
    container dynamic-profile {
      uses jsscd-dynamic-profile-type;
    }
    container authentication {
      uses jsscd-authentication-type;
    }
    list group {
      key "name";
      ordered-by user;
      uses jsscd-group-type;
    }
  }

  grouping jsscd-access-profile-type {
    uses apply-group;
    uses apply-macro;
    leaf access-profile-name {
      type string;
    }
  }

  grouping jsscd-authentication-type {
    uses apply-group;
    uses apply-macro;
    leaf password {
      type unreadable;
    }
    container username-include {
      uses apply-group;
      uses apply-macro;
      leaf domain-name {
        type string;
      }
      leaf user-prefix {
        type string;
      }
      leaf interface {
        type empty;
      }
      leaf logical-system-name {
        type empty;
      }
      leaf routing-instance-name {
        type empty;
      }
    }
  }

  grouping jsscd-dynamic-profile-type {
    uses apply-group;
    uses apply-macro;
    leaf dynamic-profile-name {
      type string;
    }
    container aggregate-clients {
      presence "enable aggregate-clients";
      uses apply-group;
      uses apply-macro;
      choice choice-3 {
        leaf merge {
          type empty;
        }
        leaf replace {
          type empty;
        }
      }
    }
  }

  grouping jsscd-group-type {
    leaf name {
      type key-attribute-string-type;
    }
    uses apply-group;
    uses apply-macro;
    container access-profile {
      uses jsscd-access-profile-type;
    }
    container dynamic-profile {
      uses jsscd-dynamic-profile-type;
    }
    container authentication {
      uses jsscd-authentication-type;
    }
    list interface {
      key "name";
      leaf name {
        type interface-unit;
      }
      leaf upto {
        type interface-unit;
      }
      leaf exclude {
        type empty;
      }
    }
  }

  grouping juniper-monitoring-options {
    leaf name {
      type string;
    }
    uses apply-group;
    uses apply-macro;
    container family {
      uses apply-group;
      uses apply-macro;
      container inet {
        presence "";
        uses apply-group;
        uses apply-macro;
        container output {
          presence "";
          uses monitoring-output-type;
        }
      }
    }
  }

  grouping juniper-multicast-snooping-options {
    uses apply-group;
    uses apply-macro;
    container options {
      uses apply-group;
      uses apply-macro;
      container syslog {
        uses apply-group;
        uses apply-macro;
        container level {
          leaf emergency {
            type empty;
          }
          leaf alert {
            type empty;
          }
          leaf critical {
            type empty;
          }
          leaf error {
            type empty;
          }
          leaf warning {
            type empty;
          }
          leaf notice {
            type empty;
          }
          leaf info {
            type empty;
          }
          leaf debug {
            type empty;
          }
        }
        leaf upto {
          type string;
        }
        leaf mark {
          type int32;
          units "seconds";
        }
      }
    }
    container traceoptions {
      uses apply-group;
      uses apply-macro;
      container file {
        presence "";
        leaf filename {
          mandatory true;
          type string;
        }
        leaf replace {
          type empty;
        }
        leaf size {
          type string;
        }
        leaf files {
          type uint32;
        }
        leaf no-stamp {
          type empty;
        }
        leaf world-readable {
          type empty;
        }
        leaf no-world-readable {
          type empty;
        }
      }
      list flag {
        key "name";
        ordered-by user;
        leaf name {
          type string;
        }
        leaf disable {
          type empty;
        }
      }
    }
    container forwarding-cache {
      uses apply-group;
      uses apply-macro;
      container threshold {
        uses apply-group;
        uses apply-macro;
        leaf suppress {
          type uint32;
        }
        leaf reuse {
          type uint32;
        }
      }
    }
    leaf-list flood-groups {
      type ipaddr;
      ordered-by user;
    }
    container host-outbound-traffic {
      uses apply-group;
      uses apply-macro;
      leaf forwarding-class {
        type string;
      }
      leaf dot1p {
        type uint32;
      }
    }
    container graceful-restart {
      uses apply-group;
      uses apply-macro;
      leaf enable-disable {
        type string;
      }
      leaf restart-duration {
        units "seconds";
        type uint32;
      }
    }
    leaf ignore-stp-topology-change {
      type empty;
    }
    container multichassis-lag-replicate-state {
      presence "enable multichassis-lag-replicate-state";
      uses apply-group;
      uses apply-macro;
      leaf suppress-report {
        type empty;
      }
    }
    leaf nexthop-hold-time {
      units "milliseconds";
      type uint32;
    }
  }

  grouping juniper-next-hop-group-options {
    leaf name {
      type string;
    }
    uses apply-group;
    uses apply-macro;
    leaf group-type {
      type string;
    }
    list interface {
      key "name";
      uses next-hop-group-intf-type;
    }
    list next-hop-subgroup {
      key "name";
      uses juniper-next-hop-subgroup-options;
    }
  }

  grouping juniper-next-hop-subgroup-options {
    leaf name {
      type string;
    }
    uses apply-group;
    uses apply-macro;
    list interface {
      key "name";
      uses next-hop-subgroup-intf-type;
    }
  }

  grouping juniper-packet-accounting-options {
    leaf name {
      type string;
    }
    uses apply-group;
    uses apply-macro;
    container output {
      presence "";
      uses packet-accounting-output-type;
    }
  }

  grouping juniper-packet-capture-options {
    uses apply-group;
    uses apply-macro;
    choice choice-3 {
      leaf disable {
        type empty;
      }
    }
    container file {
      presence "";
      leaf filename {
        type string;
      }
      leaf files {
        type uint32;
      }
      leaf size {
        type string;
      }
      leaf world-readable {
        type empty;
      }
      leaf no-world-readable {
        type empty;
      }
    }
    leaf maximum-capture-size {
      type uint32;
    }
  }

  grouping juniper-pic-services-logging-options {
    uses apply-group;
    uses apply-macro;
    container traceoptions {
      uses apply-group;
      uses apply-macro;
      leaf no-remote-trace {
        type empty;
      }
      container file {
        leaf filename {
          type string;
        }
        leaf size {
          type string;
        }
        leaf files {
          type uint32;
        }
        leaf world-readable {
          type empty;
        }
        leaf no-world-readable {
          type empty;
        }
        leaf match {
          type regular-expression;
        }
      }
      list flag {
        key "name";
        ordered-by user;
        leaf name {
          type string;
        }
      }
    }
  }

  grouping juniper-policy-options {
    uses apply-group;
    uses apply-macro;
    container apply-flags {
      container omit {
        presence "true";
      }
    }
    container satellite-policies {
      uses satellite-policy-options;
    }
    list prefix-list {
      key "name";
      ordered-by user;
      leaf name {
        type string;
      }
      uses apply-group;
      uses apply-macro;
      list prefix-list-item {
        key "name";
        uses prefix-list-items;
      }
      leaf apply-path {
        type string;
      }
      container apply-flags {
        container omit {
          presence "true";
        }
      }
    }
    list route-filter-list {
      key "name";
      ordered-by user;
      leaf name {
        type string;
      }
      uses apply-group;
      uses apply-macro;
      list rf_list {
        key "address key2 key2-arg";
        ordered-by user;
        uses route-filter-list-items;
      }
    }
    list mac-list {
      key "name";
      ordered-by user;
      leaf name {
        type string;
      }
      uses apply-advanced;
      list mac-addr-list-item {
        key "name";
        uses mac-addr-list-items;
      }
    }
    list vsi-policy {
      key "name";
      ordered-by user;
      leaf name {
        type string;
      }
      uses apply-group;
      uses apply-macro;
      container from {
        uses apply-group;
        uses apply-macro;
        list vsi-manager {
          key "vsi-manager-id vsi-type vsi-version vsi-instance";
          ordered-by user;
          leaf vsi-manager-id {
            type key-attribute-ulong-type;
          }
          leaf vsi-type {
            type key-attribute-ulong-type;
          }
          leaf vsi-version {
            type key-attribute-ulong-type;
          }
          leaf vsi-instance {
            type string;
          }
          uses apply-group;
          uses apply-macro;
        }
      }
      container then {
        presence "";
        uses apply-group;
        uses apply-macro;
        leaf filter {
          type string;
        }
      }
    }
    list policy-statement {
      key "name";
      leaf name {
        type string;
      }
      uses apply-group;
      uses apply-macro;
      container apply-flags {
        container omit {
          presence "true";
        }
      }
      leaf dynamic-db {
        type empty;
      }
      container defaults {
        uses apply-group;
        uses apply-macro;
        container route-filter {
          choice choice-no-walkup {
            leaf no-walkup {
              type empty;
            }
            leaf walkup {
              type empty;
            }
          }
        }
      }
      list term {
        key "name";
        ordered-by user;
        leaf name {
          type string;
        }
        uses apply-group;
        uses apply-macro;
        container from {
          uses apply-group;
          uses apply-macro;
          leaf instance {
            type string;
          }
          leaf instance-any {
            type empty;
          }
          leaf-list instance-list {
            type string;
          }
          list as-path-neighbors {
            key "list-type list-name";
            ordered-by user;
            uses control_as_list_type;
          }
          list as-path-origins {
            key "list-type list-name";
            ordered-by user;
            uses control_as_list_type;
          }
          list as-path-transits {
            key "list-type list-name";
            ordered-by user;
            uses control_as_list_type;
          }
          leaf family {
            type string;
          }
          leaf-list protocol {
            ordered-by user;
            type string;
          }
          leaf rib {
            type string;
          }
          leaf-list neighbor {
            type string;
            ordered-by user;
          }
          leaf-list next-hop {
            type string;
            ordered-by user;
          }
          leaf-list interface {
            type ipaddr-or-interface;
            ordered-by user;
          }
          leaf area {
            type areaid;
          }
          leaf-list as-path {
            type string;
            ordered-by user;
          }
          leaf-list as-path-group {
            type string;
            ordered-by user;
          }
          leaf origin {
            type string;
          }
          leaf-list community {
            type string;
            ordered-by user;
          }
          leaf level {
            type uint32;
          }
          container external {
            presence "enable external";
            uses apply-group;
            uses apply-macro;
            leaf type {
              type int32;
            }
          }
          leaf validation-database {
            type string;
          }
          leaf metric {
            type uint32;
          }
          leaf metric2 {
            type uint32;
          }
          leaf metric3 {
            type uint32;
          }
          leaf metric4 {
            type uint32;
          }
          leaf-list tag {
            type uint32;
            ordered-by user;
          }
          leaf tag2 {
            type uint32;
          }
          leaf preference {
            type uint32;
          }
          leaf preference2 {
            type uint32;
          }
          leaf color {
            type uint32;
          }
          leaf color2 {
            type uint32;
          }
          leaf local-preference {
            type uint32;
          }
          leaf-list policy {
            type policy-algebra;
            ordered-by user;
          }
          choice lsp-name-type {
            case case_1 {
              leaf lsp {
                type string;
              }
            }
            case case_2 {
              leaf lsp-regex {
                type string;
              }
            }
          }
          container source-routing-path {
            presence "enable source-routing-path";
            leaf name-regex {
              type string;
            }
            leaf dest {
              type ipaddr;
            }
            leaf origin {
              type ipaddr;
            }
            leaf tunnel-source {
              type string;
            }
            leaf route-distinguisher {
              type string;
            }
            leaf color {
              type string;
            }
          }
          list route-filter {
            key "address key2 key2-arg";
            ordered-by user;
            uses control-route-filter-type;
          }
          list source-address-filter {
            key "address key2 key2-arg";
            ordered-by user;
            uses control-source-address-filter-type;
          }
          list prefix-list {
            key "name";
            ordered-by user;
            uses control-prefix-list-type;
          }
          list prefix-list-filter {
            key "list_name key2";
            ordered-by user;
            uses control-prefix-list-filter-type;
          }
          list rtf-prefix-list {
            key "name";
            ordered-by user;
            uses control-rtf-prefix-list-type;
          }
          list route-filter-list {
            key "name";
            ordered-by user;
            uses control-route-filter-list-type;
          }
          list source-address-filter-list {
            key "name";
            ordered-by user;
            uses control-source-address-filter-list-type;
          }
          container multicast-scope {
            choice choice-3 {
              leaf node-local {
                type empty;
              }
              leaf link-local {
                type empty;
              }
              leaf site-local {
                type empty;
              }
              leaf organization-local {
                type empty;
              }
              leaf global {
                type empty;
              }
              leaf scope_value {
                type uint32;
              }
            }
            choice choice-4 {
              leaf orhigher {
                type empty;
              }
              leaf orlower {
                type empty;
              }
            }
          }
          leaf aggregate-contributor {
            type empty;
          }
          leaf state {
            type string;
          }
          leaf route-type {
            type string;
          }
          leaf-list nlri-route-type {
            ordered-by user;
            type uint32;
          }
          leaf-list evpn-tag {
            ordered-by user;
            type string;
          }
          leaf-list evpn-esi {
            ordered-by user;
            type string;
          }
          list mac-filter-list {
            key "name";
            ordered-by user;
            uses control-mac-address-filter-list-type;
          }
          leaf evpn-mac-route {
            type string;
          }
          leaf next-hop-type {
            type string;
          }
          leaf-list condition {
            type string;
            ordered-by user;
          }
          list community-count {
            key "name";
            ordered-by user;
            uses community-count-type;
          }
          list as-path-unique-count {
            key "name";
            ordered-by user;
            uses as-path-unique-count-type;
          }
          list as-path-calc-length {
            key "name";
            ordered-by user;
            uses as-path-calc-length-type;
          }
          container traffic-engineering {
            presence "enable traffic-engineering";
            uses apply-group;
            uses apply-macro;
            leaf-list protocol {
              ordered-by user;
              type string;
            }
            container node {
              presence "enable node";
              uses apply-group;
              uses apply-macro;
              leaf as {
                type string;
              }
              leaf node-type {
                type string;
              }
              leaf router-id {
                type ipprefix;
              }
              leaf sys-id {
                type sysid;
              }
            }
            container ipv4-prefix {
              presence "enable ipv4-prefix";
              uses apply-group;
              uses apply-macro;
              leaf as {
                type string;
              }
              leaf router-id {
                type ipprefix;
              }
              leaf prefix {
                type ipprefix;
              }
              leaf sys-id {
                type sysid;
              }
            }
            container link {
              presence "enable link";
              uses apply-group;
              uses apply-macro;
              container from {
                uses apply-group;
                uses apply-macro;
                leaf as {
                  type string;
                }
                leaf router-id {
                  type ipprefix;
                }
                leaf sys-id {
                  type sysid;
                }
                leaf node-type {
                  type string;
                }
                leaf link-address {
                  type ipprefix;
                }
              }
              container to {
                uses apply-group;
                uses apply-macro;
                leaf as {
                  type string;
                }
                leaf router-id {
                  type ipprefix;
                }
                leaf sys-id {
                  type sysid;
                }
                leaf node-type {
                  type string;
                }
                leaf link-address {
                  type ipprefix;
                }
              }
            }
          }
          leaf-list route-distinguisher {
            type string;
            ordered-by user;
          }
        }
        container to {
          uses apply-group;
          uses apply-macro;
          leaf instance {
            type string;
          }
          leaf instance-any {
            type empty;
          }
          leaf-list instance-list {
            type string;
          }
          leaf family {
            type string;
          }
          leaf-list protocol {
            ordered-by user;
            type string;
          }
          leaf rib {
            type string;
          }
          leaf-list neighbor {
            type string;
            ordered-by user;
          }
          leaf-list next-hop {
            type string;
            ordered-by user;
          }
          leaf-list interface {
            type ipaddr-or-interface;
            ordered-by user;
          }
          leaf area {
            type areaid;
          }
          leaf-list as-path {
            type string;
            ordered-by user;
          }
          leaf-list as-path-group {
            type string;
            ordered-by user;
          }
          leaf origin {
            type string;
          }
          leaf-list community {
            type string;
            ordered-by user;
          }
          leaf level {
            type uint32;
          }
          container external {
            presence "";
            uses apply-group;
            uses apply-macro;
            leaf type {
              type int32;
            }
          }
          leaf validation-database {
            type string;
          }
          leaf metric {
            type uint32;
          }
          leaf metric2 {
            type uint32;
          }
          leaf metric3 {
            type uint32;
          }
          leaf metric4 {
            type uint32;
          }
          leaf-list tag {
            type uint32;
            ordered-by user;
          }
          leaf tag2 {
            type uint32;
          }
          leaf preference {
            type uint32;
          }
          leaf preference2 {
            type uint32;
          }
          leaf color {
            type uint32;
          }
          leaf color2 {
            type uint32;
          }
          leaf local-preference {
            type uint32;
          }
          leaf-list policy {
            type policy-algebra;
            ordered-by user;
          }
        }
        container then {
          uses apply-group;
          uses apply-macro;
          container metric {
            uses apply-group;
            uses apply-macro;
            choice choice-3 {
              leaf metric {
                type uint32;
              }
              leaf add {
                type uint32;
              }
              leaf subtract {
                type uint32;
              }
              container igp {
                presence "";
                leaf metric_offset {
                  type int32;
                }
              }
              container minimum-igp {
                presence "";
                leaf metric_offset {
                  type int32;
                }
              }
              container expression {
                uses metric-expression-type;
              }
              leaf aigp {
                type empty;
              }
            }
          }
          container metric2 {
            uses apply-group;
            uses apply-macro;
            choice choice-3 {
              leaf metric2 {
                type uint32;
              }
              leaf add {
                type uint32;
              }
              leaf subtract {
                type uint32;
              }
            }
          }
          container metric3 {
            uses apply-group;
            uses apply-macro;
            choice choice-3 {
              leaf metric3 {
                type uint32;
              }
              leaf add {
                type uint32;
              }
              leaf subtract {
                type uint32;
              }
            }
          }
          container metric4 {
            uses apply-group;
            uses apply-macro;
            choice choice-3 {
              leaf metric4 {
                type uint32;
              }
              leaf add {
                type uint32;
              }
              leaf subtract {
                type uint32;
              }
            }
          }
          container tag {
            uses apply-group;
            uses apply-macro;
            choice choice-3 {
              leaf tag {
                type uint32;
              }
              leaf add {
                type uint32;
              }
              leaf subtract {
                type uint32;
              }
            }
          }
          container tag2 {
            uses apply-group;
            uses apply-macro;
            choice choice-3 {
              leaf tag2 {
                type uint32;
              }
              leaf add {
                type uint32;
              }
              leaf subtract {
                type uint32;
              }
            }
          }
          container preference {
            uses apply-group;
            uses apply-macro;
            choice choice-3 {
              leaf preference {
                type uint32;
              }
              leaf add {
                type uint32;
              }
              leaf subtract {
                type uint32;
              }
            }
          }
          container preference2 {
            uses apply-group;
            uses apply-macro;
            choice choice-3 {
              leaf preference2 {
                type uint32;
              }
              leaf add {
                type uint32;
              }
              leaf subtract {
                type uint32;
              }
            }
          }
          container color {
            uses apply-group;
            uses apply-macro;
            choice choice-3 {
              leaf color {
                type uint32;
              }
              leaf add {
                type uint32;
              }
              leaf subtract {
                type uint32;
              }
            }
          }
          container color2 {
            uses apply-group;
            uses apply-macro;
            choice choice-3 {
              leaf color2 {
                type uint32;
              }
              leaf add {
                type uint32;
              }
              leaf subtract {
                type uint32;
              }
            }
          }
          container local-preference {
            uses apply-group;
            uses apply-macro;
            choice choice-3 {
              leaf local-preference {
                type uint32;
              }
              leaf add {
                type uint32;
              }
              leaf subtract {
                type uint32;
              }
            }
          }
          leaf priority {
            type string;
          }
          container prefix-segment {
            list algorithm {
              key "name";
              leaf name {
                type string;
              }
              leaf index {
                type string;
              }
              leaf node-segment {
                type empty;
              }
            }
            leaf index {
              type string;
            }
            leaf node-segment {
              type empty;
            }
          }
          leaf label-allocation {
            type string;
          }
          container add-path {
            leaf send-count {
              type uint32;
            }
          }
          leaf validation-state {
            type string;
          }
          leaf origin {
            type string;
          }
          container aigp-originate {
            presence "";
            leaf distance {
              type uint32;
            }
          }
          container aigp-adjust {
            choice choice-add {
              leaf add {
                type empty;
              }
              leaf subtract {
                type empty;
              }
              leaf multiply {
                type empty;
              }
              leaf divide {
                type empty;
              }
            }
            choice choice-user-value {
              leaf user-value {
                type uint64;
              }
              leaf distance-to-protocol-nexthop {
                type empty;
              }
            }
          }
          list community {
            key "key1 community-name";
            ordered-by user;
            leaf key1 {
              type string;
            }
            leaf community-name {
              type string;
            }
          }
          leaf damping {
            type string;
          }
          leaf aggregate-bandwidth {
            type empty;
          }
          leaf limit-bandwidth {
            type uint32;
          }
          leaf no-entropy-label-capability {
            type empty;
          }
          leaf as-path-prepend {
            type string;
          }
          container as-path-expand {
            choice choice-3 {
              container last-as {
                presence "";
                leaf count {
                  type uint32;
                }
              }
              leaf aspath {
                type string;
              }
            }
          }
          container next-hop {
            choice choice-3 {
              leaf self {
                type empty;
              }
              leaf peer-address {
                type empty;
              }
              leaf address {
                type ipaddr;
              }
              leaf reject {
                type empty;
              }
              leaf discard {
                type empty;
              }
              leaf next-table {
                type string;
              }
            }
          }
          container install-nexthop {
            leaf strict {
              type empty;
            }
            choice choice-5 {
              leaf-list lsp {
                type string;
                ordered-by user;
              }
              leaf-list lsp-regex {
                type string;
                ordered-by user;
              }
              leaf-list static-lsp {
                type string;
                ordered-by user;
              }
              leaf-list static-lsp-regex {
                type string;
                ordered-by user;
              }
            }
            container except {
              uses apply-group;
              uses apply-macro;
              choice choice-3 {
                leaf-list lsp {
                  type string;
                  ordered-by user;
                }
                leaf-list lsp-regex {
                  type string;
                  ordered-by user;
                }
                leaf-list static-lsp {
                  type string;
                  ordered-by user;
                }
                leaf-list static-lsp-regex {
                  type string;
                  ordered-by user;
                }
              }
            }
          }
          leaf trace {
            type empty;
          }
          container external {
            presence "";
            uses apply-group;
            uses apply-macro;
            leaf type {
              type int32;
            }
            leaf nssa-only {
              type empty;
            }
          }
          container load-balance {
            choice choice-3 {
              leaf per-packet {
                type empty;
              }
              leaf random {
                type empty;
              }
              leaf per-prefix {
                type empty;
              }
              leaf consistent-hash {
                type empty;
              }
              leaf source-ip-only {
                type empty;
              }
              leaf destination-ip-only {
                type empty;
              }
              leaf per-flow {
                type empty;
              }
              leaf profile1 {
                type empty;
              }
              leaf profile2 {
                type empty;
              }
              leaf symmetric-consistent-hash {
                type empty;
              }
            }
          }
          leaf no-route-localize {
            type empty;
          }
          leaf install-to-fib {
            type empty;
          }
          leaf no-install-to-fib {
            type empty;
          }
          leaf analyze {
            type empty;
          }
          leaf class {
            type string;
          }
          leaf destination-class {
            type string;
          }
          leaf source-class {
            type string;
          }
          leaf forwarding-class {
            type string;
          }
          container map-to-interface {
            choice choice-3 {
              leaf self {
                type empty;
              }
              leaf interface {
                type interface-name;
              }
            }
          }
          leaf-list ssm-source {
            type ipaddr;
            ordered-by user;
          }
          container p2mp-lsp-root {
            uses apply-group;
            uses apply-macro;
            leaf address {
              type ipv4addr;
            }
          }
          leaf cos-next-hop-map {
            type string;
          }
          leaf dynamic-tunnel-attributes {
            type string;
          }
          leaf tunnel-end-point-address {
            type ipaddr;
          }
          leaf selected-mldp-egress {
            type empty;
          }
          leaf mhop-bfd-port {
            type empty;
          }
          leaf no-backup {
            type empty;
          }
          leaf default-action {
            type string;
          }
          leaf next {
            type string;
          }
          choice choice-65 {
            leaf accept {
              type empty;
            }
            leaf reject {
              type empty;
            }
            leaf accept-reject {
              type string;
            }
          }
          container bgp-output-queue-priority {
            choice choice-priority {
              leaf priority {
                type uint32;
              }
              leaf expedited {
                type empty;
              }
            }
          }
          leaf multipath-resolve {
            type empty;
          }
          leaf source-routing-path-template {
            type string;
          }
          leaf sr-te-template {
            type string;
          }
          leaf label-allocation-fallback-reject {
            type empty;
          }
          leaf resolution-map {
            type string;
          }
          leaf ignore-service-label {
            type empty;
          }
          container prefix-attribute-flags {
            presence "enable prefix-attribute-flags";
            uses apply-advanced;
            leaf node-segment-flag {
              type empty;
            }
            leaf external-prefix-flag {
              type empty;
            }
            leaf anycast-flag {
              type empty;
            }
          }
          leaf request-long-lived-ack {
            type empty;
          }
          leaf send-withdrawal-on-route-change {
            type empty;
          }
          container slice {
            leaf slice-name {
              type string;
            }
          }
          leaf filter {
            type string;
          }
          leaf strip-as-path {
            type empty;
          }
        }
      }
      container from {
        uses apply-group;
        uses apply-macro;
        leaf instance {
          type string;
        }
        leaf instance-any {
          type empty;
        }
        leaf-list instance-list {
          type string;
        }
        list as-path-neighbors {
          key "list-type list-name";
          ordered-by user;
          uses control_as_list_type;
        }
        list as-path-origins {
          key "list-type list-name";
          ordered-by user;
          uses control_as_list_type;
        }
        list as-path-transits {
          key "list-type list-name";
          ordered-by user;
          uses control_as_list_type;
        }
        leaf family {
          type string;
        }
        leaf-list protocol {
          ordered-by user;
          type string;
        }
        leaf rib {
          type string;
        }
        leaf-list neighbor {
          type string;
          ordered-by user;
        }
        leaf-list next-hop {
          type string;
          ordered-by user;
        }
        leaf-list interface {
          type ipaddr-or-interface;
          ordered-by user;
        }
        leaf area {
          type areaid;
        }
        leaf-list as-path {
          type string;
          ordered-by user;
        }
        leaf-list as-path-group {
          type string;
          ordered-by user;
        }
        leaf origin {
          type string;
        }
        leaf-list community {
          type string;
          ordered-by user;
        }
        leaf level {
          type uint32;
        }
        container external {
          presence "";
          uses apply-group;
          uses apply-macro;
          leaf type {
            type int32;
          }
        }
        leaf validation-database {
          type string;
        }
        leaf metric {
          type uint32;
        }
        leaf metric2 {
          type uint32;
        }
        leaf metric3 {
          type uint32;
        }
        leaf metric4 {
          type uint32;
        }
        leaf-list tag {
          type uint32;
          ordered-by user;
        }
        leaf tag2 {
          type uint32;
        }
        leaf preference {
          type uint32;
        }
        leaf preference2 {
          type uint32;
        }
        leaf color {
          type uint32;
        }
        leaf color2 {
          type uint32;
        }
        leaf local-preference {
          type uint32;
        }
        leaf-list policy {
          type policy-algebra;
          ordered-by user;
        }
        list route-filter {
          key "address key2 key2-arg";
          ordered-by user;
          uses control-route-filter-type;
        }
        list source-address-filter {
          key "address key2 key2-arg";
          ordered-by user;
          uses control-route-filter-type;
        }
        list prefix-list {
          key "name";
          ordered-by user;
          uses control-prefix-list-type;
        }
        list prefix-list-filter {
          key "list_name key2";
          ordered-by user;
          uses control-prefix-list-filter-type;
        }
        list rtf-prefix-list {
          key "name";
          ordered-by user;
          uses control-rtf-prefix-list-type;
        }
        list route-filter-list {
          key "name";
          ordered-by user;
          uses control-route-filter-list-type;
        }
        list source-address-filter-list {
          key "name";
          ordered-by user;
          uses control-source-address-filter-list-type;
        }
        container multicast-scope {
          choice choice-3 {
            leaf node-local {
              type empty;
            }
            leaf link-local {
              type empty;
            }
            leaf site-local {
              type empty;
            }
            leaf organization-local {
              type empty;
            }
            leaf global {
              type empty;
            }
            leaf scope_value {
              type uint32;
            }
          }
          choice choice-4 {
            leaf orhigher {
              type empty;
            }
            leaf orlower {
              type empty;
            }
          }
        }
        leaf aggregate-contributor {
          type empty;
        }
        leaf state {
          type string;
        }
        leaf route-type {
          type string;
        }
        leaf-list nlri-route-type {
          ordered-by user;
          type uint32;
        }
        leaf next-hop-type {
          type string;
        }
        leaf-list condition {
          type string;
          ordered-by user;
        }
        list community-count {
          key "name";
          ordered-by user;
          uses community-count-type;
        }
        list as-path-unique-count {
          key "name";
          ordered-by user;
          uses as-path-unique-count-type;
        }
        list as-path-calc-length {
          key "name";
          ordered-by user;
          uses as-path-calc-length-type;
        }
        container traffic-engineering {
          presence "enable traffic-engineering";
          uses apply-group;
          uses apply-macro;
          leaf-list protocol {
            ordered-by user;
            type string;
          }
          container node {
            presence "enable node";
            uses apply-group;
            uses apply-macro;
            leaf as {
              type string;
            }
            leaf node-type {
              type string;
            }
            leaf router-id {
              type ipprefix;
            }
            leaf sys-id {
              type sysid;
            }
          }
          container ipv4-prefix {
            presence "enable ipv4-prefix";
            uses apply-group;
            uses apply-macro;
            leaf as {
              type string;
            }
            leaf router-id {
              type ipprefix;
            }
            leaf prefix {
              type ipprefix;
            }
            leaf sys-id {
              type sysid;
            }
          }
          container link {
            presence "enable link";
            uses apply-group;
            uses apply-macro;
            container from {
              uses apply-group;
              uses apply-macro;
              leaf as {
                type string;
              }
              leaf router-id {
                type ipprefix;
              }
              leaf sys-id {
                type sysid;
              }
              leaf node-type {
                type string;
              }
              leaf link-address {
                type ipprefix;
              }
            }
            container to {
              uses apply-group;
              uses apply-macro;
              leaf as {
                type string;
              }
              leaf router-id {
                type ipprefix;
              }
              leaf sys-id {
                type sysid;
              }
              leaf node-type {
                type string;
              }
              leaf link-address {
                type ipprefix;
              }
            }
          }
        }
        leaf-list route-distinguisher {
          type string;
          ordered-by user;
        }
      }
      container to {
        uses apply-group;
        uses apply-macro;
        leaf instance {
          type string;
        }
        leaf instance-any {
          type empty;
        }
        leaf-list instance-list {
          type string;
        }
        leaf family {
          type string;
        }
        leaf-list protocol {
          ordered-by user;
          type string;
        }
        leaf rib {
          type string;
        }
        leaf-list neighbor {
          type string;
          ordered-by user;
        }
        leaf-list next-hop {
          type string;
          ordered-by user;
        }
        leaf-list interface {
          type ipaddr-or-interface;
          ordered-by user;
        }
        leaf area {
          type areaid;
        }
        leaf-list as-path {
          type string;
          ordered-by user;
        }
        leaf-list as-path-group {
          type string;
          ordered-by user;
        }
        leaf origin {
          type string;
        }
        leaf-list community {
          type string;
          ordered-by user;
        }
        leaf level {
          type uint32;
        }
        container external {
          presence "";
          uses apply-group;
          uses apply-macro;
          leaf type {
            type int32;
          }
        }
        leaf validation-database {
          type string;
        }
        leaf metric {
          type uint32;
        }
        leaf metric2 {
          type uint32;
        }
        leaf metric3 {
          type uint32;
        }
        leaf metric4 {
          type uint32;
        }
        leaf-list tag {
          type uint32;
          ordered-by user;
        }
        leaf tag2 {
          type uint32;
        }
        leaf preference {
          type uint32;
        }
        leaf preference2 {
          type uint32;
        }
        leaf color {
          type uint32;
        }
        leaf color2 {
          type uint32;
        }
        leaf local-preference {
          type uint32;
        }
        leaf-list policy {
          type policy-algebra;
          ordered-by user;
        }
      }
      container then {
        uses apply-group;
        uses apply-macro;
        container metric {
          uses apply-group;
          uses apply-macro;
          choice choice-3 {
            leaf metric {
              type uint32;
            }
            leaf add {
              type uint32;
            }
            leaf subtract {
              type uint32;
            }
            container igp {
              presence "";
              leaf metric_offset {
                type int32;
              }
            }
            container minimum-igp {
              presence "";
              leaf metric_offset {
                type int32;
              }
            }
            container expression {
              uses metric-expression-type;
            }
            leaf aigp {
              type empty;
            }
          }
        }
        container metric2 {
          uses apply-group;
          uses apply-macro;
          choice choice-3 {
            leaf metric2 {
              type uint32;
            }
            leaf add {
              type uint32;
            }
            leaf subtract {
              type uint32;
            }
          }
        }
        container metric3 {
          uses apply-group;
          uses apply-macro;
          choice choice-3 {
            leaf metric3 {
              type uint32;
            }
            leaf add {
              type uint32;
            }
            leaf subtract {
              type uint32;
            }
          }
        }
        container metric4 {
          uses apply-group;
          uses apply-macro;
          choice choice-3 {
            leaf metric4 {
              type uint32;
            }
            leaf add {
              type uint32;
            }
            leaf subtract {
              type uint32;
            }
          }
        }
        container tag {
          uses apply-group;
          uses apply-macro;
          choice choice-3 {
            leaf tag {
              type uint32;
            }
            leaf add {
              type uint32;
            }
            leaf subtract {
              type uint32;
            }
          }
        }
        container tag2 {
          uses apply-group;
          uses apply-macro;
          choice choice-3 {
            leaf tag2 {
              type uint32;
            }
            leaf add {
              type uint32;
            }
            leaf subtract {
              type uint32;
            }
          }
        }
        container preference {
          uses apply-group;
          uses apply-macro;
          choice choice-3 {
            leaf preference {
              type uint32;
            }
            leaf add {
              type uint32;
            }
            leaf subtract {
              type uint32;
            }
          }
        }
        container preference2 {
          uses apply-group;
          uses apply-macro;
          choice choice-3 {
            leaf preference2 {
              type uint32;
            }
            leaf add {
              type uint32;
            }
            leaf subtract {
              type uint32;
            }
          }
        }
        container color {
          uses apply-group;
          uses apply-macro;
          choice choice-3 {
            leaf color {
              type uint32;
            }
            leaf add {
              type uint32;
            }
            leaf subtract {
              type uint32;
            }
          }
        }
        container color2 {
          uses apply-group;
          uses apply-macro;
          choice choice-3 {
            leaf color2 {
              type uint32;
            }
            leaf add {
              type uint32;
            }
            leaf subtract {
              type uint32;
            }
          }
        }
        container local-preference {
          uses apply-group;
          uses apply-macro;
          choice choice-3 {
            leaf local-preference {
              type uint32;
            }
            leaf add {
              type uint32;
            }
            leaf subtract {
              type uint32;
            }
          }
        }
        leaf priority {
          type string;
        }
        container prefix-segment {
          list algorithm {
            key "name";
            leaf name {
              type string;
            }
            leaf index {
              type string;
            }
            leaf node-segment {
              type empty;
            }
          }
          leaf index {
            type string;
          }
          leaf node-segment {
            type empty;
          }
        }
        leaf label-allocation {
          type string;
        }
        container add-path {
          leaf send-count {
            type uint32;
          }
        }
        leaf validation-state {
          type string;
        }
        leaf origin {
          type string;
        }
        container aigp-originate {
          presence "";
          leaf distance {
            type uint32;
          }
        }
        container aigp-adjust {
          choice choice-add {
            leaf add {
              type empty;
            }
            leaf subtract {
              type empty;
            }
            leaf multiply {
              type empty;
            }
            leaf divide {
              type empty;
            }
          }
          choice choice-user-value {
            leaf user-value {
              type uint64;
            }
            leaf distance-to-protocol-nexthop {
              type empty;
            }
          }
        }
        list community {
          key "key1 community-name";
          ordered-by user;
          leaf key1 {
            type string;
          }
          leaf community-name {
            type string;
          }
        }
        leaf damping {
          type string;
        }
        leaf aggregate-bandwidth {
          type empty;
        }
        leaf limit-bandwidth {
          type uint32;
        }
        leaf no-entropy-label-capability {
          type empty;
        }
        leaf as-path-prepend {
          type string;
        }
        container as-path-expand {
          choice choice-3 {
            container last-as {
              presence "";
              leaf count {
                type uint32;
              }
            }
            leaf aspath {
              type string;
            }
          }
        }
        container next-hop {
          choice choice-3 {
            leaf self {
              type empty;
            }
            leaf peer-address {
              type empty;
            }
            leaf address {
              type ipaddr;
            }
            leaf reject {
              type empty;
            }
            leaf discard {
              type empty;
            }
            leaf next-table {
              type string;
            }
          }
        }
        container install-nexthop {
          leaf strict {
            type empty;
          }
          choice choice-5 {
            leaf-list lsp {
              type string;
              ordered-by user;
            }
            leaf-list lsp-regex {
              type string;
              ordered-by user;
            }
            leaf-list static-lsp {
              type string;
              ordered-by user;
            }
            leaf-list static-lsp-regex {
              type string;
              ordered-by user;
            }
          }
          container except {
            uses apply-group;
            uses apply-macro;
            choice choice-3 {
              leaf-list lsp {
                type string;
                ordered-by user;
              }
              leaf-list lsp-regex {
                type string;
                ordered-by user;
              }
              leaf-list static-lsp {
                type string;
                ordered-by user;
              }
              leaf-list static-lsp-regex {
                type string;
                ordered-by user;
              }
            }
          }
        }
        leaf trace {
          type empty;
        }
        container external {
          presence "";
          uses apply-group;
          uses apply-macro;
          leaf type {
            type int32;
          }
          leaf nssa-only {
            type empty;
          }
        }
        container load-balance {
          choice choice-3 {
            leaf per-packet {
              type empty;
            }
            leaf random {
              type empty;
            }
            leaf per-prefix {
              type empty;
            }
            leaf consistent-hash {
              type empty;
            }
            leaf source-ip-only {
              type empty;
            }
            leaf destination-ip-only {
              type empty;
            }
          }
        }
        leaf no-route-localize {
          type empty;
        }
        leaf install-to-fib {
          type empty;
        }
        leaf no-install-to-fib {
          type empty;
        }
        leaf analyze {
          type empty;
        }
        leaf class {
          type string;
        }
        leaf destination-class {
          type string;
        }
        leaf source-class {
          type string;
        }
        leaf forwarding-class {
          type string;
        }
        container map-to-interface {
          choice choice-3 {
            leaf self {
              type empty;
            }
            leaf interface {
              type interface-name;
            }
          }
        }
        leaf-list ssm-source {
          type ipaddr;
          ordered-by user;
        }
        container p2mp-lsp-root {
          uses apply-group;
          uses apply-macro;
          leaf address {
            type ipv4addr;
          }
        }
        leaf cos-next-hop-map {
          type string;
        }
        leaf dynamic-tunnel-attributes {
          type string;
        }
        leaf tunnel-end-point-address {
          type ipaddr;
        }
        leaf selected-mldp-egress {
          type empty;
        }
        leaf mhop-bfd-port {
          type empty;
        }
        leaf no-backup {
          type empty;
        }
        leaf default-action {
          type string;
        }
        leaf next {
          type string;
        }
        choice choice-65 {
          leaf accept {
            type empty;
          }
          leaf reject {
            type empty;
          }
          leaf accept-reject {
            type string;
          }
        }
        container bgp-output-queue-priority {
          choice choice-priority {
            leaf priority {
              type uint32;
            }
            leaf expedited {
              type empty;
            }
          }
        }
        leaf multipath-resolve {
          type empty;
        }
        leaf sr-te-template {
          type string;
        }
        leaf label-allocation-fallback-reject {
          type empty;
        }
        leaf resolution-map {
          type string;
        }
      }
    }
    container defaults {
      uses apply-group;
      uses apply-macro;
      container route-filter {
        presence "";
        leaf walkup {
          type empty;
        }
      }
      container asregex-optimize {
        choice scope-choice {
          case case_1 {
            leaf optimize {
              type empty;
            }
          }
          case case_2 {
            leaf no-optimize {
              type empty;
            }
          }
        }
      }
    }
    list tunnel-attribute {
      key "name";
      ordered-by user;
      leaf name {
        type string;
      }
      uses apply-advanced;
      leaf tunnel-type {
        type string;
      }
      leaf tunnel-color {
        type string;
      }
      leaf remote-end-point {
        type ipaddr;
      }
    }
    list community {
      key "name";
      leaf name {
        type string;
      }
      uses apply-group;
      uses apply-macro;
      leaf invert-match {
        type empty;
      }
      leaf-list members {
        type string;
        ordered-by user;
      }
    }
    list as-list {
      key "name";
      leaf name {
        type string;
      }
      uses apply-advanced;
      leaf-list members {
        ordered-by user;
        type string;
      }
    }
    list as-list-group {
      key "name";
      leaf name {
        type string;
      }
      uses apply-advanced;
      list as-list {
        key "name";
        leaf name {
          type string;
        }
        uses apply-advanced;
        leaf-list members {
          ordered-by user;
          type string;
        }
      }
    }
    list route-distinguisher {
      key "name";
      leaf name {
        type string;
      }
      uses apply-group;
      uses apply-macro;
      leaf-list members {
        type string;
        ordered-by user;
      }
    }
    list as-path {
      key "name";
      ordered-by user;
      leaf name {
        type string;
      }
      uses apply-group;
      uses apply-macro;
      leaf path {
        type string;
      }
    }
    list as-path-group {
      key "name";
      ordered-by user;
      leaf name {
        type string;
      }
      uses apply-group;
      uses apply-macro;
      list as-path {
        key "name";
        ordered-by user;
        leaf name {
          type string;
        }
        leaf path {
          type string;
        }
      }
    }
    list damping {
      key "name";
      ordered-by user;
      leaf name {
        type string;
      }
      uses apply-group;
      uses apply-macro;
      choice choice-3 {
        leaf disable {
          type empty;
        }
        leaf enable-disable {
          type string;
        }
      }
      leaf half-life {
        type uint32;
      }
      leaf reuse {
        type uint32;
      }
      leaf suppress {
        type uint32;
      }
      leaf max-suppress {
        type uint32;
      }
    }
    list condition {
      key "name";
      leaf name {
        type string;
      }
      uses apply-group;
      uses apply-macro;
      choice choice-3 {
        leaf route-active-on {
          type string;
        }
        container if-route-exists {
          presence "";
          uses apply-group;
          uses apply-macro;
          container address-family {
            presence "";
            uses apply-group;
            uses apply-macro;
            choice choice-inet {
              container inet {
                presence "";
                uses apply-group;
                uses apply-macro;
                leaf address {
                  type ipprefix;
                }
                leaf table {
                  type string;
                }
              }
              container ccc {
                presence "";
                uses apply-group;
                uses apply-macro;
                leaf address {
                  type interface-name;
                }
                leaf table {
                  type string;
                }
                leaf standby {
                  type empty;
                }
                leaf peer-unit {
                  type uint32;
                }
              }
            }
          }
          leaf address {
            type ipprefix;
          }
          leaf table {
            type string;
          }
        }
      }
    }
    list rtf-prefix-list {
      key "name";
      ordered-by user;
      leaf name {
        type string;
      }
      uses apply-group;
      uses apply-macro;
      list prefix-list {
        key "name";
        uses rtf-prefix-list-items;
      }
    }
    list resolution-map {
      key "name";
      ordered-by user;
      leaf name {
        type string;
      }
      uses apply-group;
      uses apply-macro;
      leaf-list mode {
        ordered-by user;
        type string;
      }
    }
    list application-maps {
      key "name";
      ordered-by user;
      uses application-map-object;
    }
    list redundancy-policy {
      key "name";
      leaf name {
        type key-attribute-string-type;
      }
      uses apply-group;
      uses apply-macro;
      leaf-list redundancy-events {
        type string;
      }
      container then {
        presence "enable then";
        uses srd-ev-action-object;
      }
    }
  }

  grouping application-map-object {
    leaf name {
      type key-attribute-string-type;
    }
    uses apply-group;
    uses apply-macro;
    list application {
      key "name";
      ordered-by user;
      leaf name {
        type key-attribute-string-type;
      }
      leaf-list code-points {
        type string;
        ordered-by user;
      }
    }
  }

  grouping as-path-calc-length-type {
    leaf name {
      type key-attribute-ulong-type;
    }
    uses apply-group;
    uses apply-macro;
    choice choice-equal {
      leaf equal {
        type empty;
      }
      leaf orhigher {
        type empty;
      }
      leaf orlower {
        type empty;
      }
    }
  }

  grouping as-path-unique-count-type {
    leaf name {
      type key-attribute-ulong-type;
    }
    uses apply-group;
    uses apply-macro;
    choice choice-equal {
      leaf equal {
        type empty;
      }
      leaf orhigher {
        type empty;
      }
      leaf orlower {
        type empty;
      }
    }
  }

  grouping community-count-type {
    leaf name {
      type string;
    }
    uses apply-group;
    uses apply-macro;
    choice choice-3 {
      leaf equal {
        type empty;
      }
      leaf orhigher {
        type empty;
      }
      leaf orlower {
        type empty;
      }
    }
  }

  grouping control-mac-address-filter-list-type {
    leaf name {
      type string;
    }
    uses apply-advanced;
  }

  grouping control-prefix-list-filter-type {
    leaf list_name {
      type string;
    }
    leaf key2 {
      type string;
    }
    uses apply-group;
    uses apply-macro;
    container metric {
      uses apply-group;
      uses apply-macro;
      choice choice-3 {
        leaf metric {
          type uint32;
        }
        leaf add {
          type uint32;
        }
        leaf subtract {
          type uint32;
        }
        container igp {
          presence "enable igp";
          leaf metric_offset {
            type int32;
          }
        }
        container minimum-igp {
          presence "enable minimum-igp";
          leaf metric_offset {
            type int32;
          }
        }
        container expression {
          uses metric-expression-type;
        }
        leaf aigp {
          type empty;
        }
      }
    }
    container metric2 {
      uses apply-group;
      uses apply-macro;
      choice choice-3 {
        leaf metric2 {
          type uint32;
        }
        leaf add {
          type uint32;
        }
        leaf subtract {
          type uint32;
        }
      }
    }
    container metric3 {
      uses apply-group;
      uses apply-macro;
      choice choice-3 {
        leaf metric3 {
          type uint32;
        }
        leaf add {
          type uint32;
        }
        leaf subtract {
          type uint32;
        }
      }
    }
    container metric4 {
      uses apply-group;
      uses apply-macro;
      choice choice-3 {
        leaf metric4 {
          type uint32;
        }
        leaf add {
          type uint32;
        }
        leaf subtract {
          type uint32;
        }
      }
    }
    container tag {
      uses apply-group;
      uses apply-macro;
      choice choice-3 {
        leaf tag {
          type uint32;
        }
        leaf add {
          type uint32;
        }
        leaf subtract {
          type uint32;
        }
      }
    }
    container tag2 {
      uses apply-group;
      uses apply-macro;
      choice choice-3 {
        leaf tag2 {
          type uint32;
        }
        leaf add {
          type uint32;
        }
        leaf subtract {
          type uint32;
        }
      }
    }
    container preference {
      uses apply-group;
      uses apply-macro;
      choice choice-3 {
        leaf preference {
          type uint32;
        }
        leaf add {
          type uint32;
        }
        leaf subtract {
          type uint32;
        }
      }
    }
    container preference2 {
      uses apply-group;
      uses apply-macro;
      choice choice-3 {
        leaf preference2 {
          type uint32;
        }
        leaf add {
          type uint32;
        }
        leaf subtract {
          type uint32;
        }
      }
    }
    container color {
      uses apply-group;
      uses apply-macro;
      choice choice-3 {
        leaf color {
          type uint32;
        }
        leaf add {
          type uint32;
        }
        leaf subtract {
          type uint32;
        }
      }
    }
    container color2 {
      uses apply-group;
      uses apply-macro;
      choice choice-3 {
        leaf color2 {
          type uint32;
        }
        leaf add {
          type uint32;
        }
        leaf subtract {
          type uint32;
        }
      }
    }
    container local-preference {
      uses apply-group;
      uses apply-macro;
      choice choice-3 {
        leaf local-preference {
          type uint32;
        }
        leaf add {
          type uint32;
        }
        leaf subtract {
          type uint32;
        }
      }
    }
    leaf priority {
      type string;
    }
    container prefix-segment {
      list algorithm {
        key "name";
        leaf name {
          type string;
        }
        leaf index {
          type string;
        }
        leaf node-segment {
          type empty;
        }
      }
      leaf index {
        type string;
      }
      leaf node-segment {
        type empty;
      }
    }
    leaf label-allocation {
      type string;
    }
    container add-path {
      leaf send-count {
        type uint32;
      }
    }
    leaf validation-state {
      type string;
    }
    leaf origin {
      type string;
    }
    container aigp-originate {
      presence "enable aigp-originate";
      leaf distance {
        type uint32;
      }
    }
    container aigp-adjust {
      choice choice-add {
        leaf add {
          type empty;
        }
        leaf subtract {
          type empty;
        }
        leaf multiply {
          type empty;
        }
        leaf divide {
          type empty;
        }
      }
      choice choice-user-value {
        leaf user-value {
          type uint64;
        }
        leaf distance-to-protocol-nexthop {
          type empty;
        }
      }
    }
    list community {
      key "key1 community-name";
      ordered-by user;
      leaf key1 {
        type string;
      }
      leaf community-name {
        type string;
      }
    }
    leaf damping {
      type string;
    }
    leaf aggregate-bandwidth {
      type empty;
    }
    leaf limit-bandwidth {
      type uint32;
    }
    leaf no-entropy-label-capability {
      type empty;
    }
    leaf as-path-prepend {
      type string;
    }
    container as-path-expand {
      choice choice-3 {
        container last-as {
          presence "enable last-as";
          leaf count {
            type uint32;
          }
        }
        leaf aspath {
          type string;
        }
      }
    }
    container next-hop {
      choice choice-3 {
        leaf self {
          type empty;
        }
        leaf peer-address {
          type empty;
        }
        leaf address {
          type ipaddr;
        }
        leaf reject {
          type empty;
        }
        leaf discard {
          type empty;
        }
        leaf next-table {
          type string;
        }
      }
    }
    container install-nexthop {
      leaf strict {
        type empty;
      }
      choice choice-5 {
        leaf-list lsp {
          type string;
          ordered-by user;
        }
        leaf-list lsp-regex {
          type string;
          ordered-by user;
        }
        leaf-list static-lsp {
          type string;
          ordered-by user;
        }
        leaf-list static-lsp-regex {
          type string;
          ordered-by user;
        }
      }
      container except {
        uses apply-group;
        uses apply-macro;
        choice choice-3 {
          leaf-list lsp {
            type string;
            ordered-by user;
          }
          leaf-list lsp-regex {
            type string;
            ordered-by user;
          }
          leaf-list static-lsp {
            type string;
            ordered-by user;
          }
          leaf-list static-lsp-regex {
            type string;
            ordered-by user;
          }
        }
      }
    }
    leaf trace {
      type empty;
    }
    container external {
      presence "";
      uses apply-group;
      uses apply-macro;
      leaf type {
        type int32;
      }
      leaf nssa-only {
        type empty;
      }
    }
    container load-balance {
      choice choice-3 {
        leaf per-packet {
          type empty;
        }
        leaf random {
          type empty;
        }
        leaf per-prefix {
          type empty;
        }
        leaf consistent-hash {
          type empty;
        }
        leaf source-ip-only {
          type empty;
        }
        leaf destination-ip-only {
          type empty;
        }
      }
    }
    leaf no-route-localize {
      type empty;
    }
    leaf install-to-fib {
      type empty;
    }
    leaf no-install-to-fib {
      type empty;
    }
    leaf analyze {
      type empty;
    }
    leaf class {
      type string;
    }
    leaf destination-class {
      type string;
    }
    leaf source-class {
      type string;
    }
    leaf forwarding-class {
      type string;
    }
    container map-to-interface {
      choice choice-3 {
        leaf self {
          type empty;
        }
        leaf interface {
          type interface-name;
        }
      }
    }
    leaf-list ssm-source {
      type ipaddr;
      ordered-by user;
    }
    container p2mp-lsp-root {
      uses apply-group;
      uses apply-macro;
      leaf address {
        type ipv4addr;
      }
    }
    leaf cos-next-hop-map {
      type string;
    }
    leaf dynamic-tunnel-attributes {
      type string;
    }
    leaf selected-mldp-egress {
      type empty;
    }
    leaf mhop-bfd-port {
      type empty;
    }
    leaf no-backup {
      type empty;
    }
    leaf default-action {
      type string;
    }
    leaf next {
      type string;
    }
    choice choice-65 {
      leaf accept {
        type empty;
      }
      leaf reject {
        type empty;
      }
    }
    container bgp-output-queue-priority {
      choice choice-priority {
        leaf priority {
          type uint32;
        }
        leaf expedited {
          type empty;
        }
      }
    }
    leaf multipath-resolve {
      type empty;
    }
    leaf sr-te-template {
      type string;
    }
    leaf label-allocation-fallback-reject {
      type empty;
    }
    leaf resolution-map {
      type string;
    }
  }

  grouping control-prefix-list-type {
    leaf name {
      type string;
    }
    uses apply-group;
    uses apply-macro;
  }

  grouping control-route-filter-type {
    leaf address {
      type ipprefix;
    }
    leaf key2 {
      type string;
    }
    leaf key2-arg {
      type string;
    }
    uses apply-group;
    uses apply-macro;
    container metric {
      uses apply-group;
      uses apply-macro;
      choice choice-3 {
        leaf metric {
          type uint32;
        }
        leaf add {
          type uint32;
        }
        leaf subtract {
          type uint32;
        }
        container igp {
          presence "enable igp";
          leaf metric_offset {
            type int32;
          }
        }
        container minimum-igp {
          presence "enable minimum-igp";
          leaf metric_offset {
            type int32;
          }
        }
        container expression {
          uses metric-expression-type;
        }
        leaf aigp {
          type empty;
        }
      }
    }
    container metric2 {
      uses apply-group;
      uses apply-macro;
      choice choice-3 {
        leaf metric2 {
          type uint32;
        }
        leaf add {
          type uint32;
        }
        leaf subtract {
          type uint32;
        }
      }
    }
    container metric3 {
      uses apply-group;
      uses apply-macro;
      choice choice-3 {
        leaf metric3 {
          type uint32;
        }
        leaf add {
          type uint32;
        }
        leaf subtract {
          type uint32;
        }
      }
    }
    container metric4 {
      uses apply-group;
      uses apply-macro;
      choice choice-3 {
        leaf metric4 {
          type uint32;
        }
        leaf add {
          type uint32;
        }
        leaf subtract {
          type uint32;
        }
      }
    }
    container tag {
      uses apply-group;
      uses apply-macro;
      choice choice-3 {
        leaf tag {
          type uint32;
        }
        leaf add {
          type uint32;
        }
        leaf subtract {
          type uint32;
        }
      }
    }
    container tag2 {
      uses apply-group;
      uses apply-macro;
      choice choice-3 {
        leaf tag2 {
          type uint32;
        }
        leaf add {
          type uint32;
        }
        leaf subtract {
          type uint32;
        }
      }
    }
    container preference {
      uses apply-group;
      uses apply-macro;
      choice choice-3 {
        leaf preference {
          type uint32;
        }
        leaf add {
          type uint32;
        }
        leaf subtract {
          type uint32;
        }
      }
    }
    container preference2 {
      uses apply-group;
      uses apply-macro;
      choice choice-3 {
        leaf preference2 {
          type uint32;
        }
        leaf add {
          type uint32;
        }
        leaf subtract {
          type uint32;
        }
      }
    }
    container color {
      uses apply-group;
      uses apply-macro;
      choice choice-3 {
        leaf color {
          type uint32;
        }
        leaf add {
          type uint32;
        }
        leaf subtract {
          type uint32;
        }
      }
    }
    container color2 {
      uses apply-group;
      uses apply-macro;
      choice choice-3 {
        leaf color2 {
          type uint32;
        }
        leaf add {
          type uint32;
        }
        leaf subtract {
          type uint32;
        }
      }
    }
    container local-preference {
      uses apply-group;
      uses apply-macro;
      choice choice-3 {
        leaf local-preference {
          type uint32;
        }
        leaf add {
          type uint32;
        }
        leaf subtract {
          type uint32;
        }
      }
    }
    leaf priority {
      type string;
    }
    container prefix-segment {
      list algorithm {
        key "name";
        leaf name {
          type string;
        }
        leaf index {
          type string;
        }
        leaf node-segment {
          type empty;
        }
      }
      leaf index {
        type string;
      }
      leaf node-segment {
        type empty;
      }
    }
    leaf label-allocation {
      type string;
    }
    container add-path {
      leaf send-count {
        type uint32;
      }
    }
    leaf validation-state {
      type string;
    }
    leaf origin {
      type string;
    }
    container aigp-originate {
      presence "enable aigp-originate";
      leaf distance {
        type uint32;
      }
    }
    container aigp-adjust {
      choice choice-add {
        leaf add {
          type empty;
        }
        leaf subtract {
          type empty;
        }
        leaf multiply {
          type empty;
        }
        leaf divide {
          type empty;
        }
      }
      choice choice-user-value {
        leaf user-value {
          type uint64;
        }
        leaf distance-to-protocol-nexthop {
          type empty;
        }
      }
    }
    list community {
      key "key1 community-name";
      ordered-by user;
      leaf key1 {
        type string;
      }
      leaf community-name {
        type string;
      }
    }
    leaf damping {
      type string;
    }
    leaf aggregate-bandwidth {
      type empty;
    }
    leaf limit-bandwidth {
      type uint32;
    }
    leaf no-entropy-label-capability {
      type empty;
    }
    leaf as-path-prepend {
      type string;
    }
    container as-path-expand {
      choice choice-3 {
        container last-as {
          presence "enable last-as";
          leaf count {
            type uint32;
          }
        }
        leaf aspath {
          type string;
        }
      }
    }
    container next-hop {
      choice choice-3 {
        leaf self {
          type empty;
        }
        leaf peer-address {
          type empty;
        }
        leaf address {
          type ipaddr;
        }
        leaf reject {
          type empty;
        }
        leaf discard {
          type empty;
        }
        leaf next-table {
          type string;
        }
      }
    }
    container install-nexthop {
      leaf strict {
        type empty;
      }
      choice choice-5 {
        leaf-list lsp {
          type string;
          ordered-by user;
        }
        leaf-list lsp-regex {
          type string;
          ordered-by user;
        }
        leaf-list static-lsp {
          type string;
          ordered-by user;
        }
        leaf-list static-lsp-regex {
          type string;
          ordered-by user;
        }
      }
      container except {
        uses apply-group;
        uses apply-macro;
        choice choice-3 {
          leaf-list lsp {
            type string;
            ordered-by user;
          }
          leaf-list lsp-regex {
            type string;
            ordered-by user;
          }
          leaf-list static-lsp {
            type string;
            ordered-by user;
          }
          leaf-list static-lsp-regex {
            type string;
            ordered-by user;
          }
        }
      }
    }
    leaf trace {
      type empty;
    }
    container external {
      presence "";
      uses apply-group;
      uses apply-macro;
      leaf type {
        type int32;
      }
      leaf nssa-only {
        type empty;
      }
    }
    container load-balance {
      choice choice-3 {
        leaf per-packet {
          type empty;
        }
        leaf random {
          type empty;
        }
        leaf per-prefix {
          type empty;
        }
        leaf consistent-hash {
          type empty;
        }
        leaf source-ip-only {
          type empty;
        }
        leaf destination-ip-only {
          type empty;
        }
      }
    }
    leaf no-route-localize {
      type empty;
    }
    leaf install-to-fib {
      type empty;
    }
    leaf no-install-to-fib {
      type empty;
    }
    leaf analyze {
      type empty;
    }
    leaf class {
      type string;
    }
    leaf destination-class {
      type string;
    }
    leaf source-class {
      type string;
    }
    leaf forwarding-class {
      type string;
    }
    container map-to-interface {
      choice choice-3 {
        leaf self {
          type empty;
        }
        leaf interface {
          type interface-name;
        }
      }
    }
    leaf-list ssm-source {
      type ipaddr;
      ordered-by user;
    }
    container p2mp-lsp-root {
      uses apply-group;
      uses apply-macro;
      leaf address {
        type ipv4addr;
      }
    }
    leaf cos-next-hop-map {
      type string;
    }
    leaf dynamic-tunnel-attributes {
      type string;
    }
    leaf selected-mldp-egress {
      type empty;
    }
    leaf mhop-bfd-port {
      type empty;
    }
    leaf no-backup {
      type empty;
    }
    leaf default-action {
      type string;
    }
    leaf next {
      type string;
    }
    choice choice-65 {
      leaf accept {
        type empty;
      }
      leaf reject {
        type empty;
      }
    }
    container bgp-output-queue-priority {
      choice choice-priority {
        leaf priority {
          type uint32;
        }
        leaf expedited {
          type empty;
        }
      }
    }
    leaf multipath-resolve {
      type empty;
    }
    leaf sr-te-template {
      type string;
    }
    leaf label-allocation-fallback-reject {
      type empty;
    }
    leaf resolution-map {
      type string;
    }
  }

  grouping control-route-filter-list-type {
    leaf name {
      type string;
    }
    uses apply-group;
    uses apply-macro;
  }

  grouping control-rtf-prefix-list-type {
    leaf name {
      type string;
    }
    uses apply-group;
    uses apply-macro;
  }

  grouping control-source-address-filter-list-type {
    leaf name {
      type string;
    }
    uses apply-group;
    uses apply-macro;
  }

  grouping control-source-address-filter-type {
    leaf address {
      type ipprefix;
    }
    leaf key2 {
      type string;
    }
    leaf key2-arg {
      type string;
    }
    uses apply-group;
    uses apply-macro;
    container metric {
      uses apply-group;
      uses apply-macro;
      choice choice-metric {
        leaf metric {
          type uint32;
        }
        leaf add {
          type uint32;
        }
        leaf subtract {
          type uint32;
        }
        container igp {
          presence "enable igp";
          leaf metric_offset {
            type int32;
          }
        }
        container minimum-igp {
          presence "enable minimum-igp";
          leaf metric_offset {
            type int32;
          }
        }
        container expression {
          uses metric-expression-type;
        }
        leaf aigp {
          type empty;
        }
      }
    }
    container metric2 {
      uses apply-group;
      uses apply-macro;
      choice choice-metric2 {
        leaf metric2 {
          type uint32;
        }
        leaf add {
          type uint32;
        }
        leaf subtract {
          type uint32;
        }
      }
    }
    container metric3 {
      uses apply-group;
      uses apply-macro;
      choice choice-metric3 {
        leaf metric3 {
          type uint32;
        }
        leaf add {
          type uint32;
        }
        leaf subtract {
          type uint32;
        }
      }
    }
    container metric4 {
      uses apply-group;
      uses apply-macro;
      choice choice-metric4 {
        leaf metric4 {
          type uint32;
        }
        leaf add {
          type uint32;
        }
        leaf subtract {
          type uint32;
        }
      }
    }
    container tag {
      uses apply-group;
      uses apply-macro;
      choice choice-tag {
        leaf tag {
          type uint32;
        }
        leaf add {
          type uint32;
        }
        leaf subtract {
          type uint32;
        }
      }
    }
    container tag2 {
      uses apply-group;
      uses apply-macro;
      choice choice-tag2 {
        leaf tag2 {
          type uint32;
        }
        leaf add {
          type uint32;
        }
        leaf subtract {
          type uint32;
        }
      }
    }
    container preference {
      uses apply-group;
      uses apply-macro;
      choice choice-preference {
        leaf preference {
          type uint32;
        }
        leaf add {
          type uint32;
        }
        leaf subtract {
          type uint32;
        }
      }
    }
    container preference2 {
      uses apply-group;
      uses apply-macro;
      choice choice-preference2 {
        leaf preference2 {
          type uint32;
        }
        leaf add {
          type uint32;
        }
        leaf subtract {
          type uint32;
        }
      }
    }
    container color {
      uses apply-group;
      uses apply-macro;
      choice choice-color {
        leaf color {
          type uint32;
        }
        leaf add {
          type uint32;
        }
        leaf subtract {
          type uint32;
        }
      }
    }
    container color2 {
      uses apply-group;
      uses apply-macro;
      choice choice-color2 {
        leaf color2 {
          type uint32;
        }
        leaf add {
          type uint32;
        }
        leaf subtract {
          type uint32;
        }
      }
    }
    container local-preference {
      uses apply-group;
      uses apply-macro;
      choice choice-local-preference {
        leaf local-preference {
          type uint32;
        }
        leaf add {
          type uint32;
        }
        leaf subtract {
          type uint32;
        }
      }
    }
    leaf priority {
      type string;
    }
    container prefix-segment {
      list algorithm {
        key "name";
        leaf name {
          type string;
        }
        leaf index {
          type string;
        }
        leaf node-segment {
          type empty;
        }
      }
      leaf index {
        type string;
      }
      leaf node-segment {
        type empty;
      }
    }
    leaf label-allocation {
      type string;
    }
    container add-path {
      leaf send-count {
        type uint32;
      }
    }
    leaf validation-state {
      type string;
    }
    leaf origin {
      type string;
    }
    container aigp-originate {
      presence "enable aigp-originate";
      leaf distance {
        type uint32;
      }
    }
    container aigp-adjust {
      choice choice-add {
        leaf add {
          type empty;
        }
        leaf subtract {
          type empty;
        }
        leaf multiply {
          type empty;
        }
        leaf divide {
          type empty;
        }
      }
      choice choice-user-value {
        leaf user-value {
          type uint64;
        }
        leaf distance-to-protocol-nexthop {
          type empty;
        }
      }
    }
    list community {
      key "key1 community-name";
      ordered-by user;
      leaf key1 {
        type string;
      }
      leaf community-name {
        type string;
      }
    }
    leaf damping {
      type string;
    }
    leaf aggregate-bandwidth {
      type empty;
    }
    leaf limit-bandwidth {
      type uint32;
    }
    leaf no-entropy-label-capability {
      type empty;
    }
    leaf as-path-prepend {
      type string;
    }
    container as-path-expand {
      choice choice-last-as {
        container last-as {
          presence "enable last-as";
          leaf count {
            type uint32;
          }
        }
        leaf aspath {
          type string;
        }
      }
    }
    container next-hop {
      choice choice-self {
        leaf self {
          type empty;
        }
        leaf peer-address {
          type empty;
        }
        leaf address {
          type ipaddr;
        }
        leaf reject {
          type empty;
        }
        leaf discard {
          type empty;
        }
        leaf next-table {
          type string;
        }
      }
    }
    container install-nexthop {
      leaf strict {
        type empty;
      }
      choice choice-lsp {
        leaf-list lsp {
          type string;
          ordered-by user;
        }
        leaf-list lsp-regex {
          type string;
          ordered-by user;
        }
        leaf-list static-lsp {
          type string;
          ordered-by user;
        }
        leaf-list static-lsp-regex {
          type string;
          ordered-by user;
        }
      }
      container except {
        uses apply-group;
        uses apply-macro;
        choice choice-lsp {
          leaf-list lsp {
            type string;
            ordered-by user;
          }
          leaf-list lsp-regex {
            type string;
            ordered-by user;
          }
          leaf-list static-lsp {
            type string;
            ordered-by user;
          }
          leaf-list static-lsp-regex {
            type string;
            ordered-by user;
          }
        }
      }
    }
    leaf trace {
      type empty;
    }
    container external {
      presence "enable external";
      uses apply-group;
      uses apply-macro;
      leaf type {
        type int32;
      }
      leaf nssa-only {
        type empty;
      }
    }
    container load-balance {
      choice choice-per-packet {
        leaf per-packet {
          type empty;
        }
        leaf random {
          type empty;
        }
        leaf per-prefix {
          type empty;
        }
        leaf consistent-hash {
          type empty;
        }
        leaf source-ip-only {
          type empty;
        }
        leaf destination-ip-only {
          type empty;
        }
      }
    }
    leaf no-route-localize {
      type empty;
    }
    leaf install-to-fib {
      type empty;
    }
    leaf no-install-to-fib {
      type empty;
    }
    leaf analyze {
      type empty;
    }
    leaf class {
      type string;
    }
    leaf destination-class {
      type string;
    }
    leaf source-class {
      type string;
    }
    leaf forwarding-class {
      type string;
    }
    container map-to-interface {
      choice choice-self {
        leaf self {
          type empty;
        }
        leaf interface {
          type interface-name;
        }
      }
    }
    leaf-list ssm-source {
      type ipaddr;
      ordered-by user;
    }
    container p2mp-lsp-root {
      uses apply-group;
      uses apply-macro;
      leaf address {
        type ipv4addr;
      }
    }
    leaf cos-next-hop-map {
      type string;
    }
    leaf dynamic-tunnel-attributes {
      type string;
    }
    leaf selected-mldp-egress {
      type empty;
    }
    leaf mhop-bfd-port {
      type empty;
    }
    leaf no-backup {
      type empty;
    }
    leaf default-action {
      type string;
    }
    leaf next {
      type string;
    }
    choice choice-accept {
      leaf accept {
        type empty;
      }
      leaf reject {
        type empty;
      }
    }
    container bgp-output-queue-priority {
      choice choice-priority {
        leaf priority {
          type uint32;
        }
        leaf expedited {
          type empty;
        }
      }
    }
    leaf multipath-resolve {
      type empty;
    }
    leaf sr-te-template {
      type string;
    }
    leaf label-allocation-fallback-reject {
      type empty;
    }
    leaf resolution-map {
      type string;
    }
  }

  grouping juniper-port-mirror-options {
    uses apply-group;
    uses apply-macro;
    container traceoptions {
      uses sampling-traceoptions-type;
    }
    leaf disable {
      type empty;
    }
    leaf disable-all-instances {
      type empty;
    }
    leaf mirror-once {
      type empty;
    }
    leaf no-preserve-ingress-tag {
      type empty;
    }
    container input {
      uses pm-family-input-type;
    }
    container family {
      uses apply-group;
      uses apply-macro;
      container inet {
        uses apply-group;
        uses apply-macro;
        container output {
          uses inet-pm-family-output-type;
        }
      }
      container inet6 {
        uses apply-group;
        uses apply-macro;
        container output {
          uses inet6-pm-family-output-type;
        }
      }
      container mpls {
        uses apply-group;
        uses apply-macro;
        container output {
          uses mpls-pm-family-output-type;
        }
      }
      container any {
        uses apply-group;
        uses apply-macro;
        container output {
          uses any-pm-family-output-type;
        }
      }
      container vpls {
        uses apply-group;
        uses apply-macro;
        container output {
          uses layer2-pm-family-output-type;
        }
      }
      container ethernet-switching {
        uses apply-group;
        uses apply-macro;
        container output {
          uses layer2-pm-family-output-type;
        }
      }
      container ccc {
        uses apply-group;
        uses apply-macro;
        container output {
          uses layer2-pm-family-output-type;
        }
      }
    }
    list instance {
      key "name";
      ordered-by user;
      leaf name {
        type string;
      }
      uses apply-group;
      uses apply-macro;
      leaf disable {
        type empty;
      }
      choice choice-5 {
        container input {
          uses pm-family-input-type;
        }
        leaf input-parameters-instance {
          type string;
        }
      }
      container family {
        uses apply-group;
        uses apply-macro;
        container inet {
          uses apply-group;
          uses apply-macro;
          container output {
            uses inet-pm-family-output-type;
          }
        }
        container inet6 {
          uses apply-group;
          uses apply-macro;
          container output {
            uses inet6-pm-family-output-type;
          }
        }
        container mpls {
          uses apply-group;
          uses apply-macro;
          container output {
            uses mpls-pm-family-output-type;
          }
        }
        container any {
          uses apply-group;
          uses apply-macro;
          container output {
            uses any-pm-family-output-type;
          }
        }
        container vpls {
          uses apply-group;
          uses apply-macro;
          container output {
            uses layer2-pm-family-output-type;
          }
        }
        container ethernet-switching {
          uses apply-group;
          uses apply-macro;
          container output {
            uses layer2-pm-family-output-type;
          }
        }
        container ccc {
          uses apply-group;
          uses apply-macro;
          container output {
            uses layer2-pm-family-output-type;
          }
        }
      }
    }
  }

  grouping any-pm-family-output-type {
    uses apply-group;
    uses apply-macro;
    choice choice-interface {
      list interface {
        key "name";
        uses any-pm-intf-type;
      }
      leaf next-hop-group {
        type string;
      }
    }
    leaf no-filter-check {
      type empty;
    }
    container hosted-service {
      presence "";
      uses apply-group;
      uses apply-macro;
      leaf server-profile {
        mandatory true;
        type string;
      }
    }
  }

  grouping any-pm-intf-type {
    leaf name {
      type interface-name;
    }
    uses apply-group;
    uses apply-macro;
    list next-hop {
      key "name";
      ordered-by user;
      uses inet-next-hop-type;
    }
  }

  grouping inet6-pm-family-output-type {
    uses apply-group;
    uses apply-macro;
    choice choice-3 {
      list interface {
        key "name";
        uses inet6-pm-intf-type;
      }
      leaf next-hop-group {
        type string;
      }
    }
    leaf no-filter-check {
      type empty;
    }
    leaf server-profile {
      type string;
    }
  }

  grouping inet6-pm-intf-type {
    leaf name {
      type interface-name;
    }
    uses apply-group;
    uses apply-macro;
    list next-hop {
      key "name";
      ordered-by user;
      uses inet6-next-hop-type;
    }
  }

  grouping inet6-next-hop-type {
    leaf name {
      type ipv6addr;
    }
    uses apply-group;
    uses apply-macro;
  }

  grouping inet-pm-family-output-type {
    uses apply-group;
    uses apply-macro;
    choice choice-3 {
      list interface {
        key "name";
        uses inet-pm-intf-type;
      }
      leaf next-hop-group {
        type string;
      }
    }
    leaf no-filter-check {
      type empty;
    }
    leaf ip-address {
      type ipv4addr;
    }
    list routing-instance {
      key "name";
      uses inet-pm-output-routing-instance-type;
    }
    leaf server-profile {
      type string;
    }
  }

  grouping inet-pm-intf-type {
    leaf name {
      type interface-name;
    }
    uses apply-group;
    uses apply-macro;
    list next-hop {
      key "name";
      ordered-by user;
      uses inet-next-hop-type;
    }
  }

  grouping inet-next-hop-type {
    leaf name {
      type ipv4addr;
    }
    uses apply-group;
    uses apply-macro;
  }

  grouping inet-pm-output-routing-instance-type {
    leaf name {
      type string;
    }
    uses apply-group;
    uses apply-macro;
    leaf ip-address {
      type ipv4addr;
    }
  }

  grouping juniper-protected-system-domain {
    leaf name {
      type string;
    }
    uses apply-group;
    uses apply-macro;
    leaf description {
      type string;
    }
    leaf-list fpcs {
      type uint32;
    }
    leaf control-system-id {
      type uint32;
    }
    leaf-list control-slot-numbers {
      ordered-by user;
      type uint32;
    }
    leaf control-plane-bandwidth-percent {
      type uint32;
    }
  }

  grouping juniper-protected-system-domain-traceoptions {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping juniper-protocols {
    uses apply-group;
    uses apply-macro;
    container l2iw {
      presence "enable l2iw";
      uses apply-group;
      uses apply-macro;
      container traceoptions {
        uses apply-group;
        uses apply-macro;
        container file {
          presence "";
          uses trace-file-type;
        }
        list flag {
          key "name";
          ordered-by user;
          leaf name {
            type string;
          }
          leaf send {
            type empty;
          }
          leaf receive {
            type empty;
          }
          leaf detail {
            type empty;
          }
          leaf disable {
            type empty;
          }
        }
      }
    }
    container igmp {
      presence "enable igmp";
      uses apply-group;
      uses apply-macro;
      container traceoptions {
        uses apply-group;
        uses apply-macro;
        container file {
          presence "";
          uses trace-file-type;
        }
        list flag {
          key "name";
          ordered-by user;
          leaf name {
            type string;
          }
          leaf send {
            type empty;
          }
          leaf receive {
            type empty;
          }
          leaf detail {
            type empty;
          }
          leaf disable {
            type empty;
          }
        }
      }
      leaf query-interval {
        type uint32;
      }
      leaf query-response-interval {
        type string;
      }
      leaf query-last-member-interval {
        type string;
      }
      leaf robust-count {
        type uint32;
      }
      leaf maximum-transmit-rate {
        type uint32;
      }
      leaf accounting {
        type empty;
      }
      list interface {
        key "name";
        ordered-by user;
        leaf name {
          type string;
        }
        uses apply-group;
        uses apply-macro;
        choice choice-3 {
          leaf disable {
            type empty;
          }
        }
        leaf version {
          type uint8;
        }
        container static {
          uses apply-group;
          uses apply-macro;
          list group {
            key "name";
            ordered-by user;
            leaf name {
              type ipv4addr;
            }
            uses apply-group;
            uses apply-macro;
            leaf group-increment {
              type ipv4addr;
            }
            leaf group-count {
              type uint32;
            }
            leaf exclude {
              type empty;
            }
            list source {
              key "name";
              ordered-by user;
              leaf name {
                type ipv4addr;
              }
              uses apply-group;
              uses apply-macro;
              leaf source-increment {
                type ipv4addr;
              }
              leaf source-count {
                type uint32;
              }
            }
          }
        }
        leaf ssm-map {
          type string;
        }
        leaf-list ssm-map-policy {
          type policy-algebra;
          ordered-by user;
        }
        leaf immediate-leave {
          type empty;
        }
        leaf promiscuous-mode {
          type empty;
        }
        leaf accounting {
          type empty;
        }
        leaf no-accounting {
          type empty;
        }
        leaf-list group-policy {
          type policy-algebra;
          ordered-by user;
        }
        leaf group-limit {
          type uint16;
        }
        container passive {
          presence "enable passive";
          leaf allow-receive {
            type empty;
          }
          leaf send-general-query {
            type empty;
          }
          leaf send-group-query {
            type empty;
          }
        }
        leaf-list oif-map {
          type policy-algebra;
          ordered-by user;
        }
      }
    }
    container mld {
      presence "enable mld";
      uses apply-group;
      uses apply-macro;
      container traceoptions {
        uses apply-group;
        uses apply-macro;
        container file {
          presence "";
          uses trace-file-type;
        }
        list flag {
          key "name";
          ordered-by user;
          leaf name {
            type string;
          }
          leaf send {
            type empty;
          }
          leaf receive {
            type empty;
          }
          leaf detail {
            type empty;
          }
          leaf disable {
            type empty;
          }
        }
      }
      leaf query-interval {
        type uint32;
      }
      leaf query-response-interval {
        type string;
      }
      leaf query-last-member-interval {
        type string;
      }
      leaf robust-count {
        type uint32;
      }
      leaf maximum-transmit-rate {
        type uint32;
      }
      leaf accounting {
        type empty;
      }
      list interface {
        key "name";
        ordered-by user;
        leaf name {
          type string;
        }
        uses apply-group;
        uses apply-macro;
        choice choice-3 {
          leaf disable {
            type empty;
          }
        }
        leaf version {
          type uint8;
        }
        container static {
          uses apply-group;
          uses apply-macro;
          list group {
            key "name";
            ordered-by user;
            leaf name {
              type ipv6addr;
            }
            uses apply-group;
            uses apply-macro;
            leaf group-increment {
              type ipv6addr;
            }
            leaf group-count {
              type uint32;
            }
            leaf exclude {
              type empty;
            }
            list source {
              key "name";
              ordered-by user;
              leaf name {
                type ipv6addr;
              }
              uses apply-group;
              uses apply-macro;
              leaf source-increment {
                type ipv6addr;
              }
              leaf source-count {
                type uint32;
              }
            }
          }
        }
        leaf ssm-map {
          type string;
        }
        leaf immediate-leave {
          type empty;
        }
        leaf-list group-policy {
          type policy-algebra;
          ordered-by user;
        }
        leaf group-limit {
          type uint16;
        }
        leaf accounting {
          type empty;
        }
        leaf no-accounting {
          type empty;
        }
        container passive {
          presence "enable passive";
          leaf allow-receive {
            type empty;
          }
          leaf send-general-query {
            type empty;
          }
          leaf send-group-query {
            type empty;
          }
        }
        leaf-list oif-map {
          type policy-algebra;
          ordered-by user;
        }
      }
    }
    container amt {
      uses juniper-protocols-amt;
    }
    container router-discovery {
      uses juniper-protocols-router-discovery;
    }
    container router-advertisement {
      uses apply-group;
      uses apply-macro;
      container traceoptions {
        uses apply-group;
        uses apply-macro;
        container file {
          presence "";
          uses trace-file-type;
        }
        list flag {
          key "name";
          ordered-by user;
          leaf name {
            type string;
          }
        }
      }
      list interface {
        key "name";
        ordered-by user;
        leaf name {
          type string;
        }
        uses apply-group;
        uses apply-macro;
        leaf preference {
          type string;
        }
        leaf max-advertisement-interval {
          type uint32;
        }
        leaf min-advertisement-interval {
          type uint32;
        }
        choice managed-configuration-choice {
          leaf managed-configuration {
            type empty;
          }
          leaf no-managed-configuration {
            type empty;
          }
        }
        choice other-stateful-configuration-choice {
          leaf other-stateful-configuration {
            type empty;
          }
          leaf no-other-stateful-configuration {
            type empty;
          }
        }
        choice link-mtu-choice {
          leaf link-mtu {
            type empty;
          }
          leaf no-link-mtu {
            type empty;
          }
        }
        leaf solicit-router-advertisement-unicast {
          type empty;
        }
        leaf reachable-time {
          type uint32;
        }
        leaf retransmit-timer {
          type uint32;
        }
        leaf virtual-router-only {
          type empty;
        }
        leaf current-hop-limit {
          type uint32;
        }
        leaf default-lifetime {
          type uint32;
        }
        list downstream {
          key "name";
          ordered-by user;
          leaf name {
            type string;
          }
          uses apply-advanced;
        }
        leaf upstream-mode {
          type empty;
        }
        leaf downstream-mode {
          type empty;
        }
        leaf parameter-preference {
          type string;
        }
        leaf passive-mode {
          type empty;
        }
        list dns-server-address {
          key "name";
          ordered-by user;
          leaf name {
            type string;
          }
          uses apply-advanced;
          leaf lifetime {
            units "seconds";
            type string;
          }
        }
        list prefix {
          key "name";
          ordered-by user;
          leaf name {
            type ipv6prefix;
          }
          uses apply-group;
          uses apply-macro;
          leaf valid-lifetime {
            type uint32;
          }
          leaf on-link {
            type empty;
          }
          leaf no-on-link {
            type empty;
          }
          leaf preferred-lifetime {
            type uint32;
          }
          leaf autonomous {
            type empty;
          }
          leaf no-autonomous {
            type empty;
          }
        }
        list dns-search-list {
          key "name";
          ordered-by user;
          leaf name {
            type string;
          }
          uses apply-advanced;
          leaf lifetime {
            units "seconds";
            type string;
          }
        }
        list rio-prefix {
          key "name";
          ordered-by user;
          leaf name {
            type ipv6prefix;
          }
          uses apply-advanced;
          leaf rio-lifetime {
            units "seconds";
            type string;
          }
          leaf rio-preference {
            type string;
          }
        }
        list nat-prefix {
          key "name";
          ordered-by user;
          leaf name {
            type ipv6prefix;
          }
          uses apply-advanced;
          leaf lifetime {
            units "seconds";
            type string;
          }
        }
      }
    }
    container sap {
      presence "enable sap";
      uses apply-group;
      uses apply-macro;
      choice choice-3 {
        leaf disable {
          type empty;
        }
      }
      list listen {
        key "name";
        ordered-by user;
        leaf name {
          type ipv4addr;
        }
        leaf port {
          type uint16;
        }
      }
    }
    container rsvp {
      uses apply-group;
      uses apply-macro;
      choice choice-3 {
        leaf disable {
          type empty;
        }
      }
      container graceful-restart {
        uses apply-group;
        uses apply-macro;
        choice choice-3 {
          leaf disable {
            type empty;
          }
        }
        leaf helper-disable {
          type empty;
        }
        leaf maximum-helper-restart-time {
          type uint32;
        }
        leaf maximum-helper-recovery-time {
          type uint32;
        }
      }
      container tunnel-services {
        presence "enable tunnel-services";
        uses apply-group;
        uses apply-macro;
        leaf-list devices {
          type interface-device;
          ordered-by user;
        }
      }
      leaf no-p2mp-sublsp {
        type empty;
      }
      leaf no-node-id-subobject {
        type empty;
      }
      leaf no-interface-hello {
        type empty;
      }
      leaf hello-acknowledgements {
        type empty;
      }
      container node-hello {
        presence "enable node-hello";
        leaf hello-interval {
          type uint32;
        }
      }
      leaf no-local-reversion {
        type empty;
      }
      container fast-reroute {
        uses apply-group;
        uses apply-macro;
        leaf optimize-timer {
          type int32;
        }
      }
      container load-balance {
        uses apply-group;
        uses apply-macro;
        leaf bandwidth {
          type empty;
        }
      }
      container traceoptions {
        uses apply-group;
        uses apply-macro;
        container file {
          presence "";
          uses trace-file-type;
        }
        list flag {
          key "name";
          ordered-by user;
          leaf name {
            type string;
          }
          leaf send {
            type empty;
          }
          leaf receive {
            type empty;
          }
          leaf detail {
            type empty;
          }
          leaf disable {
            type empty;
          }
        }
      }
      leaf refresh-time {
        type uint32;
      }
      leaf keep-multiplier {
        type uint32;
      }
      leaf graceful-deletion-timeout {
        type uint32;
      }
      container preemption {
        uses apply-group;
        uses apply-macro;
        choice choice-3 {
          leaf disabled {
            type empty;
          }
          leaf normal {
            type empty;
          }
          leaf aggressive {
            type empty;
          }
        }
        container soft-preemption {
          uses apply-group;
          uses apply-macro;
          leaf cleanup-timer {
            type int32;
          }
        }
      }
      leaf authentication-key {
        type unreadable;
      }
      container associated-bidirectional-lsp {
        uses apply-group;
        uses apply-macro;
        leaf single-sided-provisioning {
          type empty;
        }
      }
      leaf no-enhanced-frr-bypass {
        type empty;
      }
      list interface {
        key "name";
        ordered-by user;
        leaf name {
          type interface-name;
        }
        uses apply-group;
        uses apply-macro;
        choice choice-3 {
          leaf disable {
            type empty;
          }
          leaf enable-disable {
            type string;
          }
        }
        leaf authentication-key {
          type unreadable;
        }
        choice aggregate-choice {
          container undocumented {
            leaf aggregate {
              type empty;
            }
          }
          leaf aggregate {
            type empty;
          }
        }
        leaf no-aggregate {
          type empty;
        }
        leaf reliable {
          type empty;
        }
        leaf no-reliable {
          type empty;
        }
        leaf hello-interval {
          type uint32;
        }
        container subscription {
          uses subscription-type;
        }
        leaf bandwidth {
          type string;
        }
        leaf update-threshold {
          units "percent";
          type uint32;
        }
        container link-protection {
          presence "enable link-protection";
          uses apply-group;
          uses apply-macro;
          choice choice-3 {
            leaf disable {
              type empty;
            }
            leaf enable-disable {
              type string;
            }
          }
          container bandwidth {
            uses bandwidth-type;
          }
          leaf max-bypasses {
            type uint32;
          }
          leaf subscription {
            type uint32;
          }
          leaf no-node-protection {
            type empty;
          }
          leaf optimize-timer {
            units "seconds";
            type uint32;
          }
          leaf class-of-service {
            type int32;
          }
          leaf hop-limit {
            type uint32;
          }
          leaf no-cspf {
            type empty;
          }
          leaf exclude-srlg {
            type empty;
          }
          choice choice-priority {
            case new-priority {
              leaf setup-priority {
                type uint32;
              }
              leaf reservation-priority {
                type uint32;
              }
            }
            container priority {
              presence "";
              uses apply-group;
              uses apply-macro;
              leaf setup-priority {
                type uint32;
              }
              leaf reservation-priority {
                type uint32;
              }
            }
          }
          list path {
            key "name";
            ordered-by user;
            leaf name {
              type ipv4addr;
            }
            choice choice-3 {
              leaf loose {
                type empty;
              }
              leaf strict {
                type empty;
              }
            }
          }
          container admin-group {
            uses admin-group-include-exclude;
          }
          list bypass {
            key "name";
            ordered-by user;
            leaf name {
              type key-attribute-string-type;
            }
            uses apply-group;
            uses apply-macro;
            leaf to {
              type ipv4addr;
            }
            container bandwidth {
              uses bandwidth-type;
            }
            leaf description {
              type string;
            }
            choice choice-priority {
              case new-priority {
                leaf setup-priority {
                  type uint32;
                }
                leaf reservation-priority {
                  type uint32;
                }
              }
              container priority {
                presence "";
                uses apply-group;
                uses apply-macro;
                leaf setup-priority {
                  type uint32;
                }
                leaf reservation-priority {
                  type uint32;
                }
              }
            }
            leaf class-of-service {
              type int32;
            }
            leaf hop-limit {
              type uint32;
            }
            leaf no-cspf {
              type empty;
            }
            leaf exclude-srlg {
              type empty;
            }
            list path {
              key "name";
              ordered-by user;
              leaf name {
                type ipv4addr;
              }
              choice choice-3 {
                leaf loose {
                  type empty;
                }
                leaf strict {
                  type empty;
                }
              }
            }
            container admin-group {
              uses admin-group-include-exclude;
            }
          }
        }
      }
      list peer-interface {
        key "name";
        ordered-by user;
        leaf name {
          type string;
        }
        uses apply-group;
        uses apply-macro;
        choice choice-3 {
          leaf disable {
            type empty;
          }
        }
        leaf authentication-key {
          type unreadable;
        }
        leaf aggregate {
          type empty;
        }
        leaf no-aggregate {
          type empty;
        }
        leaf reliable {
          type empty;
        }
        leaf no-reliable {
          type empty;
        }
        leaf hello-interval {
          type uint32;
        }
      }
      container undocumented {
        leaf no-node-hello-on-bypass {
          type empty;
        }
      }
    }
    container mpls {
      uses juniper-protocols-mpls;
    }
    container bgp {
      uses juniper-protocols-bgp;
    }
    container dvmrp {
      presence "enable dvmrp";
      uses apply-group;
      uses apply-macro;
      choice choice-3 {
        leaf disable {
          type empty;
        }
      }
      container traceoptions {
        uses apply-group;
        uses apply-macro;
        container file {
          presence "";
          uses trace-file-type;
        }
        list flag {
          key "name";
          ordered-by user;
          leaf name {
            type string;
          }
          leaf send {
            type empty;
          }
          leaf receive {
            type empty;
          }
          leaf detail {
            type empty;
          }
          leaf disable {
            type empty;
          }
        }
      }
      container rib-group {
        presence "";
        uses rib-group-inet-type;
      }
      leaf-list import {
        type policy-algebra;
        ordered-by user;
      }
      leaf-list export {
        type policy-algebra;
        ordered-by user;
      }
      list interface {
        key "name";
        ordered-by user;
        leaf name {
          type interface-name;
        }
        uses apply-group;
        uses apply-macro;
        choice choice-3 {
          leaf disable {
            type empty;
          }
        }
        leaf mode {
          type string;
        }
        leaf metric {
          type uint32;
        }
        leaf hold-time {
          type uint32;
        }
      }
    }
    container isis {
      uses juniper-protocols-isis;
    }
    container esis {
      uses juniper-protocols-esis;
    }
    container msdp {
      uses juniper-protocols-msdp;
    }
    container ospf {
      uses juniper-protocols-ospf;
    }
    container ospf3 {
      uses apply-group;
      uses apply-macro;
      list realm {
        key "name";
        ordered-by user;
        leaf name {
          type string;
        }
        uses apply-group;
        uses apply-macro;
        choice choice-3 {
          leaf disable {
            type empty;
          }
        }
        container traceoptions {
          uses apply-group;
          uses apply-macro;
          container file {
            presence "";
            uses trace-file-type;
          }
          list flag {
            key "name";
            ordered-by user;
            leaf name {
              type string;
            }
            leaf send {
              type empty;
            }
            leaf receive {
              type empty;
            }
            leaf detail {
              type empty;
            }
            leaf disable {
              type empty;
            }
          }
        }
        list topology {
          key "name";
          ordered-by user;
          leaf name {
            type string;
          }
          uses apply-group;
          uses apply-macro;
          leaf disable {
            type empty;
          }
          leaf topology-id {
            type uint8;
          }
          leaf overload {
            type empty;
          }
          leaf rib-group {
            type string;
          }
          container spf-options {
            uses apply-group;
            uses apply-macro;
            leaf delay {
              type uint32;
            }
            leaf holddown {
              type uint32;
            }
            leaf rapid-runs {
              type uint32;
            }
            leaf no-ignore-our-externals {
              type empty;
            }
          }
          container backup-spf-options {
            uses apply-group;
            uses apply-macro;
            leaf disable {
              type empty;
            }
            leaf no-install {
              type empty;
            }
            leaf downstream-paths-only {
              type empty;
            }
          }
          leaf prefix-export-limit {
            type uint32;
          }
        }
        container spf-options {
          uses apply-group;
          uses apply-macro;
          leaf delay {
            type uint32;
          }
          leaf holddown {
            type uint32;
          }
          leaf rapid-runs {
            type uint32;
          }
          leaf no-ignore-our-externals {
            type empty;
          }
        }
        container backup-spf-options {
          uses apply-group;
          uses apply-macro;
          leaf disable {
            type empty;
          }
          leaf no-install {
            type empty;
          }
          leaf downstream-paths-only {
            type empty;
          }
        }
        leaf prefix-export-limit {
          type uint32;
        }
        leaf rib-group {
          type string;
        }
        container overload {
          presence "enable overload";
          uses apply-group;
          uses apply-macro;
          leaf timeout {
            type uint32;
          }
        }
        container database-protection {
          presence "";
          uses apply-group;
          uses apply-macro;
          leaf maximum-lsa {
            type uint32;
          }
          leaf warning-only {
            type empty;
          }
          leaf warning-threshold {
            type uint8;
          }
          leaf ignore-count {
            type uint8;
          }
          leaf ignore-time {
            type uint16;
          }
          leaf reset-time {
            type uint32;
          }
        }
        container graceful-restart {
          uses apply-group;
          uses apply-macro;
          choice choice-3 {
            leaf disable {
              type empty;
            }
          }
          leaf restart-duration {
            type uint32;
          }
          leaf notify-duration {
            type uint32;
          }
          container helper-disable {
            presence "enable helper-disable";
            uses apply-group;
            uses apply-macro;
            choice choice-standard {
              leaf standard {
                type empty;
              }
              leaf restart-signaling {
                type empty;
              }
              leaf both {
                type empty;
              }
            }
          }
          leaf no-strict-lsa-checking {
            type empty;
          }
        }
        container traffic-engineering {
          presence "enable traffic-engineering";
          uses apply-group;
          uses apply-macro;
          leaf no-topology {
            type empty;
          }
          leaf multicast-rpf-routes {
            type empty;
          }
          container shortcuts {
            presence "enable shortcuts";
            uses apply-group;
            uses apply-macro;
            leaf lsp-metric-into-summary {
              type empty;
            }
          }
          leaf advertise-unnumbered-interfaces {
            type empty;
          }
          leaf credibility-protocol-preference {
            type empty;
          }
          container advertisement {
            uses apply-group;
            uses apply-macro;
            leaf always {
              type empty;
            }
          }
        }
        leaf route-type-community {
          type string;
        }
        container domain-id {
          choice choice-3 {
            leaf domain-id {
              type string;
            }
            leaf disable {
              type empty;
            }
          }
        }
        choice choice-28 {
          leaf domain-vpn-tag {
            type uint32;
          }
          leaf no-domain-vpn-tag {
            type empty;
          }
        }
        leaf preference {
          type uint32;
        }
        leaf external-preference {
          type uint32;
        }
        leaf-list export {
          type policy-algebra;
          ordered-by user;
        }
        leaf-list import {
          type policy-algebra;
          ordered-by user;
        }
        leaf reference-bandwidth {
          type string;
        }
        leaf no-rfc-1583 {
          type empty;
        }
        choice choice-41 {
          leaf no-nssa-abr {
            type empty;
          }
        }
        container sham-link {
          presence "enable sham-link";
          uses apply-group;
          uses apply-macro;
          leaf local {
            type ipaddr;
          }
        }
        list area {
          key "name";
          ordered-by user;
          leaf name {
            type areaid;
          }
          uses apply-group;
          uses apply-macro;
          choice choice-3 {
            container stub {
              presence "enable stub";
              leaf default-metric {
                type uint32;
              }
              leaf summaries {
                type empty;
              }
              leaf no-summaries {
                type empty;
              }
            }
            container nssa {
              presence "enable nssa";
              uses apply-group;
              uses apply-macro;
              container default-lsa {
                presence "enable default-lsa";
                uses apply-group;
                uses apply-macro;
                leaf default-metric {
                  type uint32;
                }
                leaf metric-type {
                  type uint32;
                }
                leaf type-7 {
                  type empty;
                }
              }
              leaf summaries {
                type empty;
              }
              leaf no-summaries {
                type empty;
              }
              list area-range {
                key "name";
                ordered-by user;
                leaf name {
                  type ipprefix;
                }
                uses apply-group;
                uses apply-macro;
                leaf restrict {
                  type empty;
                }
                leaf exact {
                  type empty;
                }
                container override-metric {
                  presence "";
                  uses apply-group;
                  uses apply-macro;
                  leaf metric {
                    type uint32;
                  }
                  leaf metric-type {
                    type uint32;
                  }
                }
              }
            }
          }
          list area-range {
            key "name";
            ordered-by user;
            leaf name {
              type ipprefix;
            }
            uses apply-group;
            uses apply-macro;
            leaf restrict {
              type empty;
            }
            leaf exact {
              type empty;
            }
            leaf override-metric {
              type uint32;
            }
          }
          leaf-list network-summary-export {
            type policy-algebra;
            ordered-by user;
          }
          leaf-list network-summary-import {
            type policy-algebra;
            ordered-by user;
          }
          leaf-list inter-area-prefix-export {
            type policy-algebra;
            ordered-by user;
          }
          leaf-list inter-area-prefix-import {
            type policy-algebra;
            ordered-by user;
          }
          list virtual-link {
            key "neighbor-id transit-area";
            ordered-by user;
            leaf neighbor-id {
              type ipv4addr;
            }
            leaf transit-area {
              type areaid;
            }
            uses apply-group;
            uses apply-macro;
            choice choice-3 {
              leaf disable {
                type empty;
              }
            }
            leaf retransmit-interval {
              type uint32;
            }
            leaf transit-delay {
              type uint32;
            }
            leaf hello-interval {
              type uint32;
            }
            leaf dead-interval {
              type uint32;
            }
            choice choice-12 {
              container authentication {
                uses juniper-ospf-authentication;
              }
            }
            leaf demand-circuit {
              type empty;
            }
            leaf flood-reduction {
              type empty;
            }
            leaf no-neighbor-down-notification {
              type empty;
            }
            leaf ipsec-sa {
              type string;
            }
            list topology {
              key "name";
              ordered-by user;
              leaf name {
                type string;
              }
              uses apply-group;
              uses apply-macro;
              leaf disable {
                type empty;
              }
              leaf metric {
                type uint16;
              }
              container bandwidth-based-metrics {
                uses apply-group;
                uses apply-macro;
                list bandwidth {
                  key "name";
                  leaf name {
                    type string;
                  }
                  leaf metric {
                    type uint16;
                  }
                }
              }
            }
          }
          list sham-link-remote {
            key "name";
            ordered-by user;
            leaf name {
              type ipaddr;
            }
            uses apply-group;
            uses apply-macro;
            leaf metric {
              type uint16;
            }
            leaf ipsec-sa {
              type string;
            }
            leaf demand-circuit {
              type empty;
            }
            leaf flood-reduction {
              type empty;
            }
            list topology {
              key "name";
              ordered-by user;
              leaf name {
                type string;
              }
              uses apply-group;
              uses apply-macro;
              leaf disable {
                type empty;
              }
              leaf metric {
                type uint16;
              }
              container bandwidth-based-metrics {
                uses apply-group;
                uses apply-macro;
                list bandwidth {
                  key "name";
                  leaf name {
                    type string;
                  }
                  leaf metric {
                    type uint16;
                  }
                }
              }
            }
          }
          list interface {
            key "name";
            ordered-by user;
            leaf name {
              type ipv4addr-or-interface;
            }
            uses apply-group;
            uses apply-macro;
            choice choice-3 {
              leaf disable {
                type empty;
              }
            }
            leaf interface-type {
              type string;
            }
            choice choice-6 {
              leaf link-protection {
                type empty;
              }
              leaf node-link-protection {
                type empty;
              }
            }
            leaf no-eligible-backup {
              type empty;
            }
            container passive {
              presence "enable passive";
              uses apply-group;
              uses apply-macro;
              container traffic-engineering {
                uses apply-group;
                uses apply-macro;
                leaf remote-node-id {
                  type ipaddr;
                }
              }
            }
            leaf secondary {
              type empty;
            }
            leaf own-router-lsa {
              type empty;
            }
            container bandwidth-based-metrics {
              uses apply-group;
              uses apply-macro;
              list bandwidth {
                key "name";
                leaf name {
                  type string;
                }
                leaf metric {
                  type uint16;
                }
              }
            }
            leaf metric {
              type uint16;
            }
            leaf te-metric {
              type uint32;
            }
            leaf priority {
              type uint32;
            }
            container ldp-synchronization {
              presence "enable ldp-synchronization";
              uses ldp-sync-obj;
            }
            leaf retransmit-interval {
              type uint32;
            }
            leaf transit-delay {
              type uint32;
            }
            leaf hello-interval {
              type uint32;
            }
            leaf dead-interval {
              type uint32;
            }
            choice choice-33 {
              container authentication {
                uses juniper-ospf-authentication;
              }
            }
            leaf demand-circuit {
              type empty;
            }
            leaf flood-reduction {
              type empty;
            }
            leaf no-neighbor-down-notification {
              type empty;
            }
            leaf ipsec-sa {
              type string;
            }
            list topology {
              key "name";
              ordered-by user;
              leaf name {
                type string;
              }
              uses apply-group;
              uses apply-macro;
              leaf disable {
                type empty;
              }
              leaf metric {
                type uint16;
              }
              container bandwidth-based-metrics {
                uses apply-group;
                uses apply-macro;
                list bandwidth {
                  key "name";
                  leaf name {
                    type string;
                  }
                  leaf metric {
                    type uint16;
                  }
                }
              }
            }
            container bfd-liveness-detection {
              uses apply-group;
              uses apply-macro;
              leaf version {
                type string;
              }
              leaf minimum-interval {
                type uint32;
              }
              leaf minimum-receive-interval {
                type uint32;
              }
              leaf multiplier {
                type uint32;
              }
              choice choice-11 {
                leaf no-adaptation {
                  type empty;
                }
              }
              container transmit-interval {
                uses apply-group;
                uses apply-macro;
                leaf minimum-interval {
                  type uint32;
                }
                leaf threshold {
                  type uint32;
                }
              }
              container detection-time {
                uses apply-group;
                uses apply-macro;
                leaf threshold {
                  type uint32;
                }
              }
              container authentication {
                uses apply-group;
                uses apply-macro;
                leaf key-chain {
                  type string;
                }
                leaf algorithm {
                  type string;
                }
                leaf loose-check {
                  type empty;
                }
              }
              leaf full-neighbors-only {
                type empty;
              }
            }
            leaf dynamic-neighbors {
              type empty;
            }
            list neighbor {
              key "name";
              ordered-by user;
              leaf name {
                type ipaddr;
              }
              leaf eligible {
                type empty;
              }
            }
            leaf poll-interval {
              type uint32;
            }
            leaf no-interface-state-traps {
              type empty;
            }
          }
          leaf no-context-identifier-advertisement {
            type empty;
          }
          list context-identifier {
            key "name";
            ordered-by user;
            leaf name {
              type ipv4addr;
            }
            uses apply-group;
            uses apply-macro;
          }
          list label-switched-path {
            key "name";
            ordered-by user;
            leaf name {
              type key-attribute-string-type;
            }
            uses apply-group;
            uses apply-macro;
            choice choice-3 {
              leaf disable {
                type empty;
              }
            }
            leaf metric {
              type uint16;
            }
            list topology {
              key "name";
              ordered-by user;
              leaf name {
                type string;
              }
              uses apply-group;
              uses apply-macro;
              leaf disable {
                type empty;
              }
              leaf metric {
                type uint16;
              }
              container bandwidth-based-metrics {
                uses apply-group;
                uses apply-macro;
                list bandwidth {
                  key "name";
                  leaf name {
                    type string;
                  }
                  leaf metric {
                    type uint16;
                  }
                }
              }
            }
          }
          list peer-interface {
            key "name";
            ordered-by user;
            leaf name {
              type string;
            }
            uses apply-group;
            uses apply-macro;
            choice choice-3 {
              leaf disable {
                type empty;
              }
            }
            leaf retransmit-interval {
              type uint32;
            }
            leaf transit-delay {
              type uint32;
            }
            leaf hello-interval {
              type uint32;
            }
            leaf dead-interval {
              type uint32;
            }
            choice choice-12 {
              container authentication {
                uses juniper-ospf-authentication;
              }
            }
            leaf demand-circuit {
              type empty;
            }
            leaf flood-reduction {
              type empty;
            }
            leaf no-neighbor-down-notification {
              type empty;
            }
          }
        }
      }
      choice choice-5 {
        leaf disable {
          type empty;
        }
      }
      container traceoptions {
        uses apply-group;
        uses apply-macro;
        container file {
          presence "";
          uses trace-file-type;
        }
        list flag {
          key "name";
          ordered-by user;
          leaf name {
            type string;
          }
          leaf send {
            type empty;
          }
          leaf receive {
            type empty;
          }
          leaf detail {
            type empty;
          }
          leaf disable {
            type empty;
          }
        }
      }
      list topology {
        key "name";
        ordered-by user;
        leaf name {
          type string;
        }
        uses apply-group;
        uses apply-macro;
        leaf disable {
          type empty;
        }
        leaf topology-id {
          type uint8;
        }
        leaf overload {
          type empty;
        }
        leaf rib-group {
          type string;
        }
        container spf-options {
          uses apply-group;
          uses apply-macro;
          leaf delay {
            type uint32;
          }
          leaf holddown {
            type uint32;
          }
          leaf rapid-runs {
            type uint32;
          }
          leaf no-ignore-our-externals {
            type empty;
          }
        }
        container backup-spf-options {
          uses apply-group;
          uses apply-macro;
          leaf disable {
            type empty;
          }
          leaf no-install {
            type empty;
          }
          leaf downstream-paths-only {
            type empty;
          }
        }
        leaf prefix-export-limit {
          type uint32;
        }
      }
      container spf-options {
        uses apply-group;
        uses apply-macro;
        leaf delay {
          type uint32;
        }
        leaf holddown {
          type uint32;
        }
        leaf rapid-runs {
          type uint32;
        }
        leaf no-ignore-our-externals {
          type empty;
        }
      }
      container backup-spf-options {
        uses apply-group;
        uses apply-macro;
        leaf disable {
          type empty;
        }
        leaf no-install {
          type empty;
        }
        leaf downstream-paths-only {
          type empty;
        }
      }
      leaf prefix-export-limit {
        type uint32;
      }
      leaf rib-group {
        type string;
      }
      container overload {
        presence "enable overload";
        uses apply-group;
        uses apply-macro;
        leaf timeout {
          type uint32;
        }
      }
      container database-protection {
        presence "";
        uses apply-group;
        uses apply-macro;
        leaf maximum-lsa {
          type uint32;
        }
        leaf warning-only {
          type empty;
        }
        leaf warning-threshold {
          type uint8;
        }
        leaf ignore-count {
          type uint8;
        }
        leaf ignore-time {
          type uint16;
        }
        leaf reset-time {
          type uint32;
        }
      }
      container graceful-restart {
        uses apply-group;
        uses apply-macro;
        choice choice-3 {
          leaf disable {
            type empty;
          }
        }
        leaf restart-duration {
          type uint32;
        }
        leaf notify-duration {
          type uint32;
        }
        container helper-disable {
          presence "enable helper-disable";
          uses apply-group;
          uses apply-macro;
          choice choice-standard {
            leaf standard {
              type empty;
            }
            leaf restart-signaling {
              type empty;
            }
            leaf both {
              type empty;
            }
          }
        }
        leaf no-strict-lsa-checking {
          type empty;
        }
      }
      container traffic-engineering {
        presence "enable traffic-engineering";
        uses apply-group;
        uses apply-macro;
        leaf no-topology {
          type empty;
        }
        leaf multicast-rpf-routes {
          type empty;
        }
        leaf ignore-lsp-metrics {
          type empty;
        }
        container shortcuts {
          presence "enable shortcuts";
          uses apply-group;
          uses apply-macro;
          leaf lsp-metric-into-summary {
            type empty;
          }
        }
        leaf advertise-unnumbered-interfaces {
          type empty;
        }
        leaf credibility-protocol-preference {
          type empty;
        }
        container advertisement {
          uses apply-group;
          uses apply-macro;
          leaf always {
            type empty;
          }
        }
      }
      leaf route-type-community {
        type string;
      }
      container domain-id {
        choice choice-3 {
          leaf domain-id {
            type string;
          }
          leaf disable {
            type empty;
          }
        }
      }
      choice choice-30 {
        leaf domain-vpn-tag {
          type uint32;
        }
        leaf no-domain-vpn-tag {
          type empty;
        }
      }
      leaf preference {
        type uint32;
      }
      leaf external-preference {
        type uint32;
      }
      leaf-list export {
        type policy-algebra;
        ordered-by user;
      }
      leaf-list import {
        type policy-algebra;
        ordered-by user;
      }
      leaf reference-bandwidth {
        type string;
      }
      leaf no-rfc-1583 {
        type empty;
      }
      choice choice-43 {
        leaf no-nssa-abr {
          type empty;
        }
      }
      container sham-link {
        presence "enable sham-link";
        uses apply-group;
        uses apply-macro;
        leaf local {
          type ipaddr;
        }
      }
      list area {
        key "name";
        ordered-by user;
        leaf name {
          type areaid;
        }
        uses apply-group;
        uses apply-macro;
        choice choice-3 {
          container stub {
            presence "enable stub";
            leaf default-metric {
              type uint32;
            }
            leaf summaries {
              type empty;
            }
            leaf no-summaries {
              type empty;
            }
          }
          container nssa {
            presence "enable nssa";
            uses apply-group;
            uses apply-macro;
            container default-lsa {
              presence "enable default-lsa";
              uses apply-group;
              uses apply-macro;
              leaf default-metric {
                type uint32;
              }
              leaf metric-type {
                type uint32;
              }
              leaf type-7 {
                type empty;
              }
            }
            leaf summaries {
              type empty;
            }
            leaf no-summaries {
              type empty;
            }
            list area-range {
              key "name";
              ordered-by user;
              leaf name {
                type ipprefix;
              }
              uses apply-group;
              uses apply-macro;
              leaf restrict {
                type empty;
              }
              leaf exact {
                type empty;
              }
              container override-metric {
                presence "";
                uses apply-group;
                uses apply-macro;
                leaf metric {
                  type uint32;
                }
                leaf metric-type {
                  type uint32;
                }
              }
            }
          }
        }
        list area-range {
          key "name";
          ordered-by user;
          leaf name {
            type ipprefix;
          }
          uses apply-group;
          uses apply-macro;
          leaf restrict {
            type empty;
          }
          leaf exact {
            type empty;
          }
          leaf override-metric {
            type uint32;
          }
        }
        leaf-list network-summary-export {
          type policy-algebra;
          ordered-by user;
        }
        leaf-list network-summary-import {
          type policy-algebra;
          ordered-by user;
        }
        leaf-list inter-area-prefix-export {
          type policy-algebra;
          ordered-by user;
        }
        leaf-list inter-area-prefix-import {
          type policy-algebra;
          ordered-by user;
        }
        list virtual-link {
          key "neighbor-id transit-area";
          ordered-by user;
          leaf neighbor-id {
            type ipv4addr;
          }
          leaf transit-area {
            type areaid;
          }
          uses apply-group;
          uses apply-macro;
          choice choice-3 {
            leaf disable {
              type empty;
            }
          }
          leaf retransmit-interval {
            type uint32;
          }
          leaf transit-delay {
            type uint32;
          }
          leaf hello-interval {
            type uint32;
          }
          leaf dead-interval {
            type uint32;
          }
          choice choice-12 {
            container authentication {
              uses juniper-ospf-authentication;
            }
          }
          leaf demand-circuit {
            type empty;
          }
          leaf flood-reduction {
            type empty;
          }
          leaf no-neighbor-down-notification {
            type empty;
          }
          leaf ipsec-sa {
            type string;
          }
          list topology {
            key "name";
            ordered-by user;
            leaf name {
              type string;
            }
            uses apply-group;
            uses apply-macro;
            leaf disable {
              type empty;
            }
            leaf metric {
              type uint16;
            }
            container bandwidth-based-metrics {
              uses apply-group;
              uses apply-macro;
              list bandwidth {
                key "name";
                leaf name {
                  type string;
                }
                leaf metric {
                  type uint16;
                }
              }
            }
          }
        }
        list sham-link-remote {
          key "name";
          ordered-by user;
          leaf name {
            type ipaddr;
          }
          uses apply-group;
          uses apply-macro;
          leaf metric {
            type uint16;
          }
          leaf ipsec-sa {
            type string;
          }
          leaf demand-circuit {
            type empty;
          }
          leaf flood-reduction {
            type empty;
          }
          list topology {
            key "name";
            ordered-by user;
            leaf name {
              type string;
            }
            uses apply-group;
            uses apply-macro;
            leaf disable {
              type empty;
            }
            leaf metric {
              type uint16;
            }
            container bandwidth-based-metrics {
              uses apply-group;
              uses apply-macro;
              list bandwidth {
                key "name";
                leaf name {
                  type string;
                }
                leaf metric {
                  type uint16;
                }
              }
            }
          }
        }
        list interface {
          key "name";
          ordered-by user;
          leaf name {
            type ipv4addr-or-interface;
          }
          uses apply-group;
          uses apply-macro;
          choice choice-3 {
            leaf disable {
              type empty;
            }
          }
          leaf interface-type {
            type string;
          }
          choice choice-6 {
            leaf link-protection {
              type empty;
            }
            leaf node-link-protection {
              type empty;
            }
          }
          leaf no-eligible-backup {
            type empty;
          }
          container passive {
            presence "enable passive";
            uses apply-group;
            uses apply-macro;
            container traffic-engineering {
              uses apply-group;
              uses apply-macro;
              leaf remote-node-id {
                type ipaddr;
              }
            }
          }
          leaf secondary {
            type empty;
          }
          leaf own-router-lsa {
            type empty;
          }
          container bandwidth-based-metrics {
            uses apply-group;
            uses apply-macro;
            list bandwidth {
              key "name";
              leaf name {
                type string;
              }
              leaf metric {
                type uint16;
              }
            }
          }
          leaf metric {
            type uint16;
          }
          leaf te-metric {
            type uint32;
          }
          leaf priority {
            type uint32;
          }
          container ldp-synchronization {
            presence "enable ldp-synchronization";
            uses ldp-sync-obj;
          }
          leaf retransmit-interval {
            type uint32;
          }
          leaf transit-delay {
            type uint32;
          }
          leaf hello-interval {
            type uint32;
          }
          leaf dead-interval {
            type uint32;
          }
          choice choice-33 {
            container authentication {
              uses juniper-ospf-authentication;
            }
          }
          leaf demand-circuit {
            type empty;
          }
          leaf flood-reduction {
            type empty;
          }
          leaf no-neighbor-down-notification {
            type empty;
          }
          leaf ipsec-sa {
            type string;
          }
          list topology {
            key "name";
            ordered-by user;
            leaf name {
              type string;
            }
            uses apply-group;
            uses apply-macro;
            leaf disable {
              type empty;
            }
            leaf metric {
              type uint16;
            }
            container bandwidth-based-metrics {
              uses apply-group;
              uses apply-macro;
              list bandwidth {
                key "name";
                leaf name {
                  type string;
                }
                leaf metric {
                  type uint16;
                }
              }
            }
          }
          container bfd-liveness-detection {
            uses apply-group;
            uses apply-macro;
            leaf version {
              type string;
            }
            leaf minimum-interval {
              type uint32;
            }
            leaf minimum-receive-interval {
              type uint32;
            }
            leaf multiplier {
              type uint32;
            }
            choice choice-11 {
              leaf no-adaptation {
                type empty;
              }
            }
            container transmit-interval {
              uses apply-group;
              uses apply-macro;
              leaf minimum-interval {
                type uint32;
              }
              leaf threshold {
                type uint32;
              }
            }
            container detection-time {
              uses apply-group;
              uses apply-macro;
              leaf threshold {
                type uint32;
              }
            }
            container authentication {
              uses apply-group;
              uses apply-macro;
              leaf key-chain {
                type string;
              }
              leaf algorithm {
                type string;
              }
              leaf loose-check {
                type empty;
              }
            }
            leaf full-neighbors-only {
              type empty;
            }
          }
          leaf dynamic-neighbors {
            type empty;
          }
          list neighbor {
            key "name";
            ordered-by user;
            leaf name {
              type ipaddr;
            }
            leaf eligible {
              type empty;
            }
          }
          leaf poll-interval {
            type uint32;
          }
          leaf no-interface-state-traps {
            type empty;
          }
        }
        leaf no-context-identifier-advertisement {
          type empty;
        }
        list context-identifier {
          key "name";
          ordered-by user;
          leaf name {
            type ipv4addr;
          }
          uses apply-group;
          uses apply-macro;
        }
        list label-switched-path {
          key "name";
          ordered-by user;
          leaf name {
            type key-attribute-string-type;
          }
          uses apply-group;
          uses apply-macro;
          choice choice-3 {
            leaf disable {
              type empty;
            }
          }
          leaf metric {
            type uint16;
          }
          list topology {
            key "name";
            ordered-by user;
            leaf name {
              type string;
            }
            uses apply-group;
            uses apply-macro;
            leaf disable {
              type empty;
            }
            leaf metric {
              type uint16;
            }
            container bandwidth-based-metrics {
              uses apply-group;
              uses apply-macro;
              list bandwidth {
                key "name";
                leaf name {
                  type string;
                }
                leaf metric {
                  type uint16;
                }
              }
            }
          }
        }
        list peer-interface {
          key "name";
          ordered-by user;
          leaf name {
            type string;
          }
          uses apply-group;
          uses apply-macro;
          choice choice-3 {
            leaf disable {
              type empty;
            }
          }
          leaf retransmit-interval {
            type uint32;
          }
          leaf transit-delay {
            type uint32;
          }
          leaf hello-interval {
            type uint32;
          }
          leaf dead-interval {
            type uint32;
          }
          choice choice-12 {
            container authentication {
              uses juniper-ospf-authentication;
            }
          }
          leaf demand-circuit {
            type empty;
          }
          leaf flood-reduction {
            type empty;
          }
          leaf no-neighbor-down-notification {
            type empty;
          }
        }
      }
    }
    container ldp {
      uses juniper-protocols-ldp;
    }
    container pim {
      uses juniper-protocols-pim;
    }
    container rip {
      uses juniper-protocols-rip;
    }
    container ripng {
      uses juniper-protocols-ripng;
    }
    container connections {
      uses apply-group;
      uses apply-macro;
      list interface-switch {
        key "name";
        ordered-by user;
        leaf name {
          type string;
        }
        uses apply-group;
        uses apply-macro;
        list interface {
          key "name";
          ordered-by user;
          leaf name {
            type interface-name;
          }
          uses apply-group;
          uses apply-macro;
        }
      }
      list remote-interface-switch {
        key "name";
        ordered-by user;
        leaf name {
          type string;
        }
        uses apply-group;
        uses apply-macro;
        leaf interface {
          type interface-name;
        }
        leaf transmit-lsp {
          type string;
        }
        leaf receive-lsp {
          type string;
        }
      }
      list lsp-switch {
        key "name";
        ordered-by user;
        leaf name {
          type string;
        }
        uses apply-group;
        uses apply-macro;
        leaf transmit-lsp {
          type string;
        }
        leaf receive-lsp {
          type string;
        }
      }
      list p2mp-transmit-switch {
        key "name";
        ordered-by user;
        leaf name {
          type string;
        }
        uses apply-group;
        uses apply-macro;
        leaf input-interface {
          type interface-name;
        }
        leaf transmit-p2mp-lsp {
          type string;
        }
      }
      list p2mp-receive-switch {
        key "name";
        ordered-by user;
        leaf name {
          type string;
        }
        uses apply-group;
        uses apply-macro;
        leaf receive-p2mp-lsp {
          type string;
        }
        leaf-list output-interface {
          type interface-name;
          ordered-by user;
        }
      }
    }
    container vrrp {
      uses apply-group;
      uses apply-macro;
      container traceoptions {
        uses apply-group;
        uses apply-macro;
        leaf no-remote-trace {
          type empty;
        }
        container file {
          leaf filename {
            type string;
          }
          leaf size {
            type string;
          }
          leaf files {
            type uint32;
          }
          leaf world-readable {
            type empty;
          }
          leaf no-world-readable {
            type empty;
          }
          leaf match {
            type regular-expression;
          }
          leaf microsecond-stamp {
            type empty;
          }
        }
        list flag {
          key "name";
          ordered-by user;
          leaf name {
            type string;
          }
        }
      }
      leaf failover-delay {
        type uint32;
      }
      leaf startup-silent-period {
        type uint32;
      }
      leaf asymmetric-hold-time {
        type empty;
      }
      leaf delegate-processing {
        type empty;
      }
      leaf skew-timer-disable {
        type empty;
      }
      leaf global-advertisements-threshold {
        type uint32;
      }
      leaf inherit-advertisement-interval {
        type uint32;
      }
      leaf version-3 {
        type empty;
      }
    }
    container l2circuit {
      uses apply-group;
      uses apply-macro;
      container traceoptions {
        uses apply-group;
        uses apply-macro;
        container file {
          presence "";
          uses trace-file-type;
        }
        list flag {
          key "name";
          ordered-by user;
          leaf name {
            type string;
          }
          leaf send {
            type empty;
          }
          leaf receive {
            type empty;
          }
          leaf detail {
            type empty;
          }
          leaf disable {
            type empty;
          }
        }
      }
      list neighbor {
        key "name";
        ordered-by user;
        leaf name {
          type ipv4addr;
        }
        uses apply-group;
        uses apply-macro;
        list interface {
          key "name";
          ordered-by user;
          leaf name {
            type interface-name;
          }
          uses apply-group;
          uses apply-macro;
          container static {
            presence "";
            uses apply-group;
            uses apply-macro;
            leaf incoming-label {
              type uint32;
            }
            leaf outgoing-label {
              type uint32;
            }
            leaf send-oam {
              type empty;
            }
          }
          leaf psn-tunnel-endpoint {
            type ipv4addr;
          }
          leaf protect-interface {
            type interface-name;
          }
          leaf virtual-circuit-id {
            type uint32;
          }
          leaf description {
            type string;
          }
          leaf control-word {
            type empty;
          }
          leaf no-control-word {
            type empty;
          }
          leaf flow-label-transmit {
            type empty;
          }
          leaf flow-label-transmit-static {
            type empty;
          }
          leaf flow-label-receive {
            type empty;
          }
          leaf flow-label-receive-static {
            type empty;
          }
          leaf community {
            type string;
          }
          leaf mtu {
            type uint32;
          }
          leaf encapsulation-type {
            type string;
          }
          leaf ignore-encapsulation-mismatch {
            type empty;
          }
          leaf ignore-mtu-mismatch {
            type empty;
          }
          leaf no-revert {
            type empty;
          }
          container bandwidth {
            uses bandwidth-type;
          }
          container pseudowire-status-tlv {
            presence "enable pseudowire-status-tlv";
            uses apply-group;
            uses apply-macro;
            container apply-advanced {
              uses apply-group;
              uses apply-macro;
            }
            leaf hot-standby-vc-on {
              type empty;
            }
          }
          leaf switchover-delay {
            type uint32;
          }
          container revert-time {
            presence "";
            leaf delay {
              mandatory true;
              units "seconds";
              type uint32;
            }
            leaf maximum {
              units "seconds";
              type uint32;
            }
          }
          leaf connection-protection {
            type empty;
          }
          list backup-neighbor {
            key "name";
            ordered-by user;
            leaf name {
              type ipv4addr;
            }
            uses apply-group;
            uses apply-macro;
            container static {
              presence "";
              uses apply-group;
              uses apply-macro;
              leaf incoming-label {
                type uint32;
              }
              leaf outgoing-label {
                type uint32;
              }
            }
            leaf virtual-circuit-id {
              type uint32;
            }
            leaf community {
              type string;
            }
            leaf psn-tunnel-endpoint {
              type ipv4addr;
            }
            leaf standby {
              type empty;
            }
            leaf hot-standby {
              type empty;
            }
          }
          container oam {
            uses apply-group;
            uses apply-macro;
            leaf ping-interval {
              type uint16;
            }
            container bfd-liveness-detection {
              uses apply-group;
              uses apply-macro;
              leaf version {
                type string;
              }
              leaf minimum-interval {
                type uint32;
              }
              leaf minimum-receive-interval {
                type uint32;
              }
              leaf multiplier {
                type uint32;
              }
              choice choice-11 {
                leaf no-adaptation {
                  type empty;
                }
              }
              container transmit-interval {
                uses apply-group;
                uses apply-macro;
                leaf minimum-interval {
                  type uint32;
                }
                leaf threshold {
                  type uint32;
                }
              }
              container detection-time {
                uses apply-group;
                uses apply-macro;
                leaf threshold {
                  type uint32;
                }
              }
            }
          }
          container egress-protection {
            uses apply-group;
            uses apply-macro;
            choice choice-3 {
              leaf protector-interface {
                type interface-name;
              }
              container protector-pe {
                presence "";
                leaf address {
                  type ipv4addr;
                }
                leaf context-identifier {
                  type ipv4addr;
                }
                leaf lsp {
                  type string;
                }
              }
            }
            container protected-l2circuit {
              presence "";
              leaf l2circuit-name {
                type string;
              }
              leaf ingress-pe {
                type ipv4addr;
              }
              leaf egress-pe {
                type ipv4addr;
              }
              leaf virtual-circuit-id {
                type uint32;
              }
            }
          }
        }
      }
      container local-switching {
        uses apply-group;
        uses apply-macro;
        list interface {
          key "name";
          ordered-by user;
          leaf name {
            type interface-name;
          }
          uses apply-group;
          uses apply-macro;
          leaf no-revert {
            type empty;
          }
          leaf protect-interface {
            type interface-name;
          }
          leaf connection-protection {
            type empty;
          }
          list neighbor {
            key "name";
            ordered-by user;
            leaf name {
              type ipv4addr;
            }
            uses apply-group;
            uses apply-macro;
            leaf virtual-circuit-id {
              mandatory true;
              type uint32;
            }
            leaf community {
              type string;
            }
            leaf psn-tunnel-endpoint {
              type ipv4addr;
            }
            leaf mtu {
              type uint32;
            }
          }
          list backup-neighbor {
            key "name";
            ordered-by user;
            leaf name {
              type ipv4addr;
            }
            uses apply-group;
            uses apply-macro;
            leaf virtual-circuit-id {
              mandatory true;
              type uint32;
            }
            leaf psn-tunnel-endpoint {
              type ipv4addr;
            }
            leaf community {
              type string;
            }
            leaf mtu {
              type uint32;
            }
          }
          container end-interface {
            presence "";
            uses apply-group;
            uses apply-macro;
            leaf interface {
              type interface-name;
            }
            leaf protect-interface {
              type interface-name;
            }
          }
          leaf description {
            type string;
          }
          leaf encapsulation-type {
            type string;
          }
          leaf ignore-encapsulation-mismatch {
            type empty;
          }
          leaf ignore-mtu-mismatch {
            type empty;
          }
        }
      }
      container auto-sensing {
        presence "";
        uses apply-group;
        uses apply-macro;
        leaf password {
          mandatory true;
          type unreadable;
        }
      }
      container resolution {
        uses apply-advanced;
        leaf preserve-nexthop-heirarchy {
          type empty;
        }
      }
    }
    container evpn {
      uses apply-group;
      uses apply-macro;
      container traceoptions {
        uses apply-group;
        uses apply-macro;
        container file {
          presence "";
          uses trace-file-type;
        }
        list flag {
          key "name";
          ordered-by user;
          leaf name {
            type string;
          }
          leaf send {
            type empty;
          }
          leaf receive {
            type empty;
          }
          leaf detail {
            type empty;
          }
          leaf disable {
            type empty;
          }
        }
      }
      leaf es-import-oldstyle {
        type empty;
      }
      leaf es-label-oldstyle {
        type empty;
      }
      leaf mac-history {
        type uint16;
      }
      list mac-list {
        key "name";
        leaf name {
          type key-attribute-string-type;
        }
        uses apply-group;
        uses apply-macro;
        leaf-list mac-address {
          type mac-addr;
        }
      }
      leaf encapsulation {
        type string;
      }
      leaf-list extended-vlan-list {
        type string;
      }
      container assisted-replication {
        uses apply-group;
        uses apply-macro;
        choice choice-leaf {
          container leaf {
            presence "enable leaf";
            uses apply-group;
            uses apply-macro;
            leaf replicator-activation-delay {
              units "seconds";
              type uint32;
            }
          }
          container replicator {
            presence "";
            uses apply-group;
            uses apply-macro;
            container inet {
              presence "";
              uses apply-group;
              uses apply-macro;
              leaf ip {
                mandatory true;
                type ipv4addr;
              }
            }
            leaf vxlan-encapsulation-source-ip {
              mandatory true;
              type string;
            }
          }
        }
      }
      leaf default-gateway {
        type string;
      }
      leaf designated-forwarder-election-hold-time {
        units "seconds";
        type uint32;
      }
      leaf-list extended-vni-list {
        type string;
      }
      container duplicate-mac-detection {
        uses apply-group;
        uses apply-macro;
        leaf detection-threshold {
          type uint32;
        }
        leaf detection-window {
          units "seconds";
          type uint32;
        }
        leaf auto-recovery-time {
          units "minutes";
          type uint32;
        }
      }
      container mac-mobility {
        uses apply-group;
        uses apply-macro;
        leaf no-sequence-numbers {
          type empty;
        }
      }
      leaf no-core-isolation {
        type empty;
      }
      leaf multicast-mode {
        type string;
      }
      container vni-options {
        uses juniper-protocols-vni-routing-options;
      }
    }
    container link-management {
      uses juniper-protocols-lmp;
    }
    container pgm {
      presence "enable pgm";
      uses juniper-protocols-pgm;
    }
    container bfd {
      uses apply-group;
      uses apply-macro;
      container traceoptions {
        uses apply-group;
        uses apply-macro;
        leaf no-remote-trace {
          type empty;
        }
        container file {
          leaf filename {
            type string;
          }
          leaf size {
            type string;
          }
          leaf files {
            type uint32;
          }
          leaf world-readable {
            type empty;
          }
          leaf no-world-readable {
            type empty;
          }
          leaf match {
            type regular-expression;
          }
        }
        list flag {
          key "name";
          ordered-by user;
          leaf name {
            type string;
          }
        }
      }
      leaf no-issu-timer-negotiation {
        type empty;
      }
      container sbfd {
        uses apply-advanced;
        leaf-list pool {
          type string;
        }
        list local-discriminator {
          key "name";
          ordered-by user;
          leaf name {
            type string;
          }
          uses apply-advanced;
          leaf minimum-receive-interval {
            units "milliseconds";
            type string;
          }
          leaf local-ip-address {
            type ipv4addr;
          }
        }
      }
    }
    container vpls {
      uses apply-group;
      uses apply-macro;
      container static-vpls {
        presence "";
        uses apply-group;
        uses apply-macro;
        leaf no-tunnel-services {
          type empty;
        }
      }
    }
    container source-packet-routing {
      presence "enable source-packet-routing";
      uses apply-group;
      uses apply-macro;
      container traceoptions {
        uses apply-group;
        uses apply-macro;
        container file {
          presence "";
          leaf filename {
            type string;
          }
          leaf replace {
            type empty;
          }
          leaf size {
            type string;
          }
          leaf files {
            type uint32;
          }
          leaf no-stamp {
            type empty;
          }
          leaf world-readable {
            type empty;
          }
          leaf no-world-readable {
            type empty;
          }
        }
        list flag {
          key "name";
          ordered-by user;
          leaf name {
            type string;
          }
        }
      }
      list lsp-external-controller {
        key "name";
        ordered-by user;
        leaf name {
          type string;
        }
        uses apply-group;
        uses apply-macro;
      }
      leaf preference {
        type uint32;
      }
      leaf sr-preference-override {
        type uint32;
      }
      leaf sr-preference {
        type uint32;
      }
      leaf maximum-segment-list-depth {
        type uint32;
      }
      leaf maximum-srv6-te-segment-list-depth {
        type string;
      }
      leaf no-chained-composite-next-hop {
        type empty;
      }
      container statistics {
        presence "";
        uses apply-group;
        uses apply-macro;
        container telemetry {
          presence "enable telemetry";
          uses apply-group;
          uses apply-macro;
        }
      }
      leaf tunnel-tracking {
        type empty;
      }
      list segment-list {
        key "name";
        ordered-by user;
        leaf name {
          type key-attribute-string-type;
        }
        uses apply-group;
        uses apply-macro;
        leaf inherit-label-nexthops {
          type empty;
        }
        choice choice-auto-translate {
          container auto-translate {
            presence "enable auto-translate";
            uses apply-group;
            uses apply-macro;
            choice choice-protected {
              container protected {
                presence "enable protected";
                uses apply-group;
                uses apply-macro;
                leaf mandatory {
                  type empty;
                }
              }
              container unprotected {
                presence "enable unprotected";
                uses apply-group;
                uses apply-macro;
                leaf mandatory {
                  type empty;
                }
              }
            }
          }
          container dynamic {
            presence "enable dynamic";
            uses apply-group;
            uses apply-macro;
            choice choice-protected {
              container protected {
                presence "enable protected";
                uses apply-group;
                uses apply-macro;
                leaf mandatory {
                  type empty;
                }
              }
              container unprotected {
                presence "enable unprotected";
                uses apply-group;
                uses apply-macro;
                leaf mandatory {
                  type empty;
                }
              }
            }
          }
        }
        leaf compute {
          type empty;
        }
        list hop-list {
          key "name";
          ordered-by user;
          leaf name {
            type key-attribute-string-type;
          }
          uses apply-group;
          uses apply-macro;
          leaf label {
            type uint32;
          }
          leaf ip-address {
            type ipaddr;
          }
          choice choice-strict {
            leaf strict {
              type empty;
            }
            leaf loose {
              type empty;
            }
          }
          container label-type {
            uses apply-group;
            uses apply-macro;
            leaf node {
              type empty;
            }
          }
        }
      }
      list compute-profile {
        key "name";
        ordered-by user;
        leaf name {
          type key-attribute-string-type;
        }
        uses apply-group;
        uses apply-macro;
        container admin-group {
          uses admin-group-include-exclude;
        }
        leaf maximum-segment-list-depth {
          type uint32;
        }
        leaf algorithm {
          type string;
        }
        leaf no-label-stack-compression {
          type empty;
        }
        choice choice-protected {
          container protected {
            presence "enable protected";
            uses apply-group;
            uses apply-macro;
            leaf mandatory {
              type empty;
            }
          }
          container unprotected {
            presence "enable unprotected";
            uses apply-group;
            uses apply-macro;
            leaf mandatory {
              type empty;
            }
          }
        }
        leaf compute-segment-list {
          type string;
        }
        leaf maximum-computed-segment-lists {
          type uint32;
        }
        container metric-type {
          uses apply-group;
          uses apply-macro;
          choice choice-te {
            leaf te {
              type empty;
            }
            leaf igp {
              type empty;
            }
            case case_3 {
              container delay {
                presence "enable delay";
                uses apply-advanced;
                choice metric-choice {
                  case case_1 {
                    leaf minimum {
                      type empty;
                    }
                  }
                  case case_2 {
                    leaf maximum {
                      type empty;
                    }
                  }
                  case case_3 {
                    leaf average {
                      type empty;
                    }
                  }
                }
                leaf delay-variation-threshold {
                  type string;
                }
              }
            }
          }
        }
        container bound-metric {
          uses apply-advanced;
          leaf te {
            type string;
          }
          leaf igp {
            type string;
          }
          leaf delay {
            type string;
          }
        }
      }
      leaf srv6 {
        type empty;
      }
      container preserve-nexthop-hierarchy {
        presence "enable preserve-nexthop-hierarchy";
        uses apply-advanced;
        container sr-mpls {
          uses apply-advanced;
          choice enable-disable {
            case case_1 {
              leaf disable {
                type empty;
              }
            }
          }
        }
        container srv6 {
          uses apply-advanced;
          choice enable-disable {
            case case_1 {
              leaf disable {
                type empty;
              }
            }
          }
        }
      }
      list source-routing-path {
        key "name";
        ordered-by user;
        leaf name {
          type key-attribute-string-type;
        }
        uses apply-group;
        uses apply-macro;
        leaf srm6 {
          type empty;
        }
        leaf srv6 {
          type empty;
        }
        leaf ldp-tunneling {
          type empty;
        }
        leaf use-for-shortcut {
          type empty;
        }
        leaf to {
          type ipaddr;
        }
        leaf from {
          type ipaddr;
        }
        leaf color {
          type uint32;
        }
        leaf no-ingress {
          type empty;
        }
        leaf binding-sid {
          type uint32;
        }
        list install {
          key "name";
          ordered-by user;
          leaf name {
            type ipaddr;
          }
        }
        leaf preference {
          type uint32;
        }
        leaf metric {
          type uint32;
        }
        leaf te-group-id {
          type string;
        }
        leaf sr-preference {
          type uint32;
        }
        leaf lsp-external-controller {
          type string;
        }
        list primary {
          key "name";
          ordered-by user;
          leaf name {
            mandatory true;
            type key-attribute-string-type;
          }
          uses apply-group;
          uses apply-macro;
          leaf weight {
            type uint32;
          }
          container bfd-liveness-detection {
            presence "";
            uses apply-group;
            uses apply-macro;
            container sbfd {
              presence "";
              uses apply-group;
              uses apply-macro;
              leaf remote-discriminator {
                mandatory true;
                type uint32;
              }
            }
            leaf minimum-interval {
              units "milliseconds";
              type uint32;
            }
            leaf multiplier {
              type uint32;
            }
            leaf no-router-alert-option {
              type empty;
            }
          }
          container compute {
            presence "enable compute";
            uses apply-group;
            uses apply-macro;
            leaf compute-profile-name {
              type string;
            }
          }
          leaf lsp-external-controller {
            type string;
          }
        }
        list secondary {
          key "name";
          ordered-by user;
          leaf name {
            mandatory true;
            type key-attribute-string-type;
          }
          uses apply-group;
          uses apply-macro;
          container bfd-liveness-detection {
            presence "";
            uses apply-group;
            uses apply-macro;
            container sbfd {
              presence "";
              uses apply-group;
              uses apply-macro;
              leaf remote-discriminator {
                mandatory true;
                type uint32;
              }
            }
            leaf minimum-interval {
              units "milliseconds";
              type uint32;
            }
            leaf multiplier {
              type uint32;
            }
            leaf no-router-alert-option {
              type empty;
            }
          }
          container compute {
            presence "enable compute";
            uses apply-group;
            uses apply-macro;
            leaf compute-profile-name {
              type string;
            }
          }
        }
      }
      list source-routing-path-template {
        key "name";
        ordered-by user;
        leaf name {
          type key-attribute-string-type;
        }
        uses apply-group;
        uses apply-macro;
        leaf no-ingress {
          type empty;
        }
        leaf use-for-shortcut {
          type empty;
        }
        leaf metric {
          type uint32;
        }
        leaf sr-preference {
          type uint32;
        }
        leaf ldp-tunneling {
          type empty;
        }
        leaf lsp-external-controller {
          type string;
        }
        list primary {
          key "name";
          ordered-by user;
          leaf name {
            mandatory true;
            type key-attribute-string-type;
          }
          uses apply-group;
          uses apply-macro;
          leaf weight {
            type uint32;
          }
          container compute {
            presence "enable compute";
            uses apply-group;
            uses apply-macro;
            leaf compute-profile-name {
              type string;
            }
          }
          leaf lsp-external-controller {
            type string;
          }
        }
        list secondary {
          key "name";
          ordered-by user;
          leaf name {
            mandatory true;
            type key-attribute-string-type;
          }
          uses apply-group;
          uses apply-macro;
          container compute {
            presence "enable compute";
            uses apply-group;
            uses apply-macro;
            leaf compute-profile-name {
              type string;
            }
          }
        }
        container bfd-liveness-detection {
          presence "";
          uses apply-group;
          uses apply-macro;
          container sbfd {
            presence "";
            uses apply-group;
            uses apply-macro;
            leaf remote-discriminator {
              mandatory true;
              type uint32;
            }
          }
          leaf minimum-interval {
            units "milliseconds";
            type uint32;
          }
          leaf multiplier {
            type uint32;
          }
          leaf no-router-alert-option {
            type empty;
          }
        }
      }
      leaf inherit-label-nexthops {
        type empty;
      }
      container rib-group {
        uses apply-group;
        uses apply-macro;
        container ipv4 {
          presence "";
          uses apply-group;
          uses apply-macro;
          leaf rib-group-name {
            mandatory true;
            type string;
          }
        }
        container ipv6 {
          presence "";
          uses apply-group;
          uses apply-macro;
          leaf rib-group-name {
            mandatory true;
            type string;
          }
        }
        container ipv4-color {
          presence "";
          uses apply-group;
          uses apply-macro;
          leaf rib-group-name {
            mandatory true;
            type string;
          }
        }
        container ipv6-color {
          presence "";
          uses apply-group;
          uses apply-macro;
          leaf rib-group-name {
            mandatory true;
            type string;
          }
        }
        container tag {
          presence "";
          uses apply-group;
          uses apply-macro;
          leaf rib-group-name {
            mandatory true;
            type string;
          }
        }
      }
      container telemetry {
        uses apply-group;
        uses apply-macro;
        container statistics {
          presence "enable statistics";
          uses apply-group;
          uses apply-macro;
          leaf no-transit {
            type empty;
          }
          leaf no-ingress {
            type empty;
          }
          container per-source {
            uses apply-group;
            uses apply-macro;
            leaf per-segment-list {
              type empty;
            }
          }
        }
      }
      leaf inet-color-append-explicit-null {
        type empty;
      }
      leaf retry-timer {
        units "seconds";
        type int32;
      }
      leaf import-color-only-cross-af {
        type empty;
      }
      leaf inet6-color-append-explicit-null {
        type empty;
      }
      leaf ipv6-tunneling-append-explicit-null {
        type empty;
      }
      container source-routing-path-template-map {
        uses apply-group;
        uses apply-macro;
        leaf-list policy {
          type policy-algebra;
          ordered-by user;
        }
      }
    }
    container neighbor-discovery {
      presence "enable neighbor-discovery";
      uses apply-group;
      uses apply-macro;
      leaf onlink-subnet-only {
        type empty;
      }
      leaf no-dad-on-state-change {
        type empty;
      }
      container secure {
        uses apply-group;
        uses apply-macro;
        container security-level {
          presence "enable security-level";
          uses apply-group;
          uses apply-macro;
          choice choice-3 {
            leaf default {
              type empty;
            }
            leaf secure-messages-only {
              type empty;
            }
          }
        }
        container cryptographic-address {
          presence "enable cryptographic-address";
          uses apply-group;
          uses apply-macro;
          leaf key-length {
            type uint32;
          }
          leaf key-pair {
            type string;
          }
        }
        container timestamp {
          presence "enable timestamp";
          uses apply-group;
          uses apply-macro;
          leaf new-peer-window {
            type uint32;
          }
          leaf known-peer-window {
            type uint32;
          }
          leaf clock-drift {
            type unsigned-float;
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
      }
    }
    container iccp {
      presence "";
      uses apply-group;
      uses apply-macro;
      leaf local-ip-addr {
        type ipv4addr;
      }
      leaf session-establishment-hold-time {
        type uint32;
      }
      leaf authentication-key {
        type unreadable;
      }
      list peer {
        key "name";
        uses peer-group;
      }
      container traceoptions {
        uses apply-group;
        uses apply-macro;
        leaf no-remote-trace {
          type empty;
        }
        container file {
          leaf filename {
            type string;
          }
          leaf size {
            type string;
          }
          leaf files {
            type uint32;
          }
          leaf world-readable {
            type empty;
          }
          leaf no-world-readable {
            type empty;
          }
          leaf match {
            type regular-expression;
          }
        }
        list flag {
          key "name";
          ordered-by user;
          leaf name {
            type string;
          }
        }
      }
    }
    container ilmi {
      uses apply-group;
      uses apply-macro;
      container traceoptions {
        uses apply-group;
        uses apply-macro;
        leaf no-remote-trace {
          type empty;
        }
        container file {
          leaf filename {
            type string;
          }
          leaf size {
            type string;
          }
          leaf files {
            type uint32;
          }
          leaf world-readable {
            type empty;
          }
          leaf no-world-readable {
            type empty;
          }
          leaf match {
            type regular-expression;
          }
        }
        list flag {
          key "name";
          ordered-by user;
          leaf name {
            type string;
          }
        }
      }
    }
    container lacp {
      uses apply-group;
      uses apply-macro;
      container traceoptions {
        uses apply-group;
        uses apply-macro;
        leaf no-remote-trace {
          type empty;
        }
        container file {
          leaf filename {
            type string;
          }
          leaf size {
            type string;
          }
          leaf files {
            type uint32;
          }
          leaf world-readable {
            type empty;
          }
          leaf no-world-readable {
            type empty;
          }
          leaf match {
            type regular-expression;
          }
        }
        list flag {
          key "name";
          ordered-by user;
          leaf name {
            type string;
          }
        }
      }
      leaf ppm {
        type string;
      }
      leaf fast-hello-issu {
        type empty;
      }
    }
    container oam {
      uses apply-group;
      uses apply-macro;
      container ethernet {
        uses apply-group;
        uses apply-macro;
        container link-fault-management {
          uses apply-group;
          uses apply-macro;
          leaf hardware-assisted-keepalives {
            type empty;
          }
          container traceoptions {
            uses apply-group;
            uses apply-macro;
            leaf no-remote-trace {
              type empty;
            }
            container file {
              leaf filename {
                type string;
              }
              leaf size {
                type string;
              }
              leaf files {
                type uint32;
              }
              leaf world-readable {
                type empty;
              }
              leaf no-world-readable {
                type empty;
              }
              leaf match {
                type regular-expression;
              }
            }
            list flag {
              key "name";
              ordered-by user;
              leaf name {
                type string;
              }
            }
          }
          list action-profile {
            key "name";
            ordered-by user;
            leaf name {
              type key-attribute-string-type;
            }
            uses apply-group;
            uses apply-macro;
            container event {
              uses apply-group;
              uses apply-macro;
              leaf link-adjacency-loss {
                type empty;
              }
              leaf protocol-down {
                type empty;
              }
              container link-event-rate {
                uses apply-group;
                uses apply-macro;
                leaf symbol-period {
                  type int32;
                }
                leaf frame-error {
                  type int32;
                }
                leaf frame-period {
                  type int32;
                }
                leaf frame-period-summary {
                  type int32;
                }
              }
            }
            container action {
              uses apply-group;
              uses apply-macro;
              leaf syslog {
                type empty;
              }
              leaf link-down {
                type empty;
              }
              leaf send-critical-event {
                type empty;
              }
            }
          }
          list interface {
            key "name";
            ordered-by user;
            leaf name {
              type interface-device;
            }
            uses apply-group;
            uses apply-macro;
            leaf-list apply-action-profile {
              type string;
              ordered-by user;
            }
            leaf pdu-interval {
              type int32;
            }
            leaf loopback-tracking {
              type empty;
            }
            leaf detect-loc {
              type empty;
            }
            leaf link-discovery {
              type string;
            }
            leaf pdu-threshold {
              type int32;
            }
            leaf remote-loopback {
              type empty;
            }
            container negotiation-options {
              uses apply-group;
              uses apply-macro;
              leaf no-allow-link-events {
                type empty;
              }
              leaf allow-remote-loopback {
                type empty;
              }
            }
            container event-thresholds {
              uses apply-group;
              uses apply-macro;
              leaf symbol-period {
                type int32;
              }
              leaf frame-error {
                type int32;
              }
              leaf frame-period {
                type int32;
              }
              leaf frame-period-summary {
                type int32;
              }
            }
          }
        }
        container connectivity-fault-management {
          uses apply-group;
          uses apply-macro;
          container performance-monitoring {
            uses apply-group;
            uses apply-macro;
            leaf hardware-assisted-timestamping {
              type empty;
            }
            leaf delegate-server-processing {
              type empty;
            }
            leaf hardware-assisted-keepalives {
              type string;
            }
            leaf hardware-assisted-pm {
              type empty;
            }
            leaf enhanced-sla-iterator {
              type empty;
            }
            leaf measurement-interval {
              units "minutes";
              type string;
            }
            leaf legacy-pm-display {
              type empty;
            }
            list sla-iterator-profiles {
              key "name";
              ordered-by user;
              leaf name {
                type string;
              }
              uses apply-group;
              uses apply-macro;
              leaf disable {
                type empty;
              }
              leaf measurement-type {
                type string;
              }
              leaf cycle-time {
                units "milliseconds";
                type uint32;
              }
              leaf iteration-period {
                units "connections";
                type uint32;
              }
              container calculation-weight {
                presence "enable calculation-weight";
                uses apply-group;
                uses apply-macro;
                leaf delay {
                  type uint32;
                }
                leaf delay-variation {
                  type uint32;
                }
              }
              container avg-flr-forward-threshold {
                presence "enable avg-flr-forward-threshold";
                uses apply-advanced;
                leaf avg-flr-forward {
                  type string;
                }
                leaf flap-trap-monitor {
                  units "seconds";
                  type string;
                }
              }
              container avg-flr-backward-threshold {
                presence "enable avg-flr-backward-threshold";
                uses apply-advanced;
                leaf avg-flr-backward {
                  type string;
                }
                leaf flap-trap-monitor {
                  units "seconds";
                  type string;
                }
              }
              container avg-fd-twoway-threshold {
                presence "enable avg-fd-twoway-threshold";
                uses apply-advanced;
                leaf avg-fd-twoway {
                  units "microseconds";
                  type string;
                }
                leaf flap-trap-monitor {
                  units "seconds";
                  type string;
                }
              }
              container avg-fdv-twoway-threshold {
                presence "enable avg-fdv-twoway-threshold";
                uses apply-advanced;
                leaf avg-fdv-twoway {
                  units "microseconds";
                  type string;
                }
                leaf flap-trap-monitor {
                  units "seconds";
                  type string;
                }
              }
              leaf measurement-interval {
                units "minutes";
                type string;
              }
              container frame-delay {
                uses apply-advanced;
                leaf num-bins {
                  type string;
                }
                container two-way {
                  presence "enable two-way";
                  uses apply-advanced;
                  leaf-list lower-threshold-bin {
                    type string;
                  }
                }
                container forward {
                  presence "enable forward";
                  uses apply-advanced;
                  leaf-list lower-threshold-bin {
                    type string;
                  }
                }
                container backward {
                  presence "enable backward";
                  uses apply-advanced;
                  leaf-list lower-threshold-bin {
                    type string;
                  }
                }
              }
              container frame-delay-range {
                uses apply-advanced;
                leaf num-bins {
                  type string;
                }
                container two-way {
                  presence "enable two-way";
                  uses apply-advanced;
                  leaf-list lower-threshold-bin {
                    type string;
                  }
                }
                container forward {
                  presence "enable forward";
                  uses apply-advanced;
                  leaf-list lower-threshold-bin {
                    type string;
                  }
                }
                container backward {
                  presence "enable backward";
                  uses apply-advanced;
                  leaf-list lower-threshold-bin {
                    type string;
                  }
                }
              }
              container ifdv {
                uses apply-advanced;
                leaf num-bins {
                  type string;
                }
                container two-way {
                  presence "enable two-way";
                  uses apply-advanced;
                  leaf-list lower-threshold-bin {
                    type string;
                  }
                }
                container forward {
                  presence "enable forward";
                  uses apply-advanced;
                  leaf-list lower-threshold-bin {
                    type string;
                  }
                }
                container backward {
                  presence "enable backward";
                  uses apply-advanced;
                  leaf-list lower-threshold-bin {
                    type string;
                  }
                }
              }
              container availability {
                uses apply-advanced;
                leaf num-consecutive-pdus {
                  type string;
                }
                leaf flr-threshold {
                  type string;
                }
                leaf num-consecutive-intervals {
                  type string;
                }
                leaf num-consecutive-highflr {
                  type string;
                }
              }
            }
            list interface {
              key "name";
              ordered-by user;
              leaf name {
                type interface-unit;
              }
              leaf enable-multiclass-loss-measurement {
                type empty;
              }
              leaf code-point-based-lm-accounting {
                type empty;
              }
              leaf priority-based-lm-accounting {
                type empty;
              }
            }
            leaf enable-multiclass-loss-measurement {
              type empty;
            }
            leaf code-point-based-lm-accounting {
              type empty;
            }
            leaf priority-based-lm-accounting {
              type empty;
            }
            leaf colorless-loss-measurement {
              type empty;
            }
          }
          container connection-protection {
            uses apply-group;
            uses apply-macro;
            leaf mark-connection-protection-tlv {
              type empty;
            }
            leaf uhp-label-lookup {
              type empty;
            }
          }
          leaf no-aggregate-delegate-processing {
            type empty;
          }
          leaf enhanced-cfm-mode {
            type empty;
          }
          container expected-defect {
            uses apply-group;
            uses apply-macro;
            leaf rx-enable {
              type empty;
            }
            leaf rx-max-duration {
              type uint32;
            }
            leaf tx-enable {
              type empty;
            }
            leaf tx-duration {
              type uint32;
            }
          }
          container traceoptions {
            presence "enable traceoptions";
            uses cfm-traceoptions;
          }
          list action-profile {
            key "name";
            ordered-by user;
            leaf name {
              type string;
            }
            uses apply-group;
            uses apply-macro;
            container event {
              uses apply-group;
              uses apply-macro;
              leaf-list interface-status-tlv {
                ordered-by user;
                type string;
              }
              leaf-list port-status-tlv {
                ordered-by user;
                type string;
              }
              leaf adjacency-loss {
                type empty;
              }
              leaf rdi {
                type empty;
              }
            }
            container action {
              uses apply-group;
              uses apply-macro;
              leaf interface-down {
                type empty;
              }
            }
            container default-actions {
              uses apply-group;
              uses apply-macro;
              leaf interface-down {
                type empty;
              }
            }
          }
          list server-mep {
            key "name";
            ordered-by user;
            leaf name {
              type key-attribute-ulong-type;
            }
            uses apply-group;
            uses apply-macro;
            container protocol {
              presence "enable protocol";
              uses apply-group;
              uses apply-macro;
              choice choice-l2circuit {
                container l2circuit {
                  presence "";
                  container interface {
                    presence "";
                    leaf interface-name {
                      mandatory true;
                      type interface-name;
                    }
                  }
                }
                container l2vpn {
                  presence "";
                  container interface {
                    presence "";
                    leaf interface-name {
                      mandatory true;
                      type interface-name;
                    }
                  }
                }
                container ethernet {
                  presence "";
                  container interface {
                    presence "";
                    leaf interface-name {
                      mandatory true;
                      type interface-device;
                    }
                  }
                }
              }
            }
            container action-profile {
              presence "";
              uses apply-group;
              uses apply-macro;
              leaf action-profile-name {
                type string;
                mandatory true;
              }
            }
          }
          container policer {
            uses apply-group;
            uses apply-macro;
            leaf continuity-check {
              type string;
            }
            leaf other {
              type string;
            }
            leaf all {
              type string;
            }
          }
          container linktrace {
            presence "enable linktrace";
            uses apply-group;
            uses apply-macro;
            leaf path-database-size {
              type uint32;
            }
            leaf age {
              type string;
            }
          }
          list maintenance-domain {
            key "name";
            ordered-by user;
            leaf name {
              type string;
            }
            uses apply-group;
            uses apply-macro;
            list bridge-domain {
              key "name";
              ordered-by user;
              leaf name {
                type string;
              }
              leaf-list vlan-id {
                type string;
                ordered-by user;
              }
            }
            list virtual-switch {
              key "name";
              ordered-by user;
              leaf name {
                type string;
              }
              uses apply-group;
              uses apply-macro;
              list bridge-domain {
                key "name";
                ordered-by user;
                leaf name {
                  type string;
                }
                leaf-list vlan-id {
                  type string;
                  ordered-by user;
                }
              }
            }
            list instance {
              key "name";
              ordered-by user;
              leaf name {
                type string;
              }
            }
            list interface {
              key "name";
              ordered-by user;
              leaf name {
                type interface-unit;
              }
            }
            leaf level {
              type uint8;
            }
            leaf name-format {
              type string;
            }
            leaf mip-half-function {
              type string;
            }
            list maintenance-association {
              key "name";
              ordered-by user;
              leaf name {
                type key-attribute-string-type;
              }
              uses apply-group;
              uses apply-macro;
              leaf short-name-format {
                type string;
              }
              container protect-maintenance-association {
                presence "";
                leaf ma-name {
                  mandatory true;
                  type string;
                }
                leaf aps-profile {
                  type string;
                }
                leaf detect-path-type {
                  type empty;
                }
              }
              leaf primary-vid {
                type string;
              }
              container continuity-check {
                presence "enable continuity-check";
                uses apply-group;
                uses apply-macro;
                leaf interval {
                  type string;
                }
                leaf loss-threshold {
                  type uint32;
                }
                leaf hold-interval {
                  type uint32;
                }
                leaf port-status-tlv {
                  type empty;
                }
                leaf interface-status-tlv {
                  type empty;
                }
                leaf connection-protection-tlv {
                  type empty;
                }
                leaf convey-loss-threshold {
                  type empty;
                }
                leaf interface-status-send-rdi {
                  type empty;
                }
                container sendid-tlv {
                  uses apply-group;
                  uses apply-macro;
                  leaf send-chassis-tlv {
                    type empty;
                  }
                }
              }
              leaf mip-half-function {
                type string;
              }
              list mep {
                key "name";
                ordered-by user;
                leaf name {
                  type string;
                }
                uses apply-group;
                uses apply-macro;
                container interface {
                  presence "";
                  leaf interface-name {
                    type interface-unit;
                  }
                  leaf vlan {
                    type uint32;
                  }
                  leaf vlan-id {
                    type uint32;
                  }
                }
                leaf direction {
                  type string;
                }
                leaf priority {
                  type uint32;
                }
                leaf auto-discovery {
                  type empty;
                }
                list remote-mep {
                  key "name";
                  ordered-by user;
                  leaf name {
                    type string;
                  }
                  uses apply-group;
                  uses apply-macro;
                  leaf action-profile {
                    type string;
                  }
                  list sla-iterator-profile {
                    key "name";
                    ordered-by user;
                    leaf name {
                      type string;
                    }
                    uses apply-group;
                    uses apply-macro;
                    leaf iteration-count {
                      units "frames";
                      type uint32;
                    }
                    leaf priority {
                      type uint32;
                    }
                    leaf data-tlv-size {
                      units "bytes";
                      type uint32;
                    }
                  }
                  leaf detect-loc {
                    type empty;
                  }
                }
                leaf lowest-priority-defect {
                  type string;
                }
              }
              container policer {
                uses apply-group;
                uses apply-macro;
                leaf continuity-check {
                  type string;
                }
                leaf other {
                  type string;
                }
                leaf all {
                  type string;
                }
              }
            }
          }
          container sendid-tlv {
            uses apply-group;
            uses apply-macro;
            leaf send-chassis-tlv {
              type empty;
            }
          }
        }
        list evcs {
          key "name";
          leaf name {
            type key-attribute-string-type;
          }
          uses apply-group;
          uses apply-macro;
          container evc-protocol {
            presence "enable evc-protocol";
            choice choice-3 {
              container cfm {
                presence "";
                leaf maintenance-domain {
                  type string;
                }
                leaf maintenance-association {
                  type string;
                }
              }
              container vpls {
                presence "";
                leaf routing-instance {
                  type string;
                }
              }
            }
          }
          leaf remote-uni-count {
            type uint8;
          }
          leaf multipoint-to-multipoint {
            type empty;
          }
        }
        container lmi {
          presence "enable lmi";
          uses apply-group;
          uses apply-macro;
          container traceoptions {
            uses apply-group;
            uses apply-macro;
            leaf no-remote-trace {
              type empty;
            }
            container file {
              leaf filename {
                type string;
              }
              leaf size {
                type string;
              }
              leaf files {
                type uint32;
              }
              leaf world-readable {
                type empty;
              }
              leaf no-world-readable {
                type empty;
              }
              leaf match {
                type regular-expression;
              }
            }
            list flag {
              key "name";
              ordered-by user;
              leaf name {
                type string;
              }
            }
          }
          leaf status-counter {
            type uint8;
          }
          leaf polling-verification-timer {
            type uint8;
          }
          list interface {
            key "name";
            leaf name {
              type interface-device;
            }
            uses apply-group;
            uses apply-macro;
            leaf uni-id {
              type string;
            }
            leaf status-counter {
              type uint8;
            }
            leaf polling-verification-timer {
              type uint8;
            }
            leaf evc-map-type {
              type string;
            }
            list evc {
              key "name";
              leaf name {
                type key-attribute-string-type;
              }
              uses apply-group;
              uses apply-macro;
              leaf default-evc {
                type empty;
              }
              leaf-list vlan-list {
                type string;
                ordered-by user;
              }
            }
          }
        }
      }
      container gre-tunnel {
        presence "enable gre-tunnel";
        uses apply-group;
        uses apply-macro;
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
        list interface {
          key "name";
          ordered-by user;
          leaf name {
            type interface-unit;
          }
          uses apply-group;
          uses apply-macro;
          leaf keepalive-time {
            type int32;
          }
          leaf hold-time {
            type int32;
          }
        }
      }
    }
    container ptp {
      uses apply-group;
      uses apply-macro;
      leaf clock-mode {
        type string;
      }
      leaf profile-type {
        type string;
      }
      leaf e2e-transparent {
        type empty;
      }
      leaf timescale {
        type string;
      }
      leaf priority1 {
        type int32;
      }
      leaf priority2 {
        type int32;
      }
      leaf local-priority {
        type uint32;
      }
      leaf domain {
        type int32;
      }
      leaf path-trace {
        type empty;
      }
      leaf unicast-negotiation {
        type empty;
      }
      leaf phy-timestamping {
        type empty;
      }
      leaf ipv4-dscp {
        type int32;
      }
      leaf ipv6-dscp {
        type int32;
      }
      container performance-monitor {
        uses apply-group;
        uses apply-macro;
        container threshold {
          uses apply-group;
          uses apply-macro;
          leaf min-outbound-delay {
            type uint32;
          }
          leaf max-outbound-delay {
            type uint32;
          }
          leaf min-inbound-delay {
            type uint32;
          }
          leaf max-inbound-delay {
            type uint32;
          }
          leaf max-inbound-jitter-neg {
            type int32;
          }
          leaf max-inbound-jitter-pos {
            type uint32;
          }
          leaf max-outbound-jitter-neg {
            type int32;
          }
          leaf max-outbound-jitter-pos {
            type uint32;
          }
        }
      }
      leaf utc-leap-seconds {
        type int32;
      }
      container slave {
        uses apply-group;
        uses apply-macro;
        leaf frequency-only {
          type empty;
        }
        leaf delay-request {
          type int32;
        }
        leaf announce-timeout {
          type uint32;
        }
        leaf announce-interval {
          type int32;
        }
        leaf sync-interval {
          type int32;
        }
        leaf grant-duration {
          type uint32;
        }
        leaf convert-clock-class-to-quality-level {
          type empty;
        }
        container clock-class-to-quality-level-mapping {
          presence "";
          uses apply-group;
          uses apply-macro;
          list quality-level {
            key "name";
            leaf name {
              type string;
            }
            uses apply-group;
            uses apply-macro;
            leaf clock-class {
              type int32;
            }
          }
        }
        list interface {
          key "name";
          leaf name {
            type interface-name;
          }
          uses apply-group;
          uses apply-macro;
          container unicast-mode {
            presence "";
            uses apply-group;
            uses apply-macro;
            leaf transport {
              type string;
            }
            leaf local-priority {
              type uint32;
            }
            list clock-source {
              key "ip-address local-ip-address";
              leaf ip-address {
                type ipv4addr;
              }
              leaf local-ip-address {
                type ipv4addr;
              }
              uses apply-group;
              uses apply-macro;
              leaf asymmetry {
                type int32;
              }
            }
          }
          container multicast-mode {
            presence "";
            uses apply-group;
            uses apply-macro;
            container transport {
              presence "enable transport";
              uses apply-group;
              uses apply-macro;
              container ieee-802.3 {
                presence "enable ieee-802.3";
                leaf link-local {
                  type empty;
                }
              }
            }
            leaf local-priority {
              type uint32;
            }
            leaf asymmetry {
              type int32;
            }
            leaf local-ip-address {
              type ipv4addr;
            }
          }
          leaf primary {
            type string;
          }
          leaf secondary {
            type string;
          }
        }
        container hybrid {
          uses apply-group;
          uses apply-macro;
          leaf periodic-alignment {
            type string;
          }
          leaf re-alignment-threshold {
            type int32;
          }
          container synchronous-ethernet-mapping {
            presence "enable synchronous-ethernet-mapping";
            uses apply-group;
            uses apply-macro;
            list clock-source {
              key "name";
              leaf name {
                type ipv4addr;
              }
              uses apply-group;
              uses apply-macro;
              list interface {
                key "name";
                leaf name {
                  type interface-device;
                }
                uses apply-group;
                uses apply-macro;
              }
            }
          }
        }
      }
      container master {
        uses apply-group;
        uses apply-macro;
        leaf announce-interval {
          type int32;
        }
        leaf sync-interval {
          type int32;
        }
        leaf min-announce-interval {
          type int32;
        }
        leaf max-announce-interval {
          type int32;
        }
        leaf min-sync-interval {
          type int32;
        }
        leaf max-sync-interval {
          type int32;
        }
        leaf min-delay-response-interval {
          type int32;
        }
        leaf max-delay-response-interval {
          type int32;
        }
        leaf delay-req-timeout {
          type uint32;
        }
        leaf clock-step {
          type string;
        }
        list interface {
          key "name";
          leaf name {
            type interface-name;
          }
          uses apply-group;
          uses apply-macro;
          container unicast-mode {
            presence "";
            uses apply-group;
            uses apply-macro;
            leaf transport {
              type string;
            }
            list clock-client {
              key "ip-address local-ip-address";
              leaf ip-address {
                type ipv4prefix;
              }
              leaf local-ip-address {
                type ipv4addr;
              }
              uses apply-group;
              uses apply-macro;
              leaf manual {
                type empty;
              }
            }
          }
          container multicast-mode {
            presence "";
            uses apply-group;
            uses apply-macro;
            container transport {
              presence "enable transport";
              uses apply-group;
              uses apply-macro;
              container ieee-802.3 {
                presence "enable ieee-802.3";
                leaf link-local {
                  type empty;
                }
              }
            }
            leaf local-priority {
              type uint32;
            }
            leaf local-ip-address {
              type ipv4addr;
            }
          }
          leaf primary {
            type string;
          }
          leaf secondary {
            type string;
          }
        }
      }
      container stateful {
        uses apply-group;
        uses apply-macro;
        list interface {
          key "name";
          leaf name {
            type interface-name;
          }
          uses apply-group;
          uses apply-macro;
          container multicast-mode {
            presence "";
            uses apply-group;
            uses apply-macro;
            container transport {
              presence "enable transport";
              uses apply-group;
              uses apply-macro;
              container ieee-802.3 {
                presence "enable ieee-802.3";
                leaf link-local {
                  type empty;
                }
              }
            }
            leaf local-priority {
              type uint32;
            }
            leaf asymmetry {
              type int32;
            }
          }
          leaf primary {
            type string;
          }
          leaf secondary {
            type string;
          }
        }
      }
    }
    container clock-synchronization {
      uses apply-group;
      uses apply-macro;
      container traceoptions {
        presence "enable traceoptions";
        uses clksync-traceoptions;
      }
    }
    container l2-learning {
      uses juniper-protocols-bridge;
    }
    container network-isolation {
      uses apply-advanced;
      list group {
        key "name";
        leaf name {
          type string;
        }
        uses apply-advanced;
        container detection {
          presence "enable detection";
          uses apply-advanced;
          container hold-time {
            leaf up {
              units "milliseconds";
              type string;
            }
            leaf down {
              units "milliseconds";
              type string;
            }
          }
          container link-tracking {
            presence "enable link-tracking";
            uses apply-advanced;
            leaf minimum-links {
              type string;
            }
            leaf failure-type {
              type string;
            }
            list interface {
              key "name";
              leaf name {
                type string;
              }
              uses apply-advanced;
            }
          }
          container service-tracking {
            presence "enable service-tracking";
            uses apply-advanced;
            leaf core-isolation {
              type empty;
            }
          }
        }
        container service-tracking-action {
          choice actions {
            case case_1 {
              leaf link-down {
                type empty;
              }
            }
            case case_2 {
              leaf lacp-out-of-sync {
                type empty;
              }
            }
          }
        }
      }
    }
    container lldp {
      uses apply-group;
      uses apply-macro;
      choice choice-3 {
        leaf disable {
          type empty;
        }
        leaf enable-disable {
          type string;
        }
      }
      container traceoptions {
        uses apply-group;
        uses apply-macro;
        container file {
          presence "";
          uses trace-file-type;
        }
        list flag {
          key "name";
          leaf name {
            type string;
          }
          leaf disable {
            type empty;
          }
        }
      }
      leaf management-address {
        type ipaddr;
      }
      leaf advertisement-interval {
        type uint32;
      }
      leaf transmit-delay {
        type uint32;
      }
      leaf hold-multiplier {
        type uint32;
      }
      leaf ptopo-configuration-trap-interval {
        type uint32;
      }
      leaf ptopo-configuration-maximum-hold-time {
        type uint32;
      }
      leaf lldp-configuration-notification-interval {
        type uint32;
      }
      leaf port-id-subtype {
        type string;
      }
      leaf port-description-type {
        type string;
      }
      leaf neighbour-port-info-display {
        type string;
      }
      leaf mau-type {
        type empty;
      }
      leaf vlan-name-tlv-option {
        type string;
      }
      leaf-list tlv-select {
        ordered-by user;
        type string;
      }
      leaf-list tlv-filter {
        ordered-by user;
        type string;
      }
      list interface {
        key "name";
        ordered-by user;
        leaf name {
          type string;
        }
        uses apply-group;
        uses apply-macro;
        choice choice-3 {
          leaf disable {
            type empty;
          }
          leaf enable-disable {
            type string;
          }
        }
        container power-negotiation {
          presence "enable power-negotiation";
          uses apply-group;
          uses apply-macro;
          leaf enable-disable {
            type string;
          }
        }
        leaf-list tlv-select {
          ordered-by user;
          type string;
        }
        leaf-list tlv-filter {
          ordered-by user;
          type string;
        }
      }
    }
    container lldp-med {
      presence "enable lldp-med";
      uses apply-group;
      uses apply-macro;
      choice choice-3 {
        leaf disable {
          type empty;
        }
      }
      leaf fast-start {
        type uint32;
      }
      list interface {
        key "name";
        ordered-by user;
        leaf name {
          type string;
        }
        uses apply-group;
        uses apply-macro;
        choice choice-3 {
          leaf disable {
            type empty;
          }
        }
        container location {
          presence "enable location";
          uses apply-group;
          uses apply-macro;
          choice choice-3 {
            container civic-based {
              presence "";
              uses civic-address-elements;
            }
            leaf elin {
              type string;
            }
            container co-ordinate {
              presence "enable co-ordinate";
              uses co-ordinate-elements;
            }
          }
        }
      }
    }
    container igmp-snooping {
      presence "enable igmp-snooping";
      uses juniper-protocols-igmp-snooping;
    }
    container sflow {
      presence "enable sflow";
      uses apply-group;
      uses apply-macro;
      container traceoptions {
        uses apply-group;
        uses apply-macro;
        container file {
          presence "";
          uses trace-file-type;
        }
        list flag {
          key "name";
          ordered-by user;
          leaf name {
            type string;
          }
          leaf disable {
            type empty;
          }
        }
      }
      leaf polling-interval {
        units "seconds";
        type uint32;
      }
      leaf inline-sampling {
        type empty;
      }
      container sample-rate {
        uses apply-group;
        uses apply-macro;
        leaf ingress {
          type uint32;
        }
        leaf egress {
          type uint32;
        }
      }
      list collector {
        key "name";
        ordered-by user;
        leaf name {
          type ipv4addr;
        }
        uses apply-group;
        uses apply-macro;
        leaf udp-port {
          type uint16;
        }
      }
      list interfaces {
        key "name";
        leaf name {
          type interface-name;
        }
        uses apply-group;
        uses apply-macro;
        leaf polling-interval {
          units "seconds";
          type uint32;
        }
        container sample-rate {
          uses apply-group;
          uses apply-macro;
          leaf ingress {
            type uint32;
          }
          leaf egress {
            type uint32;
          }
        }
      }
    }
    container pcep {
      uses apply-group;
      uses apply-macro;
      leaf message-rate-limit {
        type uint16;
      }
      leaf update-rate-limit {
        type uint16;
      }
      leaf max-provisioned-lsps {
        type uint32;
      }
      leaf maximum-srmpls-segment-list-depth {
        type string;
      }
      leaf maximum-srv6-segment-list-depth {
        type string;
      }
      leaf propagate-max-segmentlist {
        type empty;
      }
      leaf propagate-lsp-max-segment-list-depth {
        type empty;
      }
      leaf disable-multipath-capability {
        type empty;
      }
      leaf tls-strict {
        type empty;
      }
      list pce-group {
        key "name";
        ordered-by user;
        leaf name {
          type key-attribute-string-type;
        }
        uses apply-group;
        uses apply-macro;
        container pce-type {
          leaf active {
            type empty;
          }
          leaf stateful {
            type empty;
          }
        }
        leaf lsp-provisioning {
          type empty;
        }
        leaf p2mp-lsp-report-capability {
          type empty;
        }
        leaf lsp-cleanup-timer {
          units "seconds";
          type uint32;
        }
        leaf spring-capability {
          type empty;
        }
        leaf max-sid-depth {
          type uint32;
        }
        leaf lsp-retry-delegation {
          type empty;
        }
        leaf lsp-retry-delegation-timer {
          units "seconds";
          type uint32;
        }
        leaf request-timer {
          units "seconds";
          type uint16;
        }
        leaf max-unknown-requests {
          units "requests-per-minute";
          type uint32;
        }
        leaf max-unknown-messages {
          units "messages-per-minute";
          type uint32;
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
        leaf delegation-cleanup-timeout {
          units "seconds";
          type string;
        }
      }
      list pce {
        key "name";
        ordered-by user;
        leaf name {
          type key-attribute-string-type;
        }
        uses apply-group;
        uses apply-macro;
        leaf local-address {
          type ipv4addr;
        }
        leaf destination-ipv4-address {
          type ipv4addr;
        }
        leaf destination-port {
          type uint16;
        }
        leaf delegation-priority {
          type uint16;
        }
        leaf request-priority {
          type uint16;
        }
        leaf pce-group {
          type string;
        }
        leaf authentication-key {
          type unreadable;
        }
        leaf authentication-algorithm {
          type string;
        }
        leaf authentication-key-chain {
          type string;
        }
        container pce-type {
          leaf active {
            type empty;
          }
          leaf stateful {
            type empty;
          }
        }
        leaf lsp-provisioning {
          type empty;
        }
        leaf p2mp-lsp-report-capability {
          type empty;
        }
        leaf p2mp-lsp-update-capability {
          type empty;
        }
        leaf p2mp-lsp-init-capability {
          type empty;
        }
        leaf lsp-cleanup-timer {
          units "seconds";
          type uint32;
        }
        leaf spring-capability {
          type empty;
        }
        leaf max-sid-depth {
          type uint32;
        }
        leaf lsp-retry-delegation {
          type empty;
        }
        leaf lsp-retry-delegation-timer {
          units "seconds";
          type uint32;
        }
        leaf request-timer {
          units "seconds";
          type uint16;
        }
        leaf max-unknown-requests {
          units "requests-per-minute";
          type uint32;
        }
        leaf max-unknown-messages {
          units "messages-per-minute";
          type uint32;
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
        leaf delegation-cleanup-timeout {
          units "seconds";
          type string;
        }
        leaf pce-traffic-steering {
          type empty;
        }
        container undocumented {
          leaf pcupdate-empty-ero-action {
            type string;
          }
        }
      }
      container traceoptions {
        uses pccd-traceoptions-type;
      }
      container undocumented {
        container object-class {
          leaf association-old-value {
            type empty;
          }
          leaf s2ls-old-value {
            type empty;
          }
        }
        container tlv-type {
          leaf p2mp-ipv4-lsp-identifier-old-value {
            type empty;
          }
        }
        leaf stateful-draft-07-compliant {
          type empty;
        }
      }
    }
    container ppp {
      uses apply-group;
      uses apply-macro;
      container traceoptions {
        uses ppp-traceoptions-type;
      }
      list monitor-session {
        key "session-name";
        leaf session-name {
          type string;
        }
        uses apply-group;
        uses apply-macro;
      }
    }
    container pppoe {
      uses apply-group;
      uses apply-macro;
      container traceoptions {
        uses pppoe-traceoptions-type;
      }
      leaf pado-advertise {
        type empty;
      }
      list service-name-tables {
        key "name";
        ordered-by user;
        leaf name {
          type key-attribute-string-type;
        }
        uses apply-group;
        uses apply-macro;
        list service {
          key "name";
          ordered-by user;
          leaf name {
            type key-attribute-string-type;
          }
          uses apply-group;
          uses apply-macro;
          choice choice-3 {
            leaf terminate {
              type empty;
            }
            leaf drop {
              type empty;
            }
            leaf delay {
              type uint32;
            }
          }
          leaf dynamic-profile {
            type string;
          }
          leaf routing-instance {
            type string;
          }
          leaf max-sessions {
            type uint32;
          }
          list agent-specifier {
            key "aci ari";
            ordered-by user;
            leaf aci {
              type key-attribute-string-type;
            }
            leaf ari {
              type key-attribute-string-type;
            }
            uses apply-group;
            uses apply-macro;
            choice choice-3 {
              leaf terminate {
                type empty;
              }
              leaf drop {
                type empty;
              }
              leaf delay {
                type uint32;
              }
            }
            leaf dynamic-profile {
              type string;
            }
            leaf routing-instance {
              type string;
            }
            leaf static-interface {
              type interface-unit;
            }
          }
        }
      }
    }
    container r2cp {
      uses apply-group;
      uses apply-macro;
      choice choice-3 {
        leaf disable {
          type empty;
        }
      }
      container traceoptions {
        uses r2cp-traceoptions-type;
      }
      leaf server-port {
        type uint16;
      }
      container client-port {
        choice choice-3 {
          leaf port-number {
            type uint16;
          }
          leaf any {
            type empty;
          }
        }
      }
      leaf node-terminate-count {
        type uint16;
      }
      leaf node-terminate-interval {
        type uint16;
      }
      leaf session-terminate-count {
        type uint16;
      }
      leaf session-terminate-interval {
        type uint16;
      }
      list radio {
        key "name";
        ordered-by user;
        leaf name {
          type string;
        }
        uses apply-group;
        uses apply-macro;
        leaf interface {
          type interface-unit;
        }
        leaf virtual-channel-group {
          type string;
        }
        list radio-interface {
          key "name";
          ordered-by user;
          leaf name {
            type interface-unit;
          }
          uses apply-group;
          uses apply-macro;
        }
      }
    }
    container layer2-control {
      uses juniper-protocols-l2control;
    }
    container rstp {
      uses juniper-protocols-stp;
    }
    container mstp {
      uses juniper-protocols-mstp;
    }
    container vstp {
      uses juniper-protocols-vstp;
    }
    container dcbx {
      presence "true";
      uses apply-group;
      uses apply-macro;
      leaf disable {
        type empty;
      }
      list interface {
        key "name";
        ordered-by user;
        leaf name {
          type string;
        }
        uses apply-group;
        uses apply-macro;
        leaf disable {
          type empty;
        }
        container priority-flow-control {
          uses apply-group;
          uses apply-macro;
          leaf no-auto-negotiation {
            type empty;
          }
        }
        container enhanced-transmission-selection {
          uses apply-group;
          uses apply-macro;
          leaf no-auto-negotiation {
            type empty;
          }
        }
        container applications {
          uses apply-group;
          uses apply-macro;
          container fcoe {
            uses apply-group;
            uses apply-macro;
            leaf no-auto-negotiation {
              type empty;
            }
          }
        }
        leaf application-map {
          type string;
        }
      }
    }
    container dot1x {
      uses juniper-protocols-dot1x;
    }
    container ppp-service {
      uses apply-group;
      uses apply-macro;
      container traceoptions {
        uses apply-group;
        uses apply-macro;
        leaf no-remote-trace {
          type empty;
        }
        container file {
          leaf filename {
            type string;
          }
          leaf size {
            type string;
          }
          leaf files {
            type uint32;
          }
          leaf world-readable {
            type empty;
          }
          leaf no-world-readable {
            type empty;
          }
          leaf match {
            type regular-expression;
          }
        }
        leaf level {
          type string;
        }
        list flag {
          key "name";
          ordered-by user;
          leaf name {
            type string;
          }
        }
        container filter {
          presence "enable filter";
          uses apply-group;
          uses apply-macro;
          leaf aci {
            type string;
          }
          leaf ari {
            type string;
          }
          leaf service-name {
            type string;
          }
          leaf underlying-interface {
            type string;
          }
          container user {
            presence "enable user";
            uses apply-group;
            uses apply-macro;
            leaf username {
              type string;
            }
          }
        }
      }
      leaf on-demand-ip-address {
        type empty;
      }
      leaf reject-unauthorized-ipv6cp {
        type empty;
      }
      leaf pppoe-lcp-options-strict {
        type empty;
      }
      container undocumented {
        leaf no-performance-boost {
          type empty;
        }
      }
    }
    container loop-detect {
      presence "enable loop-detect";
      uses apply-group;
      uses apply-macro;
      list interface {
        key "name";
        ordered-by user;
        leaf name {
          type string;
        }
        uses apply-group;
        uses apply-macro;
        leaf disable {
          type empty;
        }
      }
      container enhanced {
        uses apply-group;
        uses apply-macro;
        list interface {
          key "name";
          ordered-by user;
          leaf name {
            type string;
          }
          uses apply-group;
          uses apply-macro;
          leaf vlan-id {
            type uint32;
          }
          leaf loop-detect-action {
            type string;
          }
          leaf transmit-interval {
            type string;
          }
          leaf revert-interval {
            units "seconds";
            type uint32;
          }
        }
      }
      leaf destination-mac {
        type mac-multicast;
      }
      leaf transmit-interval {
        units "seconds";
        type uint16;
      }
    }
    container protection-group {
      presence "enable protection-group";
      uses juniper-protocols-protection-group;
    }
    container mvrp {
      uses juniper-protocols-mvrp;
    }
  }

  grouping admin-group-include-exclude {
    uses apply-group;
    uses apply-macro;
    leaf-list include-any {
      type string;
      ordered-by user;
    }
    leaf-list include-all {
      type string;
      ordered-by user;
    }
    leaf-list exclude {
      type string;
      ordered-by user;
    }
  }

  grouping bandwidth-type {
    uses apply-group;
    uses apply-macro;
    leaf per-traffic-class-bandwidth {
      type string;
    }
    leaf ct0 {
      type string;
    }
    leaf ct1 {
      type string;
    }
    leaf ct2 {
      type string;
    }
    leaf ct3 {
      type string;
    }
  }

  grouping cfm-traceoptions {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    list flag {
      key "name";
      ordered-by user;
      leaf name {
        type string;
      }
    }
  }

  grouping flow-interface-group {
    uses apply-group;
    uses apply-macro;
    leaf group {
      type uint32;
    }
    leaf exclude {
      type empty;
    }
  }

  grouping flow-route-inet {
    leaf name {
      type string;
    }
    uses apply-advanced;
    leaf no-install {
      type empty;
    }
    container match {
      uses flow-route-qualifier-inet;
    }
    container then {
      uses flow-route-op;
    }
  }

  grouping flow-route-inet6 {
    leaf name {
      type string;
    }
    uses apply-group;
    uses apply-macro;
    leaf no-install {
      type empty;
    }
    container match {
      uses flow-route-qualifier-inet6;
    }
    container then {
      uses flow-route-op;
    }
  }

  grouping flow-validation {
    uses apply-group;
    uses apply-macro;
    container traceoptions {
      uses flow-dep-traceoptions;
    }
  }

  grouping clksync-traceoptions {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    list flag {
      key "name";
      ordered-by user;
      leaf name {
        type string;
      }
    }
  }

  grouping civic-address-elements {
    uses apply-group;
    uses apply-macro;
    leaf what {
      type uint16;
    }
    leaf country-code {
      type string;
    }
    list ca-type {
      key "name";
      ordered-by user;
      leaf name {
        type string;
      }
      uses apply-group;
      uses apply-macro;
      leaf ca-value {
        type string;
      }
    }
  }

  grouping co-ordinate-elements {
    uses apply-group;
    uses apply-macro;
    leaf longitude {
      type uint16;
    }
    leaf lattitude {
      type uint16;
    }
  }

  grouping juniper-ospf-authentication {
    uses apply-group;
    uses apply-macro;
    choice choice-3 {
      leaf simple-password {
        type unreadable;
      }
      list md5 {
        key "name";
        ordered-by user;
        leaf name {
          type string;
        }
        leaf key {
          type unreadable;
        }
        leaf start-time {
          type time;
        }
      }
    }
  }

  grouping juniper-protocols-amt {
    uses apply-group;
    uses apply-macro;
    container traceoptions {
      uses apply-group;
      uses apply-macro;
      container file {
        presence "";
        uses trace-file-type;
      }
      list flag {
        key "name";
        ordered-by user;
        leaf name {
          type string;
        }
        leaf send {
          type empty;
        }
        leaf receive {
          type empty;
        }
        leaf detail {
          type empty;
        }
        leaf disable {
          type empty;
        }
      }
    }
    container relay {
      presence "enable relay";
      uses juniper-protocols-amt-relay;
    }
  }

  grouping juniper-protocols-amt-relay {
    uses apply-group;
    uses apply-macro;
    container family {
      presence "enable family";
      uses apply-group;
      uses apply-macro;
      container inet {
        presence "enable inet";
        uses apply-group;
        uses apply-macro;
        leaf anycast-prefix {
          type ipv4prefix;
        }
        leaf local-address {
          type ipv4addr;
        }
      }
    }
    leaf secret-key-timeout {
      type uint32;
    }
    leaf tunnel-limit {
      type uint32;
    }
    leaf accounting {
      type empty;
    }
  }

  grouping juniper-protocols-bd {
    uses apply-group;
    uses apply-macro;
    container mac-table-size {
      presence "enable mac-table-size";
      uses apply-group;
      uses apply-macro;
      leaf limit {
        type uint32;
      }
      leaf packet-action {
        type string;
      }
    }
    container interface-mac-limit {
      presence "enable interface-mac-limit";
      uses apply-group;
      uses apply-macro;
      leaf limit {
        type uint32;
      }
      leaf packet-action {
        type string;
      }
    }
    leaf mac-table-aging-time {
      type uint32;
    }
    leaf no-mac-learning {
      type empty;
    }
    leaf mac-statistics {
      type empty;
    }
    list interface {
      key "name";
      ordered-by user;
      leaf name {
        type interface-name;
      }
      uses apply-group;
      uses apply-macro;
      container interface-mac-limit {
        presence "enable interface-mac-limit";
        uses apply-group;
        uses apply-macro;
        leaf limit {
          type uint32;
        }
        leaf packet-action {
          type string;
        }
      }
      leaf remote-site-id {
        type uint32;
      }
      list static-mac {
        key "name";
        ordered-by user;
        leaf name {
          type mac-addr;
        }
        uses apply-group;
        uses apply-macro;
        list vlan-id {
          key "name";
          ordered-by user;
          leaf name {
            type string;
          }
          uses apply-group;
          uses apply-macro;
        }
      }
      container interface-mac-ip-limit {
        uses apply-group;
        uses apply-macro;
        leaf limit {
          type uint32;
        }
      }
      leaf no-mac-learning {
        type empty;
      }
      leaf mac-pinning {
        type empty;
      }
      leaf description {
        type string;
      }
      leaf persistent-learning {
        type empty;
      }
    }
  }

  grouping juniper-protocols-bgp {
    uses apply-group;
    uses apply-macro;
    leaf disable {
      type empty;
    }
    leaf enable-disable {
      type string;
    }
    leaf precision-timers {
      type empty;
    }
    leaf no-precision-timers {
      type empty;
    }
    container path-selection {
      uses apply-group;
      uses apply-macro;
      leaf l2vpn-use-bgp-rules {
        type empty;
      }
      leaf cisco-non-deterministic {
        type empty;
      }
      leaf always-compare-med {
        type empty;
      }
      container med-plus-igp {
        presence "enable med-plus-igp";
        uses apply-group;
        uses apply-macro;
        leaf med-multiplier {
          type uint16;
        }
        leaf igp-multiplier {
          type uint16;
        }
      }
      leaf external-router-id {
        type empty;
      }
      leaf as-path-ignore {
        type empty;
      }
    }
    container snmp-options {
      uses apply-group;
      uses apply-macro;
      leaf backward-traps-only-from-established {
        type empty;
      }
      leaf emit-inet-address-length-in-oid {
        type empty;
      }
    }
    leaf advertise-from-main-vpn-tables {
      type empty;
    }
    leaf stale-labels-holddown-period {
      type int32;
    }
    leaf holddown-all-stale-labels {
      type empty;
    }
    container egress-te-backup-paths {
      uses apply-group;
      uses apply-macro;
      list template {
        key "name";
        leaf name {
          type string;
        }
        uses apply-group;
        uses apply-macro;
        list peer {
          key "name";
          ordered-by user;
          leaf name {
            type ipaddr;
          }
          uses apply-group;
          uses apply-macro;
        }
        container remote-nexthop {
          presence "";
          uses apply-group;
          uses apply-macro;
          leaf remote-nh-addr {
            mandatory true;
            type ipaddr;
          }
        }
        container ip-forward {
          presence "enable ip-forward";
          uses apply-group;
          uses apply-macro;
          leaf rti-name {
            type string;
          }
        }
      }
    }
    leaf sr-preference-override {
      type uint32;
    }
    leaf route-age-bgp-view {
      type empty;
    }
    leaf prioritize-route-queueing {
      type empty;
    }
    container traceoptions {
      uses apply-group;
      uses apply-macro;
      container file {
        presence "";
        uses trace-file-type;
      }
      list flag {
        key "name";
        ordered-by user;
        leaf name {
          type string;
        }
        leaf send {
          type empty;
        }
        leaf receive {
          type empty;
        }
        leaf detail {
          type empty;
        }
        leaf disable {
          type empty;
        }
        container filter {
          presence "";
          uses bgp-filter-obj;
        }
      }
    }
    leaf description {
      type string;
    }
    container metric-out {
      choice choice-3 {
        leaf metric-value {
          type uint32;
        }
        container minimum-igp {
          presence "enable minimum-igp";
          leaf metric-offset {
            type int32;
          }
        }
        container igp {
          presence "enable igp";
          leaf metric-offset {
            type int32;
          }
          leaf delay-med-update {
            type empty;
          }
        }
      }
    }
    container multihop {
      presence "enable multihop";
      uses apply-group;
      uses apply-macro;
      leaf ttl {
        type uint8;
      }
      leaf no-nexthop-change {
        type empty;
      }
    }
    leaf route-server-client {
      type empty;
    }
    leaf accept-remote-nexthop {
      type empty;
    }
    leaf preference {
      type uint32;
    }
    leaf local-preference {
      type uint32;
    }
    leaf local-address {
      type ipaddr;
    }
    leaf local-interface {
      type interface-name;
    }
    leaf forwarding-context {
      type string;
    }
    leaf hold-time {
      type uint32;
    }
    leaf passive {
      type empty;
    }
    leaf advertise-inactive {
      type empty;
    }
    leaf advertise-peer-as {
      type empty;
    }
    leaf no-advertise-peer-as {
      type empty;
    }
    container advertise-external {
      presence "enable advertise-external";
      leaf conditional {
        type empty;
      }
    }
    leaf keep {
      type string;
    }
    leaf rfc6514-compliant-safi129 {
      type empty;
    }
    leaf no-aggregator-id {
      type empty;
    }
    leaf mtu-discovery {
      type empty;
    }
    leaf enforce-first-as {
      type empty;
    }
    leaf out-delay {
      type uint32;
    }
    leaf ttl {
      type string;
    }
    leaf log-updown {
      type empty;
    }
    leaf damping {
      type empty;
    }
    leaf-list import {
      type policy-algebra;
      ordered-by user;
    }
    leaf-list nlri {
      ordered-by user;
      type string;
    }
    container bgp-error-tolerance {
      presence "enable bgp-error-tolerance";
      uses apply-group;
      uses apply-macro;
      leaf malformed-update-log-interval {
        units "seconds";
        type uint32;
      }
      choice choice-malformed-route-limit {
        leaf malformed-route-limit {
          type uint32;
        }
        leaf no-malformed-route-limit {
          type empty;
        }
      }
    }
    container family {
      uses apply-group;
      uses apply-macro;
      container inet {
        uses apply-group;
        uses apply-macro;
        container unicast {
          presence "enable unicast";
          uses bgp-afi-topo;
        }
        container multicast {
          presence "enable multicast";
          uses bgp-afi-default;
        }
        container flow {
          presence "enable flow";
          uses bgp-afi-flow;
        }
        container any {
          presence "enable any";
          uses bgp-afi-default;
        }
        container labeled-unicast {
          presence "enable labeled-unicast";
          uses bgp-afi-labeled;
        }
        container segment-routing-te {
          presence "enable segment-routing-te";
          uses bgp-afi-srte;
        }
      }
      container inet-vpn {
        uses apply-group;
        uses apply-macro;
        container unicast {
          presence "enable unicast";
          uses bgp-afi-vpn;
        }
        container multicast {
          presence "enable multicast";
          uses bgp-afi-vpn;
        }
        container flow {
          presence "enable flow";
          uses bgp-afi-default;
        }
        container any {
          presence "enable any";
          uses bgp-afi-vpn;
        }
      }
      container inet6 {
        uses apply-group;
        uses apply-macro;
        container unicast {
          presence "enable unicast";
          uses bgp-afi-topo;
        }
        container multicast {
          presence "enable multicast";
          uses bgp-afi-default;
        }
        container flow {
          presence "enable flow";
          uses bgp-afi-flow;
        }
        container any {
          presence "enable any";
          uses bgp-afi-default;
        }
        container labeled-unicast {
          presence "";
          uses bgp-afi-inet6-labeled;
        }
        container segment-routing-te {
          presence "enable segment-routing-te";
          uses bgp-afi-srte;
        }
      }
      container inet6-vpn {
        uses apply-group;
        uses apply-macro;
        container unicast {
          presence "enable unicast";
          uses bgp-afi-vpn;
        }
        container multicast {
          presence "enable multicast";
          uses bgp-afi-vpn;
        }
        container flow {
          presence "enable flow";
          uses bgp-afi-flow;
        }
        container any {
          presence "enable any";
          uses bgp-afi-vpn;
        }
      }
      container iso-vpn {
        uses apply-group;
        uses apply-macro;
        container unicast {
          presence "enable unicast";
          uses bgp-afi-vpn;
        }
      }
      container l2vpn {
        uses apply-group;
        uses apply-macro;
        container auto-discovery-only {
          presence "enable auto-discovery-only";
          uses bgp-afi-default;
        }
        container signaling {
          presence "enable signaling";
          uses bgp-afi-l2vpn;
        }
      }
      container evpn {
        uses apply-group;
        container signaling {
          presence "enable signaling";
          uses bgp-afi-default;
        }
      }
      container inet-mvpn {
        uses apply-group;
        uses apply-macro;
        container signaling {
          presence "enable signaling";
          uses bgp-afi-default;
        }
      }
      container inet6-mvpn {
        uses apply-group;
        uses apply-macro;
        container signaling {
          presence "enable signaling";
          uses bgp-afi-default;
        }
      }
      container inet-mdt {
        uses apply-group;
        uses apply-macro;
        container signaling {
          presence "enable signaling";
          uses bgp-afi-default;
        }
      }
      container traffic-engineering {
        uses apply-group;
        uses apply-macro;
        container unicast {
          presence "enable unicast";
          uses bgp-afi-default;
        }
      }
      container route-target {
        presence "enable route-target";
        uses apply-group;
        uses apply-macro;
        container prefix-limit {
          presence "";
          uses bgpaf-prefix-limit;
        }
        container accepted-prefix-limit {
          presence "";
          uses bgpaf-accepted-prefix-limit;
        }
        leaf external-paths {
          type uint32;
        }
        leaf advertise-default {
          type empty;
        }
        leaf damping {
          type empty;
        }
      }
      container bridge-vpn {
        uses apply-group;
        uses apply-macro;
        container unicast {
          presence "enable unicast";
          uses bgp-afi-vpn;
        }
      }
      container fabric-vpn {
        uses apply-group;
        uses apply-macro;
        container unicast {
          presence "enable unicast";
          uses bgp-afi-vpn;
        }
      }
    }
    leaf authentication-key {
      type unreadable;
    }
    leaf authentication-algorithm {
      type string;
    }
    leaf authentication-key-chain {
      type string;
    }
    leaf-list export {
      type policy-algebra;
      ordered-by user;
    }
    leaf vpn-apply-export {
      type empty;
    }
    container remove-private {
      presence "enable remove-private";
      container all {
        presence "enable all";
        container replace {
          presence "enable replace";
          leaf nearest {
            type empty;
          }
        }
      }
    }
    leaf cluster {
      type areaid;
    }
    leaf no-client-reflect {
      type empty;
    }
    leaf peer-as {
      type string;
    }
    container local-as {
      presence "";
      leaf as-number {
        type string;
      }
      leaf loops {
        type int32;
      }
      leaf private {
        type empty;
      }
      leaf alias {
        type empty;
      }
      leaf no-prepend-global-as {
        type empty;
      }
    }
    leaf ipsec-sa {
      type string;
    }
    leaf unconfigured-peer-graceful-restart {
      type empty;
    }
    container graceful-restart {
      presence "enable graceful-restart";
      uses apply-group;
      uses apply-macro;
      choice choice-3 {
        leaf disable {
          type empty;
        }
      }
      leaf restart-time {
        type uint32;
      }
      leaf stale-routes-time {
        type uint32;
      }
      container long-lived {
        uses apply-group;
        uses apply-macro;
        container receiver {
          uses apply-group;
          uses apply-macro;
          leaf enable-disable {
            type string;
          }
        }
        container advertise-to-non-llgr-neighbor {
          presence "enable advertise-to-non-llgr-neighbor";
          uses apply-group;
          uses apply-macro;
          leaf omit-no-export {
            type empty;
          }
        }
      }
      leaf disable-notification-extensions {
        type empty;
      }
      leaf forwarding-state-bit {
        type string;
      }
    }
    leaf include-mp-next-hop {
      type empty;
    }
    container idle-after-switch-over {
      choice choice-3 {
        leaf forever {
          type empty;
        }
        leaf timeout {
          type uint32;
        }
      }
    }
    container outbound-route-filter {
      uses apply-group;
      uses apply-macro;
      leaf bgp-orf-cisco-mode {
        type empty;
      }
      container prefix-based {
        presence "enable prefix-based";
        uses apply-group;
        uses apply-macro;
        container accept {
          presence "enable accept";
          uses apply-group;
          uses apply-macro;
          leaf inet {
            type empty;
          }
          leaf inet6 {
            type empty;
          }
        }
      }
    }
    container message-batching {
      uses apply-group;
      uses apply-macro;
      leaf enable-disable {
        type string;
      }
      leaf interval {
        units "milliseconds";
        type uint32;
      }
    }
    container multipath {
      presence "enable multipath";
      uses apply-group;
      uses apply-macro;
      leaf disable {
        type empty;
      }
      leaf multiple-as {
        type empty;
      }
      leaf allow-protection {
        type empty;
      }
      leaf pause-computation-during-churn {
        type empty;
      }
      leaf list-nexthop {
        type empty;
      }
      container allow-external-internal {
        presence "enable allow-external-internal";
        uses apply-advanced;
        leaf-list prefix-policy {
          ordered-by user;
          type policy-algebra;
        }
      }
    }
    leaf tcp-mss {
      type uint32;
    }
    leaf bgp-identifier {
      type ipv4addr;
    }
    leaf tcp-aggressive-transmission {
      type empty;
    }
    container bmp {
      uses apply-group;
      uses apply-macro;
      leaf monitor {
        type string;
      }
      container route-monitoring {
        uses apply-group;
        uses apply-macro;
        leaf none {
          type empty;
        }
        container pre-policy {
          presence "enable pre-policy";
          leaf exclude-non-feasible {
            type empty;
          }
        }
        container post-policy {
          presence "enable post-policy";
          leaf exclude-non-eligible {
            type empty;
          }
        }
      }
    }
    container advertise-bgp-static {
      presence "enable advertise-bgp-static";
      uses apply-group;
      uses apply-macro;
      leaf-list policy {
        type policy-algebra;
        ordered-by user;
      }
    }
    container bfd-liveness-detection {
      uses apply-group;
      uses apply-macro;
      leaf version {
        type string;
      }
      leaf minimum-interval {
        type uint32;
      }
      leaf minimum-receive-interval {
        type uint32;
      }
      leaf multiplier {
        type uint32;
      }
      choice choice-11 {
        leaf no-adaptation {
          type empty;
        }
      }
      container transmit-interval {
        uses apply-group;
        uses apply-macro;
        leaf minimum-interval {
          type uint32;
        }
        leaf threshold {
          type uint32;
        }
      }
      container detection-time {
        uses apply-group;
        uses apply-macro;
        leaf threshold {
          type uint32;
        }
      }
      container authentication {
        uses apply-group;
        uses apply-macro;
        leaf key-chain {
          type string;
        }
        leaf algorithm {
          type string;
        }
        leaf loose-check {
          type empty;
        }
      }
      leaf session-mode {
        type string;
      }
      leaf holddown-interval {
        type uint32;
      }
    }
    list group {
      key "name";
      ordered-by user;
      leaf name {
        type string;
      }
      container undocumented {
        leaf rfc6514-compliant-safi129 {
          type empty;
        }
        uses undocumented-disable-4byte-as;
        leaf mvpn-iana-rt-import {
          type empty;
        }
        leaf drop-path-attributes {
          type string;
        }
      }
      uses apply-group;
      uses apply-macro;
      leaf type {
        type string;
      }
      leaf protocol {
        type string;
      }
      container traceoptions {
        uses apply-group;
        uses apply-macro;
        container file {
          presence "";
          uses trace-file-type;
        }
        list flag {
          key "name";
          ordered-by user;
          leaf name {
            type string;
          }
          leaf send {
            type empty;
          }
          leaf receive {
            type empty;
          }
          leaf detail {
            type empty;
          }
          leaf disable {
            type empty;
          }
          container filter {
            presence "";
            uses bgp-filter-obj;
          }
        }
      }
      leaf description {
        type string;
      }
      container metric-out {
        choice choice-3 {
          leaf metric-value {
            type uint32;
          }
          container minimum-igp {
            presence "enable minimum-igp";
            leaf metric-offset {
              type int32;
            }
          }
          container igp {
            presence "enable igp";
            leaf metric-offset {
              type int32;
            }
            leaf delay-med-update {
              type empty;
            }
          }
          container effective-aigp {
            presence "enable effective-aigp";
            leaf metric-offset {
              type string;
            }
          }
          container minimum-effective-aigp {
            presence "enable minimum-effective-aigp";
            leaf metric-offset {
              type string;
            }
          }
        }
      }
      container multihop {
        presence "enable multihop";
        uses apply-group;
        uses apply-macro;
        leaf ttl {
          type uint8;
        }
        leaf no-nexthop-change {
          type empty;
        }
      }
      container ebgp-community-cleanup {
        presence "enable ebgp-community-cleanup";
        uses apply-advanced;
        leaf origin-validation {
          type string;
        }
      }
      leaf route-server-client {
        type empty;
      }
      leaf accept-remote-nexthop {
        type empty;
      }
      leaf preference {
        type uint32;
      }
      leaf local-preference {
        type uint32;
      }
      leaf local-address {
        type ipaddr;
      }
      leaf local-interface {
        type interface-name;
      }
      leaf forwarding-context {
        type string;
      }
      leaf hold-time {
        type uint32;
      }
      leaf minimum-hold-time {
        type string;
      }
      leaf passive {
        type empty;
      }
      leaf advertise-inactive {
        type empty;
      }
      choice advertise-peer-as-choice {
        leaf advertise-peer-as {
          type empty;
        }
        leaf no-advertise-peer-as {
          type empty;
        }
      }
      container advertise-external {
        presence "enable advertise-external";
        leaf conditional {
          type empty;
        }
      }
      leaf keep {
        type string;
      }
      leaf rfc6514-compliant-safi129 {
        type empty;
      }
      leaf no-aggregator-id {
        type empty;
      }
      leaf mtu-discovery {
        type empty;
      }
      leaf enforce-first-as {
        type empty;
      }
      leaf out-delay {
        type uint32;
      }
      leaf ttl {
        type string;
      }
      leaf log-updown {
        type empty;
      }
      leaf damping {
        type empty;
      }
      leaf-list import {
        type policy-algebra;
        ordered-by user;
      }
      leaf-list nlri {
        ordered-by user;
        type string;
      }
      container bgp-error-tolerance {
        presence "enable bgp-error-tolerance";
        uses apply-group;
        uses apply-macro;
        leaf malformed-update-log-interval {
          units "seconds";
          type uint32;
        }
        choice choice-malformed-route-limit {
          leaf malformed-route-limit {
            type uint32;
          }
          leaf no-malformed-route-limit {
            type empty;
          }
        }
      }
      container family {
        uses apply-group;
        uses apply-macro;
        container inet {
          uses apply-group;
          uses apply-macro;
          container unicast {
            presence "enable unicast";
            uses bgp-afi-topo;
          }
          container multicast {
            presence "enable multicast";
            uses bgp-afi-default;
          }
          container flow {
            presence "enable flow";
            uses bgp-afi-flow;
          }
          container any {
            presence "enable any";
            uses bgp-afi-default;
          }
          container labeled-unicast {
            presence "enable labeled-unicast";
            uses bgp-afi-labeled;
          }
          container segment-routing-te {
            presence "enable segment-routing-te";
            uses bgp-afi-srte;
          }
        }
        container inet-vpn {
          uses apply-group;
          uses apply-macro;
          container unicast {
            presence "enable unicast";
            uses bgp-afi-vpn;
          }
          container multicast {
            presence "enable multicast";
            uses bgp-afi-vpn;
          }
          container flow {
            presence "enable flow";
            uses bgp-afi-flow;
          }
          container any {
            presence "enable any";
            uses bgp-afi-vpn;
          }
        }
        container inet6 {
          uses apply-group;
          uses apply-macro;
          container unicast {
            presence "enable unicast";
            uses bgp-afi-topo;
          }
          container multicast {
            presence "enable multicast";
            uses bgp-afi-default;
          }
          container flow {
            presence "enable flow";
            uses bgp-afi-flow;
          }
          container any {
            presence "enable any";
            uses bgp-afi-default;
          }
          container labeled-unicast {
            presence "";
            uses bgp-afi-inet6-labeled;
          }
          container segment-routing-te {
            presence "enable segment-routing-te";
            uses bgp-afi-srte;
          }
        }
        container inet6-vpn {
          uses apply-group;
          uses apply-macro;
          container unicast {
            presence "enable unicast";
            uses bgp-afi-vpn;
          }
          container multicast {
            presence "enable multicast";
            uses bgp-afi-vpn;
          }
          container flow {
            presence "enable flow";
            uses bgp-afi-flow;
          }
          container any {
            presence "enable any";
            uses bgp-afi-vpn;
          }
        }
        container iso-vpn {
          uses apply-group;
          uses apply-macro;
          container unicast {
            presence "enable unicast";
            uses bgp-afi-vpn;
          }
        }
        container l2vpn {
          uses apply-group;
          uses apply-macro;
          container auto-discovery-only {
            presence "enable auto-discovery-only";
            uses bgp-afi-default;
          }
          container signaling {
            presence "enable signaling";
            uses bgp-afi-l2vpn;
          }
        }
        container evpn {
          uses apply-group;
          uses apply-macro;
          container signaling {
            presence "enable signaling";
            uses bgp-afi-default;
          }
        }
        container inet-mvpn {
          uses apply-group;
          uses apply-macro;
          container signaling {
            presence "enable signaling";
            uses bgp-afi-default;
          }
        }
        container inet6-mvpn {
          uses apply-group;
          uses apply-macro;
          container signaling {
            presence "enable signaling";
            uses bgp-afi-default;
          }
        }
        container inet-mdt {
          uses apply-group;
          uses apply-macro;
          container signaling {
            presence "enable signaling";
            uses bgp-afi-default;
          }
        }
        container traffic-engineering {
          uses apply-group;
          uses apply-macro;
          container unicast {
            presence "enable unicast";
            uses bgp-afi-default;
          }
        }
        container route-target {
          presence "enable route-target";
          uses apply-group;
          uses apply-macro;
          container prefix-limit {
            presence "";
            uses bgpaf-prefix-limit;
          }
          container accepted-prefix-limit {
            presence "";
            uses bgpaf-accepted-prefix-limit;
          }
          container proxy-generate {
            presence "enable proxy-generate";
            uses apply-advanced;
            leaf-list route-target-policy {
              ordered-by user;
              type policy-algebra;
            }
          }
          leaf external-paths {
            type uint32;
          }
          leaf advertise-default {
            type empty;
          }
          leaf damping {
            type empty;
          }
          container graceful-restart {
            uses bgp-af-gr;
          }
          leaf local-ipv4-address {
            type ipv4addr;
          }
          container nexthop-resolution {
            uses apply-advanced;
            leaf no-resolution {
              type empty;
            }
          }
          container output-queue-priority {
            uses bgp-output-queue-priority-class;
          }
          container route-refresh-priority {
            uses bgp-output-queue-priority-class;
          }
          container withdraw-priority {
            uses bgp-output-queue-priority-class;
          }
        }
        container bridge-vpn {
          uses apply-group;
          uses apply-macro;
          container unicast {
            presence "enable unicast";
            uses bgp-afi-vpn;
          }
        }
        container fabric-vpn {
          uses apply-group;
          uses apply-macro;
          container unicast {
            presence "enable unicast";
            uses bgp-afi-vpn;
          }
        }
      }
      leaf authentication-key {
        type unreadable;
      }
      leaf authentication-algorithm {
        type string;
      }
      leaf tcpao-auth-mismatch {
        type string;
      }
      leaf authentication-key-chain {
        type string;
      }
      leaf-list export {
        type policy-algebra;
        ordered-by user;
      }
      leaf vpn-apply-export {
        type empty;
      }
      container remove-private {
        presence "enable remove-private";
        container all {
          presence "enable all";
          container replace {
            presence "enable replace";
            leaf nearest {
              type empty;
            }
          }
        }
      }
      leaf cluster {
        type areaid;
      }
      leaf no-client-reflect {
        type empty;
      }
      leaf peer-as {
        type string;
      }
      container local-as {
        presence "";
        leaf as-number {
          type string;
        }
        leaf loops {
          type int32;
        }
        leaf private {
          type empty;
        }
        leaf alias {
          type empty;
        }
        leaf no-prepend-global-as {
          type empty;
        }
      }
      container graceful-shutdown {
        uses apply-group;
        uses apply-macro;
        container receiver {
          presence "enable receiver";
          uses apply-group;
          uses apply-macro;
          leaf disable {
            type empty;
          }
          leaf local-preference {
            type uint32;
          }
        }
        container sender {
          presence "enable sender";
          uses apply-group;
          uses apply-macro;
          leaf local-preference {
            type uint32;
          }
        }
      }
      container shutdown {
        presence "enable shutdown";
        uses apply-advanced;
        leaf notify-message {
          type string;
        }
      }
      leaf ipsec-sa {
        type string;
      }
      leaf unconfigured-peer-graceful-restart {
        type empty;
      }
      container graceful-restart {
        presence "enable graceful-restart";
        uses apply-group;
        uses apply-macro;
        choice choice-3 {
          leaf disable {
            type empty;
          }
        }
        leaf enable-disable {
          type string;
        }
        leaf restart-time {
          type uint32;
        }
        leaf stale-routes-time {
          type uint32;
        }
        container long-lived {
          uses apply-group;
          uses apply-macro;
          container receiver {
            uses apply-group;
            uses apply-macro;
            leaf enable-disable {
              type string;
            }
            leaf disable {
              type empty;
            }
          }
          container advertise-to-non-llgr-neighbor {
            presence "enable advertise-to-non-llgr-neighbor";
            uses apply-group;
            uses apply-macro;
            leaf omit-no-export {
              type empty;
            }
          }
        }
        leaf disable-notification-extensions {
          type empty;
        }
        leaf forwarding-state-bit {
          type string;
        }
        leaf dont-help-shared-fate-bfd-down {
          type empty;
        }
      }
      leaf include-mp-next-hop {
        type empty;
      }
      leaf disable-4byte-as {
        type empty;
      }
      container idle-after-switch-over {
        choice choice-3 {
          leaf forever {
            type empty;
          }
          leaf timeout {
            type uint32;
          }
        }
      }
      container outbound-route-filter {
        uses apply-group;
        uses apply-macro;
        leaf bgp-orf-cisco-mode {
          type empty;
        }
        container prefix-based {
          presence "enable prefix-based";
          uses apply-group;
          uses apply-macro;
          container accept {
            presence "enable accept";
            uses apply-group;
            uses apply-macro;
            leaf inet {
              type empty;
            }
            leaf inet6 {
              type empty;
            }
          }
        }
      }
      leaf tcp-mss {
        type uint32;
      }
      leaf tcp-aggressive-transmission {
        type empty;
      }
      container bmp {
        uses apply-group;
        uses apply-macro;
        leaf monitor {
          type string;
        }
        container route-monitoring {
          uses apply-group;
          uses apply-macro;
          leaf none {
            type empty;
          }
          container pre-policy {
            presence "enable pre-policy";
            leaf exclude-non-feasible {
              type empty;
            }
          }
          container post-policy {
            presence "enable post-policy";
            leaf exclude-non-eligible {
              type empty;
            }
          }
        }
      }
      container bfd-liveness-detection {
        uses apply-group;
        uses apply-macro;
        leaf version {
          type string;
        }
        leaf minimum-interval {
          type uint32;
        }
        leaf minimum-receive-interval {
          type uint32;
        }
        leaf multiplier {
          type uint32;
        }
        choice choice-11 {
          leaf no-adaptation {
            type empty;
          }
        }
        container transmit-interval {
          uses apply-group;
          uses apply-macro;
          leaf minimum-interval {
            type uint32;
          }
          leaf threshold {
            type uint32;
          }
        }
        container detection-time {
          uses apply-group;
          uses apply-macro;
          leaf threshold {
            type uint32;
          }
        }
        container authentication {
          uses apply-group;
          uses apply-macro;
          leaf key-chain {
            type string;
          }
          leaf algorithm {
            type string;
          }
          leaf loose-check {
            type empty;
          }
        }
        leaf session-mode {
          type string;
        }
        leaf holddown-interval {
          type uint32;
        }
      }
      container multipath {
        presence "enable multipath";
        leaf multiple-as {
          type empty;
        }
      }
      leaf as-override {
        type empty;
      }
      container egress-te {
        presence "enable egress-te";
        uses apply-advanced;
        leaf install-address {
          type ipaddr;
        }
        container rib {
          uses apply-advanced;
          leaf inet.0 {
            type empty;
          }
          leaf inet6.0 {
            type empty;
          }
        }
        leaf no-install {
          type empty;
        }
        leaf-list import {
          ordered-by user;
          type policy-algebra;
        }
        leaf backup-path {
          type string;
        }
      }
      leaf-list allow {
        type ipprefix;
        ordered-by user;
      }
      list dynamic-neighbor {
        key "name";
        ordered-by user;
        leaf name {
          type string;
        }
        uses apply-group;
        uses apply-macro;
        leaf-list allow {
          type ipprefix;
          ordered-by user;
        }
        leaf authentication-key {
          type unreadable;
        }
        leaf authentication-algorithm {
          type string;
        }
        leaf tcpao-handling-with-digest-mismatch {
          type string;
        }
        leaf authentication-key-chain {
          type string;
        }
        container peer-auto-discovery {
          uses apply-advanced;
          container family {
            container inet6 {
              uses apply-advanced;
              choice auto-discovery-type {
                case case_1 {
                  container ipv6-nd {
                    presence "enable ipv6-nd";
                  }
                }
              }
            }
          }
          list interface {
            key "name";
            leaf name {
              type string;
            }
            uses apply-advanced;
            choice enable-disable {
              case case_1 {
                leaf disable {
                  type empty;
                }
              }
            }
          }
        }
      }
      container optimal-route-reflection {
        uses apply-group;
        uses apply-macro;
        leaf igp-primary {
          type ipv4addr;
        }
        leaf igp-backup {
          type ipv4addr;
        }
      }
      leaf peer-as-list {
        type string;
      }
      leaf mvpn-iana-rt-import {
        type empty;
      }
      list neighbor {
        key "name";
        ordered-by user;
        leaf name {
          type ipaddr;
        }
        uses apply-group;
        uses apply-macro;
        container undocumented {
          uses undocumented-disable-4byte-as;
        }
        container traceoptions {
          uses apply-group;
          uses apply-macro;
          container file {
            presence "";
            uses trace-file-type;
          }
          list flag {
            key "name";
            ordered-by user;
            leaf name {
              type string;
            }
            leaf send {
              type empty;
            }
            leaf receive {
              type empty;
            }
            leaf detail {
              type empty;
            }
            leaf disable {
              type empty;
            }
            container filter {
              presence "";
              uses bgp-filter-obj;
            }
          }
        }
        leaf description {
          type string;
        }
        container metric-out {
          choice choice-3 {
            leaf metric-value {
              type uint32;
            }
            container minimum-igp {
              presence "enable minimum-igp";
              leaf metric-offset {
                type int32;
              }
            }
            container igp {
              presence "enable igp";
              leaf metric-offset {
                type int32;
              }
              leaf delay-med-update {
                type empty;
              }
            }
          }
        }
        container multihop {
          presence "enable multihop";
          uses apply-group;
          uses apply-macro;
          leaf ttl {
            type uint8;
          }
          leaf no-nexthop-change {
            type empty;
          }
        }
        leaf route-server-client {
          type empty;
        }
        leaf accept-remote-nexthop {
          type empty;
        }
        leaf preference {
          type uint32;
        }
        leaf local-preference {
          type uint32;
        }
        leaf local-address {
          type ipaddr;
        }
        leaf local-interface {
          type interface-name;
        }
        leaf forwarding-context {
          type string;
        }
        leaf hold-time {
          type uint32;
        }
        leaf minimum-hold-time {
          type uint32;
        }
        leaf passive {
          type empty;
        }
        leaf advertise-inactive {
          type empty;
        }
        leaf advertise-peer-as {
          type empty;
        }
        leaf no-advertise-peer-as {
          type empty;
        }
        container advertise-external {
          presence "enable advertise-external";
          leaf conditional {
            type empty;
          }
        }
        leaf keep {
          type string;
        }
        leaf rfc6514-compliant-safi129 {
          type empty;
        }
        leaf no-aggregator-id {
          type empty;
        }
        leaf mtu-discovery {
          type empty;
        }
        leaf enforce-first-as {
          type empty;
        }
        leaf out-delay {
          type uint32;
        }
        leaf ttl {
          type uint8;
        }
        leaf log-updown {
          type empty;
        }
        leaf damping {
          type empty;
        }
        leaf-list import {
          type policy-algebra;
          ordered-by user;
        }
        leaf-list nlri {
          ordered-by user;
          type string;
        }
        container bgp-error-tolerance {
          presence "enable bgp-error-tolerance";
          uses apply-group;
          uses apply-macro;
          leaf malformed-update-log-interval {
            units "seconds";
            type uint32;
          }
          choice choice-malformed-route-limit {
            leaf malformed-route-limit {
              type uint32;
            }
            leaf no-malformed-route-limit {
              type empty;
            }
          }
        }
        container family {
          uses apply-group;
          uses apply-macro;
          container inet {
            uses apply-group;
            uses apply-macro;
            container unicast {
              presence "enable unicast";
              uses bgp-afi-topo;
            }
            container multicast {
              presence "enable multicast";
              uses bgp-afi-default;
            }
            container flow {
              presence "enable flow";
              uses bgp-afi-flow;
            }
            container any {
              presence "enable any";
              uses bgp-afi-default;
            }
            container labeled-unicast {
              presence "enable labeled-unicast";
              uses bgp-afi-labeled;
            }
          }
          container inet-vpn {
            uses apply-group;
            uses apply-macro;
            container unicast {
              presence "enable unicast";
              uses bgp-afi-vpn;
            }
            container multicast {
              presence "enable multicast";
              uses bgp-afi-vpn;
            }
            container flow {
              presence "enable flow";
              uses bgp-afi-default;
            }
            container any {
              presence "enable any";
              uses bgp-afi-vpn;
            }
          }
          container inet6 {
            uses apply-group;
            uses apply-macro;
            container unicast {
              presence "enable unicast";
              uses bgp-afi-topo;
            }
            container multicast {
              presence "enable multicast";
              uses bgp-afi-default;
            }
            container any {
              presence "enable any";
              uses bgp-afi-default;
            }
            container labeled-unicast {
              presence "";
              uses bgp-afi-inet6-labeled;
            }
          }
          container inet6-vpn {
            uses apply-group;
            uses apply-macro;
            container unicast {
              presence "enable unicast";
              uses bgp-afi-vpn;
            }
            container multicast {
              presence "enable multicast";
              uses bgp-afi-vpn;
            }
            container flow {
              presence "enable flow";
              uses bgp-afi-flow;
            }
            container any {
              presence "enable any";
              uses bgp-afi-vpn;
            }
          }
          container iso-vpn {
            uses apply-group;
            uses apply-macro;
            container unicast {
              presence "enable unicast";
              uses bgp-afi-vpn;
            }
          }
          container l2vpn {
            uses apply-group;
            uses apply-macro;
            container auto-discovery-only {
              presence "enable auto-discovery-only";
              uses bgp-afi-default;
            }
            container signaling {
              presence "enable signaling";
              uses bgp-afi-l2vpn;
            }
          }
          container evpn {
            uses apply-group;
            uses apply-macro;
            container signaling {
              presence "enable signaling";
              uses bgp-afi-default;
            }
          }
          container inet-mvpn {
            uses apply-group;
            uses apply-macro;
            container signaling {
              presence "enable signaling";
              uses bgp-afi-default;
            }
          }
          container inet6-mvpn {
            uses apply-group;
            uses apply-macro;
            container signaling {
              presence "enable signaling";
              uses bgp-afi-default;
            }
          }
          container inet-mdt {
            uses apply-group;
            uses apply-macro;
            container signaling {
              presence "enable signaling";
              uses bgp-afi-default;
            }
          }
          container traffic-engineering {
            uses apply-group;
            uses apply-macro;
            container unicast {
              presence "enable unicast";
              uses bgp-afi-default;
            }
          }
          container route-target {
            presence "enable route-target";
            uses apply-group;
            uses apply-macro;
            container prefix-limit {
              presence "";
              uses bgpaf-prefix-limit;
            }
            container accepted-prefix-limit {
              presence "";
              uses bgpaf-accepted-prefix-limit;
            }
            container proxy-generate {
              presence "enable proxy-generate";
              uses apply-advanced;
              leaf-list route-target-policy {
                ordered-by user;
                type policy-algebra;
              }
            }
            leaf external-paths {
              type uint32;
            }
            leaf advertise-default {
              type empty;
            }
          }
          container bridge-vpn {
            uses apply-group;
            uses apply-macro;
            container unicast {
              presence "enable unicast";
              uses bgp-afi-vpn;
            }
          }
          container fabric-vpn {
            uses apply-group;
            uses apply-macro;
            container unicast {
              presence "enable unicast";
              uses bgp-afi-vpn;
            }
          }
        }
        leaf authentication-key {
          type unreadable;
        }
        leaf authentication-algorithm {
          type string;
        }
        leaf authentication-key-chain {
          type string;
        }
        leaf-list export {
          type policy-algebra;
          ordered-by user;
        }
        container remove-private {
          presence "enable remove-private";
          container all {
            presence "enable all";
            container replace {
              presence "enable replace";
              leaf nearest {
                type empty;
              }
            }
          }
        }
        leaf cluster {
          type areaid;
        }
        leaf no-client-reflect {
          type empty;
        }
        leaf peer-as {
          type string;
        }
        container local-as {
          presence "";
          leaf as-number {
            type string;
          }
          leaf loops {
            type int32;
          }
          leaf private {
            type empty;
          }
          leaf alias {
            type empty;
          }
          leaf no-prepend-global-as {
            type empty;
          }
        }
        leaf ipsec-sa {
          type string;
        }
        container graceful-shutdown {
          uses apply-group;
          uses apply-macro;
          container receiver {
            presence "enable receiver";
            uses apply-group;
            uses apply-macro;
            leaf disable {
              type empty;
            }
            leaf local-preference {
              type uint32;
            }
          }
          container sender {
            presence "enable sender";
            uses apply-group;
            uses apply-macro;
            leaf local-preference {
              type uint32;
            }
          }
        }
        container shutdown {
          presence "enable shutdown";
          uses apply-group;
          uses apply-macro;
          leaf notify-message {
            type string;
          }
        }
        leaf unconfigured-peer-graceful-restart {
          type empty;
        }
        container graceful-restart {
          presence "enable graceful-restart";
          uses apply-group;
          uses apply-macro;
          choice choice-3 {
            leaf disable {
              type empty;
            }
          }
          leaf restart-time {
            type uint32;
          }
          leaf stale-routes-time {
            type uint32;
          }
          container long-lived {
            uses apply-group;
            uses apply-macro;
            container receiver {
              uses apply-group;
              uses apply-macro;
              leaf enable-disable {
                type string;
              }
              leaf disable {
                type empty;
              }
            }
            container advertise-to-non-llgr-neighbor {
              presence "enable advertise-to-non-llgr-neighbor";
              uses apply-group;
              uses apply-macro;
              leaf omit-no-export {
                type empty;
              }
            }
          }
          leaf disable-notification-extensions {
            type empty;
          }
          leaf forwarding-state-bit {
            type string;
          }
          leaf dont-help-shared-fate-bfd-down {
            type empty;
          }
        }
        leaf include-mp-next-hop {
          type empty;
        }
        leaf disable-4byte-as {
          type empty;
        }
        container idle-after-switch-over {
          choice choice-3 {
            leaf forever {
              type empty;
            }
            leaf timeout {
              type uint32;
            }
          }
        }
        container outbound-route-filter {
          uses apply-group;
          uses apply-macro;
          leaf bgp-orf-cisco-mode {
            type empty;
          }
          container prefix-based {
            presence "enable prefix-based";
            uses apply-group;
            uses apply-macro;
            container accept {
              presence "enable accept";
              uses apply-group;
              uses apply-macro;
              leaf inet {
                type empty;
              }
              leaf inet6 {
                type empty;
              }
            }
          }
        }
        container multipath {
          presence "enable multipath";
          uses apply-group;
          uses apply-macro;
          leaf disable {
            type empty;
          }
          leaf multiple-as {
            type empty;
          }
          leaf allow-protection {
            type empty;
          }
        }
        leaf tcp-mss {
          type uint32;
        }
        leaf tcp-aggressive-transmission {
          type empty;
        }
        container bmp {
          uses apply-group;
          uses apply-macro;
          leaf monitor {
            type string;
          }
          container route-monitoring {
            uses apply-group;
            uses apply-macro;
            leaf none {
              type empty;
            }
            container pre-policy {
              presence "enable pre-policy";
              leaf exclude-non-feasible {
                type empty;
              }
            }
            container post-policy {
              presence "enable post-policy";
              leaf exclude-non-eligible {
                type empty;
              }
            }
          }
        }
        container advertise-bgp-static {
          presence "enable advertise-bgp-static";
          uses apply-group;
          uses apply-macro;
          leaf-list policy {
            type policy-algebra;
            ordered-by user;
          }
        }
        leaf add-path-display-ipv4-address {
          type empty;
        }
        container bfd-liveness-detection {
          uses apply-group;
          uses apply-macro;
          leaf version {
            type string;
          }
          leaf minimum-interval {
            type uint32;
          }
          leaf minimum-receive-interval {
            type uint32;
          }
          leaf multiplier {
            type uint32;
          }
          choice choice-11 {
            leaf no-adaptation {
              type empty;
            }
          }
          container transmit-interval {
            uses apply-group;
            uses apply-macro;
            leaf minimum-interval {
              type uint32;
            }
            leaf threshold {
              type uint32;
            }
          }
          container detection-time {
            uses apply-group;
            uses apply-macro;
            leaf threshold {
              type uint32;
            }
          }
          container authentication {
            uses apply-group;
            uses apply-macro;
            leaf key-chain {
              type string;
            }
            leaf algorithm {
              type string;
            }
            leaf loose-check {
              type empty;
            }
          }
          leaf session-mode {
            type string;
          }
          leaf holddown-interval {
            type uint32;
          }
        }
        leaf as-override {
          type empty;
        }
        container egress-te-node-segment {
          presence "";
          uses apply-group;
          uses apply-macro;
          container label {
            uses apply-group;
            uses apply-macro;
            leaf label-value {
              type uint32;
            }
          }
          container egress-te-set {
            uses apply-group;
            uses apply-macro;
            leaf set-name {
              type string;
            }
            leaf weight {
              type uint32;
            }
          }
          container egress-te-backup-segment {
            uses apply-group;
            uses apply-macro;
            container label {
              uses apply-group;
              uses apply-macro;
              leaf label-value {
                type uint32;
              }
            }
          }
          container egress-te-backup-ip-forward {
            presence "enable egress-te-backup-ip-forward";
            uses apply-group;
            uses apply-macro;
            leaf instance-name {
              type string;
            }
          }
        }
        list egress-te-adj-segment {
          key "name";
          leaf name {
            type string;
          }
          uses apply-group;
          uses apply-macro;
          container label {
            uses apply-group;
            uses apply-macro;
            leaf label-value {
              type uint32;
            }
          }
          container next-hop {
            uses apply-group;
            uses apply-macro;
            leaf next-hop-addr {
              type ipaddr;
            }
          }
          container egress-te-set {
            uses apply-group;
            uses apply-macro;
            leaf set-name {
              type string;
            }
            leaf weight {
              type uint32;
            }
          }
          container egress-te-backup-segment {
            uses apply-group;
            uses apply-macro;
            container label {
              uses apply-group;
              uses apply-macro;
              leaf label-value {
                type uint32;
              }
            }
          }
          container egress-te-backup-ip-forward {
            presence "enable egress-te-backup-ip-forward";
            uses apply-group;
            uses apply-macro;
            leaf instance-name {
              type string;
            }
          }
        }
        leaf vpn-apply-export {
          type empty;
        }
        container egress-te {
          presence "enable egress-te";
          uses apply-group;
          uses apply-macro;
          leaf install-address {
            type ipaddr;
          }
          container rib {
            uses apply-group;
            uses apply-macro;
            leaf inet.0 {
              type empty;
            }
            leaf inet6.0 {
              type empty;
            }
          }
          leaf no-install {
            type empty;
          }
          leaf-list import {
            type policy-algebra;
            ordered-by user;
          }
          leaf backup-path {
            type string;
          }
        }
      }
    }
    container traffic-statistics-labeled-path {
      presence "enable traffic-statistics-labeled-path";
      uses apply-group;
      uses apply-macro;
      container file {
        presence "";
        leaf filename {
          mandatory true;
          type string;
        }
        leaf replace {
          type empty;
        }
        leaf size {
          type string;
        }
        leaf files {
          type uint32;
        }
        leaf no-stamp {
          type empty;
        }
        leaf world-readable {
          type empty;
        }
        leaf no-world-readable {
          type empty;
        }
      }
      leaf interval {
        units "seconds";
        type int32;
      }
    }
    container source-packet-routing {
      uses apply-group;
      uses apply-macro;
      container srgb {
        presence "";
        leaf start-label {
          mandatory true;
          type uint32;
        }
        leaf index-range {
          mandatory true;
          type uint32;
        }
      }
      container srv6 {
        uses apply-group;
        uses apply-macro;
        list locator {
          key "name";
          ordered-by user;
          leaf name {
            type string;
          }
          uses apply-group;
          uses apply-macro;
          leaf end-dt4-sid {
            type ipv6addr;
          }
          leaf end-dt6-sid {
            type ipv6addr;
          }
        }
      }
    }
    leaf rfc8950-compliant {
      type empty;
    }
    container defaults {
      uses apply-advanced;
      container ebgp {
        uses apply-advanced;
        container no-policy {
          uses apply-advanced;
          leaf receive {
            type string;
          }
          leaf advertise {
            type string;
          }
        }
      }
    }
    container undocumented {
      leaf-list drop-path-attributes {
        type string;
      }
      leaf minimum-hold-time {
        type uint32;
      }
      leaf enable {
        type empty;
      }
      leaf send-buffer {
        type string;
      }
      leaf receive-buffer {
        type string;
      }
      container enable-tcp-nodelay {
        presence "true";
      }
    }
  }

  grouping bgp-af-gr {
    uses apply-group;
    uses apply-macro;
    container long-lived {
      uses apply-group;
      uses apply-macro;
      container restarter {
        uses apply-group;
        uses apply-macro;
        leaf enable-disable {
          type string;
        }
        leaf stale-time {
          type string;
        }
      }
    }
    leaf forwarding-state-bit {
      type string;
    }
  }

  grouping bgp-afi-default {
    uses apply-group;
    uses apply-macro;
    container prefix-limit {
      presence "";
      uses bgpaf-prefix-limit;
    }
    container accepted-prefix-limit {
      presence "";
      uses bgpaf-accepted-prefix-limit;
    }
    container rib-group {
      presence "";
      uses rib-group-inet-type;
    }
    container add-path {
      uses apath-options;
    }
    container aigp {
      presence "enable aigp";
      uses bgpaf-aigp-options;
    }
    leaf damping {
      type empty;
    }
    leaf local-ipv4-address {
      type ipv4addr;
    }
    container loops {
      presence "";
      uses bgpaf-loops;
    }
    container delay-route-advertisements {
      presence "enable delay-route-advertisements";
      uses apply-group;
      uses apply-macro;
      leaf always-wait-for-krt-drain {
        type empty;
      }
      container minimum-delay {
        uses apply-group;
        uses apply-macro;
        leaf routing-uptime {
          type uint32;
        }
        leaf inbound-convergence {
          type uint32;
        }
      }
      container maximum-delay {
        uses apply-group;
        uses apply-macro;
        leaf route-age {
          type uint32;
        }
        leaf routing-uptime {
          type uint32;
        }
      }
    }
    container nexthop-resolution {
      uses apply-group;
      uses apply-macro;
      leaf no-resolution {
        type empty;
      }
      leaf preserve-nexthop-hierarchy {
        type empty;
      }
    }
    container defer-initial-multipath-build {
      presence "enable defer-initial-multipath-build";
      uses apply-group;
      uses apply-macro;
      leaf maximum-delay {
        type uint32;
      }
    }
    container graceful-restart {
      uses bgp-af-gr;
    }
    leaf extended-nexthop {
      type empty;
    }
    leaf extended-nexthop-color {
      type empty;
    }
    leaf extended-nexthop-tunnel {
      type empty;
    }
    leaf no-install {
      type empty;
    }
    leaf route-age-bgp-view {
      type empty;
    }
    container output-queue-priority {
      uses bgp-output-queue-priority-class;
    }
    container route-refresh-priority {
      uses bgp-output-queue-priority-class;
    }
    container withdraw-priority {
      uses bgp-output-queue-priority-class;
    }
    leaf advertise-srv6-service {
      type empty;
    }
    leaf accept-srv6-service {
      type empty;
    }
  }

  grouping apath-options {
    uses apply-group;
    uses apply-macro;
    leaf receive {
      type empty;
    }
    container send {
      presence "";
      uses apply-group;
      uses apply-macro;
      container path-selection-mode {
        uses apply-group;
        uses apply-macro;
        choice choice-all-paths {
          leaf all-paths {
            type empty;
          }
          leaf equal-cost-paths {
            type empty;
          }
        }
      }
      leaf-list prefix-policy {
        type policy-algebra;
        ordered-by user;
      }
      leaf path-count {
        type int32;
      }
      leaf include-backup-path {
        type int32;
      }
      leaf multipath {
        type empty;
      }
    }
  }

  grouping bgp-afi-flow {
    uses apply-group;
    uses apply-macro;
    container prefix-limit {
      presence "";
      uses bgpaf-prefix-limit;
    }
    container accepted-prefix-limit {
      presence "";
      uses bgpaf-accepted-prefix-limit;
    }
    container rib-group {
      presence "";
      uses rib-group-inet-type;
    }
    container add-path {
      uses apath-options;
    }
    container aigp {
      presence "enable aigp";
      uses bgpaf-aigp-options;
    }
    leaf damping {
      type empty;
    }
    leaf local-ipv4-address {
      type ipv4addr;
    }
    container loops {
      presence "";
      uses bgpaf-loops;
    }
    leaf-list no-validate {
      type policy-algebra;
      ordered-by user;
    }
    container legacy-redirect-ip-action {
      presence "enable legacy-redirect-ip-action";
      leaf receive {
        type empty;
      }
      leaf send {
        type empty;
      }
    }
  }

  grouping bgp-afi-inet6-labeled {
    uses apply-group;
    uses apply-macro;
    container prefix-limit {
      presence "";
      uses bgpaf-prefix-limit;
    }
    container accepted-prefix-limit {
      presence "";
      uses bgpaf-accepted-prefix-limit;
    }
    container rib-group {
      presence "";
      uses rib-group-inet-type;
    }
    container add-path {
      uses apath-options;
    }
    container aigp {
      presence "enable aigp";
      uses bgpaf-aigp-options;
    }
    leaf damping {
      type empty;
    }
    leaf local-ipv4-address {
      type ipv4addr;
    }
    container loops {
      presence "";
      uses bgpaf-loops;
    }
    container delay-route-advertisements {
      presence "enable delay-route-advertisements";
      uses apply-group;
      uses apply-macro;
      leaf always-wait-for-krt-drain {
        type empty;
      }
      container minimum-delay {
        uses apply-group;
        uses apply-macro;
        leaf routing-uptime {
          type uint32;
        }
        leaf inbound-convergence {
          type uint32;
        }
      }
      container maximum-delay {
        uses apply-group;
        uses apply-macro;
        leaf route-age {
          type uint32;
        }
        leaf routing-uptime {
          type uint32;
        }
      }
    }
    container nexthop-resolution {
      uses apply-group;
      uses apply-macro;
      leaf no-resolution {
        type empty;
      }
      leaf preserve-nexthop-hierarchy {
        type empty;
      }
    }
    container defer-initial-multipath-build {
      presence "enable defer-initial-multipath-build";
      uses apply-group;
      uses apply-macro;
      leaf maximum-delay {
        type uint32;
      }
    }
    container graceful-restart {
      uses bgp-af-gr;
    }
    leaf extended-nexthop {
      type empty;
    }
    leaf extended-nexthop-color {
      type empty;
    }
    leaf extended-nexthop-tunnel {
      type empty;
    }
    leaf no-install {
      type empty;
    }
    leaf route-age-bgp-view {
      type empty;
    }
    container output-queue-priority {
      uses bgp-output-queue-priority-class;
    }
    container route-refresh-priority {
      uses bgp-output-queue-priority-class;
    }
    container withdraw-priority {
      uses bgp-output-queue-priority-class;
    }
    leaf advertise-srv6-service {
      type empty;
    }
    leaf accept-srv6-service {
      type empty;
    }
    container aggregate-label {
      presence "";
      uses apply-group;
      uses apply-macro;
      leaf community {
        type string;
      }
    }
    leaf per-group-label {
      type empty;
    }
    container traffic-statistics {
      presence "enable traffic-statistics";
      uses bgpaf-traffic-statistics;
    }
    container rib {
      uses apply-group;
      uses apply-macro;
      leaf inet6.3 {
        type empty;
      }
    }
    container explicit-null {
      presence "enable explicit-null";
    }
    container protection {
      presence "enable protection";
    }
    list topology {
      key "name";
      ordered-by user;
      leaf name {
        type string;
      }
      uses apply-group;
      uses apply-macro;
      leaf community {
        type string;
        mandatory true;
      }
    }
  }

  grouping bgp-afi-l2vpn {
    uses apply-group;
    uses apply-macro;
    container prefix-limit {
      presence "";
      uses bgpaf-prefix-limit;
    }
    container accepted-prefix-limit {
      presence "";
      uses bgpaf-accepted-prefix-limit;
    }
    container rib-group {
      presence "";
      uses rib-group-inet-type;
    }
    container add-path {
      uses apath-options;
    }
    container aigp {
      presence "enable aigp";
      uses bgpaf-aigp-options;
    }
    leaf damping {
      type empty;
    }
    leaf local-ipv4-address {
      type ipv4addr;
    }
    container loops {
      presence "";
      uses bgpaf-loops;
    }
    container delay-route-advertisements {
      presence "enable delay-route-advertisements";
      uses apply-advanced;
      leaf always-wait-for-krt-drain {
        type empty;
      }
      container minimum-delay {
        uses apply-advanced;
        leaf routing-uptime {
          type string;
        }
        leaf inbound-convergence {
          type string;
        }
      }
      container maximum-delay {
        uses apply-advanced;
        leaf route-age {
          type string;
        }
        leaf routing-uptime {
          type string;
        }
      }
    }
    container nexthop-resolution {
      uses apply-advanced;
      leaf no-resolution {
        type empty;
      }
      leaf preserve-nexthop-hierarchy {
        type empty;
      }
    }
    container defer-initial-multipath-build {
      presence "enable defer-initial-multipath-build";
      uses apply-advanced;
      leaf maximum-delay {
        type string;
      }
    }
    container graceful-restart {
      uses bgp-af-gr;
    }
    leaf extended-nexthop {
      type empty;
    }
    leaf extended-nexthop-color {
      type empty;
    }
    leaf extended-nexthop-tunnel {
      type empty;
    }
    leaf no-install {
      type empty;
    }
    leaf route-age-bgp-view {
      type empty;
    }
    container output-queue-priority {
      uses bgp-output-queue-priority-class;
    }
    container route-refresh-priority {
      uses bgp-output-queue-priority-class;
    }
    container withdraw-priority {
      uses bgp-output-queue-priority-class;
    }
    leaf advertise-srv6-service {
      type empty;
    }
    leaf accept-srv6-service {
      type empty;
    }
    container egress-protection {
      presence "enable egress-protection";
      uses apply-advanced;
      container context-identifier {
        uses apply-advanced;
        leaf context-id {
          type ipv4addr;
        }
      }
      leaf-list keep-import {
        ordered-by user;
        type policy-algebra;
      }
    }
  }

  grouping bgp-afi-labeled {
    uses apply-group;
    uses apply-macro;
    container prefix-limit {
      presence "";
      uses bgpaf-prefix-limit;
    }
    container accepted-prefix-limit {
      presence "";
      uses bgpaf-accepted-prefix-limit;
    }
    container rib-group {
      presence "";
      uses rib-group-inet-type;
    }
    container add-path {
      uses apath-options;
    }
    container aigp {
      presence "enable aigp";
      uses bgpaf-aigp-options;
    }
    leaf damping {
      type empty;
    }
    leaf local-ipv4-address {
      type ipv4addr;
    }
    container loops {
      presence "";
      uses bgpaf-loops;
    }
    container delay-route-advertisements {
      presence "enable delay-route-advertisements";
      uses apply-advanced;
      leaf always-wait-for-krt-drain {
        type empty;
      }
      container minimum-delay {
        uses apply-advanced;
        leaf routing-uptime {
          type string;
        }
        leaf inbound-convergence {
          type string;
        }
      }
      container maximum-delay {
        uses apply-advanced;
        leaf route-age {
          type string;
        }
        leaf routing-uptime {
          type string;
        }
      }
    }
    container nexthop-resolution {
      uses apply-advanced;
      leaf no-resolution {
        type empty;
      }
      leaf preserve-nexthop-hierarchy {
        type empty;
      }
    }
    container defer-initial-multipath-build {
      presence "enable defer-initial-multipath-build";
      uses apply-advanced;
      leaf maximum-delay {
        type string;
      }
    }
    container graceful-restart {
      uses bgp-af-gr;
    }
    leaf extended-nexthop {
      type empty;
    }
    leaf extended-nexthop-color {
      type empty;
    }
    leaf extended-nexthop-tunnel {
      type empty;
    }
    leaf no-install {
      type empty;
    }
    leaf route-age-bgp-view {
      type empty;
    }
    container output-queue-priority {
      uses bgp-output-queue-priority-class;
    }
    container route-refresh-priority {
      uses bgp-output-queue-priority-class;
    }
    container withdraw-priority {
      uses bgp-output-queue-priority-class;
    }
    leaf advertise-srv6-service {
      type empty;
    }
    leaf accept-srv6-service {
      type empty;
    }
    container aggregate-label {
      presence "";
      uses apply-group;
      uses apply-macro;
      leaf community {
        type string;
      }
    }
    leaf per-prefix-label {
      type empty;
    }
    leaf per-group-label {
      type empty;
    }
    container traffic-statistics {
      presence "enable traffic-statistics";
      uses bgpaf-traffic-statistics;
    }
    container rib {
      uses apply-group;
      uses apply-macro;
      uses rib-inet3;
    }
    container explicit-null {
      presence "";
      leaf connected-only {
        type empty;
      }
    }
    leaf resolve-vpn {
      type empty;
    }
  }

  grouping bgp-afi-srte {
    uses apply-group;
    uses apply-macro;
    container prefix-limit {
      presence "";
      uses bgpaf-prefix-limit;
    }
    container accepted-prefix-limit {
      presence "";
      uses bgpaf-accepted-prefix-limit;
    }
    leaf damping {
      type empty;
    }
    container loops {
      presence "";
      uses bgpaf-loops;
    }
    container graceful-restart {
      uses bgp-af-gr;
    }
    leaf no-install {
      type empty;
    }
    container output-queue-priority {
      uses bgp-output-queue-priority-class;
    }
    container route-refresh-priority {
      uses bgp-output-queue-priority-class;
    }
    container withdraw-priority {
      uses bgp-output-queue-priority-class;
    }
  }

  grouping bgp-afi-topo {
    uses apply-group;
    uses apply-macro;
    container prefix-limit {
      presence "";
      uses bgpaf-prefix-limit;
    }
    container accepted-prefix-limit {
      presence "";
      uses bgpaf-accepted-prefix-limit;
    }
    container rib-group {
      presence "";
      uses rib-group-inet-type;
    }
    container add-path {
      uses apath-options;
    }
    container aigp {
      presence "enable aigp";
      uses bgpaf-aigp-options;
    }
    leaf damping {
      type empty;
    }
    leaf local-ipv4-address {
      type ipv4addr;
    }
    container loops {
      presence "";
      uses bgpaf-loops;
    }
    container delay-route-advertisements {
      presence "enable delay-route-advertisements";
      uses apply-group;
      uses apply-macro;
      leaf always-wait-for-krt-drain {
        type empty;
      }
      container minimum-delay {
        uses apply-group;
        uses apply-macro;
        leaf routing-uptime {
          type uint32;
        }
        leaf inbound-convergence {
          type uint32;
        }
      }
      container maximum-delay {
        uses apply-group;
        uses apply-macro;
        leaf route-age {
          type uint32;
        }
        leaf routing-uptime {
          type uint32;
        }
      }
    }
    container nexthop-resolution {
      uses apply-group;
      uses apply-macro;
      leaf no-resolution {
        type empty;
      }
      leaf preserve-nexthop-hierarchy {
        type empty;
      }
    }
    container defer-initial-multipath-build {
      presence "enable defer-initial-multipath-build";
      uses apply-group;
      uses apply-macro;
      leaf maximum-delay {
        type uint32;
      }
    }
    container graceful-restart {
      uses bgp-af-gr;
    }
    leaf extended-nexthop {
      type empty;
    }
    leaf extended-nexthop-color {
      type empty;
    }
    leaf no-install {
      type empty;
    }
    leaf route-age-bgp-view {
      type empty;
    }
    container output-queue-priority {
      uses bgp-output-queue-priority-class;
    }
    container route-refresh-priority {
      uses bgp-output-queue-priority-class;
    }
    container withdraw-priority {
      uses bgp-output-queue-priority-class;
    }
    container protection {
      presence "enable protection";
    }
    list topology {
      key "name";
      ordered-by user;
      leaf name {
        type string;
      }
      uses apply-group;
      uses apply-macro;
      leaf community {
        type string;
      }
    }
  }

  grouping bgp-afi-vpn {
    uses apply-group;
    uses apply-macro;
    container prefix-limit {
      presence "";
      uses bgpaf-prefix-limit;
    }
    container accepted-prefix-limit {
      presence "";
      uses bgpaf-accepted-prefix-limit;
    }
    container rib-group {
      presence "";
      uses rib-group-inet-type;
    }
    container add-path {
      uses apath-options;
    }
    container aigp {
      presence "enable aigp";
      uses bgpaf-aigp-options;
    }
    leaf damping {
      type empty;
    }
    leaf local-ipv4-address {
      type ipv4addr;
    }
    container loops {
      presence "";
      uses bgpaf-loops;
    }
    container delay-route-advertisements {
      presence "enable delay-route-advertisements";
      uses apply-group;
      uses apply-macro;
      leaf always-wait-for-krt-drain {
        type empty;
      }
      container minimum-delay {
        uses apply-group;
        uses apply-macro;
        leaf routing-uptime {
          type uint32;
        }
        leaf inbound-convergence {
          type uint32;
        }
      }
      container maximum-delay {
        uses apply-group;
        uses apply-macro;
        leaf route-age {
          type uint32;
        }
        leaf routing-uptime {
          type uint32;
        }
      }
    }
    container nexthop-resolution {
      uses apply-group;
      uses apply-macro;
      leaf no-resolution {
        type empty;
      }
      leaf preserve-nexthop-hierarchy {
        type empty;
      }
    }
    container defer-initial-multipath-build {
      presence "enable defer-initial-multipath-build";
      uses apply-group;
      uses apply-macro;
      leaf maximum-delay {
        type uint32;
      }
    }
    container graceful-restart {
      uses bgp-af-gr;
    }
    leaf extended-nexthop {
      type empty;
    }
    leaf extended-nexthop-color {
      type empty;
    }
    leaf extended-nexthop-tunnel {
      type empty;
    }
    leaf no-install {
      type empty;
    }
    leaf route-age-bgp-view {
      type empty;
    }
    container output-queue-priority {
      uses bgp-output-queue-priority-class;
    }
    container route-refresh-priority {
      uses bgp-output-queue-priority-class;
    }
    container withdraw-priority {
      uses bgp-output-queue-priority-class;
    }
    leaf advertise-srv6-service {
      type empty;
    }
    leaf accept-srv6-service {
      type empty;
    }
    container aggregate-label {
      presence "";
      uses apply-group;
      uses apply-macro;
      leaf community {
        type string;
      }
    }
  }

  grouping bgp-output-queue-priority-class {
    uses apply-group;
    uses apply-macro;
    choice choice-priority {
      leaf priority {
        type uint32;
      }
      leaf expedited {
        type empty;
      }
    }
  }

  grouping bgp-filter-obj {
    uses apply-group;
    uses apply-macro;
    leaf match-on {
      type string;
    }
    leaf-list policy {
      type policy-algebra;
      ordered-by user;
    }
  }

  grouping bgpaf-accepted-prefix-limit {
    uses apply-group;
    uses apply-macro;
    leaf maximum {
      type uint32;
    }
    container teardown {
      presence "enable teardown";
      leaf limit-threshold {
        type uint32;
      }
      container idle-timeout {
        presence "enable idle-timeout";
        choice choice-3 {
          leaf forever {
            type empty;
          }
          leaf timeout {
            type uint32;
          }
        }
      }
    }
  }

  grouping bgpaf-aigp-options {
    uses apply-group;
    uses apply-macro;
    leaf disable {
      type empty;
    }
  }

  grouping bgpaf-loops {
    uses apply-group;
    uses apply-macro;
    leaf loops {
      type int32;
    }
  }

  grouping bgpaf-prefix-limit {
    uses apply-group;
    uses apply-macro;
    leaf maximum {
      type uint32;
    }
    container teardown {
      presence "enable teardown";
      leaf limit-threshold {
        type uint32;
      }
      container idle-timeout {
        presence "enable idle-timeout";
        choice choice-3 {
          leaf forever {
            type empty;
          }
          leaf timeout {
            type uint32;
          }
        }
      }
    }
    container drop-excess {
      presence "enable drop-excess";
      uses apply-advanced;
      leaf limit-threshold {
        type string;
      }
    }
  }

  grouping bgpaf-traffic-statistics {
    uses apply-group;
    uses apply-macro;
    container file {
      presence "";
      uses trace-file-type;
    }
    leaf interval {
      type int32;
    }
  }

  grouping juniper-protocols-bridge {
    uses apply-group;
    uses apply-macro;
    container traceoptions {
      uses apply-advanced;
      leaf no-remote-trace {
        type empty;
      }
      container file {
        leaf filename {
          type string;
        }
        leaf size {
          type string;
        }
        leaf files {
          type string;
        }
        choice world-readable-choice {
          leaf world-readable {
            type empty;
          }
          leaf no-world-readable {
            type empty;
          }
        }
        leaf match {
          type regular-expression;
        }
      }
      leaf level {
        type string;
      }
      list flag {
        key "name";
        ordered-by user;
        leaf name {
          type string;
        }
      }
      container kernel {
        presence "enable kernel";
        uses apply-advanced;
        container irb {
          presence "enable irb";
        }
      }
      container in-memory-debug {
        presence "enable in-memory-debug";
      }
    }
    container vpls-mac-move {
      presence "enable vpls-mac-move";
      uses apply-group;
      uses apply-macro;
      leaf cooloff-time {
        type uint32;
        units "seconds";
      }
      leaf statistical-approach-wait-time {
        type uint32;
        units "seconds";
      }
      leaf interface-recovery-time {
        type uint32;
        units "seconds";
      }
      list virtual-mac {
        key "name";
        ordered-by user;
        leaf name {
          type mac-addr-prefix;
        }
        uses apply-group;
        uses apply-macro;
      }
    }
    container global-mac-move {
      presence "enable global-mac-move";
      uses apply-group;
      uses apply-macro;
      leaf notification-time {
        type uint32;
        units "seconds";
      }
      leaf threshold-time {
        type uint32;
        units "seconds";
      }
      leaf reopen-time {
        type uint32;
        units "seconds";
      }
      leaf threshold-count {
        type uint32;
        units "seconds";
      }
      container traceoptions {
        uses apply-group;
        uses apply-macro;
        leaf no-remote-trace {
          type empty;
        }
        container file {
          leaf filename {
            type string;
          }
          leaf size {
            type string;
          }
          leaf files {
            type uint32;
          }
          leaf world-readable {
            type empty;
          }
          leaf no-world-readable {
            type empty;
          }
          leaf match {
            type regular-expression;
          }
        }
      }
      leaf log {
        type empty;
      }
      leaf disable-action {
        type empty;
      }
      leaf cooloff-time {
        type uint32;
        units "seconds";
      }
      leaf statistical-approach-wait-time {
        type uint32;
        units "seconds";
      }
      leaf interface-recovery-time {
        type uint32;
        units "seconds";
      }
      list exclusive-mac {
        key "name";
        ordered-by user;
        leaf name {
          type mac-addr-prefix;
        }
        uses apply-group;
        uses apply-macro;
      }
    }
    leaf global-mac-table-aging-time {
      type uint32;
    }
    leaf global-mac-ip-table-aging-time {
      units "seconds";
      type uint32;
    }
    leaf global-mode {
      type string;
    }
    leaf global-le-aging-time {
      type uint32;
    }
    leaf global-le-bridge-domain-aging-time {
      type uint32;
    }
    leaf mclag-arpreq-sync {
      type empty;
    }
    leaf global-mac-pinning-discard-notification-interval {
      units "seconds";
      type uint32;
    }
    container global-ctx-limit {
      presence "enable global-ctx-limit";
      uses apply-advanced;
      leaf ctx-limit {
        type string;
      }
    }
    container global-mac-limit {
      presence "enable global-mac-limit";
      uses apply-group;
      uses apply-macro;
      leaf mac-limit {
        type uint64;
      }
      leaf packet-action {
        type string;
      }
    }
    container global-mac-ip-limit {
      presence "enable global-mac-ip-limit";
      uses apply-group;
      uses apply-macro;
      leaf mac-ip-limit {
        type uint64;
      }
    }
    leaf global-mac-statistics {
      type empty;
    }
    leaf global-static-mac-move-drop-log {
      type empty;
    }
    leaf decapsulate-accept-inner-vlan {
      type empty;
    }
    container telemetry {
      presence "enable telemetry";
      uses apply-advanced;
      leaf enable-remote-entries {
        type empty;
      }
    }
    leaf destination-udp-port {
      type uint16;
    }
    container disable-vxlan-multicast-transit {
      uses apply-group;
      uses apply-macro;
      list vxlan-multicast-group {
        key "name";
        ordered-by user;
        leaf name {
          type string;
        }
        uses apply-group;
        uses apply-macro;
      }
    }
    leaf global-no-mac-learning {
      type empty;
    }
    leaf global-no-hw-mac-learning {
      type empty;
    }
    leaf global-no-control-mac-aging {
      type empty;
    }
    leaf mclag-arp-nd-sync {
      type empty;
    }
    leaf no-mclag-ifa-sync {
      type empty;
    }
  }

  grouping juniper-protocols-dot1x {
    uses apply-group;
    uses apply-macro;
    container traceoptions {
      uses apply-group;
      uses apply-macro;
      container file {
        presence "";
        uses trace-file-type;
      }
      list flag {
        key "name";
        ordered-by user;
        leaf name {
          type string;
        }
        leaf disable {
          type empty;
        }
      }
    }
    container authenticator {
      presence "enable authenticator";
      uses apply-group;
      uses apply-macro;
      leaf authentication-profile-name {
        type string;
      }
      leaf no-mac-table-binding {
        type empty;
      }
      list static {
        key "name";
        ordered-by user;
        leaf name {
          type mac-addr;
        }
        uses apply-group;
        uses apply-macro;
        leaf vlan-assignment {
          type string;
        }
        leaf interface {
          type interface-name;
        }
      }
      list interface {
        key "name";
        leaf name {
          type interface-device;
        }
        uses apply-group;
        uses apply-macro;
        leaf disable {
          type empty;
        }
        leaf supplicant {
          type string;
        }
        leaf retries {
          type uint32;
        }
        leaf quiet-period {
          type uint32;
        }
        leaf transmit-period {
          type uint32;
        }
        container mac-radius {
          presence "enable mac-radius";
          uses apply-group;
          uses apply-macro;
          leaf restrict {
            type empty;
          }
          leaf flap-on-disconnect {
            type empty;
          }
        }
        choice choice-13 {
          leaf no-reauthentication {
            type empty;
          }
          leaf reauthentication {
            type uint32;
          }
        }
        leaf supplicant-timeout {
          type uint32;
        }
        leaf server-timeout {
          type uint32;
        }
        leaf maximum-requests {
          type uint32;
        }
        leaf guest-vlan {
          type string;
        }
        container server-reject-vlan {
          presence "";
          leaf vlan-name {
            type string;
          }
          leaf block-interval {
            type uint32;
          }
          leaf eapol-block {
            type empty;
          }
        }
        container server-fail {
          choice choice-3 {
            leaf deny {
              type empty;
            }
            leaf permit {
              type empty;
            }
            leaf vlan-name {
              type string;
            }
            leaf use-cache {
              type empty;
            }
          }
        }
      }
    }
  }

  grouping juniper-protocols-esis {
    uses apply-group;
    uses apply-macro;
    choice choice-3 {
      leaf disable {
        type empty;
      }
    }
    container traceoptions {
      uses apply-group;
      uses apply-macro;
      container file {
        presence "";
        uses trace-file-type;
      }
      list flag {
        key "name";
        ordered-by user;
        leaf name {
          type string;
        }
        leaf send {
          type empty;
        }
        leaf receive {
          type empty;
        }
        leaf detail {
          type empty;
        }
        leaf disable {
          type empty;
        }
      }
    }
    leaf preference {
      type uint32;
    }
    container graceful-restart {
      choice choice-3 {
        leaf disable {
          type empty;
        }
      }
      leaf restart-duration {
        type uint32;
      }
    }
    list interface {
      key "name";
      leaf name {
        type interface-name;
      }
      uses apply-group;
      uses apply-macro;
      leaf hold-time {
        type uint32;
      }
      leaf end-system-configuration-timer {
        type uint32;
      }
      choice choice-7 {
        leaf disable {
          type empty;
        }
      }
    }
  }

  grouping juniper-protocols-igmp-snooping {
    uses apply-group;
    uses apply-macro;
    container traceoptions {
      uses apply-group;
      uses apply-macro;
      container file {
        presence "";
        uses trace-file-type;
      }
      list flag {
        key "name";
        ordered-by user;
        leaf name {
          type string;
        }
        leaf send {
          type empty;
        }
        leaf receive {
          type empty;
        }
        leaf detail {
          type empty;
        }
        leaf disable {
          type empty;
        }
      }
    }
    leaf query-interval {
      type uint32;
    }
    container l2-querier {
      presence "";
      uses apply-group;
      uses apply-macro;
      leaf source-address {
        mandatory true;
        type ipv4addr;
      }
    }
    leaf query-response-interval {
      type string;
    }
    leaf query-last-member-interval {
      type string;
    }
    leaf robust-count {
      type uint32;
    }
    leaf learn-pim-router {
      type empty;
    }
    leaf immediate-leave {
      type empty;
    }
    container proxy {
      presence "enable proxy";
      uses apply-group;
      uses apply-macro;
      leaf source-address {
        type ipv4addr;
      }
      leaf irb {
        type empty;
      }
    }
    leaf evpn-ssm-reports-only {
      type empty;
    }
    list interface {
      key "name";
      ordered-by user;
      leaf name {
        type interface-name;
      }
      uses apply-group;
      uses apply-macro;
      leaf multicast-router-interface {
        type empty;
      }
      leaf immediate-leave {
        type empty;
      }
      leaf host-only-interface {
        type empty;
      }
      leaf group-limit {
        type uint16;
      }
      container static {
        uses apply-group;
        uses apply-macro;
        list group {
          key "name";
          ordered-by user;
          leaf name {
            type ipv4addr;
          }
          uses apply-group;
          uses apply-macro;
          list source {
            key "name";
            ordered-by user;
            leaf name {
              type ipv4addr;
            }
            uses apply-group;
            uses apply-macro;
          }
        }
      }
    }
    list pseudowire-remote-address {
      key "name";
      ordered-by user;
      leaf name {
        type ipv4addr;
      }
      uses apply-advanced;
      leaf multicast-router-interface {
        type empty;
      }
      leaf immediate-leave {
        type empty;
      }
    }
    list qualified-vlan {
      key "name";
      ordered-by user;
      leaf name {
        type string;
      }
      uses apply-advanced;
      leaf query-interval {
        units "seconds";
        type string;
      }
      leaf query-response-interval {
        units "seconds";
        type string;
      }
      leaf query-last-member-interval {
        units "seconds";
        type string;
      }
      leaf robust-count {
        type string;
      }
      leaf immediate-leave {
        type empty;
      }
      container proxy {
        presence "enable proxy";
        uses apply-advanced;
        leaf source-address {
          type ipv4addr;
        }
      }
      leaf evpn-ssm-reports-only {
        type empty;
      }
      list interface {
        key "name";
        ordered-by user;
        leaf name {
          type string;
        }
        uses apply-advanced;
        leaf multicast-router-interface {
          type empty;
        }
        leaf immediate-leave {
          type empty;
        }
        leaf host-only-interface {
          type empty;
        }
        leaf group-limit {
          type string;
        }
        container static {
          uses apply-advanced;
          list group {
            key "name";
            ordered-by user;
            leaf name {
              type ipv4addr;
            }
            uses apply-advanced;
            list source {
              key "name";
              ordered-by user;
              leaf name {
                type ipv4addr;
              }
              uses apply-advanced;
            }
          }
        }
      }
      list pseudowire-remote-address {
        key "name";
        ordered-by user;
        leaf name {
          type ipv4addr;
        }
        uses apply-advanced;
        leaf multicast-router-interface {
          type empty;
        }
        leaf immediate-leave {
          type empty;
        }
      }
    }
    list vlan {
      key "name";
      ordered-by user;
      leaf name {
        type string;
      }
      uses apply-group;
      uses apply-macro;
      leaf disable {
        type empty;
      }
      leaf version {
        type uint8;
      }
      leaf query-interval {
        type string;
      }
      container l2-querier {
        container apply-advanced {
          uses apply-group;
          uses apply-macro;
        }
        leaf source-address {
          type ipv4addr;
        }
      }
      leaf query-response-interval {
        type string;
      }
      leaf query-last-member-interval {
        type string;
      }
      leaf robust-count {
        type uint32;
      }
      leaf immediate-leave {
        type empty;
      }
      container proxy {
        presence "enable proxy";
        uses apply-group;
        uses apply-macro;
        leaf source-address {
          type ipv4addr;
        }
      }
      list interface {
        key "name";
        ordered-by user;
        leaf name {
          type interface-name;
        }
        uses apply-group;
        uses apply-macro;
        leaf multicast-router-interface {
          type empty;
        }
        leaf immediate-leave {
          type empty;
        }
        leaf host-only-interface {
          type empty;
        }
        leaf group-limit {
          type uint16;
        }
        container static {
          uses apply-group;
          uses apply-macro;
          list group {
            key "name";
            ordered-by user;
            leaf name {
              type ipv4addr;
            }
            uses apply-group;
            uses apply-macro;
            list source {
              key "name";
              ordered-by user;
              leaf name {
                type ipv4addr;
              }
              uses apply-group;
              uses apply-macro;
            }
          }
        }
      }
    }
  }

  grouping juniper-protocols-isis {
    uses apply-group;
    uses apply-macro;
    uses apply-advanced;
    list interface {
      key "name";
      leaf name {
        type string;
      }
      uses apply-group;
      uses apply-macro;
      uses apply-advanced;
      container ldp-synchronization {
        presence "enable ldp-synchronization";
        uses ldp-sync-obj;
      }
      list level {
        key "name";
        ordered-by user;
        leaf name {
          type string;
        }
        uses apply-advanced;
        leaf te-metric {
          type string;
        }
        leaf no-advertise-adjacency-segment {
          type empty;
        }
        container ipv4-adjacency-segment {
          uses apply-group;
          uses apply-macro;
          uses apply-advanced;
          container protected {
            choice adjsid-type {
              case case_1 {
                container index {
                  leaf index-number {
                    type string;
                  }
                }
              }
              case case_2 {
                leaf label {
                  type string;
                }
              }
              case case_3 {
                leaf dynamic {
                  type empty;
                }
              }
            }
          }
          container unprotected {
            choice adjsid-type {
              case case_1 {
                container index {
                  leaf index-number {
                    type string;
                  }
                }
              }
              case case_2 {
                leaf label {
                  type string;
                }
              }
              case case_3 {
                leaf dynamic {
                  type empty;
                }
              }
            }
          }
        }
        container ipv6-adjacency-segment {
          uses apply-group;
          uses apply-macro;
          uses apply-advanced;
          container protected {
            choice adjsid-type {
              case case_1 {
                container index {
                  leaf index-number {
                    type string;
                  }
                }
              }
              case case_2 {
                leaf label {
                  type string;
                }
              }
              case case_3 {
                leaf dynamic {
                  type empty;
                }
              }
            }
          }
          container unprotected {
            choice adjsid-type {
              case case_1 {
                container index {
                  leaf index-number {
                    type string;
                  }
                }
              }
              case case_2 {
                leaf label {
                  type string;
                }
              }
              case case_3 {
                leaf dynamic {
                  type empty;
                }
              }
            }
          }
        }
        container srm6-adjacency-segment {
          uses apply-advanced;
          container unprotected {
            leaf sid {
              type string;
            }
          }
        }
        container srv6-adjacency-segment {
          uses apply-advanced;
          container protected {
            presence "enable protected";
            uses apply-advanced;
            list locator {
              key "name";
              ordered-by user;
              leaf name {
                type string;
              }
              uses apply-advanced;
              list end-x-sid {
                key "name";
                ordered-by user;
                leaf name {
                  type ipv6addr;
                }
                uses apply-advanced;
                container flavor {
                  presence "enable flavor";
                  uses apply-advanced;
                  leaf psp {
                    type empty;
                  }
                  leaf usp {
                    type empty;
                  }
                  leaf usd {
                    type empty;
                  }
                }
              }
            }
          }
          container unprotected {
            presence "enable unprotected";
            uses apply-advanced;
            list locator {
              key "name";
              ordered-by user;
              leaf name {
                type string;
              }
              uses apply-advanced;
              list end-x-sid {
                key "name";
                ordered-by user;
                leaf name {
                  type ipv6addr;
                }
                uses apply-advanced;
                container flavor {
                  presence "enable flavor";
                  uses apply-advanced;
                  leaf psp {
                    type empty;
                  }
                  leaf usp {
                    type empty;
                  }
                  leaf usd {
                    type empty;
                  }
                }
              }
            }
          }
        }
        list lan-neighbor {
          key "name";
          ordered-by user;
          leaf name {
            type sysid;
          }
          uses apply-advanced;
          container ipv4-adjacency-segment {
            uses apply-advanced;
            container protected {
              choice adjsid-type {
                case case_1 {
                  container index {
                    leaf index-number {
                      type string;
                    }
                  }
                }
                case case_2 {
                  leaf label {
                    type string;
                  }
                }
                case case_3 {
                  leaf dynamic {
                    type empty;
                  }
                }
              }
            }
            container unprotected {
              choice adjsid-type {
                case case_1 {
                  container index {
                    leaf index-number {
                      type string;
                    }
                  }
                }
                case case_2 {
                  leaf label {
                    type string;
                  }
                }
                case case_3 {
                  leaf dynamic {
                    type empty;
                  }
                }
              }
            }
          }
          container ipv6-adjacency-segment {
            uses apply-advanced;
            container protected {
              choice adjsid-type {
                case case_1 {
                  container index {
                    leaf index-number {
                      type string;
                    }
                  }
                }
                case case_2 {
                  leaf label {
                    type string;
                  }
                }
                case case_3 {
                  leaf dynamic {
                    type empty;
                  }
                }
              }
            }
            container unprotected {
              choice adjsid-type {
                case case_1 {
                  container index {
                    leaf index-number {
                      type string;
                    }
                  }
                }
                case case_2 {
                  leaf label {
                    type string;
                  }
                }
                case case_3 {
                  leaf dynamic {
                    type empty;
                  }
                }
              }
            }
          }
          container srm6-adjacency-segment {
            uses apply-advanced;
            container unprotected {
              leaf sid {
                type string;
              }
            }
          }
          container srv6-adjacency-segment {
            uses apply-advanced;
            container protected {
              presence "enable protected";
              uses apply-advanced;
              list locator {
                key "name";
                ordered-by user;
                leaf name {
                  type string;
                }
                uses apply-advanced;
                list end-x-sid {
                  key "name";
                  ordered-by user;
                  leaf name {
                    type ipv6addr;
                  }
                  uses apply-advanced;
                  container flavor {
                    presence "enable flavor";
                    uses apply-advanced;
                    leaf psp {
                      type empty;
                    }
                    leaf usp {
                      type empty;
                    }
                    leaf usd {
                      type empty;
                    }
                  }
                }
              }
            }
            container unprotected {
              presence "enable unprotected";
              uses apply-advanced;
              list locator {
                key "name";
                ordered-by user;
                leaf name {
                  type string;
                }
                uses apply-advanced;
                list end-x-sid {
                  key "name";
                  ordered-by user;
                  leaf name {
                    type ipv6addr;
                  }
                  uses apply-advanced;
                  container flavor {
                    presence "enable flavor";
                    uses apply-advanced;
                    leaf psp {
                      type empty;
                    }
                    leaf usp {
                      type empty;
                    }
                    leaf usd {
                      type empty;
                    }
                  }
                }
              }
            }
          }
        }
        container post-convergence-lfa {
          presence "enable post-convergence-lfa";
          uses apply-group;
          uses apply-macro;
          uses apply-advanced;
          container node-protection {
            presence "enable node-protection";
            uses apply-advanced;
            leaf cost {
              type string;
            }
          }
          leaf srlg-protection {
            type empty;
          }
          leaf fate-sharing-protection {
            type empty;
          }
        }
        container application-specific {
          uses apply-advanced;
          list attribute-group {
            key "name";
            ordered-by user;
            leaf name {
              type string;
            }
            uses apply-advanced;
            leaf te-metric {
              type string;
            }
            leaf-list admin-group {
              ordered-by user;
              type string;
            }
            container application {
              uses apply-advanced;
              leaf flex-algorithm {
                type empty;
              }
            }
            container undocumented {
              leaf advertise-delay-metric {
                type empty;
              }
              leaf delay-metric {
                type uint32;
              }
            }
          }
        }
        choice enable-disable {
          case case_1 {
            leaf disable {
              type empty;
            }
          }
        }
        leaf metric {
          type string;
        }
        leaf ipv4-multicast-metric {
          type string;
        }
        leaf ipv6-unicast-metric {
          type string;
        }
        leaf ipv6-multicast-metric {
          type string;
        }
        list topology {
          key "name";
          ordered-by user;
          leaf name {
            type string;
          }
          uses apply-advanced;
          leaf metric {
            type string;
          }
          container bandwidth-based-metrics {
            uses apply-advanced;
            list bandwidth {
              key "name";
              leaf name {
                type string;
              }
              leaf metric {
                type string;
              }
            }
          }
        }
        leaf authentication-key {
          status deprecated;
          type unreadable;
        }
        leaf authentication-type {
          status deprecated;
          type string;
        }
        leaf hello-authentication-key {
          type unreadable;
        }
        leaf hello-authentication-type {
          type string;
        }
        leaf hello-authentication-key-chain {
          type string;
        }
        leaf hello-interval {
          units "seconds";
          type string;
        }
        leaf hold-time {
          units "seconds";
          type string;
        }
        leaf priority {
          type string;
        }
        container flood-reflector {
          presence "enable flood-reflector";
          uses apply-advanced;
          leaf cluster-id {
            type string;
          }
        }
        leaf passive {
          type empty;
        }
      }
      leaf delay-metric {
        units "microseconds";
        type string;
      }
      container delay-measurement {
        presence "enable delay-measurement";
        uses apply-advanced;
        leaf probe-interval {
          units "seconds";
          type string;
        }
        leaf probe-count {
          units "seconds";
          type string;
        }
        container advertisement {
          uses apply-group;
          uses apply-macro;
          uses apply-advanced;
          container periodic {
            uses apply-advanced;
            leaf threshold {
              units "percentage";
              type string;
            }
            leaf interval {
              units "seconds";
              type string;
            }
          }
          container accelerated {
            presence "enable accelerated";
            uses apply-advanced;
            leaf threshold {
              units "percentage";
              type string;
            }
          }
        }
      }
      leaf no-advertise-adjacency-segment {
        type empty;
      }
      container auto-bandwidth {
        uses apply-advanced;
        leaf template-name {
          type string;
        }
        choice enable-disable {
          case case_1 {
            leaf disable {
              type empty;
            }
          }
        }
      }
      choice protection-type {
        case case_1 {
          leaf link-protection {
            type empty;
          }
        }
        case case_2 {
          leaf node-link-protection {
            type empty;
          }
        }
      }
      leaf no-eligible-backup {
        type empty;
      }
      leaf no-eligible-remote-backup {
        type empty;
      }
      container link-degradation-threshold {
        presence "enable link-degradation-threshold";
        leaf link-down {
          type string;
        }
        leaf link-up {
          type string;
        }
      }
      choice enable-disable {
        case case_1 {
          leaf disable {
            type empty;
          }
        }
      }
      leaf authentication-key {
        status deprecated;
        type unreadable;
      }
      leaf authentication-type {
        status deprecated;
        type string;
      }
      leaf flood-group {
        type string;
      }
      leaf hello-authentication-key {
        status deprecated;
        type unreadable;
      }
      leaf hello-authentication-type {
        status deprecated;
        type string;
      }
      leaf hello-padding-type {
        type string;
      }
      leaf interface-group-holddown-delay {
        units "seconds";
        type string;
      }
      choice layer2-map-choice {
        leaf layer2-map {
          type empty;
        }
        leaf no-layer2-map {
          type empty;
        }
      }
      leaf max-hello-size {
        type string;
      }
      leaf lsp-interval {
        units "milliseconds";
        type string;
      }
      container csnp-interval {
        choice csnp_interval_option {
          case case_1 {
            leaf csnp-interval-number {
              units "seconds";
              type string;
            }
          }
          case case_2 {
            leaf disable {
              type empty;
            }
          }
        }
      }
      container strict-dual-isis {
        presence "enable strict-dual-isis";
        uses apply-advanced;
        leaf holdown {
          type string;
        }
      }
      container mesh-group {
        choice mesh_group_option {
          case case_1 {
            leaf mesh-group-number {
              type string;
            }
          }
          case case_2 {
            leaf blocked {
              type empty;
            }
          }
        }
      }
      leaf point-to-point {
        type empty;
      }
      leaf passive {
        type empty;
      }
      leaf checksum {
        type empty;
      }
      leaf no-unicast-topology {
        type empty;
      }
      leaf no-ipv4-multicast {
        type empty;
      }
      leaf no-ipv6-unicast {
        type empty;
      }
      leaf no-ipv6-multicast {
        type empty;
      }
      leaf no-adjacency-down-notification {
        type empty;
      }
      container bfd-liveness-detection {
        status deprecated;
        uses apply-group;
        uses apply-macro;
        uses apply-advanced;
        leaf version {
          type string;
        }
        leaf minimum-interval {
          units "milliseconds";
          type string;
        }
        leaf minimum-transmit-interval {
          status deprecated;
          units "milliseconds";
          type string;
        }
        leaf minimum-receive-interval {
          units "milliseconds";
          type string;
        }
        leaf multiplier {
          type string;
        }
        choice adaptation-choice {
          case case_1 {
            leaf no-adaptation {
              type empty;
            }
          }
        }
        container transmit-interval {
          uses apply-group;
          uses apply-macro;
          uses apply-advanced;
          leaf minimum-interval {
            units "milliseconds";
            type string;
          }
          leaf threshold {
            units "milliseconds";
            type string;
          }
        }
        container detection-time {
          uses apply-group;
          uses apply-macro;
          uses apply-advanced;
          leaf threshold {
            units "milliseconds";
            type string;
          }
        }
        container authentication {
          uses apply-group;
          uses apply-macro;
          uses apply-advanced;
          leaf key-chain {
            type string;
          }
          leaf algorithm {
            type string;
          }
          leaf loose-check {
            type empty;
          }
        }
      }
      list family {
        key "name";
        ordered-by user;
        leaf name {
          type string;
        }
        uses apply-group;
        uses apply-macro;
        uses apply-advanced;
        container bfd-liveness-detection {
          uses apply-group;
          uses apply-macro;
          uses apply-advanced;
          leaf version {
            type string;
          }
          leaf minimum-interval {
            units "milliseconds";
            type string;
          }
          leaf minimum-transmit-interval {
            status deprecated;
            units "milliseconds";
            type string;
          }
          leaf minimum-receive-interval {
            units "milliseconds";
            type string;
          }
          leaf multiplier {
            type string;
          }
          choice adaptation-choice {
            case case_1 {
              leaf no-adaptation {
                type empty;
              }
            }
          }
          container transmit-interval {
            uses apply-group;
            uses apply-macro;
            uses apply-advanced;
            leaf minimum-interval {
              units "milliseconds";
              type string;
            }
            leaf threshold {
              units "milliseconds";
              type string;
            }
          }
          container detection-time {
            uses apply-group;
            uses apply-macro;
            uses apply-advanced;
            leaf threshold {
              units "milliseconds";
              type string;
            }
          }
          container authentication {
            uses apply-group;
            uses apply-macro;
            uses apply-advanced;
            leaf key-chain {
              type string;
            }
            leaf algorithm {
              type string;
            }
            leaf loose-check {
              type empty;
            }
          }
        }
      }
      container undocumented {
        container bfd-liveness-detection {
          uses apply-group;
          uses apply-macro;
          leaf version {
            type string;
          }
          leaf minimum-interval {
            type uint32;
          }
          leaf minimum-receive-interval {
            type uint32;
          }
          leaf multiplier {
            type uint32;
          }
          leaf no-adaptation {
            type empty;
          }
          container transmit-interval {
            uses apply-group;
            uses apply-macro;
            leaf minimum-interval {
              type uint32;
            }
            leaf threshold {
              type uint32;
            }
          }
          container detection-time {
            uses apply-group;
            uses apply-macro;
            leaf threshold {
              type uint32;
            }
          }
          container authentication {
            uses apply-group;
            uses apply-macro;
            leaf key-chain {
              type string;
            }
            leaf algorithm {
              type string;
            }
            leaf loose-check {
              type empty;
            }
          }
        }
        leaf hello-authentication-key {
          type unreadable;
        }
        leaf hello-authentication-type {
          type string;
        }
      }
    }
    container source-packet-routing {
      presence "enable source-packet-routing";
      uses apply-group;
      uses apply-macro;
      uses apply-advanced;
      leaf enable-disable {
        type string;
      }
      container adjacency-segment {
        uses apply-advanced;
        leaf hold-time {
          type string;
        }
      }
      container udp-tunneling {
        uses apply-advanced;
        leaf encapsulation {
          type empty;
        }
        leaf decapsulation {
          type empty;
        }
      }
      container srgb {
        presence "";
        leaf start-label {
          type string;
        }
        leaf index-range {
          type string;
        }
      }
      container node-segment {
        uses apply-advanced;
        leaf ipv4-index {
          type string;
        }
        leaf ipv6-index {
          type string;
        }
        leaf index-range {
          type string;
        }
      }
      leaf-list flex-algorithm {
        type string;
      }
      leaf use-flex-algorithm-metric-always {
        type empty;
      }
      leaf strict-asla-based-flex-algorithm {
        type empty;
      }
      leaf new-capability-subtlv {
        type empty;
      }
      leaf explicit-null {
        type empty;
      }
      leaf mapping-server {
        type string;
      }
      leaf no-strict-spf {
        type empty;
      }
      leaf ldp-stitching {
        type empty;
      }
      container srv6 {
        presence "enable srv6";
        uses apply-advanced;
        list locator {
          key "name";
          ordered-by user;
          leaf name {
            type string;
          }
          uses apply-advanced;
          list end-sid {
            key "name";
            ordered-by user;
            leaf name {
              type ipv6addr;
            }
            uses apply-advanced;
            container flavor {
              presence "enable flavor";
              uses apply-advanced;
              leaf psp {
                type empty;
              }
              leaf usp {
                type empty;
              }
              leaf usd {
                type empty;
              }
            }
          }
        }
      }
      container sensor-based-stats {
        uses apply-advanced;
        container per-interface-per-member-link {
          leaf ingress {
            type empty;
          }
          leaf egress {
            type empty;
          }
        }
        container per-sid {
          leaf ingress {
            type empty;
          }
          leaf egress {
            type empty;
          }
        }
      }
      container traffic-statistics {
        uses apply-advanced;
        container statistics-granularity {
          uses apply-advanced;
          leaf per-interface {
            type empty;
          }
        }
        leaf auto-bandwidth {
          type string;
        }
      }
      leaf maximum-segment-list-depth {
        type uint32;
      }
    }
    container srm6 {
      presence "enable srm6";
      uses apply-advanced;
      container sid {
        uses apply-advanced;
        leaf node-sid {
          type string;
        }
        leaf address {
          type ipv6addr;
        }
      }
    }
    list level {
      key "name";
      ordered-by user;
      leaf name {
        type string;
      }
      uses apply-group;
      uses apply-macro;
      uses apply-advanced;
      leaf labeled-preference {
        type string;
      }
      leaf srv6-preference {
        type string;
      }
      leaf flex-algorithm-preference {
        type string;
      }
      container source-packet-routing {
        presence "enable source-packet-routing";
        uses apply-group;
        uses apply-macro;
        uses apply-advanced;
        choice enable-disable-choice {
          case case_1 {
            leaf disable {
              type empty;
            }
          }
        }
        leaf enable-disable {
          type string;
        }
        leaf srms-preference {
          type string;
        }
      }
      choice enable-disable {
        case case_1 {
          leaf disable {
            type empty;
          }
        }
      }
      leaf authentication-key {
        type unreadable;
      }
      leaf authentication-type {
        type string;
      }
      leaf purge-originator {
        type string;
      }
      leaf no-hello-authentication {
        type empty;
      }
      leaf no-csnp-authentication {
        type empty;
      }
      leaf no-psnp-authentication {
        type empty;
      }
      leaf authentication-key-chain {
        type string;
      }
      leaf wide-metrics-only {
        type empty;
      }
      leaf preference {
        type string;
      }
      leaf external-preference {
        type string;
      }
      leaf prefix-export-limit {
        type string;
      }
      container flood-reflector {
        uses apply-advanced;
        container reflector {
          uses apply-advanced;
          leaf cluster-id {
            type string;
          }
        }
        leaf client {
          type empty;
        }
      }
    }
    list interface-group {
      key "name";
      leaf name {
        type string;
      }
      uses apply-advanced;
      list level {
        key "name";
        ordered-by user;
        leaf name {
          type string;
        }
        uses apply-advanced;
        container ipv4-adjacency-segment {
          uses apply-advanced;
          container protected {
            choice adjsid-type {
              case case_1 {
                container index {
                  leaf index-number {
                    type string;
                  }
                }
              }
              case case_2 {
                leaf label {
                  type string;
                }
              }
              case case_3 {
                leaf dynamic {
                  type empty;
                }
              }
            }
          }
          container unprotected {
            choice adjsid-type {
              case case_1 {
                container index {
                  leaf index-number {
                    type string;
                  }
                }
              }
              case case_2 {
                leaf label {
                  type string;
                }
              }
              case case_3 {
                leaf dynamic {
                  type empty;
                }
              }
            }
          }
        }
        container ipv6-adjacency-segment {
          uses apply-advanced;
          container protected {
            choice adjsid-type {
              case case_1 {
                container index {
                  leaf index-number {
                    type string;
                  }
                }
              }
              case case_2 {
                leaf label {
                  type string;
                }
              }
              case case_3 {
                leaf dynamic {
                  type empty;
                }
              }
            }
          }
          container unprotected {
            choice adjsid-type {
              case case_1 {
                container index {
                  leaf index-number {
                    type string;
                  }
                }
              }
              case case_2 {
                leaf label {
                  type string;
                }
              }
              case case_3 {
                leaf dynamic {
                  type empty;
                }
              }
            }
          }
        }
        container srm6-adjacency-segment {
          uses apply-advanced;
          container unprotected {
            leaf sid {
              type string;
            }
          }
        }
        list topology {
          key "name";
          ordered-by user;
          leaf name {
            type string;
          }
          uses apply-advanced;
          leaf metric {
            type string;
          }
          container bandwidth-based-metrics {
            uses apply-advanced;
            list bandwidth {
              key "name";
              leaf name {
                type string;
              }
              leaf metric {
                type string;
              }
            }
          }
        }
      }
      container link-group-protection {
        uses apply-advanced;
        leaf minimum-bandwidth {
          type string;
        }
        leaf revert-bandwidth {
          type string;
        }
      }
      list interface {
        key "name";
        leaf name {
          type string;
        }
        uses apply-advanced;
        leaf weight {
          type string;
        }
      }
    }
    container spf-options {
      uses apply-group;
      uses apply-macro;
      uses apply-advanced;
      container microloop-avoidance {
        uses apply-advanced;
        container post-convergence-path {
          presence "enable post-convergence-path";
          uses apply-advanced;
          leaf delay {
            units "milliseconds";
            type string;
          }
          leaf maximum-labels {
            type string;
          }
          leaf maximum-srv6-sids {
            type string;
          }
        }
      }
      leaf delay {
        units "milliseconds";
        type string;
      }
      leaf holddown {
        units "milliseconds";
        type string;
      }
      leaf rapid-runs {
        type string;
      }
      container multipath {
        uses apply-group;
        uses apply-macro;
        uses apply-advanced;
        container weighted {
          uses apply-group;
          uses apply-macro;
          uses apply-advanced;
          leaf one-hop {
            type empty;
          }
        }
      }
      container undocumented {
        container microloop-avoidance {
          container use-route-convergence-delay {
            leaf route-convergence-delay {
              type uint32;
            }
          }
        }
      }
    }
    container traceoptions {
      uses apply-group;
      uses apply-macro;
      uses apply-advanced;
      list flag {
        key "name";
        ordered-by user;
        leaf name {
          type string;
        }
        leaf send {
          type empty;
        }
        leaf receive {
          type empty;
        }
        leaf detail {
          type empty;
        }
        leaf disable {
          type empty;
        }
      }
      container file {
        presence "";
        uses apply-group;
        uses apply-macro;
        leaf filename {
          type string;
        }
        leaf replace {
          status deprecated;
          type empty;
        }
        leaf size {
          type string;
        }
        leaf files {
          type string;
        }
        leaf no-stamp {
          status deprecated;
          type empty;
        }
        choice world-readable-choice {
          leaf world-readable {
            type empty;
          }
          leaf no-world-readable {
            type empty;
          }
        }
      }
    }
    container backup-spf-options {
      uses apply-group;
      uses apply-macro;
      uses apply-advanced;
      container remote-backup-calculation {
        presence "enable remote-backup-calculation";
        uses apply-group;
        uses apply-macro;
        uses apply-advanced;
      }
      container use-post-convergence-lfa {
        presence "enable use-post-convergence-lfa";
        uses apply-group;
        uses apply-macro;
        uses apply-advanced;
        leaf maximum-labels {
          type string;
        }
        leaf maximum-spf {
          type uint32;
        }
        leaf maximum-srv6-sids {
          type string;
        }
        leaf maximum-backup-paths {
          type string;
        }
      }
      container use-source-packet-routing {
        presence "enable use-source-packet-routing";
        uses apply-group;
        uses apply-macro;
        uses apply-advanced;
      }
      leaf per-prefix-calculation {
        type empty;
      }
      leaf node-link-degradation {
        type empty;
      }
    }
    list context-identifier {
      key "name";
      ordered-by user;
      leaf name {
        type ipprefix;
      }
      uses apply-group;
      uses apply-macro;
      uses apply-advanced;
      list level {
        key "name";
        ordered-by user;
        leaf name {
          type string;
        }
        uses apply-group;
        uses apply-macro;
        uses apply-advanced;
        choice enable-disable {
          case case_1 {
            leaf disable {
              type empty;
            }
          }
        }
      }
    }
    container traffic-engineering {
      uses apply-group;
      uses apply-macro;
      uses apply-advanced;
      choice enable-disable {
        case case_1 {
          leaf disable {
            type empty;
          }
        }
      }
      leaf igp-topology {
        type empty;
      }
      leaf l3-unicast-topology {
        type empty;
      }
      leaf ipv6 {
        type empty;
      }
      leaf credibility-protocol-preference {
        type empty;
      }
      leaf ipv4-multicast-rpf-routes {
        status deprecated;
        type empty;
      }
      leaf ignore-lsp-metrics {
        type empty;
      }
      container tunnel-source-protocol {
        uses apply-group;
        uses apply-macro;
        uses apply-advanced;
        container rsvp {
          presence "enable rsvp";
          uses apply-group;
          uses apply-macro;
          uses apply-advanced;
          leaf preference {
            type string;
          }
        }
        container spring-te {
          presence "enable spring-te";
          uses apply-group;
          uses apply-macro;
          uses apply-advanced;
          leaf preference {
            type string;
          }
        }
      }
      list family {
        key "name";
        ordered-by user;
        leaf name {
          type string;
        }
        uses apply-group;
        uses apply-macro;
        uses apply-advanced;
        container shortcuts {
          presence "enable shortcuts";
          uses apply-group;
          uses apply-macro;
          uses apply-advanced;
          leaf multicast-rpf-routes {
            type empty;
          }
          leaf-list import {
            ordered-by user;
            type policy-algebra;
          }
        }
      }
      container shortcuts {
        presence "enable shortcuts";
        status deprecated;
        uses apply-advanced;
        leaf ignore-lsp-metrics {
          status deprecated;
          type empty;
        }
      }
      container multipath {
        uses apply-group;
        uses apply-macro;
        uses apply-advanced;
        leaf lsp-equal-cost {
          type empty;
        }
      }
      container advertisement {
        uses apply-advanced;
        leaf always {
          type empty;
        }
        container application-specific {
          uses apply-advanced;
          container all-applications {
            presence "enable all-applications";
            uses apply-advanced;
            leaf legacy {
              type empty;
            }
          }
        }
      }
    }
    list label-switched-path {
      key "name";
      ordered-by user;
      leaf name {
        type key-attribute-string-type;
      }
      uses apply-group;
      uses apply-macro;
      uses apply-advanced;
      list level {
        key "name";
        ordered-by user;
        leaf name {
          type string;
        }
        uses apply-group;
        uses apply-macro;
        uses apply-advanced;
        choice enable-disable {
          case case_1 {
            leaf disable {
              type empty;
            }
          }
        }
        leaf metric {
          type string;
        }
      }
    }
    choice enable-disable {
      case case_1 {
        leaf disable {
          type empty;
        }
      }
    }
    leaf-list export {
      ordered-by user;
      type policy-algebra;
    }
    leaf-list import {
      ordered-by user;
      type policy-algebra;
    }
    leaf reference-bandwidth {
      type string;
    }
    choice layer2-map-choice {
      leaf layer2-map {
        type empty;
      }
      leaf no-layer2-map {
        type empty;
      }
    }
    leaf job-stats {
      type empty;
    }
    leaf lsp-lifetime {
      units "seconds";
      type string;
    }
    leaf max-lsp-size {
      type string;
    }
    leaf max-hello-size {
      type string;
    }
    leaf max-snp-size {
      type string;
    }
    leaf spf-delay {
      status deprecated;
      units "milliseconds";
      type string;
    }
    leaf authentication-key {
      status deprecated;
      type unreadable;
    }
    leaf authentication-type {
      status deprecated;
      type string;
    }
    leaf loose-authentication-check {
      type empty;
    }
    leaf max-areas {
      type string;
    }
    leaf no-authentication-check {
      type empty;
    }
    leaf no-ipv4-routing {
      type empty;
    }
    leaf no-ipv6-routing {
      type empty;
    }
    leaf clns-routing {
      type empty;
    }
    leaf clns-updown-compatibility {
      type empty;
    }
    leaf no-adjacency-holddown {
      type empty;
    }
    leaf multicast-topology {
      status deprecated;
      type empty;
    }
    leaf ignore-attached-bit {
      type empty;
    }
    container rib-group {
      uses rib-group-type;
    }
    container strict-dual-isis {
      presence "enable strict-dual-isis";
      uses apply-group;
      uses apply-macro;
      uses apply-advanced;
      leaf holdown {
        type string;
      }
    }
    container topologies {
      uses apply-group;
      uses apply-macro;
      uses apply-advanced;
      leaf ipv4-multicast {
        type empty;
      }
      leaf ipv6-unicast {
        type empty;
      }
      leaf ipv6-multicast {
        type empty;
      }
    }
    container overload {
      presence "enable overload";
      uses apply-group;
      uses apply-macro;
      uses apply-advanced;
      leaf timeout {
        units "seconds";
        type string;
      }
      leaf advertise-high-metrics {
        type empty;
      }
      leaf allow-route-leaking {
        type empty;
      }
      leaf internal-prefixes {
        type empty;
      }
      leaf external-prefixes {
        type empty;
      }
    }
    container graceful-restart {
      choice enable-disable {
        case case_1 {
          leaf disable {
            type empty;
          }
        }
      }
      leaf helper-disable {
        type empty;
      }
      leaf restart-duration {
        units "seconds";
        type string;
      }
    }
    container undocumented {
      leaf spf-delay {
        units "milliseconds";
        type uint32;
      }
    }
  }

  grouping juniper-protocols-l2control {
    uses apply-group;
    uses apply-macro;
    container traceoptions {
      uses apply-group;
      uses apply-macro;
      container file {
        presence "";
        uses trace-file-type;
      }
      list flag {
        key "name";
        ordered-by user;
        leaf name {
          type string;
        }
        leaf disable {
          type empty;
        }
      }
    }
    leaf nonstop-bridging {
      type empty;
    }
    container bpdu-block {
      presence "enable bpdu-block";
      uses apply-group;
      uses apply-macro;
      leaf-list interface {
        type interface-device;
        ordered-by user;
      }
      leaf disable-timeout {
        type int32;
      }
    }
    container mac-rewrite {
      uses apply-group;
      uses apply-macro;
      list interface {
        key "name";
        ordered-by user;
        leaf name {
          type interface-device;
        }
        uses apply-group;
        uses apply-macro;
        leaf enable-all-ifl {
          type empty;
        }
        container protocol {
          presence "enable protocol";
          uses apply-group;
          uses apply-macro;
          container stp {
            presence "enable stp";
            uses apply-group;
            uses apply-macro;
          }
          container vtp {
            presence "enable vtp";
            uses apply-group;
            uses apply-macro;
          }
          container cdp {
            presence "enable cdp";
            uses apply-group;
            uses apply-macro;
          }
          container ieee8021x {
            presence "enable ieee8021x";
            uses apply-group;
            uses apply-macro;
          }
          container ieee8023ah {
            presence "enable ieee8023ah";
            uses apply-group;
            uses apply-macro;
          }
          container elmi {
            presence "enable elmi";
            uses apply-group;
            uses apply-macro;
          }
          container lacp {
            presence "enable lacp";
            uses apply-group;
            uses apply-macro;
          }
          container lldp {
            presence "enable lldp";
            uses apply-group;
            uses apply-macro;
          }
          container mmrp {
            presence "enable mmrp";
            uses apply-group;
            uses apply-macro;
          }
          container mvrp {
            presence "enable mvrp";
            uses apply-group;
            uses apply-macro;
          }
          container pvstp {
            presence "enable pvstp";
            uses apply-group;
            uses apply-macro;
          }
          container gvrp {
            presence "enable gvrp";
            uses apply-group;
            uses apply-macro;
          }
          container vstp {
            presence "enable vstp";
            uses apply-group;
            uses apply-macro;
          }
          container udld {
            presence "enable udld";
            uses apply-group;
            uses apply-macro;
          }
        }
      }
    }
  }

  grouping juniper-protocols-ldp {
    uses apply-group;
    uses apply-macro;
    container traceoptions {
      uses apply-group;
      uses apply-macro;
      container file {
        presence "";
        uses trace-file-type;
      }
      list flag {
        key "name";
        ordered-by user;
        leaf name {
          type string;
        }
        leaf send {
          type empty;
        }
        leaf receive {
          type empty;
        }
        leaf detail {
          type empty;
        }
        leaf disable {
          type empty;
        }
        container filter {
          presence "";
          uses ldp-filter-obj;
        }
      }
    }
    container traffic-statistics {
      uses apply-group;
      uses apply-macro;
      container file {
        presence "";
        uses trace-file-type;
      }
      leaf interval {
        type int32;
      }
      leaf no-penultimate-hop {
        type empty;
      }
    }
    container graceful-restart {
      uses apply-group;
      uses apply-macro;
      choice choice-3 {
        leaf disable {
          type empty;
        }
      }
      leaf enable-disable {
        type string;
      }
      leaf helper-disable {
        type empty;
      }
      leaf recovery-time {
        type uint32;
      }
      leaf maximum-neighbor-recovery-time {
        type uint32;
      }
      leaf reconnect-time {
        type uint32;
      }
      leaf maximum-neighbor-reconnect-time {
        type uint32;
      }
    }
    container auto-targeted-session {
      presence "enable auto-targeted-session";
      uses apply-group;
      uses apply-macro;
      leaf teardown-delay {
        units "seconds";
        type uint32;
      }
      leaf maximum-sessions {
        type uint32;
      }
    }
    leaf preference {
      type uint32;
    }
    leaf no-forwarding {
      type empty;
    }
    leaf rib-group {
      type string;
    }
    leaf l2-smart-policy {
      type empty;
    }
    leaf track-igp-metric {
      type empty;
    }
    leaf strict-targeted-hellos {
      type empty;
    }
    container longest-match {
      presence "enable longest-match";
      uses apply-group;
      uses apply-macro;
      leaf-list policy {
        ordered-by user;
        type string;
      }
    }
    leaf-list import {
      type policy-algebra;
      ordered-by user;
    }
    leaf-list export {
      type policy-algebra;
      ordered-by user;
    }
    leaf-list egress-policy {
      type policy-algebra;
      ordered-by user;
    }
    leaf-list dod-request-policy {
      type policy-algebra;
      ordered-by user;
    }
    container next-hop {
      uses apply-group;
      uses apply-macro;
      container merged {
        uses apply-group;
        uses apply-macro;
        leaf-list policy {
          type policy-algebra;
          ordered-by user;
        }
      }
      container no-rsvp-tunneling {
        uses apply-group;
        uses apply-macro;
        leaf-list policy {
          type policy-algebra;
          ordered-by user;
        }
      }
    }
    leaf mtu-discovery {
      type empty;
    }
    leaf no-mtu-discovery {
      type empty;
    }
    leaf deaggregate {
      type empty;
    }
    leaf no-deaggregate {
      type empty;
    }
    leaf explicit-null {
      type empty;
    }
    leaf label-withdrawal-delay {
      type uint32;
    }
    container make-before-break {
      presence "enable make-before-break";
      uses apply-group;
      uses apply-macro;
      leaf timeout {
        units "seconds";
        type uint32;
      }
      leaf switchover-delay {
        units "seconds";
        type uint32;
      }
    }
    container transport-address {
      choice choice-3 {
        leaf router-id {
          type empty;
        }
        leaf interface {
          type empty;
        }
        leaf address {
          type ipaddr;
        }
      }
    }
    leaf keepalive-interval {
      type uint32;
    }
    leaf keepalive-timeout {
      type uint32;
    }
    list interface {
      key "name";
      leaf name {
        type interface-name;
      }
      uses apply-group;
      uses apply-macro;
      choice choice-3 {
        leaf disable {
          type empty;
        }
      }
      leaf enable-disable {
        type string;
      }
      leaf hello-interval {
        type uint32;
      }
      leaf hold-time {
        type uint32;
      }
      container link-protection {
        presence "enable link-protection";
        uses apply-group;
        uses apply-macro;
        leaf enable-disable {
          type string;
        }
        leaf dynamic-rsvp-lsp {
          type empty;
        }
      }
      leaf transport-address {
        type string;
      }
      leaf allow-subnet-mismatch {
        type empty;
      }
      leaf no-allow-subnet-mismatch {
        type empty;
      }
    }
    list neighbor {
      key "name";
      leaf name {
        type ipaddr;
      }
      uses apply-group;
      uses apply-macro;
    }
    list session {
      key "name";
      leaf name {
        type ipaddr;
      }
      uses apply-group;
      uses apply-macro;
      leaf authentication-key {
        type unreadable;
      }
      leaf authentication-algorithm {
        type string;
      }
      leaf authentication-key-chain {
        type string;
      }
      leaf downstream-on-demand {
        type empty;
      }
      leaf mtu-discovery {
        type empty;
      }
      leaf no-mtu-discovery {
        type empty;
      }
    }
    container undocumented {
      list session {
        key "name";
        leaf name {
          type ipaddr;
        }
        uses apply-group;
        uses apply-macro;
        leaf authentication-key {
          type unreadable;
        }
        leaf authentication-algorithm {
          type string;
        }
        leaf authentication-key-chain {
          type string;
        }
      }
    }
    list session-group {
      key "name";
      leaf name {
        type ipprefix;
      }
      uses apply-group;
      uses apply-macro;
      leaf authentication-key {
        type unreadable;
      }
      leaf authentication-algorithm {
        type string;
      }
      leaf authentication-key-chain {
        type string;
      }
      leaf downstream-on-demand {
        type empty;
      }
      leaf mtu-discovery {
        type empty;
      }
      leaf no-mtu-discovery {
        type empty;
      }
    }
    container session-protection {
      presence "enable session-protection";
      leaf timeout {
        type uint16;
      }
    }
    container igp-synchronization {
      uses apply-group;
      uses apply-macro;
      leaf holddown-interval {
        type uint32;
      }
    }
    container log-updown {
      uses apply-group;
      uses apply-macro;
      container trap {
        choice choice-3 {
          leaf disable {
            type empty;
          }
        }
        leaf enable-disable {
          type string;
        }
      }
    }
    container policing {
      uses apply-group;
      uses apply-macro;
      list fec {
        key "name";
        ordered-by user;
        leaf name {
          type ipv4prefix;
        }
        uses apply-group;
        uses apply-macro;
        leaf ingress-traffic {
          type string;
        }
        leaf transit-traffic {
          type string;
        }
      }
    }
    container entropy-label {
      uses apply-group;
      uses apply-macro;
      leaf-list ingress-policy {
        type policy-algebra;
        ordered-by user;
      }
    }
    container oam {
      uses apply-group;
      uses apply-macro;
      leaf-list ingress-policy {
        type policy-algebra;
        ordered-by user;
      }
      leaf-list bfd-port-egress-policy {
        type policy-algebra;
        ordered-by user;
      }
      list fec {
        key "name";
        ordered-by user;
        leaf name {
          type ipv4prefix;
        }
        uses apply-group;
        uses apply-macro;
        choice choice-3 {
          container bfd-liveness-detection {
            uses apply-group;
            uses apply-macro;
            leaf version {
              type string;
            }
            leaf minimum-interval {
              type uint32;
            }
            leaf minimum-receive-interval {
              type uint32;
            }
            leaf multiplier {
              type uint32;
            }
            choice choice-11 {
              leaf no-adaptation {
                type empty;
              }
            }
            container transmit-interval {
              uses apply-group;
              uses apply-macro;
              leaf minimum-interval {
                type uint32;
              }
              leaf threshold {
                type uint32;
              }
            }
            container detection-time {
              uses apply-group;
              uses apply-macro;
              leaf threshold {
                type uint32;
              }
            }
            leaf ecmp {
              type empty;
            }
            container failure-action {
              choice choice-3 {
                leaf remove-route {
                  type empty;
                }
                leaf remove-nexthop {
                  type empty;
                }
              }
            }
            leaf holddown-interval {
              type uint32;
            }
            leaf no-router-alert-option {
              type empty;
            }
            leaf use-ip-ttl-1 {
              type empty;
            }
          }
          leaf no-bfd-liveness-detection {
            type empty;
          }
        }
        container periodic-traceroute {
          presence "enable periodic-traceroute";
          uses apply-group;
          uses apply-macro;
          leaf frequency {
            type uint16;
          }
          leaf ttl {
            type uint16;
          }
          leaf retries {
            type uint16;
          }
          leaf wait {
            type uint16;
          }
          leaf paths {
            type uint16;
          }
          leaf source {
            type ipv4addr;
          }
          leaf exp {
            type uint16;
          }
          leaf fanout {
            type uint16;
          }
          leaf disable {
            type empty;
          }
        }
      }
      container bfd-liveness-detection {
        uses apply-group;
        uses apply-macro;
        leaf version {
          type string;
        }
        leaf minimum-interval {
          type uint32;
        }
        leaf minimum-receive-interval {
          type uint32;
        }
        leaf multiplier {
          type uint32;
        }
        choice choice-11 {
          leaf no-adaptation {
            type empty;
          }
        }
        container transmit-interval {
          uses apply-group;
          uses apply-macro;
          leaf minimum-interval {
            type uint32;
          }
          leaf threshold {
            type uint32;
          }
        }
        container detection-time {
          uses apply-group;
          uses apply-macro;
          leaf threshold {
            type uint32;
          }
        }
        leaf ecmp {
          type empty;
        }
        container failure-action {
          choice choice-3 {
            leaf remove-route {
              type empty;
            }
            leaf remove-nexthop {
              type empty;
            }
          }
        }
        leaf holddown-interval {
          type uint32;
        }
        leaf no-router-alert-option {
          type empty;
        }
        leaf use-ip-ttl-1 {
          type empty;
        }
      }
      container periodic-traceroute {
        presence "enable periodic-traceroute";
        uses apply-group;
        uses apply-macro;
        leaf frequency {
          type uint16;
        }
        leaf ttl {
          type uint16;
        }
        leaf retries {
          type uint16;
        }
        leaf wait {
          type uint16;
        }
        leaf paths {
          type uint16;
        }
        leaf source {
          type ipv4addr;
        }
        leaf exp {
          type uint16;
        }
        leaf fanout {
          type uint16;
        }
      }
      leaf lsp-ping-interval {
        type uint16;
      }
    }
    container targeted-hello {
      uses apply-group;
      uses apply-macro;
      leaf hello-interval {
        type uint32;
      }
      leaf hold-time {
        type uint32;
      }
    }
    container p2mp {
      presence "enable p2mp";
      uses apply-group;
      uses apply-macro;
      container recursive {
        uses apply-group;
        uses apply-macro;
        leaf route {
          type empty;
        }
      }
      list root-address {
        key "name";
        leaf name {
          type ipaddr;
        }
        uses apply-group;
        uses apply-macro;
        list lsp-id {
          key "name";
          leaf name {
            type key-attribute-ulong-type;
          }
          uses apply-group;
          uses apply-macro;
        }
        list group-address {
          key "name";
          leaf name {
            type ipaddr;
          }
          uses apply-group;
          uses apply-macro;
          list source-address {
            key "name";
            leaf name {
              type ipaddr;
            }
            uses apply-group;
            uses apply-macro;
          }
        }
      }
      leaf no-rsvp-tunneling {
        type empty;
      }
    }
    container sr-mapping-client {
      presence "enable sr-mapping-client";
      uses apply-group;
      uses apply-macro;
      leaf-list policy {
        type policy-algebra;
        ordered-by user;
      }
    }
    leaf upstream-label-assignment {
      type empty;
    }
    list family {
      key "name";
      ordered-by user;
      leaf name {
        type string;
      }
      uses apply-group;
      uses apply-macro;
    }
    leaf transport-preference {
      type string;
    }
    container dual-transport {
      presence "";
      uses apply-group;
      uses apply-macro;
      leaf inet-lsr-id {
        mandatory true;
        type ipv4addr;
      }
      leaf inet6-lsr-id {
        mandatory true;
        type ipv4addr;
      }
    }
    leaf no-propagate-ttl {
      type empty;
    }
  }

  grouping juniper-protocols-lmp {
    uses apply-group;
    uses apply-macro;
    list te-link {
      key "name";
      ordered-by user;
      leaf name {
        type string;
      }
      uses apply-group;
      uses apply-macro;
      leaf local-address {
        type ipaddr;
      }
      leaf remote-address {
        type ipaddr;
      }
      leaf remote-id {
        type uint32;
      }
      leaf te-metric {
        type uint32;
      }
      choice choice-11 {
        leaf disable {
          type empty;
        }
      }
      choice choice-12 {
        list interface {
          key "name";
          ordered-by user;
          leaf name {
            type interface-device;
          }
          uses apply-group;
          uses apply-macro;
          leaf local-address {
            type ipaddr;
          }
          leaf remote-address {
            type ipaddr;
          }
          leaf remote-id {
            type uint32;
          }
          choice choice-9 {
            leaf disable {
              type empty;
            }
          }
        }
        list label-switched-path {
          key "name";
          ordered-by user;
          leaf name {
            type string;
          }
          uses apply-group;
          uses apply-macro;
          leaf local-address {
            type ipaddr;
          }
          leaf remote-address {
            type ipaddr;
          }
          leaf remote-id {
            type uint32;
          }
          choice choice-9 {
            leaf disable {
              type empty;
            }
          }
        }
      }
    }
    list peer {
      key "name";
      ordered-by user;
      leaf name {
        type string;
      }
      uses apply-group;
      uses apply-macro;
      leaf address {
        type ipaddr;
      }
      container lmp-protocol {
        presence "enable lmp-protocol";
        uses apply-group;
        uses apply-macro;
        leaf hello-interval {
          type uint32;
        }
        leaf hello-dead-interval {
          type uint32;
        }
        leaf retransmission-interval {
          type uint32;
        }
        leaf retry-limit {
          type uint32;
        }
        leaf passive {
          type empty;
        }
      }
      leaf-list control-channel {
        type interface-name;
        ordered-by user;
      }
      list lmp-control-channel {
        key "name";
        ordered-by user;
        uses lmp-control-channel-type;
      }
      leaf-list te-link {
        type string;
        ordered-by user;
      }
    }
    container traceoptions {
      uses apply-group;
      uses apply-macro;
      container file {
        presence "";
        uses trace-file-type;
      }
      list flag {
        key "name";
        ordered-by user;
        leaf name {
          type string;
        }
      }
    }
  }

  grouping juniper-protocols-mpls {
    uses apply-group;
    uses apply-macro;
    leaf disable {
      type empty;
    }
    leaf enable-disable {
      type string;
    }
    list lsp-external-controller {
      key "name";
      ordered-by user;
      leaf name {
        type string;
      }
      uses apply-group;
      uses apply-macro;
      container label-switched-path-template {
        uses apply-group;
        uses apply-macro;
        choice choice-template-name {
          leaf template-name {
            type string;
          }
          leaf default-template {
            type empty;
          }
        }
      }
      list pce-controlled-lsp {
        key "name";
        ordered-by user;
        leaf name {
          type string;
        }
        uses apply-group;
        uses apply-macro;
        container label-switched-path-template {
          uses apply-group;
          uses apply-macro;
          leaf template-name {
            type string;
          }
        }
      }
    }
    container path-mtu {
      presence "enable path-mtu";
      uses apply-group;
      uses apply-macro;
      leaf allow-fragmentation {
        type empty;
      }
      container rsvp {
        presence "enable rsvp";
        uses apply-group;
        uses apply-macro;
        leaf mtu-signaling {
          type empty;
        }
      }
    }
    container diffserv-te {
      uses apply-group;
      uses apply-macro;
      leaf bandwidth-model {
        type string;
      }
      container te-class-matrix {
        uses apply-group;
        uses apply-macro;
        container te0 {
          presence "";
          uses te-class-object;
        }
        container te1 {
          presence "";
          uses te-class-object;
        }
        container te2 {
          presence "";
          uses te-class-object;
        }
        container te3 {
          presence "";
          uses te-class-object;
        }
        container te4 {
          presence "";
          uses te-class-object;
        }
        container te5 {
          presence "";
          uses te-class-object;
        }
        container te6 {
          presence "";
          uses te-class-object;
        }
        container te7 {
          presence "";
          uses te-class-object;
        }
      }
    }
    container auto-policing {
      presence "";
      uses apply-group;
      uses apply-macro;
      list class {
        key "name";
        ordered-by user;
        leaf name {
          type string;
        }
        uses apply-group;
        uses apply-macro;
        choice choice-drop {
          leaf drop {
            type empty;
          }
          leaf loss-priority-high {
            type empty;
          }
          leaf loss-priority-low {
            type empty;
          }
        }
      }
    }
    container statistics {
      uses apply-group;
      uses apply-macro;
      container file {
        uses apply-group;
        uses apply-macro;
        presence "";
        leaf filename {
          mandatory true;
          type string;
        }
        leaf replace {
          type empty;
        }
        leaf size {
          type string;
        }
        leaf files {
          type uint32;
        }
        leaf no-stamp {
          type empty;
        }
        leaf world-readable {
          type empty;
        }
        leaf no-world-readable {
          type empty;
        }
      }
      leaf interval {
        type int32;
      }
      leaf auto-bandwidth {
        type empty;
      }
      leaf no-transit-statistics {
        type empty;
      }
      choice choice-no-transit-statistics-polling {
        leaf no-transit-statistics-polling {
          type empty;
        }
        leaf transit-statistics-polling {
          type empty;
        }
      }
      leaf statistics-query-batch-size {
        type int32;
      }
      leaf traffic-class-statistics {
        type empty;
      }
    }
    container log-updown {
      uses apply-group;
      uses apply-macro;
      leaf syslog {
        type empty;
      }
      leaf no-syslog {
        type empty;
      }
      choice choice-trap {
        leaf trap {
          type empty;
        }
        container no-trap {
          presence "enable no-trap";
          uses apply-group;
          uses apply-macro;
          leaf mpls-lsp-traps {
            type empty;
          }
          leaf rfc3812-traps {
            type empty;
          }
        }
      }
      leaf trap-path-down {
        type empty;
      }
      leaf trap-path-up {
        type empty;
      }
    }
    container optimize-adaptive-teardown {
      uses apply-group;
      uses apply-macro;
      leaf p2p {
        type empty;
      }
      leaf timeout {
        units "seconds";
        type int32;
      }
    }
    container traffic-engineering {
      presence "enable traffic-engineering";
      uses apply-group;
      uses apply-macro;
      choice choice-bgp {
        leaf bgp {
          type empty;
        }
        leaf bgp-igp {
          type empty;
        }
        leaf bgp-igp-both-ribs {
          type empty;
        }
        leaf mpls-forwarding {
          type empty;
        }
      }
      container database {
        uses apply-group;
        uses apply-macro;
        container import {
          uses apply-group;
          uses apply-macro;
          container l3-unicast-topology {
            presence "enable l3-unicast-topology";
            uses apply-group;
            uses apply-macro;
            leaf bgp-link-state {
              type empty;
            }
          }
          container igp-topology {
            presence "enable igp-topology";
            uses apply-group;
            uses apply-macro;
            leaf bgp-link-state {
              type empty;
            }
          }
          leaf-list policy {
            type policy-algebra;
            ordered-by user;
          }
          leaf identifier {
            type uint64;
          }
          leaf bgp-ls-identifier {
            type uint32;
          }
          leaf ipv6 {
            type empty;
          }
        }
        container export {
          uses apply-group;
          uses apply-macro;
          leaf-list policy {
            type policy-algebra;
            ordered-by user;
          }
          container credibility {
            uses apply-group;
            uses apply-macro;
            leaf unknown {
              type uint32;
            }
            leaf direct {
              type uint32;
            }
            leaf static {
              type uint32;
            }
            leaf ospf {
              type uint32;
            }
            leaf isis-level-1 {
              type uint32;
            }
            leaf isis-level-2 {
              type uint32;
            }
          }
          leaf l3-unicast-topology {
            type empty;
          }
        }
      }
    }
    container traceoptions {
      uses apply-group;
      uses apply-macro;
      container file {
        uses apply-group;
        uses apply-macro;
        presence "";
        leaf filename {
          mandatory true;
          type string;
        }
        leaf replace {
          type empty;
        }
        leaf size {
          type string;
        }
        leaf files {
          type uint32;
        }
        leaf no-stamp {
          type empty;
        }
        leaf world-readable {
          type empty;
        }
        leaf no-world-readable {
          type empty;
        }
      }
      list flag {
        key "name";
        ordered-by user;
        leaf name {
          type string;
        }
      }
    }
    list admin-groups {
      key "name";
      ordered-by user;
      leaf name {
        type string;
      }
      uses apply-group;
      uses apply-macro;
      leaf group-value {
        type uint32;
      }
    }
    leaf advertisement-hold-time {
      units "seconds";
      type uint32;
    }
    leaf rsvp-error-hold-time {
      units "seconds";
      type uint32;
    }
    leaf optimize-aggressive {
      type empty;
    }
    leaf smart-optimize-timer {
      units "seconds";
      type int32;
    }
    leaf optimize-switchover-delay {
      units "seconds";
      type int32;
    }
    leaf no-propagate-ttl {
      type empty;
    }
    leaf sensor-based-stats {
      type empty;
    }
    leaf explicit-null {
      type empty;
    }
    leaf ipv6-tunneling {
      type empty;
    }
    leaf icmp-tunneling {
      type empty;
    }
    leaf revert-timer {
      units "seconds";
      type int32;
    }
    leaf optimize-hold-dead-delay {
      units "seconds";
      type int32;
    }
    leaf cspf-backoff-time {
      units "seconds";
      type string;
    }
    leaf expand-loose-hop {
      type empty;
    }
    leaf mib-mpls-show-p2mp {
      type empty;
    }
    container bandwidth {
      uses bandwidth-type;
    }
    leaf class-of-service {
      type int32;
    }
    leaf no-decrement-ttl {
      type empty;
    }
    leaf hop-limit {
      type int32;
    }
    leaf no-cspf {
      type empty;
    }
    leaf admin-down {
      type empty;
    }
    leaf optimize-timer {
      units "seconds";
      type int32;
    }
    leaf preference {
      type uint32;
    }
    choice priority-choice {
      case priority {
        leaf setup-priority {
          mandatory true;
          type uint32;
        }
        leaf reservation-priority {
          mandatory true;
          type uint32;
        }
      }
    }
    container priority {
      presence "";
      uses apply-group;
      uses apply-macro;
      leaf setup-priority {
        type uint32;
      }
      leaf reservation-priority {
        type uint32;
      }
    }
    leaf record {
      type empty;
    }
    leaf no-record {
      type empty;
    }
    leaf standby {
      type empty;
    }
    leaf exclude-srlg {
      type empty;
    }
    container admin-group {
      uses admin-group-include-exclude;
    }
    container admin-group-extended {
      uses admin-group-include-exclude;
    }
    container oam {
      uses periodic-oam;
    }
    leaf ultimate-hop-popping {
      type empty;
    }
    leaf sync-active-path-bandwidth {
      type empty;
    }
    leaf cross-credibility-cspf {
      type empty;
    }
    list label-switched-path {
      key "name";
      ordered-by user;
      leaf name {
        type string;
      }
      uses apply-group;
      uses apply-macro;
      leaf disable {
        type empty;
      }
      leaf enable-disable {
        type string;
      }
      container traceoptions {
        uses apply-group;
        uses apply-macro;
        container file {
          uses apply-group;
          uses apply-macro;
          presence "";
          leaf filename {
            mandatory true;
            type string;
          }
          leaf replace {
            type empty;
          }
          leaf size {
            type string;
          }
          leaf files {
            type uint32;
          }
          leaf no-stamp {
            type empty;
          }
          leaf world-readable {
            type empty;
          }
          leaf no-world-readable {
            type empty;
          }
        }
        list flag {
          key "name";
          ordered-by user;
          leaf name {
            type string;
          }
        }
      }
      leaf no-install-to-address {
        type empty;
      }
      leaf backup {
        type empty;
      }
      leaf from {
        type ipv4addr;
      }
      container pop-and-forward {
        presence "enable pop-and-forward";
        uses apply-group;
        uses apply-macro;
      }
      choice choice-to {
        leaf to {
          type ipv4addr;
        }
        leaf template {
          type empty;
        }
      }
      leaf corouted-bidirectional {
        type empty;
      }
      leaf corouted-bidirectional-passive {
        type empty;
      }
      leaf metric {
        type uint32;
      }
      container conditional-metric {
        uses apply-advanced;
        list igp-metric-threshold {
          key "name";
          leaf name {
            type string;
          }
          leaf conditional-metric-value {
            type string;
          }
        }
      }
      container metric-type {
        uses apply-advanced;
        choice metric-type-choice {
          case case_1 {
            leaf te {
              type empty;
            }
          }
          case case_2 {
            leaf igp {
              type empty;
            }
          }
          case case_3 {
            container delay {
              presence "enable delay";
              uses apply-advanced;
              choice metric-choice {
                case case_1 {
                  leaf minimum {
                    type empty;
                  }
                }
                case case_2 {
                  leaf maximum {
                    type empty;
                  }
                }
                case case_3 {
                  leaf average {
                    type empty;
                  }
                }
              }
              leaf delay-variation-threshold {
                type string;
              }
            }
          }
        }
      }
      leaf ldp-tunneling {
        type empty;
      }
      leaf soft-preemption {
        type empty;
      }
      list install {
        key "name";
        ordered-by user;
        leaf name {
          type ipprefix;
        }
        leaf active {
          type empty;
        }
      }
      leaf retry-timer {
        units "seconds";
        type uint32;
      }
      leaf retry-limit {
        type uint32;
      }
      container lsp-attributes {
        presence "";
        uses apply-group;
        uses apply-macro;
        leaf signal-bandwidth {
          type string;
        }
        leaf switching-type {
          mandatory true;
          type string;
        }
        leaf encoding-type {
          type string;
        }
        leaf gpid {
          type string;
        }
        container upstream-label {
          uses apply-group;
          uses apply-macro;
          leaf vlan-id {
            type uint32;
          }
        }
      }
      leaf revert-timer {
        units "seconds";
        type int32;
      }
      leaf optimize-hold-dead-delay {
        units "seconds";
        type int32;
      }
      leaf cspf-backoff-time {
        units "seconds";
        type string;
      }
      container bandwidth {
        uses bandwidth-type;
      }
      leaf class-of-service {
        type int32;
      }
      leaf no-decrement-ttl {
        type empty;
      }
      leaf hop-limit {
        type int32;
      }
      leaf no-cspf {
        type empty;
      }
      leaf admin-down {
        type empty;
      }
      leaf optimize-timer {
        units "seconds";
        type int32;
      }
      leaf preference {
        type uint32;
      }
      choice priority-choice {
        case priority {
          leaf setup-priority {
            mandatory true;
            type uint32;
          }
          leaf reservation-priority {
            mandatory true;
            type uint32;
          }
        }
      }
      container priority {
        presence "";
        uses apply-group;
        uses apply-macro;
        leaf setup-priority {
          type uint32;
        }
        leaf reservation-priority {
          type uint32;
        }
      }
      leaf record {
        type empty;
      }
      leaf no-record {
        type empty;
      }
      leaf standby {
        type empty;
      }
      leaf exclude-srlg {
        type empty;
      }
      container admin-group {
        uses admin-group-include-exclude;
      }
      container admin-group-extended {
        uses admin-group-include-exclude;
      }
      container oam {
        uses periodic-oam;
      }
      leaf ultimate-hop-popping {
        type empty;
      }
      leaf sync-active-path-bandwidth {
        type empty;
      }
      leaf cross-credibility-cspf {
        type empty;
      }
      leaf entropy-label {
        type empty;
      }
      leaf self-ping-duration {
        units "seconds";
        type int32;
      }
      leaf no-self-ping {
        type empty;
      }
      choice choice-random {
        leaf random {
          type empty;
        }
        leaf least-fill {
          type empty;
        }
        leaf most-fill {
          type empty;
        }
      }
      leaf description {
        type string;
      }
      choice choice-link-protection {
        leaf link-protection {
          type empty;
        }
        leaf node-link-protection {
          type empty;
        }
      }
      leaf intra-domain {
        type empty;
      }
      leaf inter-domain {
        type empty;
      }
      leaf adaptive {
        type empty;
      }
      container fast-reroute {
        presence "enable fast-reroute";
        uses apply-group;
        uses apply-macro;
        leaf hop-limit {
          type int32;
        }
        choice choice-bandwidth {
          leaf bandwidth {
            type string;
          }
          leaf bandwidth-percent {
            type int32;
          }
        }
        choice choice-no-include-any {
          leaf no-include-any {
            type empty;
          }
          leaf-list include-any {
            type string;
            ordered-by user;
          }
        }
        choice choice-no-include-all {
          leaf no-include-all {
            type empty;
          }
          leaf-list include-all {
            type string;
            ordered-by user;
          }
        }
        choice choice-no-exclude {
          leaf no-exclude {
            type empty;
          }
          leaf-list exclude {
            type string;
            ordered-by user;
          }
        }
      }
      container p2mp {
        presence "enable p2mp";
        leaf path_name {
          type string;
        }
      }
      container auto-bandwidth {
        presence "enable auto-bandwidth";
        uses apply-group;
        uses apply-macro;
        leaf adjust-interval {
          units "seconds";
          type uint32;
        }
        leaf adjust-threshold {
          units "percent";
          type uint32;
        }
        leaf adjust-threshold-absolute {
          type string;
          units "bps";
        }
        leaf adjust-threshold-activate-bandwidth {
          type string;
          units "bps";
        }
        leaf minimum-bandwidth {
          type string;
          units "bps";
        }
        leaf maximum-bandwidth {
          type string;
          units "bps";
        }
        leaf minimum-bandwidth-adjust-interval {
          units "seconds";
          type uint32;
        }
        leaf minimum-bandwidth-adjust-threshold-change {
          units "percent";
          type uint32;
        }
        leaf minimum-bandwidth-adjust-threshold-value {
          type string;
          units "bps";
        }
        leaf monitor-bandwidth {
          type empty;
        }
        leaf adjust-threshold-overflow-limit {
          type uint32;
        }
        leaf adjust-threshold-underflow-limit {
          type uint32;
        }
        leaf resignal-minimum-bandwidth {
          type empty;
        }
        leaf sync-active-path-bandwidth {
          type empty;
        }
      }
      container optimize-on-change {
        uses apply-group;
        uses apply-macro;
        leaf link-congestion {
          type empty;
        }
      }
      container deselect-on-bandwidth-failure {
        presence "enable deselect-on-bandwidth-failure";
        uses apply-group;
        uses apply-macro;
        leaf tear-lsp {
          type empty;
        }
      }
      container track-igp-metric {
        uses apply-group;
        uses apply-macro;
        leaf install-v4-prefixes {
          type empty;
        }
        leaf install-v6-prefixes {
          type empty;
        }
      }
      container associate-lsp {
        presence "";
        uses apply-group;
        uses apply-macro;
        leaf lsp-name {
          type string;
          mandatory true;
        }
        leaf from {
          type ipv4addr;
        }
      }
      list primary {
        key "name";
        ordered-by user;
        leaf name {
          type string;
        }
        uses apply-group;
        uses apply-macro;
        container bandwidth {
          uses bandwidth-type;
        }
        leaf class-of-service {
          type int32;
        }
        leaf no-decrement-ttl {
          type empty;
        }
        leaf hop-limit {
          type int32;
        }
        leaf no-cspf {
          type empty;
        }
        leaf admin-down {
          type empty;
        }
        leaf optimize-timer {
          units "seconds";
          type int32;
        }
        leaf preference {
          type uint32;
        }
        choice priority-choice {
          case priority {
            leaf setup-priority {
              mandatory true;
              type uint32;
            }
            leaf reservation-priority {
              mandatory true;
              type uint32;
            }
          }
        }
        container priority {
          presence "";
          uses apply-group;
          uses apply-macro;
          leaf setup-priority {
            type uint32;
          }
          leaf reservation-priority {
            type uint32;
          }
        }
        leaf record {
          type empty;
        }
        leaf no-record {
          type empty;
        }
        leaf standby {
          type empty;
        }
        leaf exclude-srlg {
          type empty;
        }
        container admin-group {
          uses admin-group-include-exclude;
        }
        container admin-group-extended {
          uses admin-group-include-exclude;
        }
        container oam {
          uses periodic-oam;
        }
        leaf ultimate-hop-popping {
          type empty;
        }
        leaf sync-active-path-bandwidth {
          type empty;
        }
        leaf cross-credibility-cspf {
          type empty;
        }
        leaf adaptive {
          type empty;
        }
        leaf select {
          type string;
        }
        container upstream-label {
          uses apply-group;
          uses apply-macro;
          leaf vlan-id {
            type uint32;
          }
        }
        container optimize-on-change {
          uses apply-group;
          uses apply-macro;
          leaf link-congestion {
            type empty;
          }
        }
      }
      list secondary {
        key "name";
        ordered-by user;
        leaf name {
          type string;
        }
        uses apply-group;
        uses apply-macro;
        container bandwidth {
          uses bandwidth-type;
        }
        leaf class-of-service {
          type int32;
        }
        leaf no-decrement-ttl {
          type empty;
        }
        leaf hop-limit {
          type int32;
        }
        leaf no-cspf {
          type empty;
        }
        leaf admin-down {
          type empty;
        }
        leaf optimize-timer {
          units "seconds";
          type int32;
        }
        leaf preference {
          type uint32;
        }
        choice priority-choice {
          case priority {
            leaf setup-priority {
              mandatory true;
              type uint32;
            }
            leaf reservation-priority {
              mandatory true;
              type uint32;
            }
          }
        }
        container priority {
          presence "";
          uses apply-group;
          uses apply-macro;
          leaf setup-priority {
            type uint32;
          }
          leaf reservation-priority {
            type uint32;
          }
        }
        leaf record {
          type empty;
        }
        leaf no-record {
          type empty;
        }
        leaf standby {
          type empty;
        }
        leaf exclude-srlg {
          type empty;
        }
        container admin-group {
          uses admin-group-include-exclude;
        }
        container admin-group-extended {
          uses admin-group-include-exclude;
        }
        container oam {
          uses periodic-oam;
        }
        leaf ultimate-hop-popping {
          type empty;
        }
        leaf sync-active-path-bandwidth {
          type empty;
        }
        leaf cross-credibility-cspf {
          type empty;
        }
        leaf adaptive {
          type empty;
        }
        leaf select {
          type string;
        }
        container upstream-label {
          uses apply-group;
          uses apply-macro;
          leaf vlan-id {
            type uint32;
          }
        }
        container optimize-on-change {
          uses apply-group;
          uses apply-macro;
          leaf link-congestion {
            type empty;
          }
        }
      }
      container policing {
        leaf filter {
          type string;
        }
        leaf no-auto-policing {
          type empty;
        }
      }
      leaf lsp-external-controller {
        type string;
      }
      leaf associate-backup-pe-groups {
        type empty;
      }
      leaf egress-protection {
        type empty;
      }
      leaf transport-class {
        type string;
      }
    }
    container deselect-on-bandwidth-failure {
      presence "enable deselect-on-bandwidth-failure";
      uses apply-group;
      uses apply-macro;
      leaf tear-lsp {
        type empty;
      }
    }
    container track-igp-metric {
      uses apply-group;
      uses apply-macro;
      leaf install-v4-prefixes {
        type empty;
      }
      leaf install-v6-prefixes {
        type empty;
      }
    }
    list container-label-switched-path {
      key "name";
      ordered-by user;
      leaf name {
        type string;
      }
      uses apply-group;
      uses apply-macro;
      leaf enable-disable {
        type string;
      }
      leaf description {
        type string;
      }
      container label-switched-path-template {
        uses apply-group;
        uses apply-macro;
        choice choice-template-name {
          leaf template-name {
            type string;
          }
          leaf default-template {
            type empty;
          }
        }
      }
      leaf to {
        mandatory true;
        type ipv4addr;
      }
      leaf suffix {
        type string;
      }
      container splitting-merging {
        uses apply-group;
        uses apply-macro;
        leaf maximum-member-lsps {
          type int32;
        }
        leaf minimum-member-lsps {
          type int32;
        }
        leaf splitting-bandwidth {
          type string;
          units "bps";
        }
        leaf merging-bandwidth {
          type string;
          units "bps";
        }
        leaf maximum-signaling-bandwidth {
          type string;
          units "bps";
        }
        leaf minimum-signaling-bandwidth {
          type string;
          units "bps";
        }
        leaf splitting-merging-threshold {
          units "percent";
          type uint32;
        }
        container normalization {
          uses apply-group;
          uses apply-macro;
          leaf normalize-interval {
            units "seconds";
            type uint32;
          }
          leaf failover-normalization {
            type empty;
          }
          leaf no-incremental-normalize {
            type empty;
          }
          leaf normalization-retry-duration {
            units "seconds";
            type uint32;
          }
          leaf normalization-retry-limits {
            type uint32;
          }
        }
        container sampling {
          uses apply-group;
          uses apply-macro;
          leaf cut-off-threshold {
            type uint32;
          }
          choice choice-use-average-aggregate {
            leaf use-average-aggregate {
              type empty;
            }
            leaf use-percentile {
              type uint32;
            }
          }
        }
      }
      leaf lsp-external-controller {
        type string;
      }
    }
    list transit-lsp-association {
      key "name";
      ordered-by user;
      leaf name {
        type string;
      }
      uses apply-group;
      uses apply-macro;
      leaf lsp-name-1 {
        type string;
      }
      leaf from-1 {
        type ipv4addr;
      }
      leaf lsp-name-2 {
        type string;
      }
      leaf from-2 {
        type ipv4addr;
      }
    }
    list path {
      key "name";
      ordered-by user;
      leaf name {
        type string;
      }
      uses apply-group;
      uses apply-macro;
      list path-list {
        key "name";
        ordered-by user;
        leaf name {
          type string;
        }
        leaf abstract {
          type empty;
        }
        choice choice-loose {
          leaf loose {
            type empty;
          }
          leaf loose-link {
            type empty;
          }
          leaf strict {
            type empty;
          }
        }
        leaf loose-strict-none {
          type string;
        }
      }
    }
    list static-label-switched-path {
      key "name";
      ordered-by user;
      leaf name {
        type string;
      }
      uses apply-group;
      uses apply-macro;
      choice choice-bypass {
        container bypass {
          presence "";
          uses apply-group;
          uses apply-macro;
          leaf bandwidth {
            type string;
            units "bps";
          }
          leaf description {
            type string;
          }
          leaf next-hop {
            type ipaddr-or-interface;
          }
          leaf next-table {
            type string;
          }
          leaf push {
            type uint32;
          }
          leaf to {
            mandatory true;
            type ipaddr;
          }
        }
        list transit {
          key "name";
          ordered-by user;
          leaf name {
            type string;
          }
          uses apply-group;
          uses apply-macro;
          leaf bandwidth {
            type string;
            units "bps";
          }
          leaf description {
            type string;
          }
          container link-protection {
            presence "";
            leaf bypass-name {
              type string;
              mandatory true;
            }
          }
          leaf next-hop {
            mandatory true;
            type ipaddr-or-interface;
          }
          leaf member-interface {
            type interface-unit;
          }
          container node-protection {
            presence "";
            leaf bypass-name {
              type string;
              mandatory true;
            }
            leaf next-next-label {
              type uint32;
            }
          }
          choice choice-swap {
            leaf swap {
              type uint32;
            }
            leaf pop {
              type empty;
            }
            leaf stitch {
              type empty;
            }
          }
        }
        container ingress {
          presence "";
          uses apply-group;
          uses apply-macro;
          leaf bandwidth {
            type string;
            units "bps";
          }
          leaf class-of-service {
            type int32;
          }
          leaf description {
            type string;
          }
          list install {
            key "name";
            ordered-by user;
            leaf name {
              type ipv4prefix;
            }
            leaf active {
              type empty;
            }
          }
          leaf metric {
            type uint32;
          }
          leaf next-hop {
            mandatory true;
            type ipv4addr-or-interface;
          }
          container link-protection {
            presence "";
            leaf bypass-name {
              type string;
              mandatory true;
            }
          }
          container node-protection {
            presence "";
            leaf bypass-name {
              type string;
              mandatory true;
            }
            leaf next-next-label {
              type uint32;
            }
          }
          leaf no-install-to-address {
            type empty;
          }
          container policing {
            leaf filter {
              type string;
            }
            leaf no-auto-policing {
              type empty;
            }
          }
          leaf preference {
            type uint32;
          }
          leaf to {
            mandatory true;
            type ipv4addr;
          }
          leaf push {
            type uint32;
          }
          leaf entropy-label {
            type empty;
          }
        }
        container segment {
          presence "";
          uses apply-group;
          uses apply-macro;
          leaf sid-label {
            mandatory true;
            type uint32;
          }
          leaf description {
            type string;
          }
          leaf next-hop {
            mandatory true;
            type ipv4addr-or-interface;
          }
          choice choice-swap {
            leaf swap {
              type uint32;
            }
            leaf pop {
              type empty;
            }
          }
        }
      }
    }
    list constituent-list {
      key "name";
      ordered-by user;
      leaf name {
        type string;
      }
      uses apply-group;
      uses apply-macro;
      leaf-list srlg {
        type string;
        ordered-by user;
      }
      leaf-list admin-group {
        type string;
        ordered-by user;
      }
      leaf-list admin-group-extended {
        type string;
        ordered-by user;
      }
    }
    list abstract-hop {
      key "name";
      ordered-by user;
      leaf name {
        type string;
      }
      uses apply-group;
      uses apply-macro;
      leaf operator {
        mandatory true;
        type string;
      }
      list constituent-list {
        key "name";
        ordered-by user;
        leaf name {
          type key-attribute-string-type;
        }
        uses apply-group;
        uses apply-macro;
        choice choice-include-any-list {
          leaf include-any-list {
            type empty;
          }
          leaf include-all-list {
            type empty;
          }
          leaf exclude-any-list {
            type empty;
          }
          leaf exclude-all-list {
            type empty;
          }
        }
      }
    }
    list interface {
      key "name";
      ordered-by user;
      leaf name {
        type interface-name;
      }
      uses apply-group;
      uses apply-macro;
      leaf disable {
        type empty;
      }
      leaf enable-disable {
        type string;
      }
      leaf-list srlg {
        type string;
        ordered-by user;
      }
      leaf always-mark-connection-protection-tlv {
        type empty;
      }
      leaf switch-away-lsps {
        type empty;
      }
      leaf-list admin-group {
        type string;
        ordered-by user;
      }
      leaf-list admin-group-extended {
        type string;
        ordered-by user;
      }
      container static {
        uses apply-group;
        uses apply-macro;
        leaf protection-revert-time {
          units "seconds";
          type uint32;
        }
      }
    }
    container egress-protection {
      uses apply-group;
      uses apply-macro;
      list context-identifier {
        key "name";
        leaf name {
          type ipv4addr;
        }
        uses apply-group;
        uses apply-macro;
        choice choice-primary {
          leaf primary {
            type empty;
          }
          leaf protector {
            type empty;
          }
        }
        leaf metric {
          type uint32;
        }
        leaf advertise-mode {
          type string;
        }
        leaf-list admin-group {
          type string;
          ordered-by user;
        }
      }
      container traceoptions {
        uses apply-group;
        uses apply-macro;
        container file {
          uses apply-group;
          uses apply-macro;
          presence "";
          leaf filename {
            mandatory true;
            type string;
          }
          leaf replace {
            type empty;
          }
          leaf size {
            type string;
          }
          leaf files {
            type uint32;
          }
          leaf no-stamp {
            type empty;
          }
          leaf world-readable {
            type empty;
          }
          leaf no-world-readable {
            type empty;
          }
        }
        list flag {
          key "name";
          ordered-by user;
          leaf name {
            type string;
          }
        }
      }
    }
    container label-history {
      presence "enable label-history";
      uses apply-group;
      uses apply-macro;
      leaf max-entries {
        type uint32;
      }
    }
    container label-range {
      uses apply-group;
      uses apply-macro;
      list lsi-label-range {
        key "name";
        ordered-by user;
        leaf name {
          type key-attribute-ulong-type;
        }
        leaf range-end {
          type uint32;
        }
      }
      list dynamic-label-range {
        key "name";
        ordered-by user;
        leaf name {
          type key-attribute-ulong-type;
        }
        leaf range-end {
          type uint32;
        }
      }
      list block-label-range {
        key "name";
        ordered-by user;
        leaf name {
          type string;
        }
        leaf range-end {
          type string;
        }
      }
      list srgb-label-range {
        key "name";
        ordered-by user;
        leaf name {
          type string;
        }
        leaf range-end {
          type string;
        }
      }
      leaf label-limit {
        type string;
      }
      list static-label-range {
        key "name";
        ordered-by user;
        leaf name {
          type key-attribute-ulong-type;
        }
        leaf range-end {
          type uint32;
        }
      }
    }
  }

  grouping juniper-protocols-mobile-ipv4 {
    uses apply-group;
    uses apply-macro;
    container traceoptions {
      uses mip-trace-options-type;
    }
    container authenticate {
      leaf order {
        type string;
      }
    }
    container home-agent {
      uses mip-home-agent-type;
    }
    container peer {
      uses mip-peer-type;
    }
    container access-type {
      uses mip-access-type;
    }
    container dynamic-home-assignment {
      uses dynamic-home-assignment-type;
    }
  }

  grouping dynamic-home-assignment-type {
    uses apply-group;
    uses apply-macro;
    container home-agent {
      list nai {
        key "name";
        ordered-by user;
        leaf name {
          type key-attribute-string-type;
        }
        leaf home-agent {
          type ipv4addr;
        }
      }
    }
  }

  grouping juniper-protocols-msdp {
    uses apply-group;
    uses apply-macro;
    leaf data-encapsulation {
      type string;
    }
    container rib-group {
      presence "";
      uses rib-group-inet-type;
    }
    container active-source-limit {
      uses apply-group;
      uses apply-macro;
      leaf maximum {
        type uint32;
      }
      leaf threshold {
        type uint32;
      }
    }
    choice choice-9 {
      leaf disable {
        type empty;
      }
    }
    leaf-list export {
      type policy-algebra;
      ordered-by user;
    }
    leaf-list import {
      type policy-algebra;
      ordered-by user;
    }
    leaf local-address {
      type ipv4addr;
    }
    container traceoptions {
      uses apply-group;
      uses apply-macro;
      container file {
        presence "";
        uses trace-file-type;
      }
      list flag {
        key "name";
        ordered-by user;
        leaf name {
          type string;
        }
        leaf send {
          type empty;
        }
        leaf receive {
          type empty;
        }
        leaf detail {
          type empty;
        }
        leaf disable {
          type empty;
        }
      }
    }
    list peer {
      key "name";
      ordered-by user;
      leaf name {
        type ipv4addr;
      }
      uses apply-group;
      uses apply-macro;
      choice choice-3 {
        leaf disable {
          type empty;
        }
      }
      leaf-list export {
        type policy-algebra;
        ordered-by user;
      }
      leaf-list import {
        type policy-algebra;
        ordered-by user;
      }
      leaf local-address {
        type ipv4addr;
      }
      container traceoptions {
        uses apply-group;
        uses apply-macro;
        container file {
          presence "";
          uses trace-file-type;
        }
        list flag {
          key "name";
          ordered-by user;
          leaf name {
            type string;
          }
          leaf send {
            type empty;
          }
          leaf receive {
            type empty;
          }
          leaf detail {
            type empty;
          }
          leaf disable {
            type empty;
          }
        }
      }
      container active-source-limit {
        uses apply-group;
        uses apply-macro;
        leaf maximum {
          type uint32;
        }
        leaf threshold {
          type uint32;
        }
      }
      leaf default-peer {
        type empty;
      }
      leaf authentication-key {
        type unreadable;
      }
    }
    list source {
      key "name";
      ordered-by user;
      leaf name {
        type ipprefix;
      }
      uses apply-group;
      uses apply-macro;
      container active-source-limit {
        uses apply-group;
        uses apply-macro;
        leaf maximum {
          type uint32;
        }
        leaf threshold {
          type uint32;
        }
      }
    }
    list group {
      key "name";
      ordered-by user;
      leaf name {
        type string;
      }
      uses apply-group;
      uses apply-macro;
      leaf mode {
        type string;
      }
      choice choice-5 {
        leaf disable {
          type empty;
        }
      }
      leaf-list export {
        type policy-algebra;
        ordered-by user;
      }
      leaf-list import {
        type policy-algebra;
        ordered-by user;
      }
      leaf local-address {
        type ipv4addr;
      }
      container traceoptions {
        uses apply-group;
        uses apply-macro;
        container file {
          presence "";
          uses trace-file-type;
        }
        list flag {
          key "name";
          ordered-by user;
          leaf name {
            type string;
          }
          leaf send {
            type empty;
          }
          leaf receive {
            type empty;
          }
          leaf detail {
            type empty;
          }
          leaf disable {
            type empty;
          }
        }
      }
      list peer {
        key "name";
        ordered-by user;
        leaf name {
          type ipv4addr;
        }
        uses apply-group;
        uses apply-macro;
        choice choice-3 {
          leaf disable {
            type empty;
          }
        }
        leaf enable-disable {
          type string;
        }
        leaf-list export {
          type policy-algebra;
          ordered-by user;
        }
        leaf-list import {
          type policy-algebra;
          ordered-by user;
        }
        leaf local-address {
          type ipv4addr;
        }
        container traceoptions {
          uses apply-group;
          uses apply-macro;
          container file {
            presence "";
            uses trace-file-type;
          }
          list flag {
            key "name";
            ordered-by user;
            leaf name {
              type string;
            }
            leaf send {
              type empty;
            }
            leaf receive {
              type empty;
            }
            leaf detail {
              type empty;
            }
            leaf disable {
              type empty;
            }
          }
        }
        container active-source-limit {
          uses apply-group;
          uses apply-macro;
          leaf maximum {
            type uint32;
          }
          leaf threshold {
            type uint32;
          }
          leaf log-warning {
            type uint32;
          }
          leaf log-interval {
            type uint32;
          }
        }
        leaf keep-alive {
          units "seconds";
          type uint32;
        }
        leaf hold-time {
          units "seconds";
          type uint32;
        }
        leaf sa-hold-time {
          units "seconds";
          type uint32;
        }
        leaf default-peer {
          type empty;
        }
        leaf authentication-key {
          type unreadable;
        }
      }
    }
  }

  grouping juniper-protocols-mstp {
    uses apply-group;
    uses apply-macro;
    choice choice-3 {
      leaf disable {
        type empty;
      }
    }
    leaf bpdu-destination-mac-address {
      type string;
    }
    leaf configuration-name {
      type string;
    }
    leaf revision-level {
      type uint16;
    }
    leaf max-hops {
      type uint16;
    }
    leaf max-age {
      type uint16;
    }
    leaf hello-time {
      type uint16;
    }
    leaf forward-delay {
      type uint16;
    }
    container traceoptions {
      uses stp-trace-options;
    }
    leaf bridge-priority {
      type string;
    }
    leaf backup-bridge-priority {
      type string;
    }
    leaf bpdu-block-on-edge {
      type empty;
    }
    leaf vpls-flush-on-topology-change {
      type empty;
    }
    leaf priority-hold-time {
      type uint16;
    }
    list system-id {
      key "name";
      ordered-by user;
      uses system-id-ip-map;
    }
    list interface {
      key "name";
      uses stp-interface;
    }
    list msti {
      key "name";
      leaf name {
        type string;
      }
      uses apply-group;
      uses apply-macro;
      leaf bridge-priority {
        type string;
      }
      leaf backup-bridge-priority {
        type string;
      }
      leaf-list vlan {
        type string;
        ordered-by user;
      }
      list interface {
        key "name";
        uses stp-interface;
      }
    }
  }

  grouping juniper-protocols-mvrp {
    uses apply-group;
    uses apply-macro;
    container traceoptions {
      uses mrp-trace-options;
    }
    leaf join-timer {
      type uint16;
    }
    leaf leave-timer {
      type uint16;
    }
    leaf leaveall-timer {
      type uint16;
    }
    leaf no-dynamic-vlan {
      type empty;
    }
    leaf bpdu-destination-mac-address {
      type string;
    }
    list interface {
      key "name";
      ordered-by user;
      leaf name {
        type interface-device;
      }
      uses apply-group;
      uses apply-macro;
      leaf join-timer {
        type uint16;
      }
      leaf leave-timer {
        type uint16;
      }
      leaf leaveall-timer {
        type uint16;
      }
      leaf point-to-point {
        type empty;
      }
      leaf registration {
        type string;
      }
    }
  }

  grouping juniper-protocols-ospf {
    uses apply-group;
    uses apply-macro;
    leaf enable-disable {
      type string;
    }
    choice choice-3 {
      leaf disable {
        type empty;
      }
    }
    container traceoptions {
      uses apply-group;
      uses apply-macro;
      container file {
        presence "";
        uses trace-file-type;
      }
      list flag {
        key "name";
        ordered-by user;
        leaf name {
          type string;
        }
        leaf send {
          type empty;
        }
        leaf receive {
          type empty;
        }
        leaf detail {
          type empty;
        }
        leaf disable {
          type empty;
        }
      }
    }
    list topology {
      key "name";
      ordered-by user;
      leaf name {
        type string;
      }
      uses apply-group;
      uses apply-macro;
      leaf disable {
        type empty;
      }
      leaf topology-id {
        type uint8;
      }
      leaf overload {
        type empty;
      }
      leaf rib-group {
        type string;
      }
      container spf-options {
        uses apply-group;
        uses apply-macro;
        leaf delay {
          type uint32;
        }
        leaf holddown {
          type uint32;
        }
        leaf rapid-runs {
          type uint32;
        }
        leaf no-ignore-our-externals {
          type empty;
        }
      }
      container backup-spf-options {
        uses apply-group;
        uses apply-macro;
        leaf disable {
          type empty;
        }
        leaf no-install {
          type empty;
        }
        leaf downstream-paths-only {
          type empty;
        }
        container remote-backup-calculation {
          presence "enable remote-backup-calculation";
          uses apply-group;
          uses apply-macro;
        }
        container use-post-convergence-lfa {
          presence "enable use-post-convergence-lfa";
          uses apply-group;
          uses apply-macro;
          leaf maximum-labels {
            type uint32;
          }
          leaf maximum-backup-paths {
            type uint32;
          }
        }
        container per-prefix-calculation {
          uses apply-group;
          uses apply-macro;
          leaf stubs {
            type empty;
          }
          leaf summary {
            type empty;
          }
          leaf externals {
            type empty;
          }
          leaf all {
            type empty;
          }
        }
        leaf node-link-degradation {
          type empty;
        }
        leaf use-source-packet-routing {
          type empty;
        }
      }
      leaf prefix-export-limit {
        type uint32;
      }
    }
    container spf-options {
      uses apply-group;
      uses apply-macro;
      leaf delay {
        type uint32;
      }
      leaf holddown {
        type uint32;
      }
      leaf rapid-runs {
        type uint32;
      }
      leaf no-ignore-our-externals {
        type empty;
      }
    }
    container backup-spf-options {
      uses apply-group;
      uses apply-macro;
      leaf disable {
        type empty;
      }
      leaf no-install {
        type empty;
      }
      leaf downstream-paths-only {
        type empty;
      }
      container remote-backup-calculation {
        presence "enable remote-backup-calculation";
        uses apply-group;
        uses apply-macro;
      }
      container use-post-convergence-lfa {
        presence "enable use-post-convergence-lfa";
        uses apply-group;
        uses apply-macro;
        leaf maximum-labels {
          type uint32;
        }
        leaf maximum-backup-paths {
          type uint32;
        }
      }
      container per-prefix-calculation {
        uses apply-group;
        uses apply-macro;
        leaf stubs {
          type empty;
        }
        leaf summary {
          type empty;
        }
        leaf externals {
          type empty;
        }
        leaf all {
          type empty;
        }
      }
      leaf node-link-degradation {
        type empty;
      }
      leaf use-source-packet-routing {
        type empty;
      }
    }
    leaf prefix-export-limit {
      type uint32;
    }
    leaf rib-group {
      type string;
    }
    container overload {
      presence "enable overload";
      uses apply-group;
      uses apply-macro;
      leaf timeout {
        units "seconds";
        type uint32;
      }
      leaf allow-route-leaking {
        type empty;
      }
      leaf stub-network {
        type empty;
      }
      leaf intra-area-prefix {
        type empty;
      }
      leaf as-external {
        type empty;
      }
    }
    container database-protection {
      presence "";
      uses apply-group;
      uses apply-macro;
      leaf maximum-lsa {
        type uint32;
      }
      leaf warning-only {
        type empty;
      }
      leaf warning-threshold {
        type uint8;
      }
      leaf ignore-count {
        type uint8;
      }
      leaf ignore-time {
        type uint16;
      }
      leaf reset-time {
        type uint32;
      }
    }
    container graceful-restart {
      uses apply-group;
      uses apply-macro;
      choice choice-3 {
        leaf disable {
          type empty;
        }
      }
      leaf enable-disable {
        type string;
      }
      leaf restart-duration {
        type uint32;
      }
      leaf notify-duration {
        type uint32;
      }
      container helper-disable {
        presence "enable helper-disable";
        uses apply-group;
        uses apply-macro;
        choice choice-standard {
          leaf standard {
            type empty;
          }
          leaf restart-signaling {
            type empty;
          }
          leaf both {
            type empty;
          }
        }
      }
      leaf no-strict-lsa-checking {
        type empty;
      }
    }
    container traffic-engineering {
      presence "enable traffic-engineering";
      uses apply-group;
      uses apply-macro;
      leaf no-topology {
        type empty;
      }
      leaf l3-unicast-topology {
        type empty;
      }
      leaf multicast-rpf-routes {
        type empty;
      }
      leaf igp-topology {
        type empty;
      }
      container shortcuts {
        presence "enable shortcuts";
        uses apply-group;
        uses apply-macro;
        leaf ignore-lsp-metrics {
          type empty;
        }
        leaf lsp-metric-into-summary {
          type empty;
        }
      }
      leaf advertise-unnumbered-interfaces {
        type empty;
      }
      leaf credibility-protocol-preference {
        type empty;
      }
      container advertisement {
        uses apply-group;
        uses apply-macro;
        leaf always {
          type empty;
        }
      }
    }
    leaf route-type-community {
      type string;
    }
    container domain-id {
      choice choice-3 {
        leaf domain-id {
          type string;
        }
        leaf disable {
          type empty;
        }
      }
    }
    choice choice-28 {
      leaf domain-vpn-tag {
        type uint32;
      }
      leaf no-domain-vpn-tag {
        type empty;
      }
    }
    leaf preference {
      type uint32;
    }
    leaf external-preference {
      type uint32;
    }
    leaf labeled-preference {
      type uint32;
    }
    leaf-list export {
      type policy-algebra;
      ordered-by user;
    }
    leaf-list import {
      type policy-algebra;
      ordered-by user;
    }
    leaf reference-bandwidth {
      type string;
    }
    leaf lsa-refresh-interval {
      type uint32;
    }
    leaf spf-delay {
      units "milliseconds";
      type uint32;
    }
    leaf no-rfc-1583 {
      type empty;
    }
    container source-packet-routing {
      presence "enable source-packet-routing";
      uses apply-group;
      uses apply-macro;
      container adjacency-segment {
        uses apply-group;
        uses apply-macro;
        leaf hold-time {
          type uint32;
        }
      }
      leaf-list prefix-segment {
        type policy-algebra;
        ordered-by user;
      }
      leaf explicit-null {
        type empty;
      }
      container node-segment {
        presence "enable node-segment";
        uses apply-group;
        uses apply-macro;
        leaf ipv4-index {
          type string;
        }
        leaf index-range {
          type uint32;
        }
      }
      container srgb {
        presence "";
        leaf start-label {
          mandatory true;
          type uint32;
        }
        leaf index-range {
          mandatory true;
          type uint32;
        }
      }
      leaf mapping-server {
        type string;
      }
      leaf install-prefix-sid-for-best-route {
        type empty;
      }
      leaf ldp-stitching {
        type empty;
      }
    }
    leaf forwarding-address-to-broadcast {
      type empty;
    }
    choice choice-41 {
      leaf no-nssa-abr {
        type empty;
      }
    }
    container sham-link {
      presence "enable sham-link";
      uses apply-group;
      uses apply-macro;
      leaf local {
        type ipaddr;
      }
      leaf no-advertise-local {
        type empty;
      }
    }
    list area {
      key "name";
      ordered-by user;
      leaf name {
        type areaid;
      }
      uses apply-group;
      uses apply-macro;
      choice choice-3 {
        container stub {
          presence "enable stub";
          leaf default-metric {
            type uint32;
          }
          leaf summaries {
            type empty;
          }
          leaf no-summaries {
            type empty;
          }
        }
        container nssa {
          presence "enable nssa";
          uses apply-group;
          uses apply-macro;
          container default-lsa {
            presence "enable default-lsa";
            uses apply-group;
            uses apply-macro;
            leaf default-metric {
              type uint32;
            }
            leaf metric-type {
              type uint32;
            }
            leaf type-7 {
              type empty;
            }
          }
          leaf summaries {
            type empty;
          }
          leaf no-summaries {
            type empty;
          }
          list area-range {
            key "name";
            ordered-by user;
            leaf name {
              type ipprefix;
            }
            uses apply-group;
            uses apply-macro;
            leaf restrict {
              type empty;
            }
            leaf exact {
              type empty;
            }
            container override-metric {
              presence "";
              uses apply-group;
              uses apply-macro;
              leaf metric {
                type uint32;
              }
              leaf metric-type {
                type uint32;
              }
            }
          }
        }
      }
      list area-range {
        key "name";
        ordered-by user;
        leaf name {
          type ipprefix;
        }
        uses apply-group;
        uses apply-macro;
        leaf restrict {
          type empty;
        }
        leaf exact {
          type empty;
        }
        leaf override-metric {
          type uint32;
        }
      }
      leaf-list network-summary-export {
        type policy-algebra;
        ordered-by user;
      }
      leaf-list network-summary-import {
        type policy-algebra;
        ordered-by user;
      }
      leaf-list inter-area-prefix-export {
        type policy-algebra;
        ordered-by user;
      }
      leaf-list inter-area-prefix-import {
        type policy-algebra;
        ordered-by user;
      }
      leaf authentication-type {
        type string;
      }
      list virtual-link {
        key "neighbor-id transit-area";
        ordered-by user;
        leaf neighbor-id {
          type ipv4addr;
        }
        leaf transit-area {
          type areaid;
        }
        uses apply-group;
        uses apply-macro;
        leaf enable-disable {
          type string;
        }
        choice choice-3 {
          leaf disable {
            type empty;
          }
        }
        leaf retransmit-interval {
          type uint32;
        }
        leaf transit-delay {
          type uint32;
        }
        leaf hello-interval {
          type uint32;
        }
        leaf dead-interval {
          type uint32;
        }
        leaf mtu {
          type uint32;
        }
        choice choice-12 {
          container authentication {
            uses juniper-ospf-authentication;
          }
          container authentication-key {
            presence "";
            leaf keyname {
              mandatory true;
              type unreadable;
            }
            leaf key-id {
              type uint32;
            }
          }
        }
        leaf demand-circuit {
          type empty;
        }
        leaf flood-reduction {
          type empty;
        }
        leaf no-neighbor-down-notification {
          type empty;
        }
        leaf ipsec-sa {
          type string;
        }
        list topology {
          key "name";
          ordered-by user;
          leaf name {
            type string;
          }
          uses apply-group;
          uses apply-macro;
          leaf disable {
            type empty;
          }
          leaf metric {
            type uint16;
          }
          container bandwidth-based-metrics {
            uses apply-group;
            uses apply-macro;
            list bandwidth {
              key "name";
              leaf name {
                type string;
              }
              leaf metric {
                type uint16;
              }
            }
          }
        }
      }
      list sham-link-remote {
        key "name";
        ordered-by user;
        leaf name {
          type ipaddr;
        }
        uses apply-group;
        uses apply-macro;
        leaf metric {
          type uint16;
        }
        leaf ipsec-sa {
          type string;
        }
        leaf demand-circuit {
          type empty;
        }
        leaf flood-reduction {
          type empty;
        }
        list topology {
          key "name";
          ordered-by user;
          leaf name {
            type string;
          }
          uses apply-group;
          uses apply-macro;
          leaf disable {
            type empty;
          }
          leaf metric {
            type uint16;
          }
          container bandwidth-based-metrics {
            uses apply-group;
            uses apply-macro;
            list bandwidth {
              key "name";
              leaf name {
                type string;
              }
              leaf metric {
                type uint16;
              }
            }
          }
        }
      }
      list interface {
        key "name";
        ordered-by user;
        leaf name {
          type ipv4addr-or-interface;
        }
        uses apply-group;
        uses apply-macro;
        leaf enable-disable {
          type string;
        }
        choice choice-3 {
          leaf disable {
            type empty;
          }
        }
        leaf interface-type {
          type string;
        }
        container post-convergence-lfa {
          presence "enable post-convergence-lfa";
          uses apply-group;
          uses apply-macro;
          container node-protection {
            presence "enable node-protection";
            uses apply-group;
            uses apply-macro;
            leaf cost {
              type uint16;
            }
          }
        }
        choice choice-6 {
          leaf link-protection {
            type empty;
          }
          leaf node-link-protection {
            type empty;
          }
        }
        leaf no-eligible-backup {
          type empty;
        }
        leaf no-eligible-remote-backup {
          type empty;
        }
        container passive {
          presence "enable passive";
          uses apply-group;
          uses apply-macro;
          container traffic-engineering {
            uses apply-group;
            uses apply-macro;
            leaf remote-node-id {
              type ipaddr;
            }
            leaf remote-node-router-id {
              type ipv4addr;
            }
          }
        }
        leaf secondary {
          type empty;
        }
        leaf own-router-lsa {
          type empty;
        }
        container bandwidth-based-metrics {
          uses apply-group;
          uses apply-macro;
          list bandwidth {
            key "name";
            leaf name {
              type string;
            }
            leaf metric {
              type uint16;
            }
          }
        }
        leaf metric {
          type uint16;
        }
        leaf te-metric {
          type uint32;
        }
        leaf priority {
          type uint32;
        }
        container ldp-synchronization {
          presence "enable ldp-synchronization";
          uses ldp-sync-obj;
        }
        container ipv4-adjacency-segment {
          uses apply-group;
          uses apply-macro;
          container protected {
            choice choice-index {
              container index {
                leaf index-number {
                  type uint32;
                }
              }
              leaf label {
                type uint32;
              }
              leaf dynamic {
                type empty;
              }
            }
          }
          container unprotected {
            choice choice-index {
              container index {
                leaf index-number {
                  type uint32;
                }
              }
              leaf label {
                type uint32;
              }
              leaf dynamic {
                type empty;
              }
            }
          }
        }
        leaf retransmit-interval {
          type uint32;
        }
        leaf transit-delay {
          type uint32;
        }
        leaf hello-interval {
          type uint32;
        }
        leaf dead-interval {
          type uint32;
        }
        leaf mtu {
          type uint32;
        }
        choice choice-33 {
          container authentication {
            uses juniper-ospf-authentication;
          }
          container authentication-key {
            presence "";
            leaf keyname {
              mandatory true;
              type unreadable;
            }
            leaf key-id {
              type uint32;
            }
          }
        }
        leaf demand-circuit {
          type empty;
        }
        leaf flood-reduction {
          type empty;
        }
        leaf no-neighbor-down-notification {
          type empty;
        }
        leaf ipsec-sa {
          type string;
        }
        list topology {
          key "name";
          ordered-by user;
          leaf name {
            type string;
          }
          uses apply-group;
          uses apply-macro;
          leaf disable {
            type empty;
          }
          leaf metric {
            type uint16;
          }
          container bandwidth-based-metrics {
            uses apply-group;
            uses apply-macro;
            list bandwidth {
              key "name";
              leaf name {
                type string;
              }
              leaf metric {
                type uint16;
              }
            }
          }
        }
        leaf transmit-interval {
          type uint32;
        }
        container bfd-liveness-detection {
          uses apply-group;
          uses apply-macro;
          leaf version {
            type string;
          }
          leaf minimum-interval {
            type uint32;
          }
          leaf minimum-receive-interval {
            type uint32;
          }
          leaf multiplier {
            type uint32;
          }
          choice choice-11 {
            leaf no-adaptation {
              type empty;
            }
          }
          container transmit-interval {
            uses apply-group;
            uses apply-macro;
            leaf minimum-interval {
              type uint32;
            }
            leaf threshold {
              type uint32;
            }
          }
          container detection-time {
            uses apply-group;
            uses apply-macro;
            leaf threshold {
              type uint32;
            }
          }
          container authentication {
            uses apply-group;
            uses apply-macro;
            leaf key-chain {
              type string;
            }
            leaf algorithm {
              type string;
            }
            leaf loose-check {
              type empty;
            }
          }
          leaf full-neighbors-only {
            type empty;
          }
        }
        leaf dynamic-neighbors {
          type empty;
        }
        leaf no-advertise-adjacency-segment {
          type empty;
        }
        list neighbor {
          key "name";
          ordered-by user;
          leaf name {
            type ipaddr;
          }
          leaf eligible {
            type empty;
          }
        }
        leaf poll-interval {
          type uint32;
        }
        leaf no-interface-state-traps {
          type empty;
        }
        container undocumented {
          leaf point-to-point {
            type empty;
          }
        }
      }
      leaf no-source-packet-routing {
        type empty;
      }
      leaf no-context-identifier-advertisement {
        type empty;
      }
      list context-identifier {
        key "name";
        ordered-by user;
        leaf name {
          type ipv4addr;
        }
        uses apply-group;
        uses apply-macro;
      }
      list label-switched-path {
        key "name";
        ordered-by user;
        leaf name {
          type key-attribute-string-type;
        }
        uses apply-group;
        uses apply-macro;
        leaf enable-disable {
          type string;
        }
        choice choice-3 {
          leaf disable {
            type empty;
          }
        }
        leaf metric {
          type uint16;
        }
        list topology {
          key "name";
          ordered-by user;
          leaf name {
            type string;
          }
          uses apply-group;
          uses apply-macro;
          leaf disable {
            type empty;
          }
          leaf metric {
            type uint16;
          }
          container bandwidth-based-metrics {
            uses apply-group;
            uses apply-macro;
            list bandwidth {
              key "name";
              leaf name {
                type string;
              }
              leaf metric {
                type uint16;
              }
            }
          }
        }
      }
      list peer-interface {
        key "name";
        ordered-by user;
        leaf name {
          type string;
        }
        uses apply-group;
        uses apply-macro;
        leaf enable-disable {
          type string;
        }
        choice choice-3 {
          leaf disable {
            type empty;
          }
        }
        leaf retransmit-interval {
          type uint32;
        }
        leaf transit-delay {
          type uint32;
        }
        leaf hello-interval {
          type uint32;
        }
        leaf dead-interval {
          type uint32;
        }
        leaf mtu {
          type uint32;
        }
        choice choice-12 {
          container authentication {
            uses juniper-ospf-authentication;
          }
          container authentication-key {
            presence "";
            leaf keyname {
              mandatory true;
              type unreadable;
            }
            leaf key-id {
              type uint32;
            }
          }
        }
        leaf demand-circuit {
          type empty;
        }
        leaf flood-reduction {
          type empty;
        }
        leaf no-neighbor-down-notification {
          type empty;
        }
      }
      container undocumented {
        leaf authentication-type {
          type string;
        }
      }
    }
    container undocumented {
      leaf no-active-backbone {
        type empty;
      }
    }
  }

  grouping juniper-protocols-pgm {
    uses apply-group;
    uses apply-macro;
    container traceoptions {
      uses apply-group;
      uses apply-macro;
      list flag {
        key "name";
        ordered-by user;
        leaf name {
          type string;
        }
        leaf send {
          type empty;
        }
        leaf receive {
          type empty;
        }
        leaf detail {
          type empty;
        }
        leaf disable {
          type empty;
        }
      }
    }
  }

  grouping juniper-protocols-pim {
    uses apply-group;
    uses apply-macro;
    container family {
      uses apply-group;
      uses apply-macro;
      container any {
        presence "enable any";
        uses apply-group;
        uses apply-macro;
        leaf disable {
          type empty;
        }
      }
      container inet {
        uses apply-group;
        uses apply-macro;
        choice choice-3 {
          leaf disable {
            type empty;
          }
        }
      }
      container inet6 {
        uses apply-group;
        uses apply-macro;
        choice choice-3 {
          leaf disable {
            type empty;
          }
        }
      }
    }
    choice choice-5 {
      leaf enable-disable {
        type string;
      }
      leaf disable {
        type empty;
      }
    }
    container nonstop-routing {
      uses apply-group;
      uses apply-macro;
      choice choice-3 {
        leaf disable {
          type empty;
        }
      }
    }
    container traceoptions {
      uses apply-group;
      uses apply-macro;
      container file {
        presence "";
        uses trace-file-type;
      }
      list flag {
        key "name";
        ordered-by user;
        leaf name {
          type string;
        }
        leaf send {
          type empty;
        }
        leaf receive {
          type empty;
        }
        leaf detail {
          type empty;
        }
        leaf disable {
          type empty;
        }
        container filter {
          presence "";
          uses pim-filter-obj;
        }
      }
    }
    container dense-groups {
      uses apply-group;
      uses apply-macro;
      leaf dynamic-reject {
        type empty;
      }
      list pim-dense-group-type {
        key "name";
        ordered-by user;
        leaf name {
          type ipprefix;
        }
        leaf dense-group-flags {
          type string;
        }
      }
    }
    leaf vpn-tunnel-source {
      type ipv4addr;
    }
    leaf vpn-group-address {
      type ipv4addr;
    }
    leaf-list tunnel-devices {
      type interface-device;
      ordered-by user;
    }
    container rpf-selection {
      uses apply-group;
      uses apply-macro;
      list group {
        key "name";
        ordered-by user;
        leaf name {
          type ipprefix;
        }
        uses apply-group;
        uses apply-macro;
        container wildcard-source {
          presence "";
          uses apply-group;
          uses apply-macro;
          leaf next-hop {
            type ipaddr;
          }
        }
        list source {
          key "name";
          ordered-by user;
          leaf name {
            type ipprefix;
          }
          uses apply-group;
          uses apply-macro;
          leaf next-hop {
            type ipaddr;
          }
        }
      }
      list prefix-list {
        key "name";
        ordered-by user;
        leaf name {
          type string;
        }
        uses apply-group;
        uses apply-macro;
        container wildcard-source {
          presence "";
          uses apply-group;
          uses apply-macro;
          leaf next-hop {
            type ipaddr;
          }
        }
        list source {
          key "name";
          ordered-by user;
          leaf name {
            type ipprefix;
          }
          uses apply-group;
          uses apply-macro;
          leaf next-hop {
            type ipaddr;
          }
        }
      }
    }
    container mvpn {
      presence "enable mvpn";
      uses apply-group;
      uses apply-macro;
      container autodiscovery {
        uses apply-group;
        uses apply-macro;
        leaf inet-mdt {
          type empty;
        }
      }
      container family {
        uses apply-group;
        uses apply-macro;
        container inet {
          uses apply-group;
          uses apply-macro;
          leaf rosen-mvpn {
            type empty;
          }
          leaf ngen-mvpn {
            type empty;
          }
          container autodiscovery {
            uses apply-group;
            uses apply-macro;
            leaf inet-mdt {
              type empty;
            }
          }
          leaf disable {
            type empty;
          }
        }
        container inet6 {
          uses apply-group;
          uses apply-macro;
          leaf rosen-mvpn {
            type empty;
          }
          leaf ngen-mvpn {
            type empty;
          }
        }
      }
    }
    container rib-group {
      uses rib-group-type;
    }
    leaf-list import {
      type policy-algebra;
      ordered-by user;
    }
    leaf-list export {
      type policy-algebra;
      ordered-by user;
    }
    container mldp-inband-signalling {
      presence "enable mldp-inband-signalling";
      uses apply-group;
      uses apply-macro;
      leaf-list policy {
        type policy-algebra;
        ordered-by user;
      }
    }
    leaf assert-timeout {
      type uint32;
    }
    leaf assert-robust-count {
      type uint32;
    }
    leaf join-prune-timeout {
      type uint32;
    }
    container spt-threshold {
      uses apply-group;
      uses apply-macro;
      leaf-list infinity {
        type policy-algebra;
        ordered-by user;
      }
    }
    container sglimit {
      uses apply-group;
      uses apply-macro;
      list family {
        key "name";
        ordered-by user;
        leaf name {
          type string;
        }
        uses apply-group;
        uses apply-macro;
        leaf maximum {
          type uint32;
        }
        leaf threshold {
          type uint32;
        }
        leaf log-interval {
          type uint32;
        }
      }
      leaf maximum {
        type uint32;
      }
      leaf threshold {
        type uint32;
      }
      leaf log-interval {
        type uint32;
      }
    }
    container rp {
      uses apply-group;
      uses apply-macro;
      leaf bootstrap-priority {
        type uint32;
      }
      leaf-list bootstrap-import {
        type policy-algebra;
        ordered-by user;
      }
      leaf-list bootstrap-export {
        type policy-algebra;
        ordered-by user;
      }
      container bootstrap {
        uses apply-group;
        uses apply-macro;
        container family {
          uses apply-group;
          uses apply-macro;
          container inet {
            uses pim-bootstrap-options-type;
          }
          container inet6 {
            uses pim-bootstrap-options-type;
          }
        }
      }
      container register-limit {
        uses apply-group;
        uses apply-macro;
        list family {
          key "name";
          ordered-by user;
          leaf name {
            type string;
          }
          uses apply-group;
          uses apply-macro;
          leaf maximum {
            type uint32;
          }
          leaf threshold {
            type uint32;
          }
          leaf log-interval {
            type uint32;
          }
        }
        leaf maximum {
          type uint32;
        }
        leaf threshold {
          type uint32;
        }
        leaf log-interval {
          type uint32;
        }
      }
      container group-rp-mapping {
        uses apply-group;
        uses apply-macro;
        list family {
          key "name";
          ordered-by user;
          leaf name {
            type string;
          }
          uses apply-group;
          uses apply-macro;
          leaf maximum {
            type uint32;
          }
          leaf threshold {
            type uint32;
          }
          leaf log-interval {
            type uint32;
          }
        }
        leaf maximum {
          type uint32;
        }
        leaf threshold {
          type uint32;
        }
        leaf log-interval {
          type uint32;
        }
      }
      leaf-list rp-register-policy {
        type policy-algebra;
        ordered-by user;
      }
      leaf-list dr-register-policy {
        type policy-algebra;
        ordered-by user;
      }
      container local {
        uses apply-group;
        uses apply-macro;
        leaf address {
          type ipv4addr;
        }
        choice enable-disable-choice {
          leaf enable-disable {
            type string;
          }
          leaf disable {
            type empty;
          }
        }
        leaf priority {
          type uint32;
        }
        leaf hold-time {
          type uint32;
        }
        list group-ranges {
          key "name";
          ordered-by user;
          leaf name {
            type ipv4prefix;
          }
          uses apply-group;
          uses apply-macro;
        }
        leaf override {
          type empty;
        }
        container family {
          uses apply-group;
          uses apply-macro;
          container inet {
            presence "";
            uses apply-group;
            uses apply-macro;
            leaf address {
              type ipv4addr;
            }
            choice choice-5 {
              leaf enable-disable {
                type string;
              }
              leaf disable {
                type empty;
              }
            }
            leaf priority {
              type uint32;
            }
            leaf hold-time {
              type uint32;
            }
            list group-ranges {
              key "name";
              ordered-by user;
              leaf name {
                type ipv4prefix;
              }
              uses apply-group;
              uses apply-macro;
            }
            leaf override {
              type empty;
            }
            container anycast-pim {
              uses apply-group;
              uses apply-macro;
              container rp-set {
                uses apply-group;
                uses apply-macro;
                list address {
                  key "name";
                  ordered-by user;
                  leaf name {
                    type ipaddr;
                  }
                  uses apply-group;
                  uses apply-macro;
                  leaf forward-msdp-sa {
                    type empty;
                  }
                }
              }
              leaf local-address {
                type ipaddr;
              }
            }
          }
          container inet6 {
            presence "";
            uses apply-group;
            uses apply-macro;
            leaf address {
              type ipv6addr;
            }
            choice choice-5 {
              leaf enable-disable {
                type string;
              }
              leaf disable {
                type empty;
              }
            }
            leaf priority {
              type uint32;
            }
            leaf hold-time {
              type uint32;
            }
            list group-ranges {
              key "name";
              ordered-by user;
              leaf name {
                type ipv6prefix;
              }
              uses apply-group;
              uses apply-macro;
            }
            leaf override {
              type empty;
            }
            container anycast-pim {
              uses apply-group;
              uses apply-macro;
              container rp-set {
                uses apply-group;
                uses apply-macro;
                list address {
                  key "name";
                  ordered-by user;
                  leaf name {
                    type ipv6addr;
                  }
                  uses apply-group;
                  uses apply-macro;
                }
              }
              leaf local-address {
                type ipv6addr;
              }
            }
          }
        }
      }
      container embedded-rp {
        presence "enable embedded-rp";
        uses apply-group;
        uses apply-macro;
        list group-ranges {
          key "name";
          ordered-by user;
          uses pim-rp-group-range-type;
        }
        leaf maximum-rps {
          type uint32;
        }
      }
      container auto-rp {
        presence "";
        uses apply-group;
        uses apply-macro;
        choice choice-3 {
          leaf discovery {
            type empty;
          }
          leaf announce {
            type empty;
          }
          leaf mapping {
            type empty;
          }
        }
        leaf autorp-mode {
          type string;
        }
        leaf mapping-agent-election {
          type empty;
        }
        leaf no-mapping-agent-election {
          type empty;
        }
      }
      container static {
        uses apply-group;
        uses apply-macro;
        list address {
          key "name";
          ordered-by user;
          leaf name {
            type ipaddr;
          }
          uses apply-group;
          uses apply-macro;
          leaf version {
            type uint32;
          }
          list group-ranges {
            key "name";
            ordered-by user;
            uses pim-rp-group-range-type;
          }
          leaf override {
            type empty;
          }
        }
      }
      container bidirectional {
        uses apply-group;
        uses apply-macro;
        list address {
          key "name";
          ordered-by user;
          leaf name {
            type ipaddr;
          }
          uses apply-group;
          uses apply-macro;
          leaf priority {
            type uint32;
          }
          leaf hold-time {
            units "seconds";
            type uint32;
          }
          list group-ranges {
            key "name";
            ordered-by user;
            uses pim-rp-group-range-type;
          }
        }
      }
      leaf register-probe-time {
        units "seconds";
        type uint32;
      }
    }
    list interface {
      key "name";
      ordered-by user;
      leaf name {
        type interface-name;
      }
      uses apply-group;
      uses apply-macro;
      container family {
        uses apply-group;
        uses apply-macro;
        container any {
          presence "enable any";
          uses apply-group;
          uses apply-macro;
          leaf disable {
            type empty;
          }
        }
        container inet {
          presence "enable inet";
          uses apply-group;
          uses apply-macro;
          container bfd-liveness-detection {
            uses apply-group;
            uses apply-macro;
            leaf version {
              type string;
            }
            leaf minimum-interval {
              units "milliseconds";
              type uint32;
            }
            leaf minimum-transmit-interval {
              units "milliseconds";
              type uint32;
            }
            leaf minimum-receive-interval {
              units "milliseconds";
              type uint32;
            }
            leaf multiplier {
              type uint32;
            }
            leaf no-adaptation {
              type empty;
            }
            container transmit-interval {
              uses apply-group;
              uses apply-macro;
              leaf minimum-interval {
                units "milliseconds";
                type uint32;
              }
              leaf threshold {
                type uint32;
                units "milliseconds";
              }
            }
            container detection-time {
              uses apply-group;
              uses apply-macro;
              leaf threshold {
                type uint32;
                units "milliseconds";
              }
            }
            container authentication {
              uses apply-group;
              uses apply-macro;
              leaf key-chain {
                type string;
              }
              leaf algorithm {
                type string;
              }
              leaf loose-check {
                type empty;
              }
            }
          }
          choice enable-disable-choice {
            leaf enable-disable {
              type string;
            }
            leaf disable {
              type empty;
            }
          }
        }
        container inet6 {
          presence "enable inet6";
          uses apply-group;
          uses apply-macro;
          container bfd-liveness-detection {
            uses apply-group;
            uses apply-macro;
            leaf version {
              type string;
            }
            leaf minimum-interval {
              units "milliseconds";
              type uint32;
            }
            leaf minimum-transmit-interval {
              units "milliseconds";
              type uint32;
            }
            leaf minimum-receive-interval {
              units "milliseconds";
              type uint32;
            }
            leaf multiplier {
              type uint32;
            }
            leaf no-adaptation {
              type empty;
            }
            container transmit-interval {
              uses apply-group;
              uses apply-macro;
              leaf minimum-interval {
                units "milliseconds";
                type uint32;
              }
              leaf threshold {
                type uint32;
                units "milliseconds";
              }
            }
            container detection-time {
              uses apply-group;
              uses apply-macro;
              leaf threshold {
                type uint32;
                units "milliseconds";
              }
            }
            container authentication {
              uses apply-group;
              uses apply-macro;
              leaf key-chain {
                type string;
              }
              leaf algorithm {
                type string;
              }
              leaf loose-check {
                type empty;
              }
            }
          }
          choice enable-disable-choice {
            leaf enable-disable {
              type string;
            }
            leaf disable {
              type empty;
            }
          }
        }
      }
      choice choice-5 {
        leaf enable-disable {
          type string;
        }
        leaf disable {
          type empty;
        }
      }
      container bidirectional {
        uses apply-group;
        uses apply-macro;
        container df-election {
          uses apply-group;
          uses apply-macro;
          leaf robustness-count {
            type uint32;
          }
          leaf offer-period {
            units "milliseconds";
            type uint32;
          }
          leaf backoff-period {
            units "milliseconds";
            type uint32;
          }
        }
      }
      leaf mode {
        type string;
      }
      leaf priority {
        type uint32;
      }
      container stickydr {
        presence "enable stickydr";
        uses apply-group;
        uses apply-macro;
      }
      container multiple-triggered-joins {
        presence "enable multiple-triggered-joins";
        uses apply-group;
        uses apply-macro;
        leaf count {
          type uint16;
        }
        leaf interval {
          type uint16;
        }
      }
      leaf version {
        type uint32;
      }
      leaf hello-interval {
        units "seconds";
        type uint32;
      }
      leaf-list neighbor-policy {
        type policy-algebra;
        ordered-by user;
      }
      leaf-list accept-join-always-from {
        type policy-algebra;
        ordered-by user;
      }
      leaf accept-remote-source {
        type empty;
      }
      leaf dual-dr {
        type empty;
      }
      leaf distributed-dr {
        type empty;
      }
      leaf reset-tracking-bit {
        type empty;
      }
      leaf propagation-delay {
        units "milliseconds";
        type uint32;
      }
      leaf override-interval {
        units "milliseconds";
        type uint32;
      }
      container bfd-liveness-detection {
        uses apply-group;
        uses apply-macro;
        leaf version {
          type string;
        }
        leaf minimum-interval {
          units "milliseconds";
          type uint32;
        }
        leaf minimum-transmit-interval {
          units "milliseconds";
          type uint32;
        }
        leaf minimum-receive-interval {
          units "milliseconds";
          type uint32;
        }
        leaf multiplier {
          type uint32;
        }
        leaf no-adaptation {
          type empty;
        }
        container transmit-interval {
          uses apply-group;
          uses apply-macro;
          leaf minimum-interval {
            units "milliseconds";
            type uint32;
          }
          leaf threshold {
            type uint32;
            units "milliseconds";
          }
        }
        container detection-time {
          uses apply-group;
          uses apply-macro;
          leaf threshold {
            type uint32;
            units "milliseconds";
          }
        }
        container authentication {
          uses apply-group;
          uses apply-macro;
          leaf key-chain {
            type string;
          }
          leaf algorithm {
            type string;
          }
          leaf loose-check {
            type empty;
          }
        }
      }
      container undocumented {
        leaf version {
          type string;
        }
      }
    }
    container mdt {
      uses apply-group;
      uses apply-macro;
      container threshold {
        uses apply-group;
        uses apply-macro;
        list group {
          key "name";
          ordered-by user;
          leaf name {
            type ipprefix;
          }
          uses apply-group;
          uses apply-macro;
          list source {
            key "name";
            ordered-by user;
            leaf name {
              type ipprefix;
            }
            uses apply-group;
            uses apply-macro;
            leaf rate {
              type uint32;
            }
          }
        }
      }
      leaf data-mdt-reuse {
        type empty;
      }
      leaf tunnel-limit {
        type uint32;
      }
      leaf group-range {
        type ipprefix;
      }
    }
    container undocumented {
      leaf vpn-group-address {
        type ipv4addr;
      }
      leaf secondary-vtep-address {
        type ipv4addr;
      }
      container mdt {
        uses apply-group;
        uses apply-macro;
        container threshold {
          uses apply-group;
          uses apply-macro;
          list group {
            key "name";
            ordered-by user;
            leaf name {
              type ipprefix;
            }
            uses apply-group;
            uses apply-macro;
            list source {
              key "name";
              ordered-by user;
              leaf name {
                type ipprefix;
              }
              uses apply-group;
              uses apply-macro;
              leaf rate {
                type uint32;
              }
            }
          }
        }
        leaf data-mdt-reuse {
          type empty;
        }
        leaf tunnel-limit {
          type uint32;
        }
        leaf group-range {
          type ipprefix;
        }
      }
    }
    container graceful-restart {
      uses apply-group;
      uses apply-macro;
      choice choice-3 {
        leaf disable {
          type empty;
        }
      }
      leaf restart-duration {
        type uint32;
      }
    }
    container join-load-balance {
      presence "enable join-load-balance";
      uses apply-group;
      uses apply-macro;
      leaf automatic {
        type empty;
      }
    }
    leaf standby-path-creation-delay {
      units "seconds";
      type uint32;
    }
    leaf idle-standby-path-switchover-delay {
      units "seconds";
      type uint32;
    }
    leaf dr-election-on-p2p {
      type empty;
    }
    leaf no-wildcard-register-stop {
      type empty;
    }
    leaf nexthop-hold-time {
      type uint32;
    }
    leaf mpls-internet-multicast {
      type empty;
    }
    container join-make-before-break {
      uses apply-group;
      uses apply-macro;
      choice enable-disable-choice {
        leaf enable-disable {
          type string;
        }
        leaf disable {
          type empty;
        }
      }
    }
    leaf reset-tracking-bit {
      type empty;
    }
    leaf propagation-delay {
      type uint32;
    }
    leaf override-interval {
      type uint32;
    }
    container default-vpn-source {
      presence "enable default-vpn-source";
      uses apply-group;
      uses apply-macro;
      leaf interface-name {
        type interface-unit;
      }
    }
  }

  grouping juniper-protocols-protection-group {
    uses apply-group;
    uses apply-macro;
    container traceoptions {
      uses erp-trace-options;
    }
    leaf restore-interval {
      type uint32;
    }
    leaf guard-interval {
      type uint32;
    }
    leaf hold-interval {
      type uint32;
    }
    list ethernet-ring {
      key "name";
      ordered-by user;
      uses juniper-protocols-protection-group-ethernet-ring;
    }
  }

  grouping erp-trace-options {
    uses apply-group;
    uses apply-macro;
    container file {
      presence "";
      uses trace-file-type;
    }
    list flag {
      key "name";
      ordered-by user;
      leaf name {
        type string;
      }
    }
  }

  grouping juniper-protocols-protection-group-ethernet-ring {
    leaf name {
      type key-attribute-string-type;
    }
    uses apply-group;
    uses apply-macro;
    leaf node-id {
      type mac-unicaset;
    }
    leaf ring-protection-link-owner {
      type empty;
    }
    leaf restore-interval {
      type uint32;
    }
    leaf guard-interval {
      type uint32;
    }
    leaf hold-interval {
      type uint32;
    }
    container east-interface {
      presence "enable east-interface";
      uses erp-interface;
    }
    container west-interface {
      presence "enable west-interface";
      uses erp-interface;
    }
    container data-channel {
      presence "";
      uses erp-data-channel;
    }
  }

  grouping erp-data-channel {
    uses apply-group;
    uses apply-macro;
    leaf-list vlan {
      type string;
      ordered-by user;
    }
  }

  grouping erp-interface {
    uses apply-group;
    uses apply-macro;
    container control-channel {
      presence "";
      uses apply-group;
      uses apply-macro;
      leaf control-channel-name {
        type interface-name;
      }
      leaf vlan {
        type uint16;
      }
    }
    leaf ring-protection-link-end {
      type empty;
    }
    leaf interface-none {
      type empty;
    }
  }

  grouping juniper-protocols-rip {
    uses apply-group;
    uses apply-macro;
    container traceoptions {
      uses apply-group;
      uses apply-macro;
      container file {
        presence "";
        uses trace-file-type;
      }
      list flag {
        key "name";
        ordered-by user;
        leaf name {
          type string;
        }
        leaf send {
          type empty;
        }
        leaf receive {
          type empty;
        }
        leaf detail {
          type empty;
        }
        leaf disable {
          type empty;
        }
        container filter {
          presence "";
          uses rip-filter-obj;
        }
      }
    }
    container rib-group {
      presence "";
      uses rib-group-inet-type;
    }
    leaf metric-in {
      type uint32;
    }
    container send {
      choice choice-3 {
        leaf broadcast {
          type empty;
        }
        leaf multicast {
          type empty;
        }
        leaf none {
          type empty;
        }
        leaf version-1 {
          type empty;
        }
      }
    }
    container receive {
      choice choice-3 {
        leaf both {
          type empty;
        }
        leaf none {
          type empty;
        }
        leaf version-1 {
          type empty;
        }
        leaf version-2 {
          type empty;
        }
      }
    }
    leaf check-zero {
      type empty;
    }
    leaf no-check-zero {
      type empty;
    }
    leaf message-size {
      type uint32;
    }
    leaf-list import {
      type policy-algebra;
      ordered-by user;
    }
    leaf holddown {
      type uint32;
    }
    leaf route-timeout {
      type uint32;
    }
    leaf update-interval {
      type uint32;
    }
    leaf authentication-type {
      type string;
    }
    leaf authentication-key {
      type unreadable;
    }
    list group {
      key "name";
      ordered-by user;
      leaf name {
        type string;
      }
      uses apply-group;
      uses apply-macro;
      leaf route-timeout {
        type uint32;
      }
      leaf update-interval {
        type uint32;
      }
      leaf preference {
        type uint32;
      }
      leaf metric-out {
        type uint32;
      }
      leaf-list export {
        type policy-algebra;
        ordered-by user;
      }
      leaf-list import {
        type policy-algebra;
        ordered-by user;
      }
      container bfd-liveness-detection {
        uses apply-group;
        uses apply-macro;
        leaf version {
          type string;
        }
        leaf minimum-interval {
          type uint32;
        }
        leaf minimum-receive-interval {
          type uint32;
        }
        leaf multiplier {
          type uint32;
        }
        choice choice-11 {
          leaf no-adaptation {
            type empty;
          }
        }
        container transmit-interval {
          uses apply-group;
          uses apply-macro;
          leaf minimum-interval {
            type uint32;
          }
          leaf threshold {
            type uint32;
          }
        }
        container detection-time {
          uses apply-group;
          uses apply-macro;
          leaf threshold {
            type uint32;
          }
        }
        container authentication {
          uses apply-group;
          uses apply-macro;
          leaf key-chain {
            type string;
          }
          leaf algorithm {
            type string;
          }
          leaf loose-check {
            type empty;
          }
        }
      }
      list neighbor {
        key "name";
        ordered-by user;
        leaf name {
          type interface-name;
        }
        uses apply-group;
        uses apply-macro;
        leaf route-timeout {
          type uint32;
        }
        leaf update-interval {
          type uint32;
        }
        leaf metric-in {
          type uint32;
        }
        container send {
          choice choice-3 {
            leaf broadcast {
              type empty;
            }
            leaf multicast {
              type empty;
            }
            leaf none {
              type empty;
            }
            leaf version-1 {
              type empty;
            }
          }
        }
        container receive {
          choice choice-3 {
            leaf both {
              type empty;
            }
            leaf none {
              type empty;
            }
            leaf version-1 {
              type empty;
            }
            leaf version-2 {
              type empty;
            }
          }
        }
        leaf check-zero {
          type empty;
        }
        leaf no-check-zero {
          type empty;
        }
        leaf any-sender {
          type empty;
        }
        leaf message-size {
          type uint32;
        }
        leaf-list import {
          type policy-algebra;
          ordered-by user;
        }
        leaf authentication-type {
          type string;
        }
        leaf authentication-key {
          type unreadable;
        }
        container bfd-liveness-detection {
          uses apply-group;
          uses apply-macro;
          leaf version {
            type string;
          }
          leaf minimum-interval {
            type uint32;
          }
          leaf minimum-receive-interval {
            type uint32;
          }
          leaf multiplier {
            type uint32;
          }
          choice choice-11 {
            leaf no-adaptation {
              type empty;
            }
          }
          container transmit-interval {
            uses apply-group;
            uses apply-macro;
            leaf minimum-interval {
              type uint32;
            }
            leaf threshold {
              type uint32;
            }
          }
          container detection-time {
            uses apply-group;
            uses apply-macro;
            leaf threshold {
              type uint32;
            }
          }
          container authentication {
            uses apply-group;
            uses apply-macro;
            leaf key-chain {
              type string;
            }
            leaf algorithm {
              type string;
            }
            leaf loose-check {
              type empty;
            }
          }
        }
      }
    }
    container graceful-restart {
      presence "enable graceful-restart";
      uses apply-group;
      uses apply-macro;
      choice choice-3 {
        leaf disable {
          type empty;
        }
      }
      leaf restart-time {
        type uint32;
      }
    }
  }

  grouping juniper-protocols-ripng {
    uses apply-group;
    uses apply-macro;
    container traceoptions {
      uses apply-group;
      uses apply-macro;
      container file {
        presence "";
        uses trace-file-type;
      }
      list flag {
        key "name";
        ordered-by user;
        leaf name {
          type string;
        }
        leaf send {
          type empty;
        }
        leaf receive {
          type empty;
        }
        leaf detail {
          type empty;
        }
        leaf disable {
          type empty;
        }
      }
    }
    leaf metric-in {
      type uint32;
    }
    container send {
      choice choice-3 {
        leaf none {
          type empty;
        }
      }
    }
    container receive {
      choice choice-3 {
        leaf none {
          type empty;
        }
      }
    }
    leaf-list import {
      type policy-algebra;
      ordered-by user;
    }
    leaf holddown {
      type uint32;
    }
    leaf route-timeout {
      type uint32;
    }
    leaf update-interval {
      type uint32;
    }
    list group {
      key "name";
      ordered-by user;
      leaf name {
        type string;
      }
      uses apply-group;
      uses apply-macro;
      leaf route-timeout {
        type uint32;
      }
      leaf update-interval {
        type uint32;
      }
      leaf preference {
        type uint32;
      }
      leaf metric-out {
        type uint32;
      }
      leaf-list export {
        type policy-algebra;
        ordered-by user;
      }
      leaf-list import {
        type policy-algebra;
        ordered-by user;
      }
      list neighbor {
        key "name";
        ordered-by user;
        leaf name {
          type interface-name;
        }
        uses apply-group;
        uses apply-macro;
        leaf route-timeout {
          type uint32;
        }
        leaf update-interval {
          type uint32;
        }
        leaf metric-in {
          type uint32;
        }
        container send {
          choice choice-3 {
            leaf none {
              type empty;
            }
          }
        }
        container receive {
          choice choice-3 {
            leaf none {
              type empty;
            }
          }
        }
        leaf-list import {
          type policy-algebra;
          ordered-by user;
        }
      }
    }
    container graceful-restart {
      presence "enable graceful-restart";
      uses apply-group;
      uses apply-macro;
      choice choice-3 {
        leaf disable {
          type empty;
        }
      }
      leaf restart-time {
        type uint32;
      }
    }
  }

  grouping juniper-protocols-router-discovery {
    uses apply-group;
    uses apply-macro;
    choice choice-3 {
      leaf disable {
        type empty;
      }
    }
    container traceoptions {
      uses apply-group;
      uses apply-macro;
      container file {
        presence "";
        uses trace-file-type;
      }
      list flag {
        key "name";
        ordered-by user;
        leaf name {
          type string;
        }
      }
    }
    list interface {
      key "name";
      ordered-by user;
      leaf name {
        type interface-name;
      }
      uses apply-group;
      uses apply-macro;
      leaf max-advertisement-interval {
        type uint32;
      }
      leaf min-advertisement-interval {
        type uint32;
      }
      leaf lifetime {
        type uint32;
      }
    }
    list address {
      key "name";
      ordered-by user;
      leaf name {
        type ipv4addr;
      }
      uses apply-group;
      uses apply-macro;
      leaf advertise {
        type empty;
      }
      leaf ignore {
        type empty;
      }
      leaf broadcast {
        type empty;
      }
      leaf multicast {
        type empty;
      }
      leaf ineligible {
        type empty;
      }
      leaf priority {
        type int32;
      }
    }
  }

  grouping juniper-protocols-stp {
    uses apply-group;
    uses apply-macro;
    choice choice-3 {
      leaf disable {
        type empty;
      }
    }
    leaf bpdu-destination-mac-address {
      type string;
    }
    leaf bridge-priority {
      type string;
    }
    leaf backup-bridge-priority {
      type string;
    }
    leaf max-age {
      type uint16;
    }
    leaf hello-time {
      type uint16;
    }
    leaf forward-delay {
      type uint16;
    }
    container traceoptions {
      uses stp-trace-options;
    }
    leaf vpls-flush-on-topology-change {
      type empty;
    }
    leaf priority-hold-time {
      type uint16;
    }
    list system-id {
      key "name";
      ordered-by user;
      uses system-id-ip-map;
    }
    list interface {
      key "name";
      uses stp-interface;
    }
    leaf extended-system-id {
      type uint16;
    }
    leaf force-version {
      type string;
    }
    leaf bpdu-block-on-edge {
      type empty;
    }
  }

  grouping juniper-protocols-vni-routing-options {
    uses apply-group;
    uses apply-macro;
    list vni {
      key "name";
      leaf name {
        type string;
      }
      uses apply-group;
      uses apply-macro;
      container vrf-target {
        uses apply-group;
        uses apply-macro;
        leaf export {
          type string;
        }
        container undocumented {
          leaf export {
            type string;
          }
        }
        leaf community {
          type string;
        }
      }
      leaf designated-forwarder-election-hold-time {
        units "seconds";
        type uint32;
      }
    }
  }

  grouping juniper-protocols-vstp {
    uses apply-group;
    uses apply-macro;
    choice choice-3 {
      leaf disable {
        type empty;
      }
    }
    leaf force-version {
      type string;
    }
    leaf bpdu-block-on-edge {
      type empty;
    }
    leaf vpls-flush-on-topology-change {
      type empty;
    }
    leaf priority-hold-time {
      type uint16;
    }
    list system-id {
      key "name";
      ordered-by user;
      uses system-id-ip-map;
    }
    list interface {
      key "name";
      uses stp-interface;
    }
    list vlan {
      key "name";
      leaf name {
        type string;
      }
      uses apply-group;
      uses apply-macro;
      leaf bridge-priority {
        type string;
      }
      leaf backup-bridge-priority {
        type string;
      }
      leaf max-age {
        type uint16;
      }
      leaf hello-time {
        type uint16;
      }
      leaf forward-delay {
        type uint16;
      }
      container traceoptions {
        uses stp-trace-options;
      }
      list interface {
        key "name";
        uses stp-interface;
      }
    }
  }

  grouping juniper-routing-instance {
    leaf name {
      type string;
    }
    uses apply-group;
    uses apply-macro;
    leaf description {
      type string;
    }
    leaf vlan-model {
      type string;
    }
    leaf vtep-source-interface {
      type interface-unit;
    }
    container vtep-remote-interface {
      uses apply-group;
      uses apply-macro;
      list remote-ip {
        key "name";
        ordered-by user;
        leaf name {
          type ipv4addr;
        }
        uses apply-group;
        uses apply-macro;
        leaf dynamic-profile {
          type string;
        }
      }
      container default {
        uses apply-group;
        uses apply-macro;
        leaf dynamic-profile {
          type string;
        }
      }
    }
    leaf-list remote-vtep-list {
      type ipaddr;
    }
    leaf-list remote-vtep-v6-list {
      type ipv6addr;
    }
    leaf instance-role {
      type string;
    }
    leaf instance-type {
      type string;
    }
    choice choice-7 {
      leaf no-vrf-propagate-ttl {
        type empty;
      }
      leaf vrf-propagate-ttl {
        type empty;
      }
    }
    container egress-protection {
      uses apply-group;
      uses apply-macro;
      leaf protector {
        type empty;
      }
      container context-identifier {
        uses apply-group;
        uses apply-macro;
        leaf context-id {
          type ipv4addr;
        }
      }
    }
    choice choice-8 {
      leaf vlan-id {
        type string;
      }
      container vlan-tags {
        presence "";
        leaf outer {
          type string;
        }
        leaf inner {
          type string;
        }
      }
    }
    container system {
      uses apply-group;
      uses apply-macro;
      container services {
        uses apply-group;
        uses apply-macro;
        container dhcp-local-server {
          uses jdhcp-local-server-type;
        }
        container static-subscribers {
          uses jsscd-static-subscribers-type;
        }
      }
    }
    container services {
      uses apply-group;
      uses apply-macro;
      container mobile-ip {
        presence "enable mobile-ip";
        uses juniper-protocols-mobile-ipv4;
      }
    }
    container access {
      uses apply-group;
      uses apply-macro;
      container address-assignment {
        uses address-assignment-type;
      }
      leaf address-protection {
        type empty;
      }
    }
    container access-profile {
      leaf access-profile-name {
        type string;
      }
    }
    list interface {
      key "name";
      leaf name {
        type string;
      }
      uses apply-group;
      uses apply-macro;
      choice choice-3 {
        leaf any {
          type empty;
        }
        leaf unicast {
          type empty;
        }
        leaf multicast {
          type empty;
        }
      }
      leaf primary {
        type empty;
      }
    }
    leaf routing-interface {
      type interface-unit;
    }
    container vxlan {
      presence "";
      uses apply-group;
      uses apply-macro;
      leaf ovsdb-managed {
        type empty;
      }
      leaf vni {
        mandatory true;
        type uint32;
      }
      leaf multicast-group {
        type ipv4addr;
      }
      leaf multicast-v6-group {
        type ipv6addr;
      }
      leaf encapsulate-inner-vlan {
        type empty;
      }
      leaf decapsulate-accept-inner-vlan {
        type empty;
      }
      leaf unreachable-vtep-aging-timer {
        units "seconds";
        type uint16;
      }
      leaf ingress-node-replication {
        type empty;
      }
    }
    leaf l3-interface {
      type interface-unit;
    }
    leaf no-local-switching {
      type empty;
    }
    leaf no-normalization {
      type empty;
    }
    leaf qualified-bum-pruning-mode {
      type empty;
    }
    leaf no-irb-layer-2-copy {
      type empty;
    }
    container route-distinguisher {
      leaf rd-type {
        type string;
      }
    }
    container l2vpn-id {
      uses apply-group;
      uses apply-macro;
      leaf community {
        type string;
      }
    }
    container provider-tunnel {
      uses apply-group;
      uses apply-macro;
      choice choice-3 {
        container rsvp-te {
          uses apply-group;
          uses apply-macro;
          choice choice-3 {
            leaf static-lsp {
              type string;
            }
            container label-switched-path-template {
              uses apply-group;
              uses apply-macro;
              choice choice-3 {
                leaf template-name {
                  type string;
                }
                leaf default-template {
                  type empty;
                }
              }
            }
          }
        }
        container ingress-replication {
          uses apply-group;
          uses apply-macro;
          leaf create-new-ucast-tunnel {
            type empty;
          }
          container label-switched-path {
            presence "enable label-switched-path";
            uses apply-group;
            uses apply-macro;
            container label-switched-path-template {
              uses apply-group;
              uses apply-macro;
              choice choice-3 {
                leaf template-name {
                  type string;
                }
                leaf default-template {
                  type empty;
                }
              }
            }
          }
        }
        container pim-asm {
          uses apply-group;
          uses apply-macro;
          leaf group-address {
            type ipv4addr;
          }
        }
        container pim-ssm {
          uses apply-group;
          uses apply-macro;
          leaf group-address {
            type ipv4addr;
          }
        }
        container ldp-p2mp {
          presence "enable ldp-p2mp";
          uses apply-group;
          uses apply-macro;
        }
      }
      container selective {
        uses apply-group;
        uses apply-macro;
        leaf tunnel-limit {
          type uint32;
        }
        leaf leaf-tunnel-limit-inet {
          type uint32;
        }
        leaf leaf-tunnel-limit-inet6 {
          type uint32;
        }
        container wildcard-group-inet {
          uses apply-group;
          uses apply-macro;
          container wildcard-source {
            presence "enable wildcard-source";
            uses apply-group;
            uses apply-macro;
            leaf threshold-rate {
              units "kilobits";
              type uint32;
            }
            choice choice-5 {
              container ingress-replication {
                uses apply-group;
                uses apply-macro;
                leaf create-new-ucast-tunnel {
                  type empty;
                }
                container label-switched-path {
                  presence "enable label-switched-path";
                  uses apply-group;
                  uses apply-macro;
                  container label-switched-path-template {
                    uses apply-group;
                    uses apply-macro;
                    choice choice-3 {
                      leaf template-name {
                        type string;
                      }
                      leaf default-template {
                        type empty;
                      }
                    }
                  }
                }
              }
              container rsvp-te {
                uses apply-group;
                uses apply-macro;
                choice choice-3 {
                  leaf static-lsp {
                    type string;
                  }
                  container label-switched-path-template {
                    uses apply-group;
                    uses apply-macro;
                    choice choice-3 {
                      leaf template-name {
                        type string;
                      }
                      leaf default-template {
                        type empty;
                      }
                    }
                  }
                }
              }
              container ldp-p2mp {
                presence "enable ldp-p2mp";
                uses apply-group;
                uses apply-macro;
              }
              container pim-ssm {
                uses apply-group;
                uses apply-macro;
                leaf group-range {
                  type ipv4prefix;
                }
              }
            }
          }
        }
        container wildcard-group-inet6 {
          uses apply-group;
          uses apply-macro;
          container wildcard-source {
            presence "enable wildcard-source";
            uses apply-group;
            uses apply-macro;
            leaf threshold-rate {
              units "kilobits";
              type uint32;
            }
            choice choice-5 {
              container ingress-replication {
                uses apply-group;
                uses apply-macro;
                leaf create-new-ucast-tunnel {
                  type empty;
                }
                container label-switched-path {
                  presence "enable label-switched-path";
                  uses apply-group;
                  uses apply-macro;
                  container label-switched-path-template {
                    uses apply-group;
                    uses apply-macro;
                    choice choice-3 {
                      leaf template-name {
                        type string;
                      }
                      leaf default-template {
                        type empty;
                      }
                    }
                  }
                }
              }
              container rsvp-te {
                uses apply-group;
                uses apply-macro;
                choice choice-3 {
                  leaf static-lsp {
                    type string;
                  }
                  container label-switched-path-template {
                    uses apply-group;
                    uses apply-macro;
                    choice choice-3 {
                      leaf template-name {
                        type string;
                      }
                      leaf default-template {
                        type empty;
                      }
                    }
                  }
                }
              }
              container ldp-p2mp {
                presence "enable ldp-p2mp";
                uses apply-group;
                uses apply-macro;
              }
              container pim-ssm {
                uses apply-group;
                uses apply-macro;
                leaf group-range {
                  type ipv4prefix;
                }
              }
            }
          }
        }
        list group {
          key "name";
          ordered-by user;
          leaf name {
            type ipprefix;
          }
          uses apply-group;
          uses apply-macro;
          container wildcard-source {
            presence "enable wildcard-source";
            uses apply-group;
            uses apply-macro;
            leaf threshold-rate {
              units "kilobits";
              type uint32;
            }
            choice choice-5 {
              container ingress-replication {
                uses apply-group;
                uses apply-macro;
                leaf create-new-ucast-tunnel {
                  type empty;
                }
                container label-switched-path {
                  presence "enable label-switched-path";
                  uses apply-group;
                  uses apply-macro;
                  container label-switched-path-template {
                    uses apply-group;
                    uses apply-macro;
                    choice choice-3 {
                      leaf template-name {
                        type string;
                      }
                      leaf default-template {
                        type empty;
                      }
                    }
                  }
                }
              }
              container rsvp-te {
                uses apply-group;
                uses apply-macro;
                choice choice-3 {
                  leaf static-lsp {
                    type string;
                  }
                  container label-switched-path-template {
                    uses apply-group;
                    uses apply-macro;
                    choice choice-3 {
                      leaf template-name {
                        type string;
                      }
                      leaf default-template {
                        type empty;
                      }
                    }
                  }
                }
              }
              container ldp-p2mp {
                presence "enable ldp-p2mp";
                uses apply-group;
                uses apply-macro;
              }
              container pim-ssm {
                uses apply-group;
                uses apply-macro;
                leaf group-range {
                  type ipv4prefix;
                }
              }
            }
          }
          list source {
            key "name";
            ordered-by user;
            leaf name {
              type ipprefix;
            }
            uses apply-group;
            uses apply-macro;
            choice choice-3 {
              container ingress-replication {
                uses apply-group;
                uses apply-macro;
                leaf create-new-ucast-tunnel {
                  type empty;
                }
                container label-switched-path {
                  presence "enable label-switched-path";
                  uses apply-group;
                  uses apply-macro;
                  container label-switched-path-template {
                    uses apply-group;
                    uses apply-macro;
                    choice choice-3 {
                      leaf template-name {
                        type string;
                      }
                      leaf default-template {
                        type empty;
                      }
                    }
                  }
                }
              }
              container rsvp-te {
                uses apply-group;
                uses apply-macro;
                choice choice-3 {
                  leaf static-lsp {
                    type string;
                  }
                  container label-switched-path-template {
                    uses apply-group;
                    uses apply-macro;
                    choice choice-3 {
                      leaf template-name {
                        type string;
                      }
                      leaf default-template {
                        type empty;
                      }
                    }
                  }
                }
              }
              container pim-ssm {
                uses apply-group;
                uses apply-macro;
                leaf group-range {
                  type ipv4prefix;
                }
              }
              container ldp-p2mp {
                presence "enable ldp-p2mp";
                uses apply-group;
                uses apply-macro;
              }
            }
            leaf threshold-rate {
              units "kilobits";
              type uint32;
            }
          }
        }
      }
      container mdt {
        uses apply-group;
        uses apply-macro;
        container threshold {
          uses apply-group;
          uses apply-macro;
          list group {
            key "name";
            ordered-by user;
            leaf name {
              type ipprefix;
            }
            uses apply-group;
            uses apply-macro;
            list source {
              key "name";
              ordered-by user;
              leaf name {
                type ipprefix;
              }
              uses apply-group;
              uses apply-macro;
              leaf rate {
                type uint32;
              }
            }
          }
        }
        leaf data-mdt-reuse {
          type empty;
        }
        leaf tunnel-limit {
          type uint32;
        }
        leaf group-range {
          type ipprefix;
        }
      }
      container family {
        presence "enable family";
        uses apply-group;
        uses apply-macro;
        container inet {
          presence "enable inet";
          uses apply-group;
          uses apply-macro;
          choice choice-rsvp-te {
            container rsvp-te {
              uses apply-group;
              uses apply-macro;
              choice choice-static-lsp {
                leaf static-lsp {
                  type string;
                }
                container label-switched-path-template {
                  uses apply-group;
                  uses apply-macro;
                  choice choice-template-name {
                    leaf template-name {
                      type string;
                    }
                    leaf default-template {
                      type empty;
                    }
                  }
                }
              }
            }
            container ldp-p2mp {
              presence "enable ldp-p2mp";
              uses apply-group;
              uses apply-macro;
            }
            container ingress-replication {
              uses apply-group;
              uses apply-macro;
              leaf create-new-ucast-tunnel {
                type empty;
              }
              container label-switched-path {
                presence "enable label-switched-path";
                uses apply-group;
                uses apply-macro;
                container label-switched-path-template {
                  uses apply-group;
                  uses apply-macro;
                  choice choice-template-name {
                    leaf template-name {
                      type string;
                    }
                    leaf default-template {
                      type empty;
                    }
                  }
                }
              }
            }
            container pim-asm {
              uses apply-group;
              uses apply-macro;
              leaf group-address {
                type ipv4addr;
              }
              leaf tunnel-source {
                type ipv4addr;
              }
            }
            container pim-ssm {
              uses apply-group;
              uses apply-macro;
              leaf group-address {
                type ipv4addr;
              }
              leaf tunnel-source {
                type ipv4addr;
              }
            }
          }
          container mdt {
            uses apply-group;
            uses apply-macro;
            container threshold {
              uses apply-group;
              uses apply-macro;
              list group {
                key "name";
                ordered-by user;
                leaf name {
                  type ipprefix;
                }
                uses apply-group;
                uses apply-macro;
                list source {
                  key "name";
                  ordered-by user;
                  leaf name {
                    type ipprefix;
                  }
                  uses apply-group;
                  uses apply-macro;
                  leaf rate {
                    units "kilobits";
                    type uint32;
                  }
                }
              }
            }
            leaf data-mdt-reuse {
              type empty;
            }
            leaf tunnel-limit {
              type uint32;
            }
            leaf group-range {
              type ipprefix;
            }
          }
        }
        container inet6 {
          presence "enable inet6";
          uses apply-group;
          uses apply-macro;
          choice choice-rsvp-te {
            container rsvp-te {
              uses apply-group;
              uses apply-macro;
              choice choice-static-lsp {
                leaf static-lsp {
                  type string;
                }
                container label-switched-path-template {
                  uses apply-group;
                  uses apply-macro;
                  choice choice-template-name {
                    leaf template-name {
                      type string;
                    }
                    leaf default-template {
                      type empty;
                    }
                  }
                }
              }
            }
            container ldp-p2mp {
              presence "enable ldp-p2mp";
              uses apply-group;
              uses apply-macro;
            }
            container ingress-replication {
              uses apply-group;
              uses apply-macro;
              leaf create-new-ucast-tunnel {
                type empty;
              }
              container label-switched-path {
                presence "enable label-switched-path";
                uses apply-group;
                uses apply-macro;
                container label-switched-path-template {
                  uses apply-group;
                  uses apply-macro;
                  choice choice-template-name {
                    leaf template-name {
                      type string;
                    }
                    leaf default-template {
                      type empty;
                    }
                  }
                }
              }
            }
            container pim-asm {
              uses apply-group;
              uses apply-macro;
              leaf group-address {
                type ipv4addr;
              }
            }
            container pim-ssm {
              uses apply-group;
              uses apply-macro;
              leaf group-address {
                type ipv4addr;
              }
            }
          }
          container mdt {
            uses apply-group;
            uses apply-macro;
            container threshold {
              uses apply-group;
              uses apply-macro;
              list group {
                key "name";
                ordered-by user;
                leaf name {
                  type ipprefix;
                }
                uses apply-group;
                uses apply-macro;
                list source {
                  key "name";
                  ordered-by user;
                  leaf name {
                    type ipprefix;
                  }
                  uses apply-group;
                  uses apply-macro;
                  leaf rate {
                    units "kilobits";
                    type uint32;
                  }
                }
              }
            }
            leaf data-mdt-reuse {
              type empty;
            }
            leaf tunnel-limit {
              type uint32;
            }
            leaf group-range {
              type ipprefix;
            }
          }
        }
      }
    }
    leaf-list vrf-import {
      type policy-algebra;
      ordered-by user;
    }
    leaf-list vrf-export {
      type policy-algebra;
      ordered-by user;
    }
    container vrf-target {
      uses apply-group;
      uses apply-macro;
      leaf community {
        type string;
      }
      leaf import {
        type string;
      }
      leaf export {
        type string;
      }
      leaf auto {
        type empty;
      }
    }
    leaf no-vrf-advertise {
      type empty;
    }
    leaf connector-id-advertise {
      type empty;
    }
    container vrf-advertise-selective {
      uses apply-group;
      uses apply-macro;
      container family {
        uses apply-group;
        uses apply-macro;
        leaf inet-mvpn {
          type empty;
        }
        leaf inet6-mvpn {
          type empty;
        }
      }
    }
    container vrf-table-label {
      presence "enable vrf-table-label";
      leaf source-class-usage {
        type empty;
      }
    }
    container routing-options {
      uses juniper-routing-options;
    }
    container forwarding-options {
      uses juniper-forwarding-options;
    }
    container multicast-snooping-options {
      uses juniper-multicast-snooping-options;
    }
    container igmp-snooping-options {
      uses juniper-igmp-snooping-options;
    }
    container protocols {
      uses apply-group;
      uses apply-macro;
      container bgp {
        uses juniper-protocols-bgp;
      }
      container mpls {
        uses juniper-protocols-mpls;
      }
      container ospf {
        uses juniper-protocols-ospf;
      }
      container ospf3 {
        uses apply-group;
        uses apply-macro;
        list realm {
          key "name";
          ordered-by user;
          leaf name {
            type string;
          }
          uses apply-group;
          uses apply-macro;
          choice choice-3 {
            leaf disable {
              type empty;
            }
          }
          container traceoptions {
            uses apply-group;
            uses apply-macro;
            container file {
              presence "";
              uses trace-file-type;
            }
            list flag {
              key "name";
              ordered-by user;
              leaf name {
                type string;
              }
              leaf send {
                type empty;
              }
              leaf receive {
                type empty;
              }
              leaf detail {
                type empty;
              }
              leaf disable {
                type empty;
              }
            }
          }
          list topology {
            key "name";
            ordered-by user;
            leaf name {
              type string;
            }
            uses apply-group;
            uses apply-macro;
            leaf disable {
              type empty;
            }
            leaf topology-id {
              type uint8;
            }
            leaf overload {
              type empty;
            }
            leaf rib-group {
              type string;
            }
            container spf-options {
              uses apply-group;
              uses apply-macro;
              leaf delay {
                type uint32;
              }
              leaf holddown {
                type uint32;
              }
              leaf rapid-runs {
                type uint32;
              }
              leaf no-ignore-our-externals {
                type empty;
              }
            }
            container backup-spf-options {
              uses apply-group;
              uses apply-macro;
              leaf disable {
                type empty;
              }
              leaf no-install {
                type empty;
              }
              leaf downstream-paths-only {
                type empty;
              }
            }
            leaf prefix-export-limit {
              type uint32;
            }
          }
          container spf-options {
            uses apply-group;
            uses apply-macro;
            leaf delay {
              type uint32;
            }
            leaf holddown {
              type uint32;
            }
            leaf rapid-runs {
              type uint32;
            }
            leaf no-ignore-our-externals {
              type empty;
            }
          }
          container backup-spf-options {
            uses apply-group;
            uses apply-macro;
            leaf disable {
              type empty;
            }
            leaf no-install {
              type empty;
            }
            leaf downstream-paths-only {
              type empty;
            }
          }
          leaf prefix-export-limit {
            type uint32;
          }
          leaf rib-group {
            type string;
          }
          container overload {
            presence "enable overload";
            uses apply-group;
            uses apply-macro;
            leaf timeout {
              type uint32;
            }
          }
          container database-protection {
            presence "";
            uses apply-group;
            uses apply-macro;
            leaf maximum-lsa {
              type uint32;
            }
            leaf warning-only {
              type empty;
            }
            leaf warning-threshold {
              type uint8;
            }
            leaf ignore-count {
              type uint8;
            }
            leaf ignore-time {
              type uint16;
            }
            leaf reset-time {
              type uint32;
            }
          }
          container graceful-restart {
            uses apply-group;
            uses apply-macro;
            choice choice-3 {
              leaf disable {
                type empty;
              }
            }
            leaf restart-duration {
              type uint32;
            }
            leaf notify-duration {
              type uint32;
            }
            container helper-disable {
              presence "enable helper-disable";
              uses apply-group;
              uses apply-macro;
              choice choice-standard {
                leaf standard {
                  type empty;
                }
                leaf restart-signaling {
                  type empty;
                }
                leaf both {
                  type empty;
                }
              }
            }
            leaf no-strict-lsa-checking {
              type empty;
            }
          }
          container traffic-engineering {
            presence "enable traffic-engineering";
            uses apply-group;
            uses apply-macro;
            leaf no-topology {
              type empty;
            }
            leaf multicast-rpf-routes {
              type empty;
            }
            leaf ignore-lsp-metrics {
              type empty;
            }
            container shortcuts {
              presence "enable shortcuts";
              uses apply-group;
              uses apply-macro;
              leaf lsp-metric-into-summary {
                type empty;
              }
            }
            leaf advertise-unnumbered-interfaces {
              type empty;
            }
            leaf credibility-protocol-preference {
              type empty;
            }
          }
          leaf route-type-community {
            type string;
          }
          container domain-id {
            choice choice-3 {
              leaf domain-id {
                type string;
              }
              leaf disable {
                type empty;
              }
            }
          }
          choice choice-28 {
            leaf domain-vpn-tag {
              type uint32;
            }
            leaf no-domain-vpn-tag {
              type empty;
            }
          }
          leaf preference {
            type uint32;
          }
          leaf external-preference {
            type uint32;
          }
          leaf-list export {
            type policy-algebra;
            ordered-by user;
          }
          leaf-list import {
            type policy-algebra;
            ordered-by user;
          }
          leaf reference-bandwidth {
            type string;
          }
          leaf no-rfc-1583 {
            type empty;
          }
          choice choice-41 {
            leaf no-nssa-abr {
              type empty;
            }
          }
          container sham-link {
            presence "enable sham-link";
            uses apply-group;
            uses apply-macro;
            leaf local {
              type ipaddr;
            }
          }
          list area {
            key "name";
            ordered-by user;
            leaf name {
              type areaid;
            }
            uses apply-group;
            uses apply-macro;
            choice choice-3 {
              container stub {
                presence "enable stub";
                leaf default-metric {
                  type uint32;
                }
                leaf summaries {
                  type empty;
                }
                leaf no-summaries {
                  type empty;
                }
              }
              container nssa {
                presence "enable nssa";
                uses apply-group;
                uses apply-macro;
                container default-lsa {
                  presence "enable default-lsa";
                  uses apply-group;
                  uses apply-macro;
                  leaf default-metric {
                    type uint32;
                  }
                  leaf metric-type {
                    type uint32;
                  }
                  leaf type-7 {
                    type empty;
                  }
                }
                leaf summaries {
                  type empty;
                }
                leaf no-summaries {
                  type empty;
                }
                list area-range {
                  key "name";
                  ordered-by user;
                  leaf name {
                    type ipprefix;
                  }
                  uses apply-group;
                  uses apply-macro;
                  leaf restrict {
                    type empty;
                  }
                  leaf exact {
                    type empty;
                  }
                  container override-metric {
                    presence "";
                    uses apply-group;
                    uses apply-macro;
                    leaf metric {
                      type uint32;
                    }
                    leaf metric-type {
                      type uint32;
                    }
                  }
                }
              }
            }
            list area-range {
              key "name";
              ordered-by user;
              leaf name {
                type ipprefix;
              }
              uses apply-group;
              uses apply-macro;
              leaf restrict {
                type empty;
              }
              leaf exact {
                type empty;
              }
              leaf override-metric {
                type uint32;
              }
            }
            leaf-list network-summary-export {
              type policy-algebra;
              ordered-by user;
            }
            leaf-list network-summary-import {
              type policy-algebra;
              ordered-by user;
            }
            leaf-list inter-area-prefix-export {
              type policy-algebra;
              ordered-by user;
            }
            leaf-list inter-area-prefix-import {
              type policy-algebra;
              ordered-by user;
            }
            list virtual-link {
              key "neighbor-id transit-area";
              ordered-by user;
              leaf neighbor-id {
                type ipv4addr;
              }
              leaf transit-area {
                type areaid;
              }
              uses apply-group;
              uses apply-macro;
              choice choice-3 {
                leaf disable {
                  type empty;
                }
              }
              leaf retransmit-interval {
                type uint32;
              }
              leaf transit-delay {
                type uint32;
              }
              leaf hello-interval {
                type uint32;
              }
              leaf dead-interval {
                type uint32;
              }
              choice choice-12 {
                container authentication {
                  uses juniper-ospf-authentication;
                }
              }
              leaf demand-circuit {
                type empty;
              }
              leaf flood-reduction {
                type empty;
              }
              leaf no-neighbor-down-notification {
                type empty;
              }
              leaf ipsec-sa {
                type string;
              }
              list topology {
                key "name";
                ordered-by user;
                leaf name {
                  type string;
                }
                uses apply-group;
                uses apply-macro;
                leaf disable {
                  type empty;
                }
                leaf metric {
                  type uint16;
                }
                container bandwidth-based-metrics {
                  uses apply-group;
                  uses apply-macro;
                  list bandwidth {
                    key "name";
                    leaf name {
                      type string;
                    }
                    leaf metric {
                      type uint16;
                    }
                  }
                }
              }
            }
            list sham-link-remote {
              key "name";
              ordered-by user;
              leaf name {
                type ipaddr;
              }
              uses apply-group;
              uses apply-macro;
              leaf metric {
                type uint16;
              }
              leaf ipsec-sa {
                type string;
              }
              leaf demand-circuit {
                type empty;
              }
              leaf flood-reduction {
                type empty;
              }
              list topology {
                key "name";
                ordered-by user;
                leaf name {
                  type string;
                }
                uses apply-group;
                uses apply-macro;
                leaf disable {
                  type empty;
                }
                leaf metric {
                  type uint16;
                }
                container bandwidth-based-metrics {
                  uses apply-group;
                  uses apply-macro;
                  list bandwidth {
                    key "name";
                    leaf name {
                      type string;
                    }
                    leaf metric {
                      type uint16;
                    }
                  }
                }
              }
            }
            list interface {
              key "name";
              ordered-by user;
              leaf name {
                type ipv4addr-or-interface;
              }
              uses apply-group;
              uses apply-macro;
              choice choice-3 {
                leaf disable {
                  type empty;
                }
              }
              leaf interface-type {
                type string;
              }
              choice choice-6 {
                leaf link-protection {
                  type empty;
                }
                leaf node-link-protection {
                  type empty;
                }
              }
              leaf no-eligible-backup {
                type empty;
              }
              container passive {
                presence "enable passive";
                uses apply-group;
                uses apply-macro;
                container traffic-engineering {
                  uses apply-group;
                  uses apply-macro;
                  leaf remote-node-id {
                    type ipaddr;
                  }
                }
              }
              leaf secondary {
                type empty;
              }
              leaf own-router-lsa {
                type empty;
              }
              container bandwidth-based-metrics {
                uses apply-group;
                uses apply-macro;
                list bandwidth {
                  key "name";
                  leaf name {
                    type string;
                  }
                  leaf metric {
                    type uint16;
                  }
                }
              }
              leaf metric {
                type uint16;
              }
              leaf te-metric {
                type uint32;
              }
              leaf priority {
                type uint32;
              }
              container ldp-synchronization {
                presence "enable ldp-synchronization";
                uses ldp-sync-obj;
              }
              leaf retransmit-interval {
                type uint32;
              }
              leaf transit-delay {
                type uint32;
              }
              leaf hello-interval {
                type uint32;
              }
              leaf dead-interval {
                type uint32;
              }
              choice choice-33 {
                container authentication {
                  uses juniper-ospf-authentication;
                }
              }
              leaf demand-circuit {
                type empty;
              }
              leaf flood-reduction {
                type empty;
              }
              leaf no-neighbor-down-notification {
                type empty;
              }
              leaf ipsec-sa {
                type string;
              }
              list topology {
                key "name";
                ordered-by user;
                leaf name {
                  type string;
                }
                uses apply-group;
                uses apply-macro;
                leaf disable {
                  type empty;
                }
                leaf metric {
                  type uint16;
                }
                container bandwidth-based-metrics {
                  uses apply-group;
                  uses apply-macro;
                  list bandwidth {
                    key "name";
                    leaf name {
                      type string;
                    }
                    leaf metric {
                      type uint16;
                    }
                  }
                }
              }
              container bfd-liveness-detection {
                uses apply-group;
                uses apply-macro;
                leaf version {
                  type string;
                }
                leaf minimum-interval {
                  type uint32;
                }
                leaf minimum-receive-interval {
                  type uint32;
                }
                leaf multiplier {
                  type uint32;
                }
                choice choice-11 {
                  leaf no-adaptation {
                    type empty;
                  }
                }
                container transmit-interval {
                  uses apply-group;
                  uses apply-macro;
                  leaf minimum-interval {
                    type uint32;
                  }
                  leaf threshold {
                    type uint32;
                  }
                }
                container detection-time {
                  uses apply-group;
                  uses apply-macro;
                  leaf threshold {
                    type uint32;
                  }
                }
                container authentication {
                  uses apply-group;
                  uses apply-macro;
                  leaf key-chain {
                    type string;
                  }
                  leaf algorithm {
                    type string;
                  }
                  leaf loose-check {
                    type empty;
                  }
                }
                leaf full-neighbors-only {
                  type empty;
                }
              }
              leaf dynamic-neighbors {
                type empty;
              }
              list neighbor {
                key "name";
                ordered-by user;
                leaf name {
                  type ipaddr;
                }
                leaf eligible {
                  type empty;
                }
              }
              leaf poll-interval {
                type uint32;
              }
              leaf no-interface-state-traps {
                type empty;
              }
            }
            leaf no-context-identifier-advertisement {
              type empty;
            }
            list context-identifier {
              key "name";
              ordered-by user;
              leaf name {
                type ipv4addr;
              }
              uses apply-group;
              uses apply-macro;
            }
            list label-switched-path {
              key "name";
              ordered-by user;
              leaf name {
                type key-attribute-string-type;
              }
              uses apply-group;
              uses apply-macro;
              choice choice-3 {
                leaf disable {
                  type empty;
                }
              }
              leaf metric {
                type uint16;
              }
              list topology {
                key "name";
                ordered-by user;
                leaf name {
                  type string;
                }
                uses apply-group;
                uses apply-macro;
                leaf disable {
                  type empty;
                }
                leaf metric {
                  type uint16;
                }
                container bandwidth-based-metrics {
                  uses apply-group;
                  uses apply-macro;
                  list bandwidth {
                    key "name";
                    leaf name {
                      type string;
                    }
                    leaf metric {
                      type uint16;
                    }
                  }
                }
              }
            }
            list peer-interface {
              key "name";
              ordered-by user;
              leaf name {
                type string;
              }
              uses apply-group;
              uses apply-macro;
              choice choice-3 {
                leaf disable {
                  type empty;
                }
              }
              leaf retransmit-interval {
                type uint32;
              }
              leaf transit-delay {
                type uint32;
              }
              leaf hello-interval {
                type uint32;
              }
              leaf dead-interval {
                type uint32;
              }
              choice choice-12 {
                container authentication {
                  uses juniper-ospf-authentication;
                }
              }
              leaf demand-circuit {
                type empty;
              }
              leaf flood-reduction {
                type empty;
              }
              leaf no-neighbor-down-notification {
                type empty;
              }
            }
          }
        }
        choice choice-5 {
          leaf disable {
            type empty;
          }
        }
        container traceoptions {
          uses apply-group;
          uses apply-macro;
          container file {
            presence "";
            uses trace-file-type;
          }
          list flag {
            key "name";
            ordered-by user;
            leaf name {
              type string;
            }
            leaf send {
              type empty;
            }
            leaf receive {
              type empty;
            }
            leaf detail {
              type empty;
            }
            leaf disable {
              type empty;
            }
          }
        }
        list topology {
          key "name";
          ordered-by user;
          leaf name {
            type string;
          }
          uses apply-group;
          uses apply-macro;
          leaf disable {
            type empty;
          }
          leaf topology-id {
            type uint8;
          }
          leaf overload {
            type empty;
          }
          leaf rib-group {
            type string;
          }
          container spf-options {
            uses apply-group;
            uses apply-macro;
            leaf delay {
              type uint32;
            }
            leaf holddown {
              type uint32;
            }
            leaf rapid-runs {
              type uint32;
            }
            leaf no-ignore-our-externals {
              type empty;
            }
          }
          container backup-spf-options {
            uses apply-group;
            uses apply-macro;
            leaf disable {
              type empty;
            }
            leaf no-install {
              type empty;
            }
            leaf downstream-paths-only {
              type empty;
            }
          }
          leaf prefix-export-limit {
            type uint32;
          }
        }
        container spf-options {
          uses apply-group;
          uses apply-macro;
          leaf delay {
            type uint32;
          }
          leaf holddown {
            type uint32;
          }
          leaf rapid-runs {
            type uint32;
          }
          leaf no-ignore-our-externals {
            type empty;
          }
        }
        container backup-spf-options {
          uses apply-group;
          uses apply-macro;
          leaf disable {
            type empty;
          }
          leaf no-install {
            type empty;
          }
          leaf downstream-paths-only {
            type empty;
          }
        }
        leaf prefix-export-limit {
          type uint32;
        }
        leaf rib-group {
          type string;
        }
        container overload {
          presence "enable overload";
          uses apply-group;
          uses apply-macro;
          leaf timeout {
            type uint32;
          }
        }
        container database-protection {
          presence "";
          uses apply-group;
          uses apply-macro;
          leaf maximum-lsa {
            type uint32;
          }
          leaf warning-only {
            type empty;
          }
          leaf warning-threshold {
            type uint8;
          }
          leaf ignore-count {
            type uint8;
          }
          leaf ignore-time {
            type uint16;
          }
          leaf reset-time {
            type uint32;
          }
        }
        container graceful-restart {
          uses apply-group;
          uses apply-macro;
          choice choice-3 {
            leaf disable {
              type empty;
            }
          }
          leaf restart-duration {
            type uint32;
          }
          leaf notify-duration {
            type uint32;
          }
          container helper-disable {
            presence "enable helper-disable";
            uses apply-group;
            uses apply-macro;
            choice choice-standard {
              leaf standard {
                type empty;
              }
              leaf restart-signaling {
                type empty;
              }
              leaf both {
                type empty;
              }
            }
          }
          leaf no-strict-lsa-checking {
            type empty;
          }
        }
        container traffic-engineering {
          presence "enable traffic-engineering";
          uses apply-group;
          uses apply-macro;
          leaf no-topology {
            type empty;
          }
          leaf multicast-rpf-routes {
            type empty;
          }
          leaf ignore-lsp-metrics {
            type empty;
          }
          container shortcuts {
            presence "enable shortcuts";
            uses apply-group;
            uses apply-macro;
            leaf lsp-metric-into-summary {
              type empty;
            }
          }
          leaf advertise-unnumbered-interfaces {
            type empty;
          }
          leaf credibility-protocol-preference {
            type empty;
          }
        }
        leaf route-type-community {
          type string;
        }
        container domain-id {
          choice choice-3 {
            leaf domain-id {
              type string;
            }
            leaf disable {
              type empty;
            }
          }
        }
        choice choice-30 {
          leaf domain-vpn-tag {
            type uint32;
          }
          leaf no-domain-vpn-tag {
            type empty;
          }
        }
        leaf preference {
          type uint32;
        }
        leaf external-preference {
          type uint32;
        }
        leaf-list export {
          type policy-algebra;
          ordered-by user;
        }
        leaf-list import {
          type policy-algebra;
          ordered-by user;
        }
        leaf reference-bandwidth {
          type string;
        }
        leaf no-rfc-1583 {
          type empty;
        }
        choice choice-43 {
          leaf no-nssa-abr {
            type empty;
          }
        }
        container sham-link {
          presence "enable sham-link";
          uses apply-group;
          uses apply-macro;
          leaf local {
            type ipaddr;
          }
        }
        list area {
          key "name";
          ordered-by user;
          leaf name {
            type areaid;
          }
          uses apply-group;
          uses apply-macro;
          choice choice-3 {
            container stub {
              presence "enable stub";
              leaf default-metric {
                type uint32;
              }
              leaf summaries {
                type empty;
              }
              leaf no-summaries {
                type empty;
              }
            }
            container nssa {
              presence "enable nssa";
              uses apply-group;
              uses apply-macro;
              container default-lsa {
                presence "enable default-lsa";
                uses apply-group;
                uses apply-macro;
                leaf default-metric {
                  type uint32;
                }
                leaf metric-type {
                  type uint32;
                }
                leaf type-7 {
                  type empty;
                }
              }
              leaf summaries {
                type empty;
              }
              leaf no-summaries {
                type empty;
              }
              list area-range {
                key "name";
                ordered-by user;
                leaf name {
                  type ipprefix;
                }
                uses apply-group;
                uses apply-macro;
                leaf restrict {
                  type empty;
                }
                leaf exact {
                  type empty;
                }
                container override-metric {
                  presence "";
                  uses apply-group;
                  uses apply-macro;
                  leaf metric {
                    type uint32;
                  }
                  leaf metric-type {
                    type uint32;
                  }
                }
              }
            }
          }
          list area-range {
            key "name";
            ordered-by user;
            leaf name {
              type ipprefix;
            }
            uses apply-group;
            uses apply-macro;
            leaf restrict {
              type empty;
            }
            leaf exact {
              type empty;
            }
            leaf override-metric {
              type uint32;
            }
          }
          leaf-list network-summary-export {
            type policy-algebra;
            ordered-by user;
          }
          leaf-list network-summary-import {
            type policy-algebra;
            ordered-by user;
          }
          leaf-list inter-area-prefix-export {
            type policy-algebra;
            ordered-by user;
          }
          leaf-list inter-area-prefix-import {
            type policy-algebra;
            ordered-by user;
          }
          list virtual-link {
            key "neighbor-id transit-area";
            ordered-by user;
            leaf neighbor-id {
              type ipv4addr;
            }
            leaf transit-area {
              type areaid;
            }
            uses apply-group;
            uses apply-macro;
            choice choice-3 {
              leaf disable {
                type empty;
              }
            }
            leaf retransmit-interval {
              type uint32;
            }
            leaf transit-delay {
              type uint32;
            }
            leaf hello-interval {
              type uint32;
            }
            leaf dead-interval {
              type uint32;
            }
            choice choice-12 {
              container authentication {
                uses juniper-ospf-authentication;
              }
            }
            leaf demand-circuit {
              type empty;
            }
            leaf flood-reduction {
              type empty;
            }
            leaf no-neighbor-down-notification {
              type empty;
            }
            leaf ipsec-sa {
              type string;
            }
            list topology {
              key "name";
              ordered-by user;
              leaf name {
                type string;
              }
              uses apply-group;
              uses apply-macro;
              leaf disable {
                type empty;
              }
              leaf metric {
                type uint16;
              }
              container bandwidth-based-metrics {
                uses apply-group;
                uses apply-macro;
                list bandwidth {
                  key "name";
                  leaf name {
                    type string;
                  }
                  leaf metric {
                    type uint16;
                  }
                }
              }
            }
          }
          list sham-link-remote {
            key "name";
            ordered-by user;
            leaf name {
              type ipaddr;
            }
            uses apply-group;
            uses apply-macro;
            leaf metric {
              type uint16;
            }
            leaf ipsec-sa {
              type string;
            }
            leaf demand-circuit {
              type empty;
            }
            leaf flood-reduction {
              type empty;
            }
            list topology {
              key "name";
              ordered-by user;
              leaf name {
                type string;
              }
              uses apply-group;
              uses apply-macro;
              leaf disable {
                type empty;
              }
              leaf metric {
                type uint16;
              }
              container bandwidth-based-metrics {
                uses apply-group;
                uses apply-macro;
                list bandwidth {
                  key "name";
                  leaf name {
                    type string;
                  }
                  leaf metric {
                    type uint16;
                  }
                }
              }
            }
          }
          list interface {
            key "name";
            ordered-by user;
            leaf name {
              type ipv4addr-or-interface;
            }
            uses apply-group;
            uses apply-macro;
            choice choice-3 {
              leaf disable {
                type empty;
              }
            }
            leaf interface-type {
              type string;
            }
            choice choice-6 {
              leaf link-protection {
                type empty;
              }
              leaf node-link-protection {
                type empty;
              }
            }
            leaf no-eligible-backup {
              type empty;
            }
            container passive {
              presence "enable passive";
              uses apply-group;
              uses apply-macro;
              container traffic-engineering {
                uses apply-group;
                uses apply-macro;
                leaf remote-node-id {
                  type ipaddr;
                }
              }
            }
            leaf secondary {
              type empty;
            }
            leaf own-router-lsa {
              type empty;
            }
            container bandwidth-based-metrics {
              uses apply-group;
              uses apply-macro;
              list bandwidth {
                key "name";
                leaf name {
                  type string;
                }
                leaf metric {
                  type uint16;
                }
              }
            }
            leaf metric {
              type uint16;
            }
            leaf te-metric {
              type uint32;
            }
            leaf priority {
              type uint32;
            }
            container ldp-synchronization {
              presence "enable ldp-synchronization";
              uses ldp-sync-obj;
            }
            leaf retransmit-interval {
              type uint32;
            }
            leaf transit-delay {
              type uint32;
            }
            leaf hello-interval {
              type uint32;
            }
            leaf dead-interval {
              type uint32;
            }
            choice choice-33 {
              container authentication {
                uses juniper-ospf-authentication;
              }
            }
            leaf demand-circuit {
              type empty;
            }
            leaf flood-reduction {
              type empty;
            }
            leaf no-neighbor-down-notification {
              type empty;
            }
            leaf ipsec-sa {
              type string;
            }
            list topology {
              key "name";
              ordered-by user;
              leaf name {
                type string;
              }
              uses apply-group;
              uses apply-macro;
              leaf disable {
                type empty;
              }
              leaf metric {
                type uint16;
              }
              container bandwidth-based-metrics {
                uses apply-group;
                uses apply-macro;
                list bandwidth {
                  key "name";
                  leaf name {
                    type string;
                  }
                  leaf metric {
                    type uint16;
                  }
                }
              }
            }
            container bfd-liveness-detection {
              uses apply-group;
              uses apply-macro;
              leaf version {
                type string;
              }
              leaf minimum-interval {
                type uint32;
              }
              leaf minimum-receive-interval {
                type uint32;
              }
              leaf multiplier {
                type uint32;
              }
              choice choice-11 {
                leaf no-adaptation {
                  type empty;
                }
              }
              container transmit-interval {
                uses apply-group;
                uses apply-macro;
                leaf minimum-interval {
                  type uint32;
                }
                leaf threshold {
                  type uint32;
                }
              }
              container detection-time {
                uses apply-group;
                uses apply-macro;
                leaf threshold {
                  type uint32;
                }
              }
              container authentication {
                uses apply-group;
                uses apply-macro;
                leaf key-chain {
                  type string;
                }
                leaf algorithm {
                  type string;
                }
                leaf loose-check {
                  type empty;
                }
              }
              leaf full-neighbors-only {
                type empty;
              }
            }
            leaf dynamic-neighbors {
              type empty;
            }
            list neighbor {
              key "name";
              ordered-by user;
              leaf name {
                type ipaddr;
              }
              leaf eligible {
                type empty;
              }
            }
            leaf poll-interval {
              type uint32;
            }
            leaf no-interface-state-traps {
              type empty;
            }
          }
          leaf no-context-identifier-advertisement {
            type empty;
          }
          list context-identifier {
            key "name";
            ordered-by user;
            leaf name {
              type ipv4addr;
            }
            uses apply-group;
            uses apply-macro;
          }
          list label-switched-path {
            key "name";
            ordered-by user;
            leaf name {
              type key-attribute-string-type;
            }
            uses apply-group;
            uses apply-macro;
            choice choice-3 {
              leaf disable {
                type empty;
              }
            }
            leaf metric {
              type uint16;
            }
            list topology {
              key "name";
              ordered-by user;
              leaf name {
                type string;
              }
              uses apply-group;
              uses apply-macro;
              leaf disable {
                type empty;
              }
              leaf metric {
                type uint16;
              }
              container bandwidth-based-metrics {
                uses apply-group;
                uses apply-macro;
                list bandwidth {
                  key "name";
                  leaf name {
                    type string;
                  }
                  leaf metric {
                    type uint16;
                  }
                }
              }
            }
          }
          list peer-interface {
            key "name";
            ordered-by user;
            leaf name {
              type string;
            }
            uses apply-group;
            uses apply-macro;
            choice choice-3 {
              leaf disable {
                type empty;
              }
            }
            leaf retransmit-interval {
              type uint32;
            }
            leaf transit-delay {
              type uint32;
            }
            leaf hello-interval {
              type uint32;
            }
            leaf dead-interval {
              type uint32;
            }
            choice choice-12 {
              container authentication {
                uses juniper-ospf-authentication;
              }
            }
            leaf demand-circuit {
              type empty;
            }
            leaf flood-reduction {
              type empty;
            }
            leaf no-neighbor-down-notification {
              type empty;
            }
          }
        }
      }
      container rip {
        uses juniper-protocols-rip;
      }
      container ripng {
        uses juniper-protocols-ripng;
      }
      container isis {
        uses juniper-protocols-isis;
      }
      container esis {
        uses juniper-protocols-esis;
      }
      choice choice-17 {
        container l2vpn {
          uses juniper-protocols-l2vpn;
        }
        container vpls {
          presence "enable vpls";
          uses juniper-protocols-l2vpn;
        }
        container evpn {
          presence "enable evpn";
          uses juniper-protocols-l2vpn;
        }
      }
      container pim {
        uses juniper-protocols-pim;
      }
      container amt {
        uses juniper-protocols-amt;
      }
      container ldp {
        uses juniper-protocols-ldp;
      }
      container router-discovery {
        uses juniper-protocols-router-discovery;
      }
      container msdp {
        uses juniper-protocols-msdp;
      }
      container mvpn {
        presence "enable mvpn";
        uses juniper-protocols-mvpn;
      }
      container igmp-snooping {
        presence "enable igmp-snooping";
        uses juniper-protocols-igmp-snooping;
      }
      container mld-snooping {
        presence "enable mld-snooping";
        uses juniper-ri-protocols-mld-snooping;
      }
      container rstp {
        uses juniper-protocols-stp;
      }
      container mstp {
        uses juniper-protocols-mstp;
      }
      container vstp {
        uses juniper-protocols-vstp;
      }
      container mvrp {
        uses juniper-protocols-mvrp;
      }
    }
    container bridge-domains {
      uses apply-group;
      uses apply-macro;
      list domain {
        key "name";
        uses juniper-bridge-domains;
      }
    }
    container switch-options {
      uses juniper-routing-instance-switch-options;
    }
    container pbb-options {
      uses juniper-routing-instance-pbb-options;
    }
    list service-groups {
      key "name";
      uses juniper-routing-instance-service-groups;
    }
    leaf layer3-domain-identifier {
      type uint32;
    }
    leaf l2-domain-id-for-l3 {
      type uint32;
    }
    container forwarding-instance {
      leaf identifier {
        type uint32;
      }
    }
    leaf service-type {
      type string;
    }
    leaf non-forwarding-vrf {
      type empty;
    }
    container mld-snooping-options {
      uses juniper-mld-snooping-options;
    }
    container vlans {
      uses apply-group;
      uses apply-macro;
      list vlan {
        key "name";
        uses vlan-types;
      }
    }
  }

  grouping juniper-mld-snooping-options {
    uses apply-group;
    uses apply-macro;
    leaf use-p2mp-lsp {
      type empty;
    }
    container snoop-pseudowires {
      presence "enable snoop-pseudowires";
      uses apply-group;
      uses apply-macro;
    }
  }

  grouping juniper-igmp-snooping-options {
    uses apply-group;
    uses apply-macro;
    leaf use-p2mp-lsp {
      type empty;
    }
    container snoop-pseudowires {
      presence "enable snoop-pseudowires";
      uses apply-group;
      uses apply-macro;
      container undocumented {
        leaf no-flood-reports {
          type empty;
        }
      }
    }
  }

  grouping juniper-protocols-l2vpn {
    uses apply-group;
    uses apply-macro;
    container traceoptions {
      uses apply-group;
      uses apply-macro;
      container file {
        presence "";
        uses trace-file-type;
      }
      list flag {
        key "name";
        ordered-by user;
        leaf name {
          type string;
        }
        leaf send {
          type empty;
        }
        leaf receive {
          type empty;
        }
        leaf detail {
          type empty;
        }
        leaf disable {
          type empty;
        }
      }
    }
    leaf encapsulation-type {
      type string;
    }
    choice choice-control-word {
      leaf control-word {
        type empty;
      }
      leaf no-control-word {
        type empty;
      }
    }
    leaf site-range {
      type uint32;
    }
    leaf bum-hashing {
      type empty;
    }
    leaf enable-mac-move-action {
      type empty;
    }
    leaf mac-pinning {
      type empty;
    }
    leaf label-block-size {
      type string;
    }
    container mac-table-size {
      uses apply-group;
      uses apply-macro;
      leaf limit {
        type string;
      }
      leaf packet-action {
        type string;
      }
    }
    container mac-ip-table-size {
      uses apply-group;
      uses apply-macro;
      leaf limit {
        type string;
      }
    }
    container interface-mac-limit {
      uses apply-group;
      uses apply-macro;
      leaf limit {
        type string;
      }
      leaf packet-action {
        type string;
      }
    }
    container interface-mac-ip-limit {
      uses apply-group;
      uses apply-macro;
      leaf limit {
        type string;
      }
    }
    container mac-notification {
      presence "enable mac-notification";
      uses apply-group;
      uses apply-macro;
      leaf notification-interval {
        units "seconds";
        type uint32;
      }
    }
    leaf mac-table-aging-time {
      units "seconds";
      type uint32;
    }
    leaf no-mac-learning {
      type empty;
    }
    leaf no-normalization {
      type empty;
    }
    leaf normalization {
      type empty;
    }
    leaf mac-statistics {
      type empty;
    }
    container mib {
      presence "enable mib";
      uses apply-group;
      uses apply-macro;
      container dot1q-mib {
        presence "enable dot1q-mib";
        uses apply-group;
        uses apply-macro;
        leaf port-list {
          type string;
        }
      }
    }
    container static-rvtep-mac {
      uses apply-group;
      uses apply-macro;
      list mac {
        key "mac_addr remote-vtep";
        leaf mac_addr {
          type mac-unicast;
        }
        leaf remote-vtep {
          type ipaddr;
        }
      }
    }
    list interface {
      key "name";
      ordered-by user;
      leaf name {
        type interface-name;
      }
      uses apply-group;
      uses apply-macro;
      container interface-mac-limit {
        uses apply-group;
        uses apply-macro;
        leaf limit {
          type string;
        }
        leaf disable {
          type empty;
        }
        leaf packet-action {
          type string;
        }
      }
      leaf protect-interface {
        type interface-name;
      }
      leaf action-priority {
        type uint32;
      }
      leaf remote-site-id {
        type uint32;
      }
      leaf target-attachment-identifier {
        type string;
      }
      leaf flow-label-transmit {
        type empty;
      }
      leaf flow-label-receive {
        type empty;
      }
      leaf encapsulation-type {
        type string;
      }
      leaf ignore-encapsulation-mismatch {
        type empty;
      }
      leaf mtu {
        type uint16;
      }
      leaf ignore-mtu-mismatch {
        type empty;
      }
      leaf control-word {
        type empty;
      }
      leaf no-control-word {
        type empty;
      }
      leaf pseudowire-status-tlv {
        type empty;
      }
      container oam {
        uses apply-group;
        uses apply-macro;
        leaf ping-interval {
          units "seconds";
          type uint16;
        }
        leaf ping-multiplier {
          type uint8;
        }
        container bfd-liveness-detection {
          uses apply-group;
          uses apply-macro;
          leaf version {
            type string;
          }
          leaf minimum-interval {
            units "milliseconds";
            type uint32;
          }
          leaf minimum-transmit-interval {
            units "milliseconds";
            type uint32;
          }
          leaf minimum-receive-interval {
            units "milliseconds";
            type uint32;
          }
          leaf multiplier {
            type uint32;
          }
          leaf no-adaptation {
            type empty;
          }
          container transmit-interval {
            uses apply-group;
            uses apply-macro;
            leaf minimum-interval {
              units "milliseconds";
              type uint32;
            }
            leaf threshold {
              type uint32;
              units "milliseconds";
            }
          }
          container detection-time {
            uses apply-group;
            uses apply-macro;
            leaf threshold {
              type uint32;
              units "milliseconds";
            }
          }
        }
      }
      leaf community {
        type string;
      }
      list static-mac {
        key "name";
        ordered-by user;
        leaf name {
          type mac-addr;
        }
        uses apply-group;
        uses apply-macro;
        list vlan-id {
          key "name";
          ordered-by user;
          leaf name {
            type key-attribute-ulong-type;
          }
          uses apply-group;
          uses apply-macro;
        }
      }
      container interface-mac-ip-limit {
        uses apply-group;
        uses apply-macro;
        leaf limit {
          type string;
        }
      }
      leaf no-mac-learning {
        type empty;
      }
      leaf mac-pinning {
        type empty;
      }
      leaf description {
        type string;
      }
      container vpws-service-id {
        presence "";
        uses apply-group;
        uses apply-macro;
        leaf local {
          mandatory true;
          type uint32;
        }
        leaf remote {
          mandatory true;
          type uint32;
        }
      }
      leaf persistent-learning {
        type empty;
      }
    }
    choice choice-tunnel-services {
      container tunnel-services {
        uses apply-group;
        uses apply-macro;
        leaf-list devices {
          type interface-device;
          ordered-by user;
        }
        leaf primary {
          type interface-device;
        }
      }
      leaf no-tunnel-services {
        type empty;
      }
    }
    list site {
      key "name";
      ordered-by user;
      leaf name {
        type string;
      }
      uses apply-group;
      uses apply-macro;
      choice choice-site-identifier {
        leaf site-identifier {
          type uint32;
        }
        container automatic-site-id {
          presence "enable automatic-site-id";
          uses apply-group;
          uses apply-macro;
          leaf startup-wait-time {
            units "seconds";
            type uint32;
          }
          leaf new-site-wait-time {
            units "seconds";
            type uint32;
          }
          leaf collision-detect-time {
            units "seconds";
            type uint32;
          }
          container reclaim-wait-time {
            presence "";
            leaf minimum {
              type uint32;
              units "milliseconds";
            }
            leaf maximum {
              type uint32;
              units "milliseconds";
            }
          }
        }
      }
      leaf source-attachment-identifier {
        type string;
      }
      leaf flow-label-transmit {
        type empty;
      }
      leaf flow-label-receive {
        type empty;
      }
      leaf encapsulation-type {
        type string;
      }
      leaf ignore-encapsulation-mismatch {
        type empty;
      }
      leaf control-word {
        type empty;
      }
      leaf no-control-word {
        type empty;
      }
      leaf pseudowire-status-tlv {
        type empty;
      }
      container oam {
        uses apply-group;
        uses apply-macro;
        leaf ping-interval {
          units "seconds";
          type uint16;
        }
        container bfd-liveness-detection {
          uses apply-group;
          uses apply-macro;
          leaf version {
            type string;
          }
          leaf minimum-interval {
            units "milliseconds";
            type uint32;
          }
          leaf minimum-transmit-interval {
            units "milliseconds";
            type uint32;
          }
          leaf minimum-receive-interval {
            units "milliseconds";
            type uint32;
          }
          leaf multiplier {
            type uint32;
          }
          leaf no-adaptation {
            type empty;
          }
          container transmit-interval {
            uses apply-group;
            uses apply-macro;
            leaf minimum-interval {
              units "milliseconds";
              type uint32;
            }
            leaf threshold {
              type uint32;
              units "milliseconds";
            }
          }
          container detection-time {
            uses apply-group;
            uses apply-macro;
            leaf threshold {
              type uint32;
              units "milliseconds";
            }
          }
        }
      }
      leaf community {
        type string;
      }
      container multi-homing {
        presence "enable multi-homing";
        uses apply-group;
        uses apply-macro;
        leaf hold-time {
          units "seconds";
          type uint32;
        }
      }
      leaf site-preference {
        type string;
      }
      leaf mtu {
        type uint16;
      }
      leaf ignore-mtu-mismatch {
        type empty;
      }
      list mesh-group {
        key "name";
        ordered-by user;
        leaf name {
          type string;
        }
        uses apply-group;
        uses apply-macro;
      }
      container active-interface {
        choice choice-any {
          leaf any {
            type empty;
          }
          leaf primary {
            type interface-name;
          }
        }
      }
      leaf best-site {
        type empty;
      }
      list interface {
        key "name";
        ordered-by user;
        leaf name {
          type interface-name;
        }
        uses apply-group;
        uses apply-macro;
        container interface-mac-limit {
          uses apply-group;
          uses apply-macro;
          leaf limit {
            type string;
          }
          leaf packet-action {
            type string;
          }
        }
        container vpws-service-id {
          presence "";
          uses apply-group;
          uses apply-macro;
          leaf local {
            mandatory true;
            type uint32;
          }
          leaf remote {
            mandatory true;
            type uint32;
          }
        }
        leaf protect-interface {
          type interface-name;
        }
        leaf action-priority {
          type uint32;
        }
        leaf remote-site-id {
          type uint32;
        }
        leaf target-attachment-identifier {
          type string;
        }
        leaf flow-label-transmit {
          type empty;
        }
        leaf flow-label-receive {
          type empty;
        }
        leaf encapsulation-type {
          type string;
        }
        leaf ignore-encapsulation-mismatch {
          type empty;
        }
        leaf mtu {
          type uint16;
        }
        leaf ignore-mtu-mismatch {
          type empty;
        }
        leaf control-word {
          type empty;
        }
        leaf no-control-word {
          type empty;
        }
        leaf pseudowire-status-tlv {
          type empty;
        }
        container oam {
          uses apply-group;
          uses apply-macro;
          leaf ping-interval {
            units "seconds";
            type uint16;
          }
          container bfd-liveness-detection {
            uses apply-group;
            uses apply-macro;
            leaf version {
              type string;
            }
            leaf minimum-interval {
              units "milliseconds";
              type uint32;
            }
            leaf minimum-transmit-interval {
              units "milliseconds";
              type uint32;
            }
            leaf minimum-receive-interval {
              units "milliseconds";
              type uint32;
            }
            leaf multiplier {
              type uint32;
            }
            leaf no-adaptation {
              type empty;
            }
            container transmit-interval {
              uses apply-group;
              uses apply-macro;
              leaf minimum-interval {
                units "milliseconds";
                type uint32;
              }
              leaf threshold {
                type uint32;
                units "milliseconds";
              }
            }
            container detection-time {
              uses apply-group;
              uses apply-macro;
              leaf threshold {
                type uint32;
                units "milliseconds";
              }
            }
          }
        }
        leaf community {
          type string;
        }
        list static-mac {
          key "name";
          ordered-by user;
          leaf name {
            type mac-addr;
          }
          uses apply-group;
          uses apply-macro;
          list vlan-id {
            key "name";
            ordered-by user;
            leaf name {
              type key-attribute-ulong-type;
            }
            uses apply-group;
            uses apply-macro;
          }
        }
        leaf no-mac-learning {
          type empty;
        }
        leaf description {
          type string;
        }
      }
    }
    leaf community {
      type string;
    }
    leaf vpls-id {
      type string;
    }
    leaf mtu {
      type uint16;
    }
    leaf ignore-mtu-mismatch {
      type empty;
    }
    container undocumented {
      leaf mac-tlv-receive {
        type empty;
      }
      leaf mac-tlv-send {
        type empty;
      }
      leaf no-vlan-id-validate {
        type empty;
      }
      leaf no-arp-suppression {
        type empty;
      }
      leaf advertise-zero-ethernet-tag {
        type empty;
      }
    }
    container mac-flush {
      presence "enable mac-flush";
      uses apply-group;
      uses apply-macro;
      leaf any-interface {
        type empty;
      }
      leaf any-spoke {
        type empty;
      }
      leaf propagate {
        type empty;
      }
    }
    leaf ignore-encapsulation-mismatch {
      type empty;
    }
    leaf pseudowire-status-tlv {
      type empty;
    }
    list neighbor {
      key "name";
      ordered-by user;
      leaf name {
        type ipv4addr;
      }
      uses apply-group;
      uses apply-macro;
      container undocumented {
        leaf virtual-circuit-id {
          type uint32;
        }
      }
      container static {
        presence "";
        uses apply-group;
        uses apply-macro;
        leaf incoming-label {
          type uint32;
        }
        leaf outgoing-label {
          type uint32;
        }
      }
      container associate-profile {
        presence "";
        uses apply-group;
        uses apply-macro;
        leaf profile-name {
          type string;
        }
        leaf profile-variable-set {
          type string;
        }
      }
      leaf psn-tunnel-endpoint {
        type ipv4addr;
      }
      leaf community {
        type string;
      }
      leaf mac-pinning {
        type empty;
      }
      leaf encapsulation-type {
        type string;
      }
      leaf ignore-encapsulation-mismatch {
        type empty;
      }
      leaf pseudowire-status-tlv {
        type empty;
      }
      leaf switchover-delay {
        units "milliseconds";
        type uint32;
      }
      container revert-time {
        presence "";
        leaf delay {
          mandatory true;
          units "seconds";
          type uint32;
        }
        leaf maximum {
          units "seconds";
          type uint32;
        }
      }
      leaf connection-protection {
        type empty;
      }
      list backup-neighbor {
        key "name";
        ordered-by user;
        leaf name {
          type ipv4addr;
        }
        uses apply-group;
        uses apply-macro;
        container undocumented {
          leaf virtual-circuit-id {
            type uint32;
          }
        }
        container static {
          presence "";
          uses apply-group;
          uses apply-macro;
          leaf incoming-label {
            type uint32;
          }
          leaf outgoing-label {
            type uint32;
          }
        }
        leaf community {
          type string;
        }
        leaf psn-tunnel-endpoint {
          type ipv4addr;
        }
        leaf standby {
          type empty;
        }
        leaf hot-standby {
          type empty;
        }
      }
      container oam {
        uses apply-group;
        uses apply-macro;
        leaf ping-interval {
          units "seconds";
          type uint16;
        }
        container bfd-liveness-detection {
          uses apply-group;
          uses apply-macro;
          leaf version {
            type string;
          }
          leaf minimum-interval {
            units "milliseconds";
            type uint32;
          }
          leaf minimum-transmit-interval {
            units "milliseconds";
            type uint32;
          }
          leaf minimum-receive-interval {
            units "milliseconds";
            type uint32;
          }
          leaf multiplier {
            type uint32;
          }
          leaf no-adaptation {
            type empty;
          }
          container transmit-interval {
            uses apply-group;
            uses apply-macro;
            leaf minimum-interval {
              units "milliseconds";
              type uint32;
            }
            leaf threshold {
              type uint32;
              units "milliseconds";
            }
          }
          container detection-time {
            uses apply-group;
            uses apply-macro;
            leaf threshold {
              type uint32;
              units "milliseconds";
            }
          }
        }
      }
    }
    leaf flow-label-transmit {
      type empty;
    }
    leaf flow-label-receive {
      type empty;
    }
    leaf flow-label-transmit-static {
      type empty;
    }
    leaf flow-label-receive-static {
      type empty;
    }
    leaf flow-label {
      type empty;
    }
    leaf flow-label-static {
      type empty;
    }
    list import-labeled-routes {
      key "name";
      ordered-by user;
      leaf name {
        type string;
      }
    }
    container associate-profile {
      presence "";
      uses apply-group;
      uses apply-macro;
      leaf profile-name {
        type string;
      }
      leaf profile-variable-set {
        type string;
      }
    }
    list mesh-group {
      key "name";
      leaf name {
        type string;
      }
      uses apply-group;
      uses apply-macro;
      list interface {
        key "name";
        leaf name {
          type string;
        }
        uses apply-advanced;
      }
      container associate-profile {
        presence "";
        uses apply-group;
        uses apply-macro;
        leaf profile-name {
          type string;
        }
        leaf profile-variable-set {
          type string;
        }
      }
      container peer-as {
        uses apply-group;
        uses apply-macro;
        leaf all {
          type empty;
        }
      }
      leaf vpls-id {
        type string;
      }
      leaf-list vrf-import {
        type policy-algebra;
        ordered-by user;
      }
      leaf-list vrf-export {
        type policy-algebra;
        ordered-by user;
      }
      container vrf-target {
        uses apply-group;
        uses apply-macro;
        leaf community {
          type string;
        }
        leaf import {
          type string;
        }
        leaf export {
          type string;
        }
      }
      container mac-flush {
        presence "enable mac-flush";
        uses apply-group;
        uses apply-macro;
        leaf any-interface {
          type empty;
        }
        leaf any-spoke {
          type empty;
        }
        leaf propagate {
          type empty;
        }
      }
      leaf local-switching {
        type empty;
      }
      list neighbor {
        key "name";
        ordered-by user;
        leaf name {
          type ipv4addr;
        }
        uses apply-group;
        uses apply-macro;
        container static {
          presence "";
          uses apply-group;
          uses apply-macro;
          leaf incoming-label {
            type uint32;
          }
          leaf outgoing-label {
            type uint32;
          }
        }
        container associate-profile {
          presence "";
          uses apply-group;
          uses apply-macro;
          leaf profile-name {
            type string;
          }
          leaf profile-variable-set {
            type string;
          }
        }
        leaf psn-tunnel-endpoint {
          type ipv4addr;
        }
        leaf community {
          type string;
        }
        leaf mac-pinning {
          type empty;
        }
        leaf encapsulation-type {
          type string;
        }
        leaf ignore-encapsulation-mismatch {
          type empty;
        }
        container pseudowire-status-tlv {
          presence "enable pseudowire-status-tlv";
          uses apply-group;
          uses apply-macro;
          leaf hot-standby-vc-on {
            type empty;
          }
        }
        leaf switchover-delay {
          units "milliseconds";
          type uint32;
        }
        container revert-time {
          presence "";
          leaf delay {
            mandatory true;
            units "seconds";
            type uint32;
          }
          leaf maximum {
            units "seconds";
            type uint32;
          }
        }
        leaf connection-protection {
          type empty;
        }
        list backup-neighbor {
          key "name";
          ordered-by user;
          leaf name {
            type ipv4addr;
          }
          uses apply-group;
          uses apply-macro;
          container static {
            presence "";
            uses apply-group;
            uses apply-macro;
            leaf incoming-label {
              type uint32;
            }
            leaf outgoing-label {
              type uint32;
            }
          }
          leaf community {
            type string;
          }
          leaf psn-tunnel-endpoint {
            type ipv4addr;
          }
          leaf standby {
            type empty;
          }
          leaf hot-standby {
            type empty;
          }
        }
        container oam {
          uses apply-group;
          uses apply-macro;
          leaf ping-interval {
            units "seconds";
            type uint16;
          }
          leaf ping-multiplier {
            type uint8;
          }
          container bfd-liveness-detection {
            uses apply-group;
            uses apply-macro;
            leaf version {
              type string;
            }
            leaf minimum-interval {
              units "milliseconds";
              type uint32;
            }
            leaf minimum-transmit-interval {
              units "milliseconds";
              type uint32;
            }
            leaf minimum-receive-interval {
              units "milliseconds";
              type uint32;
            }
            leaf multiplier {
              type uint32;
            }
            leaf no-adaptation {
              type empty;
            }
            container transmit-interval {
              uses apply-group;
              uses apply-macro;
              leaf minimum-interval {
                units "milliseconds";
                type uint32;
              }
              leaf threshold {
                type uint32;
                units "milliseconds";
              }
            }
            container detection-time {
              uses apply-group;
              uses apply-macro;
              leaf threshold {
                type uint32;
                units "milliseconds";
              }
            }
          }
        }
        leaf-list vpls-id-list {
          ordered-by user;
          type uint32;
        }
        container undocumented {
          leaf virtual-circuit-id {
            type string;
          }
        }
      }
      container route-distinguisher {
        leaf rd-type {
          type string;
        }
      }
    }
    leaf connectivity-type {
      type string;
    }
    container oam {
      uses apply-group;
      uses apply-macro;
      leaf ping-interval {
        units "seconds";
        type uint16;
      }
      container bfd-liveness-detection {
        uses apply-group;
        uses apply-macro;
        leaf version {
          type string;
        }
        leaf minimum-interval {
          units "milliseconds";
          type uint32;
        }
        leaf minimum-transmit-interval {
          units "milliseconds";
          type uint32;
        }
        leaf minimum-receive-interval {
          units "milliseconds";
          type uint32;
        }
        leaf multiplier {
          type uint32;
        }
        leaf no-adaptation {
          type empty;
        }
        container transmit-interval {
          uses apply-group;
          uses apply-macro;
          leaf minimum-interval {
            units "milliseconds";
            type uint32;
          }
          leaf threshold {
            type uint32;
            units "milliseconds";
          }
        }
        container detection-time {
          uses apply-group;
          uses apply-macro;
          leaf threshold {
            type uint32;
            units "milliseconds";
          }
        }
      }
      container control-channel {
        uses apply-group;
        uses apply-macro;
        choice choice-pwe3-control-word {
          leaf pwe3-control-word {
            type empty;
          }
          leaf router-alert-label {
            type empty;
          }
          leaf pw-label-ttl-1 {
            type empty;
          }
        }
      }
    }
    container multi-homing {
      uses apply-group;
      uses apply-macro;
      leaf peer-active {
        type empty;
      }
      list site {
        key "name";
        leaf name {
          type string;
        }
        uses apply-group;
        uses apply-macro;
        leaf identifier {
          type uint16;
        }
        leaf preference {
          type string;
        }
        container active-interface {
          uses apply-group;
          uses apply-macro;
          choice choice-any {
            leaf any {
              type empty;
            }
            leaf primary {
              type interface-name;
            }
          }
        }
        list interface {
          key "name";
          ordered-by user;
          leaf name {
            type interface-name;
          }
          uses apply-group;
          uses apply-macro;
          leaf preference {
            type uint16;
          }
        }
        leaf peer-active {
          type empty;
        }
      }
    }
    container evi-options {
      uses juniper-protocols-evi-options;
    }
    leaf p2mp-bud-support {
      type empty;
    }
    container remote-ip-host-routes {
      presence "enable remote-ip-host-routes";
      uses apply-advanced;
      leaf-list import {
        ordered-by user;
        type policy-algebra;
      }
      leaf no-advertise-community {
        type empty;
      }
    }
    leaf pbb-evpn-core {
      type empty;
    }
    leaf label-allocation {
      type string;
    }
    container proxy-mac {
      uses apply-group;
      uses apply-macro;
      leaf irb {
        type empty;
      }
      leaf proxy-mac-address {
        type mac-unicast;
      }
    }
    leaf service-type {
      type string;
    }
    leaf designated-forwarder-election-hold-time {
      units "seconds";
      type uint32;
    }
    leaf evpn-etree {
      type empty;
    }
    leaf igmp-id {
      type uint32;
    }
    leaf designated-forwarder-preference-least {
      type empty;
    }
    leaf encapsulation {
      type string;
    }
    leaf-list extended-vlan-list {
      type string;
    }
    leaf-list extended-vni-list {
      type string;
    }
    leaf-list extended-isid-list {
      type string;
    }
    container mclag {
      uses apply-group;
      uses apply-macro;
      leaf bgp-peer {
        type ipaddr;
      }
    }
    container vni-options {
      uses apply-group;
      uses apply-macro;
      list vni {
        key "name";
        leaf name {
          type key-attribute-long-type;
        }
        uses apply-group;
        uses apply-macro;
        container vrf-target {
          uses apply-group;
          uses apply-macro;
          leaf export {
            type string;
          }
          leaf community {
            type string;
          }
        }
      }
    }
    container ip-prefix-routes {
      presence "";
      uses apply-group;
      uses apply-macro;
      leaf advertise {
        mandatory true;
        type string;
      }
      leaf gateway-interface {
        type interface-unit;
      }
      leaf encapsulation {
        type string;
      }
      leaf vni {
        type uint32;
      }
      leaf-list import {
        type policy-algebra;
        ordered-by user;
      }
      leaf-list export {
        type policy-algebra;
        ordered-by user;
      }
    }
    leaf multicast-mode {
      type string;
    }
    container vrf-target {
      uses apply-group;
      uses apply-macro;
      leaf community {
        type string;
      }
    }
    leaf default-gateway {
      type string;
    }
    leaf no-arp-suppression {
      type empty;
    }
    container duplicate-mac-detection {
      uses apply-group;
      uses apply-macro;
      leaf detection-threshold {
        type uint32;
      }
      leaf detection-window {
        units "seconds";
        type uint32;
      }
      leaf auto-recovery-time {
        units "minutes";
        type uint32;
      }
    }
    choice choice-flexible-cross-connect-vlan-aware {
      leaf flexible-cross-connect-vlan-aware {
        type empty;
      }
      leaf flexible-cross-connect-vlan-unaware {
        type empty;
      }
    }
    leaf auto-service-id {
      type empty;
    }
    leaf hot-standby-on {
      type empty;
    }
    list group {
      key "name";
      ordered-by user;
      leaf name {
        type string;
      }
      uses apply-group;
      uses apply-macro;
      container esi {
        presence "";
        uses apply-group;
        uses apply-macro;
        leaf identifier {
          mandatory true;
          type esi;
        }
      }
      list interface {
        key "name";
        ordered-by user;
        leaf name {
          type interface-name;
        }
        uses apply-group;
        uses apply-macro;
      }
      container service-id {
        presence "";
        uses apply-group;
        uses apply-macro;
        leaf local {
          mandatory true;
          type uint32;
        }
        leaf remote {
          mandatory true;
          type uint32;
        }
      }
    }
  }

  grouping juniper-protocols-evi-options {
    uses apply-group;
    uses apply-macro;
    list isid {
      key "name";
      leaf name {
        type key-attribute-long-type;
      }
      uses apply-group;
      uses apply-macro;
      container vrf-target {
        uses apply-group;
        uses apply-macro;
        leaf community {
          type string;
        }
      }
    }
  }

  grouping juniper-ri-protocols-mld-snooping {
    uses apply-group;
    uses apply-macro;
    container traceoptions {
      uses apply-group;
      uses apply-macro;
      container file {
        presence "";
        uses trace-file-type;
      }
      list flag {
        key "name";
        ordered-by user;
        leaf name {
          type string;
        }
        leaf send {
          type empty;
        }
        leaf receive {
          type empty;
        }
        leaf detail {
          type empty;
        }
        leaf disable {
          type empty;
        }
      }
    }
    leaf query-interval {
      units "seconds";
      type uint32;
    }
    leaf query-response-interval {
      type string;
      units "seconds";
    }
    leaf query-last-member-interval {
      type string;
      units "seconds";
    }
    leaf robust-count {
      type uint32;
    }
    leaf immediate-leave {
      type empty;
    }
    container proxy {
      presence "";
      uses apply-group;
      uses apply-macro;
      leaf source-address {
        mandatory true;
        type ipv6addr;
      }
      leaf irb {
        type empty;
      }
    }
    list interface {
      key "name";
      ordered-by user;
      leaf name {
        type interface-name;
      }
      uses apply-group;
      uses apply-macro;
      leaf multicast-router-interface {
        type empty;
      }
      leaf immediate-leave {
        type empty;
      }
      leaf host-only-interface {
        type empty;
      }
      leaf group-limit {
        type uint16;
      }
      container static {
        uses apply-group;
        uses apply-macro;
        list group {
          key "name";
          ordered-by user;
          leaf name {
            type ipv6addr;
          }
          uses apply-group;
          uses apply-macro;
          list source {
            key "name";
            ordered-by user;
            leaf name {
              type ipv6addr;
            }
            uses apply-group;
            uses apply-macro;
          }
        }
      }
    }
    list pseudowire-remote-address {
      key "name";
      ordered-by user;
      leaf name {
        type ipv4addr;
      }
      uses apply-group;
      uses apply-macro;
      leaf multicast-router-interface {
        type empty;
      }
      leaf immediate-leave {
        type empty;
      }
    }
    list qualified-vlan {
      key "name";
      ordered-by user;
      leaf name {
        type key-attribute-ulong-type;
      }
      uses apply-group;
      uses apply-macro;
      leaf query-interval {
        units "seconds";
        type uint32;
      }
      leaf query-response-interval {
        type string;
        units "seconds";
      }
      leaf query-last-member-interval {
        type string;
        units "seconds";
      }
      leaf robust-count {
        type uint32;
      }
      leaf immediate-leave {
        type empty;
      }
      container proxy {
        presence "";
        uses apply-group;
        uses apply-macro;
        leaf source-address {
          mandatory true;
          type ipv6addr;
        }
      }
      list interface {
        key "name";
        ordered-by user;
        leaf name {
          type interface-name;
        }
        uses apply-group;
        uses apply-macro;
        leaf multicast-router-interface {
          type empty;
        }
        leaf immediate-leave {
          type empty;
        }
        leaf host-only-interface {
          type empty;
        }
        leaf group-limit {
          type uint16;
        }
        container static {
          uses apply-group;
          uses apply-macro;
          list group {
            key "name";
            ordered-by user;
            leaf name {
              type ipv6addr;
            }
            uses apply-group;
            uses apply-macro;
            list source {
              key "name";
              ordered-by user;
              leaf name {
                type ipv6addr;
              }
              uses apply-group;
              uses apply-macro;
            }
          }
        }
      }
      list pseudowire-remote-address {
        key "name";
        ordered-by user;
        leaf name {
          type ipv4addr;
        }
        uses apply-group;
        uses apply-macro;
        leaf multicast-router-interface {
          type empty;
        }
        leaf immediate-leave {
          type empty;
        }
      }
    }
    list vlan {
      key "name";
      ordered-by user;
      leaf name {
        type key-attribute-string-type;
      }
      uses apply-group;
      uses apply-macro;
      leaf query-interval {
        units "seconds";
        type uint32;
      }
      leaf query-response-interval {
        type string;
        units "seconds";
      }
      leaf query-last-member-interval {
        type string;
        units "seconds";
      }
      leaf robust-count {
        type uint32;
      }
      leaf immediate-leave {
        type empty;
      }
      container proxy {
        presence "";
        uses apply-group;
        uses apply-macro;
        leaf source-address {
          mandatory true;
          type ipv6addr;
        }
      }
      list interface {
        key "name";
        ordered-by user;
        leaf name {
          type interface-name;
        }
        uses apply-group;
        uses apply-macro;
        leaf multicast-router-interface {
          type empty;
        }
        leaf immediate-leave {
          type empty;
        }
        leaf host-only-interface {
          type empty;
        }
        leaf group-limit {
          type uint16;
        }
        container static {
          uses apply-group;
          uses apply-macro;
          list group {
            key "name";
            ordered-by user;
            leaf name {
              type ipv6addr;
            }
            uses apply-group;
            uses apply-macro;
            list source {
              key "name";
              ordered-by user;
              leaf name {
                type ipv6addr;
              }
              uses apply-group;
              uses apply-macro;
            }
          }
        }
      }
      list pseudowire-remote-address {
        key "name";
        ordered-by user;
        leaf name {
          type ipv4addr;
        }
        uses apply-group;
        uses apply-macro;
        leaf multicast-router-interface {
          type empty;
        }
        leaf immediate-leave {
          type empty;
        }
      }
      list qualified-vlan {
        key "name";
        ordered-by user;
        leaf name {
          type key-attribute-ulong-type;
        }
        uses apply-group;
        uses apply-macro;
        leaf query-interval {
          units "seconds";
          type uint32;
        }
        leaf query-response-interval {
          type string;
          units "seconds";
        }
        leaf query-last-member-interval {
          type string;
          units "seconds";
        }
        leaf robust-count {
          type uint32;
        }
        leaf immediate-leave {
          type empty;
        }
        container proxy {
          presence "";
          uses apply-group;
          uses apply-macro;
          leaf source-address {
            mandatory true;
            type ipv6addr;
          }
        }
        list interface {
          key "name";
          ordered-by user;
          leaf name {
            type interface-name;
          }
          uses apply-group;
          uses apply-macro;
          leaf multicast-router-interface {
            type empty;
          }
          leaf immediate-leave {
            type empty;
          }
          leaf host-only-interface {
            type empty;
          }
          leaf group-limit {
            type uint16;
          }
          container static {
            uses apply-group;
            uses apply-macro;
            list group {
              key "name";
              ordered-by user;
              leaf name {
                type ipv6addr;
              }
              uses apply-group;
              uses apply-macro;
              list source {
                key "name";
                ordered-by user;
                leaf name {
                  type ipv6addr;
                }
                uses apply-group;
                uses apply-macro;
              }
            }
          }
        }
        list pseudowire-remote-address {
          key "name";
          ordered-by user;
          leaf name {
            type ipv4addr;
          }
          uses apply-group;
          uses apply-macro;
          leaf multicast-router-interface {
            type empty;
          }
          leaf immediate-leave {
            type empty;
          }
        }
      }
    }
  }

  grouping juniper-protocols-mvpn {
    uses apply-group;
    uses apply-macro;
    container traceoptions {
      uses apply-group;
      uses apply-macro;
      container file {
        presence "";
        uses trace-file-type;
      }
      list flag {
        key "name";
        ordered-by user;
        leaf name {
          type string;
        }
        leaf send {
          type empty;
        }
        leaf receive {
          type empty;
        }
        leaf detail {
          type empty;
        }
        leaf disable {
          type empty;
        }
      }
    }
    container autodiscovery-only {
      uses apply-group;
      uses apply-macro;
      container intra-as {
        presence "";
        uses apply-group;
        uses apply-macro;
        leaf inclusive {
          type empty;
        }
      }
    }
    container family {
      uses apply-group;
      uses apply-macro;
      container any {
        presence "enable any";
        uses apply-group;
        uses apply-macro;
        leaf disable {
          type empty;
        }
      }
      container inet {
        presence "enable inet";
        uses apply-group;
        uses apply-macro;
        container autodiscovery-only {
          uses apply-group;
          uses apply-macro;
          container intra-as {
            presence "";
            uses apply-group;
            uses apply-macro;
            leaf inclusive {
              type empty;
            }
          }
        }
        leaf disable {
          type empty;
        }
      }
      container inet6 {
        presence "enable inet6";
        uses apply-group;
        uses apply-macro;
        leaf disable {
          type empty;
        }
      }
    }
    choice choice-7 {
      leaf receiver-site {
        type empty;
      }
      leaf sender-site {
        type empty;
      }
    }
    leaf unicast-umh-election {
      type empty;
    }
    leaf cmcast-joins-limit-inet {
      type uint32;
    }
    leaf cmcast-joins-limit-inet6 {
      type uint32;
    }
    container mvpn-mode {
      uses apply-group;
      uses apply-macro;
      choice choice-3 {
        container rpt-spt {
          presence "enable rpt-spt";
          uses apply-group;
          uses apply-macro;
          leaf spt-switch-timer {
            type uint32;
          }
        }
        container spt-only {
          presence "enable spt-only";
          uses apply-group;
          uses apply-macro;
        }
      }
    }
    container route-target {
      uses apply-group;
      uses apply-macro;
      container import-target {
        uses apply-group;
        uses apply-macro;
        container unicast {
          presence "enable unicast";
          choice choice-3 {
            leaf receiver {
              type empty;
            }
            leaf sender {
              type empty;
            }
          }
        }
        container target {
          presence "enable target";
          leaf target-value {
            type string;
          }
          choice choice-5 {
            leaf receiver {
              type empty;
            }
            leaf sender {
              type empty;
            }
          }
        }
      }
      container export-target {
        uses apply-group;
        uses apply-macro;
        leaf unicast {
          type empty;
        }
        leaf target {
          type string;
        }
      }
    }
    container mvpn-join-load-balance {
      uses apply-group;
      uses apply-macro;
      container bytewise-xor-hash {
        presence "enable bytewise-xor-hash";
        uses apply-group;
        uses apply-macro;
      }
    }
    leaf install-discard {
      type empty;
    }
    leaf sender-based-rpf {
      type empty;
    }
    container hot-root-standby {
      uses apply-advanced;
      choice tree {
        case case_1 {
          container source-tree {
            presence "enable source-tree";
          }
        }
      }
      container min-rate {
        uses apply-advanced;
        leaf rate {
          units "bits per second";
          type string;
        }
        leaf revert-delay {
          units "seconds";
          type string;
        }
      }
    }
    leaf hierarchical-nexthop {
      type empty;
    }
    leaf no-nexthop-sharing-for-selective-tunnel {
      type empty;
    }
    container inter-region-template {
      uses apply-advanced;
      list template {
        key "name";
        ordered-by user;
        leaf name {
          type string;
        }
        uses apply-advanced;
        list region {
          key "name";
          ordered-by user;
          leaf name {
            type string;
          }
          uses apply-advanced;
          choice tunnel-type {
            case case_1 {
              container rsvp-te {
                uses apply-advanced;
                choice static-or-dynamic {
                  case case_1 {
                    leaf static-lsp {
                      type string;
                    }
                  }
                  case case_2 {
                    container label-switched-path-template {
                      uses apply-advanced;
                      choice dynamic-template {
                        case case_1 {
                          leaf template-name {
                            type string;
                          }
                        }
                        case case_2 {
                          leaf default-template {
                            type empty;
                          }
                        }
                      }
                    }
                  }
                }
              }
            }
            case case_2 {
              container ldp-p2mp {
                presence "enable ldp-p2mp";
              }
            }
            case case_3 {
              container ingress-replication {
                uses apply-advanced;
                leaf create-new-ucast-tunnel {
                  type empty;
                }
                container label-switched-path {
                  presence "enable label-switched-path";
                  uses apply-advanced;
                  container label-switched-path-template {
                    uses apply-advanced;
                    choice dynamic-template {
                      case case_1 {
                        leaf template-name {
                          type string;
                        }
                      }
                      case case_2 {
                        leaf default-template {
                          type empty;
                        }
                      }
                    }
                  }
                }
              }
            }
            case case_4 {
              leaf incoming {
                type empty;
              }
            }
          }
        }
        container all-regions {
          uses apply-advanced;
          choice tunnel-type {
            case case_1 {
              container rsvp-te {
                uses apply-advanced;
                choice static-or-dynamic {
                  case case_1 {
                    leaf static-lsp {
                      type string;
                    }
                  }
                  case case_2 {
                    container label-switched-path-template {
                      uses apply-advanced;
                      choice dynamic-template {
                        case case_1 {
                          leaf template-name {
                            type string;
                          }
                        }
                        case case_2 {
                          leaf default-template {
                            type empty;
                          }
                        }
                      }
                    }
                  }
                }
              }
            }
            case case_2 {
              container ldp-p2mp {
                presence "enable ldp-p2mp";
              }
            }
            case case_3 {
              container ingress-replication {
                uses apply-advanced;
                leaf create-new-ucast-tunnel {
                  type empty;
                }
                container label-switched-path {
                  presence "enable label-switched-path";
                  uses apply-advanced;
                  container label-switched-path-template {
                    uses apply-advanced;
                    choice dynamic-template {
                      case case_1 {
                        leaf template-name {
                          type string;
                        }
                      }
                      case case_2 {
                        leaf default-template {
                          type empty;
                        }
                      }
                    }
                  }
                }
              }
            }
            case case_4 {
              leaf incoming {
                type empty;
              }
            }
          }
        }
      }
    }
    leaf source-redundancy {
      type empty;
    }
    container umh-selection-additional-input {
      uses apply-advanced;
      leaf source-active-preference {
        type empty;
      }
      leaf tunnel-status {
        type empty;
      }
    }
  }

  grouping juniper-routing-instance-pbb-options {
    uses apply-group;
    uses apply-macro;
    leaf peer-instance {
      type string;
    }
    list vlan-id {
      key "name";
      ordered-by user;
      leaf name {
        type string;
      }
      leaf-list isid-list {
        type string;
        ordered-by user;
      }
    }
    leaf default-bvlan {
      type uint32;
    }
  }

  grouping juniper-routing-instance-service-groups {
    leaf name {
      type string;
    }
    uses apply-group;
    uses apply-macro;
    leaf service-type {
      type string;
    }
    container pbb-service-options {
      presence "enable pbb-service-options";
      uses apply-group;
      uses apply-macro;
      list isid {
        key "name";
        ordered-by user;
        leaf name {
          type string;
        }
        choice choice-3 {
          leaf-list vlan-id-list {
            type string;
            ordered-by user;
          }
          leaf interface {
            type interface-name;
          }
        }
      }
      leaf default-isid {
        type uint32;
      }
      leaf mac-address {
        type mac-addr;
      }
    }
  }

  grouping juniper-routing-instance-switch-options {
    uses apply-group;
    uses apply-macro;
    container mac-table-size {
      presence "enable mac-table-size";
      uses apply-group;
      uses apply-macro;
      leaf limit {
        type string;
      }
      leaf packet-action {
        type string;
      }
    }
    container mac-ip-table-size {
      uses apply-advanced;
      leaf limit {
        type string;
      }
    }
    container interface-mac-limit {
      presence "enable interface-mac-limit";
      uses apply-group;
      uses apply-macro;
      leaf limit {
        type string;
      }
      leaf packet-action {
        type string;
      }
    }
    container interface-mac-ip-limit {
      uses apply-advanced;
      leaf limit {
        type string;
      }
    }
    container mac-notification {
      presence "enable mac-notification";
      uses apply-advanced;
      leaf notification-interval {
        units "seconds";
        type string;
      }
    }
    leaf mac-table-aging-time {
      type uint32;
    }
    leaf no-mac-learning {
      type empty;
    }
    leaf mac-statistics {
      type empty;
    }
    list interface {
      key "name";
      ordered-by user;
      leaf name {
        type interface-name;
      }
      uses apply-group;
      uses apply-macro;
      container interface-mac-limit {
        presence "enable interface-mac-limit";
        uses apply-group;
        uses apply-macro;
        leaf limit {
          type string;
        }
        leaf packet-action {
          type string;
        }
      }
      leaf remote-site-id {
        type uint32;
      }
      leaf action-priority {
        type string;
      }
      list static-mac {
        key "name";
        ordered-by user;
        leaf name {
          type mac-addr;
        }
        uses apply-group;
        uses apply-macro;
        list vlan-id {
          key "name";
          ordered-by user;
          leaf name {
            type string;
          }
          uses apply-group;
          uses apply-macro;
        }
      }
      container interface-mac-ip-limit {
        uses apply-advanced;
        leaf limit {
          type string;
        }
      }
      leaf no-mac-learning {
        type empty;
      }
      leaf mac-pinning {
        type empty;
      }
      leaf persistent-learning {
        type empty;
      }
      leaf description {
        type string;
      }
    }
  }

  grouping juniper-routing-options {
    uses apply-advanced;
    container rpm-tracking {
      uses apply-advanced;
      list route {
        key "name";
        ordered-by user;
        leaf name {
          type ipprefix;
        }
        uses apply-advanced;
        list next-hop {
          key "name";
          ordered-by user;
          uses rpm-next-hop;
        }
        leaf metric {
          type string;
        }
        leaf preference {
          type string;
        }
        leaf tag {
          type string;
        }
        list rpm-probe {
          key "name";
          ordered-by user;
          leaf name {
            type string;
          }
          leaf rpm-test {
            type string;
          }
        }
      }
    }
    container logical-system-mux {
      uses apply-advanced;
      container traceoptions {
        uses apply-advanced;
        container file {
          presence "";
          leaf filename {
            type string;
          }
          leaf replace {
            status deprecated;
            type empty;
          }
          leaf size {
            type string;
          }
          leaf files {
            type string;
          }
          leaf no-stamp {
            status deprecated;
            type empty;
          }
          choice world-readable-choice {
            leaf world-readable {
              type empty;
            }
            leaf no-world-readable {
              type empty;
            }
          }
        }
        list flag {
          key "name";
          ordered-by user;
          leaf name {
            type string;
          }
          leaf send {
            type empty;
          }
          leaf receive {
            type empty;
          }
          leaf detail {
            type empty;
          }
          leaf disable {
            type empty;
          }
        }
      }
    }
    container auto-bandwidth {
      presence "enable auto-bandwidth";
      uses apply-advanced;
      list template {
        key "name";
        ordered-by user;
        leaf name {
          type string;
        }
        uses apply-advanced;
        leaf adjust-interval {
          type string;
        }
        leaf adjust-threshold {
          type string;
        }
        leaf statistic-collection-interval {
          type string;
        }
        leaf auto-bandwidth-subscription {
          type string;
        }
      }
      container traceoptions {
        uses apply-advanced;
        container file {
          leaf filename {
            type string;
          }
          leaf replace {
            status deprecated;
            type empty;
          }
          leaf size {
            type string;
          }
          leaf files {
            type string;
          }
          leaf no-stamp {
            status deprecated;
            type empty;
          }
          choice world-readable-choice {
            leaf world-readable {
              type empty;
            }
            leaf no-world-readable {
              type empty;
            }
          }
        }
        list flag {
          key "name";
          ordered-by user;
          leaf name {
            type string;
          }
          leaf send {
            type empty;
          }
          leaf receive {
            type empty;
          }
          leaf detail {
            type empty;
          }
          leaf disable {
            type empty;
          }
        }
      }
    }
    container backup-selection {
      presence "enable backup-selection";
      uses apply-advanced;
      list destination {
        key "name";
        leaf name {
          type ipprefix-mandatory;
        }
        uses apply-advanced;
        list interface {
          key "name";
          leaf name {
            type string;
          }
          uses apply-advanced;
          container admin-group {
            uses apply-advanced;
            leaf-list exclude {
              type string;
            }
            leaf-list include-all {
              type string;
            }
            leaf-list include-any {
              type string;
            }
            leaf-list preference {
              ordered-by user;
              type string;
            }
          }
          leaf srlg {
            type string;
          }
          leaf protection-type {
            type string;
          }
          leaf downstream-paths-only {
            type empty;
          }
          leaf bandwidth-greater-equal-primary {
            type empty;
          }
          container neighbor {
            uses apply-group;
            uses apply-macro;
            leaf-list exclude {
              type ipv4addr;
            }
            leaf-list preference {
              type ipv4addr;
              ordered-by user;
            }
          }
          container neighbor-tag {
            uses apply-group;
            uses apply-macro;
            leaf-list exclude {
              type uint32;
            }
            leaf-list preference {
              type uint32;
              ordered-by user;
            }
          }
          container backup-neighbor {
            uses apply-advanced;
            leaf-list exclude {
              type ipv4addr;
            }
            leaf-list preference {
              ordered-by user;
              type ipv4addr;
            }
          }
          container node {
            uses apply-advanced;
            leaf-list exclude {
              type ipv4addr;
            }
            leaf-list preference {
              ordered-by user;
              type ipv4addr;
            }
          }
          container node-tag {
            uses apply-advanced;
            leaf-list exclude {
              type string;
            }
            leaf-list preference {
              ordered-by user;
              type string;
            }
          }
          leaf root-metric {
            type string;
          }
          leaf dest-metric {
            type string;
          }
          leaf-list metric-order {
            ordered-by user;
            type string;
          }
          leaf-list evaluation-order {
            ordered-by user;
            type string;
          }
        }
      }
    }
    list flex-algorithm {
      key "name";
      leaf name {
        type string;
      }
      uses apply-advanced;
      container definition {
        uses apply-advanced;
        leaf metric-type {
          type string;
        }
        choice calculation-type {
          case case_1 {
            leaf spf {
              type empty;
            }
          }
          case case_2 {
            leaf strict-spf {
              type empty;
            }
          }
        }
        leaf use-flex-algorithm-prefix-metric {
          type empty;
        }
        leaf priority {
          type string;
        }
        container admin-group {
          uses admin-group-include-exclude;
        }
      }
      leaf color {
        type string;
      }
      leaf use-transport-class {
        type empty;
      }
    }
    container source-packet-routing {
      uses apply-advanced;
      list mapping-server-entry {
        key "name";
        ordered-by user;
        leaf name {
          type key-attribute-string-type;
        }
        uses apply-advanced;
        list prefix-segment {
          key "name";
          ordered-by user;
          leaf name {
            type ipprefix;
          }
          uses apply-advanced;
          leaf index {
            type string;
          }
          leaf attached {
            type empty;
          }
          leaf domain-wide-flooding {
            type empty;
          }
          leaf no-node-segment {
            type empty;
          }
        }
        list prefix-segment-range {
          key "name";
          ordered-by user;
          leaf name {
            type key-attribute-string-type;
          }
          uses apply-advanced;
          leaf start-prefix {
            type ipprefix;
          }
          leaf start-index {
            type string;
          }
          leaf size {
            type string;
          }
          leaf attached {
            type empty;
          }
          leaf domain-wide-flooding {
            type empty;
          }
          leaf no-node-segment {
            type empty;
          }
        }
      }
      container srv6 {
        uses apply-advanced;
        list locator {
          key "name";
          ordered-by user;
          leaf name {
            type string;
          }
          uses apply-advanced;
          leaf algorithm {
            type string;
          }
          leaf address {
            type ipv6prefix;
          }
        }
        leaf no-reduced-srh {
          type empty;
        }
        leaf transit-srh-insert {
          type empty;
        }
        leaf no-psp {
          type empty;
        }
      }
    }
    leaf route-distinguisher-id {
      type ipv4addr;
    }
    container uniform-propagation-mode {
      presence "enable uniform-propagation-mode";
      uses apply-advanced;
      list domain-id {
        key "name";
        ordered-by user;
        uses domain-id-type;
      }
    }
    list rib {
      key "name";
      ordered-by user;
      leaf name {
        type string;
      }
      uses apply-advanced;
      container static {
        uses apply-advanced;
        leaf rib-group {
          type string;
        }
        container defaults {
          uses apply-advanced;
          choice retain-choice {
            leaf retain {
              type empty;
            }
            leaf no-retain {
              type empty;
            }
          }
          choice install-choice {
            leaf install {
              type empty;
            }
            leaf no-install {
              type empty;
            }
          }
          choice readvertise-choice {
            leaf readvertise {
              type empty;
            }
            leaf no-readvertise {
              type empty;
            }
          }
          choice resolve-choice {
            leaf resolve {
              type empty;
            }
            leaf no-resolve {
              type empty;
            }
          }
          choice longest-match-choice {
            leaf longest-match {
              type empty;
            }
            leaf no-longest-match {
              type empty;
            }
          }
          choice passive_flag {
            case case_1 {
              leaf active {
                type empty;
              }
            }
            case case_2 {
              leaf passive {
                type empty;
              }
            }
          }
          container metric {
            presence "enable metric";
            uses rib-static-metric-type;
          }
          container metric2 {
            presence "enable metric2";
            uses rib-static-metric-type;
          }
          container metric3 {
            presence "enable metric3";
            uses rib-static-metric-type;
          }
          container metric4 {
            presence "enable metric4";
            uses rib-static-metric-type;
          }
          container tag {
            presence "enable tag";
            uses rib-static-metric-type;
          }
          container tag2 {
            presence "enable tag2";
            uses rib-static-metric-type;
          }
          container preference {
            presence "enable preference";
            uses rib-static-metric-type;
          }
          container preference2 {
            presence "enable preference2";
            uses rib-static-metric-type;
          }
          container color {
            presence "enable color";
            uses rib-static-metric-type;
          }
          container color2 {
            presence "enable color2";
            uses rib-static-metric-type;
          }
          leaf-list community {
            ordered-by user;
            type community;
          }
          container as-path {
            uses apply-advanced;
            leaf path {
              type string;
            }
            leaf origin {
              type string;
            }
            leaf atomic-aggregate {
              type empty;
            }
            container aggregator {
              presence "enable aggregator";
              leaf as-number {
                type string;
              }
              leaf address {
                type ipv4addr;
              }
            }
            leaf as-number {
              type string;
            }
            leaf address {
              type ipv4addr;
            }
          }
        }
        list route {
          key "name";
          ordered-by user;
          leaf name {
            type ipprefix;
          }
          uses apply-advanced;
          choice next_hop {
            case case_1 {
              leaf-list next-hop {
                ordered-by user;
                type string;
              }
            }
            case case_2 {
              leaf reject {
                type empty;
              }
            }
            case case_3 {
              leaf discard {
                type empty;
              }
            }
            case case_4 {
              leaf receive {
                type empty;
              }
            }
            case case_5 {
              leaf next-table {
                type string;
              }
            }
          }
          leaf description {
            type string;
          }
          list qualified-next-hop {
            key "name";
            ordered-by user;
            uses qualified-nh-obj;
          }
          leaf backup-pe-group {
            type string;
          }
          container bfd-liveness-detection {
            uses apply-advanced;
            leaf version {
              type string;
            }
            leaf minimum-interval {
              units "milliseconds";
              type string;
            }
            leaf minimum-transmit-interval {
              status deprecated;
              units "milliseconds";
              type string;
            }
            leaf minimum-receive-interval {
              units "milliseconds";
              type string;
            }
            leaf multiplier {
              type string;
            }
            choice adaptation-choice {
              case case_1 {
                leaf no-adaptation {
                  type empty;
                }
              }
            }
            container transmit-interval {
              uses apply-advanced;
              leaf minimum-interval {
                units "milliseconds";
                type string;
              }
              leaf threshold {
                units "milliseconds";
                type string;
              }
            }
            container detection-time {
              uses apply-advanced;
              leaf threshold {
                units "milliseconds";
                type string;
              }
            }
            container authentication {
              uses apply-advanced;
              leaf key-chain {
                type string;
              }
              leaf algorithm {
                type string;
              }
              leaf loose-check {
                type empty;
              }
            }
            leaf neighbor {
              type ipaddr;
            }
            leaf local-address {
              type ipaddr;
            }
            leaf holddown-interval {
              units "milliseconds";
              type string;
            }
            leaf minimum-receive-ttl {
              type string;
            }
          }
          choice retain-choice {
            leaf retain {
              type empty;
            }
            leaf no-retain {
              type empty;
            }
          }
          choice install-choice {
            leaf install {
              type empty;
            }
            leaf no-install {
              type empty;
            }
          }
          choice readvertise-choice {
            leaf readvertise {
              type empty;
            }
            leaf no-readvertise {
              type empty;
            }
          }
          choice resolve-choice {
            leaf resolve {
              type empty;
            }
            leaf no-resolve {
              type empty;
            }
          }
          choice longest-match-choice {
            leaf longest-match {
              type empty;
            }
            leaf no-longest-match {
              type empty;
            }
          }
          choice passive_flag {
            case case_1 {
              leaf active {
                type empty;
              }
            }
            case case_2 {
              leaf passive {
                type empty;
              }
            }
          }
          container metric {
            presence "enable metric";
            uses rib-static-metric-type;
          }
          container metric2 {
            presence "enable metric2";
            uses rib-static-metric-type;
          }
          container metric3 {
            presence "enable metric3";
            uses rib-static-metric-type;
          }
          container metric4 {
            presence "enable metric4";
            uses rib-static-metric-type;
          }
          container tag {
            presence "enable tag";
            uses rib-static-metric-type;
          }
          container tag2 {
            presence "enable tag2";
            uses rib-static-metric-type;
          }
          container preference {
            presence "enable preference";
            uses rib-static-metric-type;
          }
          container preference2 {
            presence "enable preference2";
            uses rib-static-metric-type;
          }
          container color {
            presence "enable color";
            uses rib-static-metric-type;
          }
          container color2 {
            presence "enable color2";
            uses rib-static-metric-type;
          }
          leaf-list community {
            ordered-by user;
            type community;
          }
          container as-path {
            uses apply-advanced;
            leaf path {
              type string;
            }
            leaf origin {
              type string;
            }
            leaf atomic-aggregate {
              type empty;
            }
            container aggregator {
              presence "enable aggregator";
              leaf as-number {
                type string;
              }
              leaf address {
                type ipv4addr;
              }
            }
            leaf as-number {
              type string;
            }
            leaf address {
              type ipv4addr;
            }
          }
          list lsp-next-hop {
            key "name";
            ordered-by user;
            uses lsp-nh-obj;
          }
          list p2mp-lsp-next-hop {
            key "name";
            ordered-by user;
            uses lsp-nh-obj;
          }
          container spring-te-lsp-next-hop {
            uses springte-lsp-nh-obj;
          }
          container p2mp-ldp-next-hop {
            presence "";
            uses p2mp-ldp-lsp-nh-obj;
          }
          list static-lsp-next-hop {
            key "name";
            ordered-by user;
            uses lsp-nh-obj;
          }
        }
        container static-route {
          leaf bfd-admin-down {
            type string;
          }
        }
        list iso-route {
          key "name";
          ordered-by user;
          leaf name {
            type isoprefix;
          }
          uses apply-advanced;
          choice next_hop {
            case case_1 {
              leaf-list next-hop {
                ordered-by user;
                type string;
              }
            }
            case case_2 {
              leaf reject {
                type empty;
              }
            }
            case case_3 {
              leaf discard {
                type empty;
              }
            }
            case case_4 {
              leaf receive {
                type empty;
              }
            }
            case case_5 {
              leaf next-table {
                type string;
              }
            }
          }
          list qualified-next-hop {
            key "name";
            ordered-by user;
            uses qualified-nh-obj;
          }
          leaf backup-pe-group {
            type string;
          }
          container bfd-liveness-detection {
            uses apply-advanced;
            leaf version {
              type string;
            }
            leaf minimum-interval {
              units "milliseconds";
              type string;
            }
            leaf minimum-transmit-interval {
              status deprecated;
              units "milliseconds";
              type string;
            }
            leaf minimum-receive-interval {
              units "milliseconds";
              type string;
            }
            leaf multiplier {
              type string;
            }
            choice adaptation-choice {
              case case_1 {
                leaf no-adaptation {
                  type empty;
                }
              }
            }
            container transmit-interval {
              uses apply-advanced;
              leaf minimum-interval {
                units "milliseconds";
                type string;
              }
              leaf threshold {
                units "milliseconds";
                type string;
              }
            }
            container detection-time {
              uses apply-advanced;
              leaf threshold {
                units "milliseconds";
                type string;
              }
            }
            container authentication {
              uses apply-advanced;
              leaf key-chain {
                type string;
              }
              leaf algorithm {
                type string;
              }
              leaf loose-check {
                type empty;
              }
            }
            leaf neighbor {
              type ipaddr;
            }
            leaf local-address {
              type ipaddr;
            }
            leaf holddown-interval {
              units "milliseconds";
              type string;
            }
            leaf minimum-receive-ttl {
              type string;
            }
          }
          choice retain-choice {
            leaf retain {
              type empty;
            }
            leaf no-retain {
              type empty;
            }
          }
          choice install-choice {
            leaf install {
              type empty;
            }
            leaf no-install {
              type empty;
            }
          }
          choice readvertise-choice {
            leaf readvertise {
              type empty;
            }
            leaf no-readvertise {
              type empty;
            }
          }
          choice resolve-choice {
            leaf resolve {
              type empty;
            }
            leaf no-resolve {
              type empty;
            }
          }
          choice longest-match-choice {
            leaf longest-match {
              type empty;
            }
            leaf no-longest-match {
              type empty;
            }
          }
          choice passive_flag {
            case case_1 {
              leaf active {
                type empty;
              }
            }
            case case_2 {
              leaf passive {
                type empty;
              }
            }
          }
          container metric {
            presence "enable metric";
            uses rib-static-metric-type;
          }
          container metric2 {
            presence "enable metric2";
            uses rib-static-metric-type;
          }
          container metric3 {
            presence "enable metric3";
            uses rib-static-metric-type;
          }
          container metric4 {
            presence "enable metric4";
            uses rib-static-metric-type;
          }
          container tag {
            presence "enable tag";
            uses rib-static-metric-type;
          }
          container tag2 {
            presence "enable tag2";
            uses rib-static-metric-type;
          }
          container preference {
            presence "enable preference";
            uses rib-static-metric-type;
          }
          container preference2 {
            presence "enable preference2";
            uses rib-static-metric-type;
          }
          container color {
            presence "enable color";
            uses rib-static-metric-type;
          }
          container color2 {
            presence "enable color2";
            uses rib-static-metric-type;
          }
          leaf-list community {
            ordered-by user;
            type community;
          }
          container as-path {
            uses apply-advanced;
            leaf path {
              type string;
            }
            leaf origin {
              type string;
            }
            leaf atomic-aggregate {
              type empty;
            }
            container aggregator {
              presence "enable aggregator";
              leaf as-number {
                type string;
              }
              leaf address {
                type ipv4addr;
              }
            }
            leaf as-number {
              type string;
            }
            leaf address {
              type ipv4addr;
            }
          }
          list lsp-next-hop {
            key "name";
            ordered-by user;
            uses lsp-nh-obj;
          }
          list static-lsp-next-hop {
            key "name";
            ordered-by user;
            uses lsp-nh-obj;
          }
          list p2mp-lsp-next-hop {
            key "name";
            ordered-by user;
            uses lsp-nh-obj;
          }
          container spring-te-lsp-next-hop {
            uses springte-lsp-nh-obj;
          }
          container p2mp-ldp-next-hop {
            presence "";
            uses p2mp-ldp-lsp-nh-obj;
          }
        }
        list route-target-filter {
          key "name";
          ordered-by user;
          leaf name {
            type key-attribute-string-type;
          }
          uses apply-advanced;
          leaf-list neighbor {
            ordered-by user;
            type ipaddr-scoped;
          }
          leaf-list group {
            ordered-by user;
            type string;
          }
          leaf local {
            type empty;
          }
        }
      }
      list martians {
        key "address key2 key2-arg";
        ordered-by user;
        uses martian-type;
      }
      container aggregate {
        uses rib-aggregate-type;
      }
      container generate {
        uses rib-aggregate-type;
      }
      choice maximum-paths-type {
        case case_1 {
          container maximum-routes {
            presence "";
            status deprecated;
            leaf limit {
              type string;
            }
            choice log_type {
              case case_1 {
                leaf threshold {
                  type string;
                }
              }
              case case_2 {
                leaf log-only {
                  type empty;
                }
              }
            }
            leaf log-interval {
              units "seconds";
              type string;
            }
          }
        }
        case case_2 {
          container maximum-paths {
            presence "";
            leaf limit {
              type string;
            }
            choice log_type {
              case case_1 {
                leaf threshold {
                  type string;
                }
              }
              case case_2 {
                leaf log-only {
                  type empty;
                }
              }
            }
            leaf log-interval {
              units "seconds";
              type string;
            }
          }
        }
      }
      container maximum-prefixes {
        presence "";
        leaf limit {
          type string;
        }
        choice log_type {
          case case_1 {
            leaf threshold {
              type string;
            }
          }
          case case_2 {
            leaf log-only {
              type empty;
            }
          }
        }
        leaf log-interval {
          units "seconds";
          type string;
        }
      }
      container multipath {
        presence "enable multipath";
        uses apply-advanced;
        container vpn-unequal-cost {
          presence "enable vpn-unequal-cost";
          leaf equal-external-internal {
            type empty;
          }
        }
        leaf as-path-compare {
          type empty;
        }
        leaf preserve-nexthop-hierarchy {
          type empty;
        }
      }
      container policy-multipath {
        presence "";
        uses apply-advanced;
        leaf-list policy {
          ordered-by user;
          type policy-algebra;
        }
        container traceoptions {
          uses apply-advanced;
          container file {
            presence "";
            leaf filename {
              type string;
            }
            leaf replace {
              status deprecated;
              type empty;
            }
            leaf size {
              type string;
            }
            leaf files {
              type string;
            }
            leaf no-stamp {
              status deprecated;
              type empty;
            }
            choice world-readable-choice {
              leaf world-readable {
                type empty;
              }
              leaf no-world-readable {
                type empty;
              }
            }
          }
          list flag {
            key "name";
            ordered-by user;
            leaf name {
              type string;
            }
            leaf send {
              type empty;
            }
            leaf receive {
              type empty;
            }
            leaf detail {
              type empty;
            }
            leaf disable {
              type empty;
            }
          }
        }
        leaf preserve-nexthop-hierarchy {
          type empty;
        }
      }
      container protect {
        leaf core {
          type empty;
        }
      }
      container access {
        uses apply-advanced;
        list route {
          key "name";
          ordered-by user;
          leaf name {
            type ipprefix;
          }
          uses apply-advanced;
          leaf-list next-hop {
            ordered-by user;
            type string;
          }
          list qualified-next-hop {
            key "name";
            ordered-by user;
            uses qualified-nh-obj;
          }
          leaf metric {
            type string;
          }
          leaf preference {
            type string;
          }
          leaf tag {
            type string;
          }
          leaf tag2 {
            type string;
          }
        }
      }
      container access-internal {
        uses apply-advanced;
        list route {
          key "name";
          ordered-by user;
          leaf name {
            type ipprefix;
          }
          uses apply-advanced;
          leaf-list next-hop {
            ordered-by user;
            type string;
          }
          list qualified-next-hop {
            key "name";
            ordered-by user;
            uses qualified-nh-obj;
          }
        }
      }
      container bgp-static {
        uses apply-advanced;
        list route {
          key "name";
          ordered-by user;
          leaf name {
            type ipprefix;
          }
          uses apply-advanced;
          container metric {
            presence "enable metric";
            uses rib-static-metric-type;
          }
          container metric2 {
            presence "enable metric2";
            uses rib-static-metric-type;
          }
          container metric3 {
            presence "enable metric3";
            uses rib-static-metric-type;
          }
          container metric4 {
            presence "enable metric4";
            uses rib-static-metric-type;
          }
          container tag {
            presence "enable tag";
            uses rib-static-metric-type;
          }
          container tag2 {
            presence "enable tag2";
            uses rib-static-metric-type;
          }
          container preference {
            presence "enable preference";
            uses rib-static-metric-type;
          }
          container preference2 {
            presence "enable preference2";
            uses rib-static-metric-type;
          }
          container color {
            presence "enable color";
            uses rib-static-metric-type;
          }
          container color2 {
            presence "enable color2";
            uses rib-static-metric-type;
          }
          leaf-list community {
            ordered-by user;
            type community;
          }
          container as-path {
            uses apply-advanced;
            leaf path {
              type string;
            }
            leaf origin {
              type string;
            }
            leaf atomic-aggregate {
              type empty;
            }
            container aggregator {
              presence "enable aggregator";
              leaf as-number {
                type string;
              }
              leaf address {
                type ipv4addr;
              }
            }
            leaf as-number {
              type string;
            }
            leaf address {
              type ipv4addr;
            }
          }
        }
      }
      container flow {
        uses apply-advanced;
        container validation {
          presence "";
          uses flow-validation;
        }
        list route {
          key "name";
          ordered-by user;
          uses flow-route-inet6;
        }
        list security-group {
          key "name";
          ordered-by user;
          leaf name {
            type string;
          }
          uses apply-advanced;
          list rule {
            key "name";
            ordered-by user;
            uses flow-rule-inet6;
          }
        }
        container interface-group {
          presence "";
          uses flow-interface-group;
        }
        leaf discard-action-for-unresolved-redir-addr {
          type empty;
        }
        choice per-route-accounting-choice {
          leaf per-route-accounting {
            type empty;
          }
          leaf no-per-route-accounting {
            type empty;
          }
        }
      }
      container label {
        presence "enable label";
        uses apply-advanced;
        leaf-list allocation {
          ordered-by user;
          type policy-algebra;
        }
        leaf-list substitution {
          ordered-by user;
          type policy-algebra;
        }
      }
    }
    container label {
      presence "enable label";
      uses apply-advanced;
      leaf-list allocation {
        ordered-by user;
        type policy-algebra;
      }
      leaf-list substitution {
        ordered-by user;
        type policy-algebra;
      }
    }
    container options {
      uses apply-advanced;
      leaf no-send {
        status deprecated;
        type empty;
      }
      leaf no-resolve {
        status deprecated;
        type empty;
      }
      container syslog {
        uses apply-advanced;
        container level {
          leaf emergency {
            type empty;
          }
          leaf alert {
            type empty;
          }
          leaf critical {
            type empty;
          }
          leaf error {
            type empty;
          }
          leaf warning {
            type empty;
          }
          leaf notice {
            type empty;
          }
          leaf info {
            type empty;
          }
          leaf debug {
            type empty;
          }
        }
        leaf upto {
          type string;
        }
      }
      leaf mark {
        units "seconds";
        type string;
      }
    }
    container resolution {
      presence "enable resolution";
      uses apply-advanced;
      leaf-list tracefilter {
        ordered-by user;
        type policy-algebra;
      }
      container traceoptions {
        uses apply-advanced;
        container file {
          presence "";
          leaf filename {
            type string;
          }
          leaf replace {
            status deprecated;
            type empty;
          }
          leaf size {
            type string;
          }
          leaf files {
            type string;
          }
          leaf no-stamp {
            status deprecated;
            type empty;
          }
          choice world-readable-choice {
            leaf world-readable {
              type empty;
            }
            leaf no-world-readable {
              type empty;
            }
          }
        }
        list flag {
          key "name";
          ordered-by user;
          leaf name {
            type string;
          }
          leaf send {
            type empty;
          }
          leaf receive {
            type empty;
          }
          leaf detail {
            type empty;
          }
          leaf disable {
            type empty;
          }
        }
      }
      choice preserve-nexthop-hierarchy-choice {
        leaf preserve-nexthop-hierarchy {
          type empty;
        }
        leaf no-preserve-nexthop-hierarchy {
          type empty;
        }
      }
      list rib {
        key "name";
        ordered-by user;
        leaf name {
          type string;
        }
        uses apply-advanced;
        leaf-list resolution-family {
          ordered-by user;
          type string;
        }
        leaf-list resolution-ribs {
          ordered-by user;
          type string;
        }
        leaf-list inet-resolution-ribs {
          ordered-by user;
          type string;
        }
        leaf-list inet6-resolution-ribs {
          ordered-by user;
          type string;
        }
        leaf-list iso-resolution-ribs {
          ordered-by user;
          type string;
        }
        leaf-list import {
          ordered-by user;
          type policy-algebra;
        }
        leaf-list inet-import {
          ordered-by user;
          type policy-algebra;
        }
        leaf-list inet6-import {
          ordered-by user;
          type policy-algebra;
        }
        leaf-list iso-import {
          ordered-by user;
          type policy-algebra;
        }
        leaf-list inetcolor-import {
          ordered-by user;
          type policy-algebra;
        }
        leaf-list inet6color-import {
          ordered-by user;
          type policy-algebra;
        }
      }
      choice prefer-recursive-primary-path-choice {
        leaf prefer-recursive-primary-path {
          type empty;
        }
        leaf no-prefer-recursive-primary-path {
          type empty;
        }
      }
      leaf disable-auto-resolve-on-scheme-changes {
        type empty;
      }
      list scheme {
        key "name";
        ordered-by user;
        leaf name {
          type string;
        }
        uses apply-advanced;
        leaf-list resolution-ribs {
          ordered-by user;
          type string;
        }
        leaf mapping-community {
          type community;
        }
      }
    }
    container interface-routes {
      uses apply-advanced;
      container rib-group {
        uses rib-group-type;
      }
      list family {
        key "name";
        ordered-by user;
        leaf name {
          type string;
        }
        uses apply-advanced;
        leaf-list import {
          ordered-by user;
          type policy-algebra;
        }
        container export {
          uses apply-advanced;
          leaf point-to-point {
            type empty;
          }
          leaf lan {
            type empty;
          }
        }
      }
    }
    leaf loopback-strict-disable {
      type empty;
    }
    container traceoptions {
      uses apply-advanced;
      container file {
        presence "";
        leaf filename {
          type string;
        }
        leaf replace {
          status deprecated;
          type empty;
        }
        leaf size {
          type string;
        }
        leaf files {
          type string;
        }
        leaf no-stamp {
          status deprecated;
          type empty;
        }
        choice world-readable-choice {
          leaf world-readable {
            type empty;
          }
          leaf no-world-readable {
            type empty;
          }
        }
      }
      list flag {
        key "name";
        ordered-by user;
        leaf name {
          type string;
        }
        leaf disable {
          type empty;
        }
      }
    }
    container topologies {
      uses apply-advanced;
      list family {
        key "name";
        ordered-by user;
        leaf name {
          type string;
        }
        uses apply-advanced;
        list topology {
          key "name";
          ordered-by user;
          leaf name {
            type string;
          }
          uses apply-advanced;
          leaf table-id {
            type string;
          }
        }
      }
    }
    leaf router-id {
      type ipv4addr;
    }
    leaf route-distinguisher-id-use-router-id {
      type empty;
    }
    container autonomous-system {
      presence "";
      uses apply-advanced;
      leaf as-number {
        type string;
      }
      leaf loops {
        type string;
      }
      leaf asdot-notation {
        type empty;
      }
      container independent-domain {
        presence "enable independent-domain";
        uses apply-advanced;
        leaf no-attrset {
          type empty;
        }
      }
    }
    container confederation {
      presence "";
      leaf confederation-as {
        type string;
      }
      leaf-list members {
        ordered-by user;
        type string;
      }
    }
    leaf ipv6-router-id {
      type string;
    }
    container graceful-restart {
      presence "enable graceful-restart";
      uses apply-advanced;
      choice enable-disable {
        case case_1 {
          leaf disable {
            type empty;
          }
        }
      }
      leaf restart-duration {
        type string;
      }
    }
    container flow {
      uses apply-advanced;
      leaf firewall-install-disable {
        type empty;
      }
      choice per-route-accounting-choice {
        leaf per-route-accounting {
          type empty;
        }
        leaf no-per-route-accounting {
          type empty;
        }
      }
      container validation {
        uses flow-validation;
      }
      container interface-group {
        presence "";
        uses flow-interface-group;
      }
      list route {
        key "name";
        ordered-by user;
        uses flow-route-inet;
      }
      leaf term-order {
        type string;
      }
      leaf discard-action-for-unresolved-redir-addr {
        type empty;
      }
      list security-group {
        key "name";
        ordered-by user;
        leaf name {
          type string;
        }
        uses apply-advanced;
        list rule {
          key "name";
          ordered-by user;
          uses flow-rule-inet;
        }
      }
    }
    leaf no-soft-core {
      type empty;
    }
    leaf med-igp-update-interval {
      type string;
    }
    container bmp {
      presence "enable bmp";
      uses apply-advanced;
      leaf authentication-key {
        type unreadable;
      }
      leaf authentication-algorithm {
        type string;
      }
      leaf tcpao-auth-mismatch {
        type string;
      }
      leaf authentication-key-chain {
        type string;
      }
      container hold-down {
        presence "enable hold-down";
        leaf hold-down-time {
          units "seconds";
          type string;
        }
        leaf flaps {
          type string;
        }
        leaf period {
          units "seconds";
          type string;
        }
      }
      leaf initiation-message {
        type string;
      }
      leaf local-address {
        type ipaddr;
      }
      leaf local-port {
        type string;
      }
      leaf connection-mode {
        type string;
      }
      leaf priority {
        type string;
      }
      leaf monitor {
        type string;
      }
      container route-monitoring {
        uses apply-advanced;
        leaf none {
          type empty;
        }
        leaf loc-rib {
          type empty;
        }
        container pre-policy {
          presence "enable pre-policy";
          leaf exclude-non-feasible {
            type empty;
          }
        }
        container post-policy {
          presence "enable post-policy";
          leaf exclude-non-eligible {
            type empty;
          }
        }
        container rib-out {
          presence "enable rib-out";
          leaf pre-policy {
            type empty;
          }
          leaf post-policy {
            type empty;
          }
        }
      }
      leaf max-loc-rib-buffer-count {
        type string;
      }
      leaf station-address {
        type ipaddr;
      }
      leaf routing-instance {
        type string;
      }
      leaf station-port {
        type string;
      }
      leaf statistics-timeout {
        units "seconds";
        type string;
      }
      container traceoptions {
        uses apply-advanced;
        container file {
          presence "";
          leaf filename {
            type string;
          }
          leaf replace {
            status deprecated;
            type empty;
          }
          leaf size {
            type string;
          }
          leaf files {
            type string;
          }
          leaf no-stamp {
            status deprecated;
            type empty;
          }
          choice world-readable-choice {
            leaf world-readable {
              type empty;
            }
            leaf no-world-readable {
              type empty;
            }
          }
        }
        list flag {
          key "name";
          ordered-by user;
          leaf name {
            type string;
          }
          leaf send {
            type empty;
          }
          leaf receive {
            type empty;
          }
          leaf detail {
            type empty;
          }
          leaf disable {
            type empty;
          }
        }
      }
      list station {
        key "name";
        leaf name {
          type string;
        }
        uses apply-advanced;
        leaf authentication-key {
          type string;
        }
        leaf authentication-algorithm {
          type string;
        }
        leaf tcpao-auth-mismatch {
          type string;
        }
        leaf authentication-key-chain {
          type string;
        }
        container hold-down {
          presence "enable hold-down";
          leaf hold-down-time {
            units "seconds";
            type string;
          }
          leaf flaps {
            type string;
          }
          leaf period {
            units "seconds";
            type string;
          }
        }
        leaf initiation-message {
          type string;
        }
        leaf local-address {
          type ipaddr;
        }
        leaf local-port {
          type string;
        }
        leaf connection-mode {
          type string;
        }
        leaf priority {
          type string;
        }
        leaf monitor {
          type string;
        }
        container route-monitoring {
          uses apply-advanced;
          leaf none {
            type empty;
          }
          leaf loc-rib {
            type empty;
          }
          container pre-policy {
            presence "enable pre-policy";
            leaf exclude-non-feasible {
              type empty;
            }
          }
          container post-policy {
            presence "enable post-policy";
            leaf exclude-non-eligible {
              type empty;
            }
          }
          container rib-out {
            presence "enable rib-out";
            leaf pre-policy {
              type empty;
            }
            leaf post-policy {
              type empty;
            }
          }
        }
        leaf max-loc-rib-buffer-count {
          type string;
        }
        leaf station-address {
          type ipaddr;
        }
        leaf routing-instance {
          type string;
        }
        leaf station-port {
          type string;
        }
        leaf statistics-timeout {
          units "seconds";
          type string;
        }
        container traceoptions {
          uses apply-advanced;
          container file {
            presence "";
            leaf filename {
              type string;
            }
            leaf replace {
              status deprecated;
              type empty;
            }
            leaf size {
              type string;
            }
            leaf files {
              type string;
            }
            leaf no-stamp {
              status deprecated;
              type empty;
            }
            choice world-readable-choice {
              leaf world-readable {
                type empty;
              }
              leaf no-world-readable {
                type empty;
              }
            }
          }
          list flag {
            key "name";
            ordered-by user;
            leaf name {
              type string;
            }
            leaf send {
              type empty;
            }
            leaf receive {
              type empty;
            }
            leaf detail {
              type empty;
            }
            leaf disable {
              type empty;
            }
          }
        }
      }
      leaf memory-limit {
        type uint32;
      }
    }
    leaf bgp-orf-cisco-mode {
      type empty;
    }
    leaf highwatermark-log-interval {
      units "seconds";
      type string;
    }
    leaf time-averaged-watermark-interval {
      units "days";
      type string;
    }
    container ppm {
      presence "enable ppm";
      uses apply-advanced;
      container undocumented {
        uses undocumented-traceoptions;
      }
      leaf delegate-processing {
        status deprecated;
        type empty;
      }
      leaf no-delegate-processing {
        type empty;
      }
      leaf inline-processing-enable {
        type empty;
      }
      leaf inline-ae-processing-enable {
        type empty;
      }
      leaf redistribution-timer {
        type string;
      }
    }
    leaf no-bfd-triggered-local-repair {
      type empty;
    }
    leaf enable-sensors {
      type empty;
    }
    leaf maximum-ecmp {
      type string;
    }
    container static {
      uses apply-advanced;
      leaf rib-group {
        type string;
      }
      container defaults {
        uses apply-advanced;
        choice retain-choice {
          leaf retain {
            type empty;
          }
          leaf no-retain {
            type empty;
          }
        }
        choice install-choice {
          leaf install {
            type empty;
          }
          leaf no-install {
            type empty;
          }
        }
        choice readvertise-choice {
          leaf readvertise {
            type empty;
          }
          leaf no-readvertise {
            type empty;
          }
        }
        choice resolve-choice {
          leaf resolve {
            type empty;
          }
          leaf no-resolve {
            type empty;
          }
        }
        choice longest-match-choice {
          leaf longest-match {
            type empty;
          }
          leaf no-longest-match {
            type empty;
          }
        }
        choice passive_flag {
          case case_1 {
            leaf active {
              type empty;
            }
          }
          case case_2 {
            leaf passive {
              type empty;
            }
          }
        }
        container metric {
          presence "enable metric";
          uses rib-static-metric-type;
        }
        container metric2 {
          presence "enable metric2";
          uses rib-static-metric-type;
        }
        container metric3 {
          presence "enable metric3";
          uses rib-static-metric-type;
        }
        container metric4 {
          presence "enable metric4";
          uses rib-static-metric-type;
        }
        container tag {
          presence "enable tag";
          uses rib-static-metric-type;
        }
        container tag2 {
          presence "enable tag2";
          uses rib-static-metric-type;
        }
        container preference {
          presence "enable preference";
          uses rib-static-metric-type;
        }
        container preference2 {
          presence "enable preference2";
          uses rib-static-metric-type;
        }
        container color {
          presence "enable color";
          uses rib-static-metric-type;
        }
        container color2 {
          presence "enable color2";
          uses rib-static-metric-type;
        }
        leaf-list community {
          ordered-by user;
          type community;
        }
        container as-path {
          uses apply-advanced;
          leaf path {
            type string;
          }
          leaf origin {
            type string;
          }
          leaf atomic-aggregate {
            type empty;
          }
          container aggregator {
            presence "enable aggregator";
            leaf as-number {
              type string;
            }
            leaf address {
              type ipv4addr;
            }
          }
          leaf as-number {
            type string;
          }
          leaf address {
            type ipv4addr;
          }
        }
      }
      list route {
        key "name";
        ordered-by user;
        leaf name {
          type ipprefix;
        }
        uses apply-advanced;
        choice next_hop {
          case case_1 {
            leaf-list next-hop {
              ordered-by user;
              type string;
            }
          }
          case case_2 {
            leaf reject {
              type empty;
            }
          }
          case case_3 {
            leaf discard {
              type empty;
            }
          }
          case case_4 {
            leaf receive {
              type empty;
            }
          }
          case case_5 {
            leaf next-table {
              type string;
            }
          }
        }
        leaf description {
          type string;
        }
        list qualified-next-hop {
          key "name";
          ordered-by user;
          uses qualified-nh-obj;
        }
        leaf backup-pe-group {
          type string;
        }
        container bfd-liveness-detection {
          uses apply-advanced;
          leaf version {
            type string;
          }
          leaf minimum-interval {
            units "milliseconds";
            type string;
          }
          leaf minimum-transmit-interval {
            status deprecated;
            units "milliseconds";
            type string;
          }
          leaf minimum-receive-interval {
            units "milliseconds";
            type string;
          }
          leaf multiplier {
            type string;
          }
          choice adaptation-choice {
            case case_1 {
              leaf no-adaptation {
                type empty;
              }
            }
          }
          container transmit-interval {
            uses apply-advanced;
            leaf minimum-interval {
              units "milliseconds";
              type string;
            }
            leaf threshold {
              units "milliseconds";
              type string;
            }
          }
          container detection-time {
            uses apply-advanced;
            leaf threshold {
              units "milliseconds";
              type string;
            }
          }
          container authentication {
            uses apply-advanced;
            leaf key-chain {
              type string;
            }
            leaf algorithm {
              type string;
            }
            leaf loose-check {
              type empty;
            }
          }
          leaf neighbor {
            type ipaddr;
          }
          leaf local-address {
            type ipaddr;
          }
          leaf holddown-interval {
            units "milliseconds";
            type string;
          }
          leaf minimum-receive-ttl {
            type string;
          }
        }
        choice retain-choice {
          leaf retain {
            type empty;
          }
          leaf no-retain {
            type empty;
          }
        }
        choice install-choice {
          leaf install {
            type empty;
          }
          leaf no-install {
            type empty;
          }
        }
        choice readvertise-choice {
          leaf readvertise {
            type empty;
          }
          leaf no-readvertise {
            type empty;
          }
        }
        choice resolve-choice {
          leaf resolve {
            type empty;
          }
          leaf no-resolve {
            type empty;
          }
        }
        choice longest-match-choice {
          leaf longest-match {
            type empty;
          }
          leaf no-longest-match {
            type empty;
          }
        }
        choice passive_flag {
          case case_1 {
            leaf active {
              type empty;
            }
          }
          case case_2 {
            leaf passive {
              type empty;
            }
          }
        }
        container metric {
          presence "enable metric";
          uses rib-static-metric-type;
        }
        container metric2 {
          presence "enable metric2";
          uses rib-static-metric-type;
        }
        container metric3 {
          presence "enable metric3";
          uses rib-static-metric-type;
        }
        container metric4 {
          presence "enable metric4";
          uses rib-static-metric-type;
        }
        container tag {
          presence "enable tag";
          uses rib-static-metric-type;
        }
        container tag2 {
          presence "enable tag2";
          uses rib-static-metric-type;
        }
        container preference {
          presence "enable preference";
          uses rib-static-metric-type;
        }
        container preference2 {
          presence "enable preference2";
          uses rib-static-metric-type;
        }
        container color {
          presence "enable color";
          uses rib-static-metric-type;
        }
        container color2 {
          presence "enable color2";
          uses rib-static-metric-type;
        }
        leaf-list community {
          ordered-by user;
          type community;
        }
        container as-path {
          uses apply-advanced;
          leaf path {
            type string;
          }
          leaf origin {
            type string;
          }
          leaf atomic-aggregate {
            type empty;
          }
          container aggregator {
            presence "enable aggregator";
            leaf as-number {
              type string;
            }
            leaf address {
              type ipv4addr;
            }
          }
          leaf as-number {
            type string;
          }
          leaf address {
            type ipv4addr;
          }
        }
        list lsp-next-hop {
          key "name";
          ordered-by user;
          uses lsp-nh-obj;
        }
        list p2mp-lsp-next-hop {
          key "name";
          ordered-by user;
          uses lsp-nh-obj;
        }
        container spring-te-lsp-next-hop {
          uses springte-lsp-nh-obj;
        }
        container p2mp-ldp-next-hop {
          presence "";
          uses p2mp-ldp-lsp-nh-obj;
        }
        list static-lsp-next-hop {
          key "name";
          ordered-by user;
          uses lsp-nh-obj;
        }
      }
      container static-route {
        leaf bfd-admin-down {
          type string;
        }
      }
      list iso-route {
        key "name";
        ordered-by user;
        leaf name {
          type isoprefix;
        }
        uses apply-advanced;
        choice next_hop {
          case case_1 {
            leaf-list next-hop {
              ordered-by user;
              type string;
            }
          }
          case case_2 {
            leaf reject {
              type empty;
            }
          }
          case case_3 {
            leaf discard {
              type empty;
            }
          }
          case case_4 {
            leaf receive {
              type empty;
            }
          }
          case case_5 {
            leaf next-table {
              type string;
            }
          }
        }
        list qualified-next-hop {
          key "name";
          ordered-by user;
          uses qualified-nh-obj;
        }
        leaf backup-pe-group {
          type string;
        }
        container bfd-liveness-detection {
          uses apply-advanced;
          leaf version {
            type string;
          }
          leaf minimum-interval {
            units "milliseconds";
            type string;
          }
          leaf minimum-transmit-interval {
            status deprecated;
            units "milliseconds";
            type string;
          }
          leaf minimum-receive-interval {
            units "milliseconds";
            type string;
          }
          leaf multiplier {
            type string;
          }
          choice adaptation-choice {
            case case_1 {
              leaf no-adaptation {
                type empty;
              }
            }
          }
          container transmit-interval {
            uses apply-advanced;
            leaf minimum-interval {
              units "milliseconds";
              type string;
            }
            leaf threshold {
              units "milliseconds";
              type string;
            }
          }
          container detection-time {
            uses apply-advanced;
            leaf threshold {
              units "milliseconds";
              type string;
            }
          }
          container authentication {
            uses apply-advanced;
            leaf key-chain {
              type string;
            }
            leaf algorithm {
              type string;
            }
            leaf loose-check {
              type empty;
            }
          }
          leaf neighbor {
            type ipaddr;
          }
          leaf local-address {
            type ipaddr;
          }
          leaf holddown-interval {
            units "milliseconds";
            type string;
          }
          leaf minimum-receive-ttl {
            type string;
          }
        }
        choice retain-choice {
          leaf retain {
            type empty;
          }
          leaf no-retain {
            type empty;
          }
        }
        choice install-choice {
          leaf install {
            type empty;
          }
          leaf no-install {
            type empty;
          }
        }
        choice readvertise-choice {
          leaf readvertise {
            type empty;
          }
          leaf no-readvertise {
            type empty;
          }
        }
        choice resolve-choice {
          leaf resolve {
            type empty;
          }
          leaf no-resolve {
            type empty;
          }
        }
        choice longest-match-choice {
          leaf longest-match {
            type empty;
          }
          leaf no-longest-match {
            type empty;
          }
        }
        choice passive_flag {
          case case_1 {
            leaf active {
              type empty;
            }
          }
          case case_2 {
            leaf passive {
              type empty;
            }
          }
        }
        container metric {
          presence "enable metric";
          uses rib-static-metric-type;
        }
        container metric2 {
          presence "enable metric2";
          uses rib-static-metric-type;
        }
        container metric3 {
          presence "enable metric3";
          uses rib-static-metric-type;
        }
        container metric4 {
          presence "enable metric4";
          uses rib-static-metric-type;
        }
        container tag {
          presence "enable tag";
          uses rib-static-metric-type;
        }
        container tag2 {
          presence "enable tag2";
          uses rib-static-metric-type;
        }
        container preference {
          presence "enable preference";
          uses rib-static-metric-type;
        }
        container preference2 {
          presence "enable preference2";
          uses rib-static-metric-type;
        }
        container color {
          presence "enable color";
          uses rib-static-metric-type;
        }
        container color2 {
          presence "enable color2";
          uses rib-static-metric-type;
        }
        leaf-list community {
          ordered-by user;
          type community;
        }
        container as-path {
          uses apply-advanced;
          leaf path {
            type string;
          }
          leaf origin {
            type string;
          }
          leaf atomic-aggregate {
            type empty;
          }
          container aggregator {
            presence "enable aggregator";
            leaf as-number {
              type string;
            }
            leaf address {
              type ipv4addr;
            }
          }
          leaf as-number {
            type string;
          }
          leaf address {
            type ipv4addr;
          }
        }
        list lsp-next-hop {
          key "name";
          ordered-by user;
          uses lsp-nh-obj;
        }
        list static-lsp-next-hop {
          key "name";
          ordered-by user;
          uses lsp-nh-obj;
        }
        list p2mp-lsp-next-hop {
          key "name";
          ordered-by user;
          uses lsp-nh-obj;
        }
        container spring-te-lsp-next-hop {
          uses springte-lsp-nh-obj;
        }
        container p2mp-ldp-next-hop {
          presence "";
          uses p2mp-ldp-lsp-nh-obj;
        }
      }
      list route-target-filter {
        key "name";
        ordered-by user;
        leaf name {
          type string;
        }
        uses apply-advanced;
        leaf-list neighbor {
          ordered-by user;
          type ipaddr-scoped;
        }
        leaf-list group {
          ordered-by user;
          type string;
        }
        leaf local {
          type empty;
        }
      }
    }
    list martians {
      key "address key2 key2-arg";
      ordered-by user;
      uses martian-type;
    }
    container aggregate {
      uses rib-aggregate-type;
    }
    container generate {
      uses rib-aggregate-type;
    }
    choice maximum-paths-type {
      case case_1 {
        container maximum-routes {
          status deprecated;
          leaf limit {
            type string;
          }
          choice log_type {
            case case_1 {
              leaf threshold {
                type string;
              }
            }
            case case_2 {
              leaf log-only {
                type empty;
              }
            }
          }
          leaf log-interval {
            units "seconds";
            type string;
          }
        }
      }
      case case_2 {
        container maximum-paths {
          presence "";
          leaf limit {
            type string;
          }
          choice log_type {
            case case_1 {
              leaf threshold {
                type string;
              }
            }
            case case_2 {
              leaf log-only {
                type empty;
              }
            }
          }
          leaf log-interval {
            units "seconds";
            type string;
          }
        }
      }
    }
    container maximum-prefixes {
      presence "";
      leaf limit {
        type string;
      }
      choice log_type {
        case case_1 {
          leaf threshold {
            type string;
          }
        }
        case case_2 {
          leaf log-only {
            type empty;
          }
        }
      }
      leaf log-interval {
        units "seconds";
        type string;
      }
    }
    container multipath {
      presence "enable multipath";
      uses apply-advanced;
      container vpn-unequal-cost {
        presence "enable vpn-unequal-cost";
        leaf equal-external-internal {
          type empty;
        }
      }
      leaf as-path-compare {
        type empty;
      }
      leaf preserve-nexthop-hierarchy {
        type empty;
      }
    }
    container policy-multipath {
      uses apply-advanced;
      leaf-list policy {
        ordered-by user;
        type policy-algebra;
      }
      container traceoptions {
        uses apply-advanced;
        container file {
          leaf filename {
            type string;
          }
          leaf replace {
            status deprecated;
            type empty;
          }
          leaf size {
            type string;
          }
          leaf files {
            type string;
          }
          leaf no-stamp {
            status deprecated;
            type empty;
          }
          choice world-readable-choice {
            leaf world-readable {
              type empty;
            }
            leaf no-world-readable {
              type empty;
            }
          }
        }
        list flag {
          key "name";
          ordered-by user;
          leaf name {
            type string;
          }
          leaf send {
            type empty;
          }
          leaf receive {
            type empty;
          }
          leaf detail {
            type empty;
          }
          leaf disable {
            type empty;
          }
        }
      }
      leaf preserve-nexthop-hierarchy {
        type empty;
      }
    }
    container protect {
      leaf core {
        type empty;
      }
    }
    container access {
      uses apply-advanced;
      list route {
        key "name";
        ordered-by user;
        leaf name {
          type ipprefix;
        }
        uses apply-advanced;
        leaf-list next-hop {
          ordered-by user;
          type string;
        }
        list qualified-next-hop {
          key "name";
          ordered-by user;
          uses qualified-nh-obj;
        }
        leaf metric {
          type string;
        }
        leaf preference {
          type string;
        }
        leaf tag {
          type string;
        }
        leaf tag2 {
          type string;
        }
      }
    }
    container access-internal {
      uses apply-advanced;
      list route {
        key "name";
        ordered-by user;
        leaf name {
          type ipprefix;
        }
        uses apply-advanced;
        leaf-list next-hop {
          ordered-by user;
          type string;
        }
        list qualified-next-hop {
          key "name";
          ordered-by user;
          uses qualified-nh-obj;
        }
      }
    }
    container bgp-static {
      uses apply-advanced;
      list route {
        key "name";
        ordered-by user;
        leaf name {
          type ipprefix;
        }
        uses apply-advanced;
        container metric {
          presence "enable metric";
          uses rib-static-metric-type;
        }
        container metric2 {
          presence "enable metric2";
          uses rib-static-metric-type;
        }
        container metric3 {
          presence "enable metric3";
          uses rib-static-metric-type;
        }
        container metric4 {
          presence "enable metric4";
          uses rib-static-metric-type;
        }
        container tag {
          presence "enable tag";
          uses rib-static-metric-type;
        }
        container tag2 {
          presence "enable tag2";
          uses rib-static-metric-type;
        }
        container preference {
          presence "enable preference";
          uses rib-static-metric-type;
        }
        container preference2 {
          presence "enable preference2";
          uses rib-static-metric-type;
        }
        container color {
          presence "enable color";
          uses rib-static-metric-type;
        }
        container color2 {
          presence "enable color2";
          uses rib-static-metric-type;
        }
        leaf-list community {
          ordered-by user;
          type community;
        }
        container as-path {
          uses apply-advanced;
          leaf path {
            type string;
          }
          leaf origin {
            type string;
          }
          leaf atomic-aggregate {
            type empty;
          }
          container aggregator {
            presence "enable aggregator";
          }
          leaf as-number {
            type string;
          }
          leaf address {
            type ipv4addr;
          }
        }
      }
    }
    list rib-groups {
      key "name";
      ordered-by user;
      uses rpd-rib-group-type;
    }
    leaf route-record {
      type empty;
    }
    container localized-fib {
      presence "enable localized-fib";
      uses apply-advanced;
      leaf-list fpc-slot {
        ordered-by user;
        type string;
      }
    }
    leaf-list instance-import {
      ordered-by user;
      type policy-algebra;
    }
    leaf-list instance-export {
      ordered-by user;
      type policy-algebra;
    }
    container auto-export {
      presence "enable auto-export";
      uses apply-advanced;
      choice enable-disable {
        case case_1 {
          leaf disable {
            type empty;
          }
        }
      }
      container traceoptions {
        uses apply-advanced;
        container file {
          presence "";
          leaf filename {
            type string;
          }
          leaf replace {
            status deprecated;
            type empty;
          }
          leaf size {
            type string;
          }
          leaf files {
            type string;
          }
          leaf no-stamp {
            status deprecated;
            type empty;
          }
          choice world-readable-choice {
            leaf world-readable {
              type empty;
            }
            leaf no-world-readable {
              type empty;
            }
          }
        }
        list flag {
          key "name";
          ordered-by user;
          leaf name {
            type string;
          }
          leaf send {
            type empty;
          }
          leaf receive {
            type empty;
          }
          leaf detail {
            type empty;
          }
          leaf disable {
            type empty;
          }
        }
      }
      container family {
        container inet {
          uses export-af-obj;
        }
        container inet6 {
          uses export-af-obj;
        }
        container iso {
          uses export-af-obj;
        }
      }
    }
    container transport-class {
      presence "enable transport-class";
      uses apply-advanced;
      leaf auto-create {
        type empty;
      }
      container fallback {
        uses apply-advanced;
        leaf none {
          type empty;
        }
      }
      list name {
        key "name";
        ordered-by user;
        leaf name {
          type string;
        }
        uses apply-advanced;
        leaf color {
          type string;
        }
        container fallback {
          uses apply-advanced;
          leaf none {
            type empty;
          }
        }
        container tunnel-egress {
          uses apply-advanced;
          list end-point {
            key "name";
            ordered-by user;
            leaf name {
              type ipaddr;
            }
            uses apply-advanced;
            leaf-list import {
              ordered-by user;
              type policy-algebra;
            }
          }
        }
      }
      container any-class {
        uses apply-advanced;
        leaf color {
          type string;
        }
        container fallback {
          uses apply-advanced;
          leaf none {
            type empty;
          }
        }
      }
      container best-effort {
        uses apply-advanced;
        leaf color {
          type string;
        }
        container fallback {
          uses apply-advanced;
          leaf none {
            type empty;
          }
        }
      }
    }
    container dynamic-tunnels {
      uses apply-advanced;
      list tunnel-attributes {
        key "name";
        ordered-by user;
        leaf name {
          type string;
        }
        uses apply-advanced;
        leaf dynamic-tunnel-source-prefix {
          type ipaddr;
        }
        leaf dynamic-tunnel-type {
          type string;
        }
        leaf dynamic-tunnel-mtu {
          type string;
        }
        leaf dynamic-tunnel-gre-key {
          type string;
        }
        leaf dynamic-tunnel-anchor-pfe {
          type string;
        }
        leaf dynamic-tunnel-anti-spoof {
          type string;
        }
        leaf dynamic-tunnel-reassembly {
          type string;
        }
      }
      list forwarding-rib {
        key "name";
        ordered-by user;
        leaf name {
          type string;
        }
        uses apply-advanced;
        leaf-list inet-import {
          ordered-by user;
          type policy-algebra;
        }
      }
      container statistics {
        uses apply-advanced;
        leaf interval {
          units "seconds";
          type string;
        }
      }
      container traceoptions {
        uses apply-advanced;
        container file {
          presence "";
          leaf filename {
            type string;
          }
          leaf replace {
            status deprecated;
            type empty;
          }
          leaf size {
            type string;
          }
          leaf files {
            type string;
          }
          leaf no-stamp {
            status deprecated;
            type empty;
          }
          choice world-readable-choice {
            leaf world-readable {
              type empty;
            }
            leaf no-world-readable {
              type empty;
            }
          }
        }
        list flag {
          key "name";
          ordered-by user;
          leaf name {
            type string;
          }
          leaf send {
            type empty;
          }
          leaf receive {
            type empty;
          }
          leaf detail {
            type empty;
          }
          leaf disable {
            type empty;
          }
        }
      }
      leaf udp {
        type string;
      }
      leaf v4ov6 {
        type string;
      }
      leaf ipip {
        type string;
      }
      leaf gre {
        type string;
      }
      container signal-tunnel-preference {
        presence "enable signal-tunnel-preference";
        uses apply-advanced;
        leaf gre {
          type string;
        }
        leaf udp {
          type string;
        }
        leaf ipip {
          type string;
        }
      }
      list dynamic-tunnel {
        key "name";
        ordered-by user;
        uses dynamic-tunnel-type;
      }
    }
    list interface {
      key "name";
      ordered-by user;
      leaf name {
        type string;
      }
      uses apply-advanced;
      leaf arp-prefix-limit {
        type string;
      }
      leaf supplementary-blackout-timer {
        type string;
      }
      choice protection-type {
        case case_1 {
          leaf link-protection {
            type empty;
          }
        }
      }
    }
    container host-fast-reroute {
      presence "enable host-fast-reroute";
      uses apply-advanced;
      leaf global-arp-prefix-limit {
        type string;
      }
      leaf global-supplementary-blackout-timer {
        type string;
      }
    }
    leaf warm-standby {
      type empty;
    }
    leaf nonstop-routing {
      type empty;
    }
    container nonstop-routing-options {
      presence "enable nonstop-routing-options";
      uses apply-advanced;
      leaf precision-timers-max-period {
        type string;
      }
    }
    leaf nsr-phantom-holdtime {
      type string;
    }
    list srlg {
      key "name";
      ordered-by user;
      leaf name {
        type key-attribute-string-type;
      }
      uses apply-advanced;
      leaf srlg-value {
        type string;
      }
      leaf srlg-cost {
        type string;
      }
    }
    container admin-groups-extended-range {
      uses apply-advanced;
      presence "true";
      leaf minimum {
        type string;
      }
      leaf maximum {
        type string;
      }
    }
    list admin-groups-extended {
      key "name";
      ordered-by user;
      leaf name {
        type key-attribute-string-type;
      }
      uses apply-advanced;
      leaf group-value {
        type string;
      }
    }
    leaf lsp-telemetry {
      type empty;
    }
    container l3vpn-composite-nexthop {
      presence "enable l3vpn-composite-nexthop";
      status deprecated;
      uses apply-advanced;
    }
    container source-routing {
      uses apply-advanced;
      leaf ip {
        type empty;
      }
      leaf ipv6 {
        type empty;
      }
    }
    container forwarding-table {
      uses forwarding-table-type;
    }
    container fate-sharing {
      uses apply-advanced;
      list group {
        key "name";
        ordered-by user;
        leaf name {
          type string;
        }
        uses apply-advanced;
        leaf cost {
          type string;
        }
        leaf use-for-post-convergence-lfa {
          type empty;
        }
        list from {
          key "name";
          uses fate-sharing-links;
        }
      }
    }
    container multicast {
      uses apply-advanced;
      container traceoptions {
        uses apply-advanced;
        container file {
          presence "";
          leaf filename {
            type string;
          }
          leaf replace {
            status deprecated;
            type empty;
          }
          leaf size {
            type string;
          }
          leaf files {
            type string;
          }
          leaf no-stamp {
            status deprecated;
            type empty;
          }
          choice world-readable-choice {
            leaf world-readable {
              type empty;
            }
            leaf no-world-readable {
              type empty;
            }
          }
        }
        list flag {
          key "name";
          ordered-by user;
          leaf name {
            type string;
          }
          leaf disable {
            type empty;
          }
        }
      }
      leaf rpf {
        status deprecated;
        type string;
      }
      list scope {
        key "name";
        ordered-by user;
        leaf name {
          type string;
        }
        uses apply-advanced;
        leaf prefix {
          type ipprefix;
        }
        leaf-list interface {
          ordered-by user;
          type string;
        }
      }
      leaf-list scope-policy {
        ordered-by user;
        type policy-algebra;
      }
      list flow-map {
        key "name";
        ordered-by user;
        leaf name {
          type string;
        }
        uses apply-advanced;
        leaf-list policy {
          ordered-by user;
          type policy-algebra;
        }
        container bandwidth {
          presence "enable bandwidth";
          leaf bandwidth-value {
            units "bps";
            type string;
          }
          leaf adaptive {
            type empty;
          }
        }
        leaf-list redundant-sources {
          ordered-by user;
          type ipaddr;
        }
        container forwarding-cache {
          presence "";
          uses apply-advanced;
          container timeout {
            choice timeout_choice {
              case case_1 {
                leaf timeout-value {
                  units "minutes";
                  type string;
                }
              }
              case case_2 {
                container never {
                  presence "enable never";
                  uses apply-advanced;
                  leaf non-discard-entry-only {
                    type empty;
                  }
                }
              }
            }
          }
        }
      }
      leaf-list resolve-filter {
        ordered-by user;
        status deprecated;
        type policy-algebra;
      }
      leaf-list ssm-groups {
        ordered-by user;
        type ipprefix;
      }
      leaf cont-stats-collection-interval {
        type string;
      }
      leaf asm-override-ssm {
        type empty;
      }
      leaf-list rpf-check-policy {
        ordered-by user;
        type policy-algebra;
      }
      container pim-to-igmp-proxy {
        presence "";
        uses apply-advanced;
        leaf-list upstream-interface {
          ordered-by user;
          type string;
        }
      }
      container pim-to-mld-proxy {
        presence "";
        uses apply-advanced;
        leaf-list upstream-interface {
          ordered-by user;
          type string;
        }
      }
      container forwarding-cache {
        uses apply-advanced;
        container undocumented {
          leaf linger {
            type empty;
          }
        }
        leaf allow-maximum {
          type empty;
        }
        list family {
          key "name";
          ordered-by user;
          leaf name {
            type string;
          }
          uses apply-advanced;
          container threshold {
            presence "enable threshold";
            uses apply-advanced;
            leaf suppress {
              type string;
            }
            leaf reuse {
              type string;
            }
            leaf mvpn-rpt-suppress {
              type string;
            }
            leaf mvpn-rpt-reuse {
              type string;
            }
            leaf log-warning {
              type string;
            }
          }
        }
        container threshold {
          uses apply-advanced;
          leaf suppress {
            type string;
          }
          leaf reuse {
            type string;
          }
          leaf mvpn-rpt-suppress {
            type string;
          }
          leaf mvpn-rpt-reuse {
            type string;
          }
          leaf log-warning {
            type string;
          }
        }
        leaf timeout {
          type string;
        }
      }
      list interface {
        key "name";
        ordered-by user;
        uses multicast-interface-options-type;
      }
      list ssm-map {
        key "name";
        ordered-by user;
        leaf name {
          type string;
        }
        uses apply-advanced;
        leaf-list policy {
          ordered-by user;
          type policy-algebra;
        }
        leaf-list source {
          ordered-by user;
          type ipaddr;
        }
      }
      container stream-protection {
        presence "enable stream-protection";
        uses apply-advanced;
        leaf mofrr-primary-path-selection-by-routing {
          type empty;
        }
        leaf mofrr-disjoint-upstream-only {
          type empty;
        }
        leaf mofrr-no-backup-join {
          type empty;
        }
        leaf mofrr-asm-starg {
          type empty;
        }
        leaf-list policy {
          ordered-by user;
          type policy-algebra;
        }
      }
      list backup-pe-group {
        key "name";
        ordered-by user;
        leaf name {
          type string;
        }
        uses apply-advanced;
        leaf-list backups {
          ordered-by user;
          type ipaddr;
        }
        leaf local-address {
          type ipaddr;
        }
      }
      leaf omit-wildcard-address {
        type empty;
      }
      leaf local-address {
        type ipv4addr;
      }
    }
    container programmable-rpd {
      uses programmable-rpd-type;
    }
    container validation {
      uses apply-advanced;
      container traceoptions {
        uses apply-advanced;
        container file {
          presence "";
          leaf filename {
            type string;
          }
          leaf replace {
            status deprecated;
            type empty;
          }
          leaf size {
            type string;
          }
          leaf files {
            type string;
          }
          leaf no-stamp {
            status deprecated;
            type empty;
          }
          choice world-readable-choice {
            leaf world-readable {
              type empty;
            }
            leaf no-world-readable {
              type empty;
            }
          }
        }
        list flag {
          key "name";
          ordered-by user;
          leaf name {
            type string;
          }
          leaf send {
            type empty;
          }
          leaf receive {
            type empty;
          }
          leaf detail {
            type empty;
          }
          leaf disable {
            type empty;
          }
        }
      }
      leaf-list notification-rib {
        ordered-by user;
        type string;
      }
      list group {
        key "name";
        leaf name {
          type string;
        }
        uses apply-advanced;
        leaf authentication-algorithm {
          type string;
        }
        leaf tcpao-auth-mismatch {
          type string;
        }
        leaf authentication-key-chain {
          type string;
        }
        leaf max-sessions {
          type string;
        }
        list session {
          key "name";
          leaf name {
            type ipaddr;
          }
          uses apply-advanced;
          container traceoptions {
            uses apply-advanced;
            container file {
              presence "";
              leaf filename {
                type string;
              }
              leaf replace {
                status deprecated;
                type empty;
              }
              leaf size {
                type string;
              }
              leaf files {
                type string;
              }
              leaf no-stamp {
                status deprecated;
                type empty;
              }
              choice world-readable-choice {
                leaf world-readable {
                  type empty;
                }
                leaf no-world-readable {
                  type empty;
                }
              }
            }
            list flag {
              key "name";
              ordered-by user;
              leaf name {
                type string;
              }
              leaf send {
                type empty;
              }
              leaf receive {
                type empty;
              }
              leaf detail {
                type empty;
              }
              leaf disable {
                type empty;
              }
            }
          }
          leaf authentication-algorithm {
            type string;
          }
          leaf tcpao-auth-mismatch {
            type string;
          }
          leaf authentication-key-chain {
            type string;
          }
          leaf database {
            type string;
          }
          leaf refresh-time {
            units "seconds";
            type string;
          }
          leaf hold-time {
            units "seconds";
            type string;
          }
          leaf record-lifetime {
            units "seconds";
            type string;
          }
          leaf preference {
            type string;
          }
          leaf port {
            type string;
          }
          leaf local-address {
            type ipaddr;
          }
        }
      }
      container static {
        uses apply-advanced;
        list record {
          key "name";
          leaf name {
            type ipprefix;
          }
          uses apply-advanced;
          list maximum-length {
            key "name";
            ordered-by user;
            leaf name {
              type string;
            }
            uses apply-advanced;
            list origin-autonomous-system {
              key "name";
              ordered-by user;
              leaf name {
                type string;
              }
              uses apply-advanced;
              leaf validation-state {
                type string;
              }
            }
          }
        }
      }
      list database {
        key "name";
        leaf name {
          type string;
        }
        uses apply-advanced;
        container static {
          uses apply-advanced;
          list record {
            key "name";
            leaf name {
              type ipprefix;
            }
            uses apply-advanced;
            list maximum-length {
              key "name";
              ordered-by user;
              leaf name {
                type string;
              }
              uses apply-advanced;
              list origin-autonomous-system {
                key "name";
                ordered-by user;
                leaf name {
                  type string;
                }
                uses apply-advanced;
                leaf validation-state {
                  type string;
                }
              }
            }
          }
        }
      }
    }
    container undocumented {
      container l3vpn-composite-nexthop {
        presence "enable l3vpn-composite-nexthop";
        uses apply-group;
        uses apply-macro;
      }
    }
  }

  grouping dynamic-tunnel-type {
    leaf name {
      type string;
    }
    uses apply-group;
    uses apply-macro;
    leaf source-address {
      type ipaddr;
    }
    choice choice-5 {
      list rsvp-te {
        key "name";
        ordered-by user;
        leaf name {
          type string;
        }
        uses apply-group;
        uses apply-macro;
        container label-switched-path-template {
          uses apply-group;
          uses apply-macro;
          choice choice-3 {
            leaf template-name {
              type string;
            }
            leaf default-template {
              type empty;
            }
          }
        }
        list destination-networks {
          key "name";
          ordered-by user;
          uses network-type;
        }
      }
      container spring-te {
        presence "";
        uses apply-group;
        uses apply-macro;
        list source-routing-path-template {
          key "name";
          ordered-by user;
          uses spring-te-template-map;
        }
        list destination-networks {
          key "name";
          ordered-by user;
          uses app-network-type;
        }
      }
      leaf gre {
        type empty;
      }
    }
    list destination-networks {
      key "name";
      ordered-by user;
      uses network-type;
    }
  }

  grouping app-network-type {
    leaf name {
      type ipprefix;
    }
    uses apply-group;
    uses apply-macro;
  }

  grouping export-af-obj {
    uses apply-group;
    uses apply-macro;
    choice choice-3 {
      leaf disable {
        type empty;
      }
    }
    container unicast {
      presence "enable unicast";
      uses export-subaf-obj;
    }
    container multicast {
      presence "enable multicast";
      uses export-subaf-obj;
    }
    container flow {
      presence "enable flow";
      uses export-subaf-obj;
    }
  }

  grouping export-subaf-obj {
    uses apply-group;
    uses apply-macro;
    choice choice-3 {
      leaf disable {
        type empty;
      }
    }
    leaf rib-group {
      type string;
    }
  }

  grouping fate-sharing-links {
    leaf name {
      type ipv4addr;
    }
    uses apply-group;
    uses apply-macro;
    leaf to {
      type ipv4addr;
    }
  }

  grouping flow-dep-traceoptions {
    uses apply-group;
    uses apply-macro;
    container file {
      presence "";
      uses trace-file-type;
    }
    list flag {
      key "name";
      ordered-by user;
      leaf name {
        type string;
      }
      leaf send {
        type empty;
      }
      leaf receive {
        type empty;
      }
      leaf detail {
        type empty;
      }
      leaf disable {
        type empty;
      }
      container filter {
        presence "";
        leaf match-on {
          type string;
        }
        leaf-list policy {
          type policy-algebra;
          ordered-by user;
        }
      }
    }
  }

  grouping flow-route-op {
    uses apply-group;
    uses apply-macro;
    leaf community {
      type string;
    }
    choice choice-5 {
      leaf accept {
        type empty;
      }
      leaf discard {
        type empty;
      }
      leaf rate-limit {
        type string;
      }
    }
    leaf routing-instance {
      type string;
    }
    leaf sample {
      type empty;
    }
    leaf mark {
      type string;
    }
    leaf next-term {
      type empty;
    }
    choice redirect_op_action {
      case case_1 {
        leaf-list redirect {
          ordered-by user;
          type ipaddr;
        }
      }
    }
  }

  grouping flow-route-qualifier-inet {
    uses apply-advanced;
    leaf-list protocol {
      ordered-by user;
      type string;
    }
    leaf-list port {
      ordered-by user;
      type string;
    }
    leaf-list destination-port {
      ordered-by user;
      type string;
    }
    leaf-list source-port {
      ordered-by user;
      type string;
    }
    leaf-list tcp-flags {
      ordered-by user;
      type string;
    }
    leaf-list packet-length {
      ordered-by user;
      type policy-algebra;
    }
    leaf-list dscp {
      ordered-by user;
      type policy-algebra;
    }
    leaf-list fragment {
      ordered-by user;
      type string;
    }
    leaf destination {
      type ipv4prefix;
    }
    leaf source {
      type ipv4prefix;
    }
    leaf-list icmp-code {
      ordered-by user;
      type string;
    }
    leaf-list icmp-type {
      ordered-by user;
      type string;
    }
  }

  grouping flow-route-qualifier-inet6 {
    uses apply-group;
    uses apply-macro;
    leaf-list protocol {
      ordered-by user;
      type string;
    }
    leaf-list port {
      ordered-by user;
      type string;
    }
    leaf-list destination-port {
      ordered-by user;
      type string;
    }
    leaf-list source-port {
      ordered-by user;
      type string;
    }
    leaf-list tcp-flags {
      ordered-by user;
      type string;
    }
    leaf-list packet-length {
      type policy-algebra;
      ordered-by user;
    }
    leaf-list dscp {
      type policy-algebra;
      ordered-by user;
    }
    leaf-list fragment {
      ordered-by user;
      type string;
    }
    container destination {
      presence "";
      uses flow-prefix-with-offset;
    }
    container source {
      presence "";
      uses flow-prefix-with-offset;
    }
    leaf-list icmp6-type {
      ordered-by user;
      type string;
    }
    leaf-list icmp6-code {
      ordered-by user;
      type string;
    }
    leaf-list flow-label {
      type policy-algebra;
      ordered-by user;
    }
  }

  grouping flow-prefix-with-offset {
    uses apply-group;
    uses apply-macro;
    leaf prefix {
      mandatory true;
      type ipv6prefix;
    }
    leaf prefix-offset {
      type uint32;
    }
  }

  grouping flow-rule-inet {
    leaf name {
      type string;
    }
    uses apply-advanced;
    leaf no-install {
      type empty;
    }
    container match {
      uses flow-rule-qualifier-inet;
    }
    container then {
      uses flow-rule-op;
    }
  }

  grouping flow-rule-inet6 {
    leaf name {
      type string;
    }
    uses apply-advanced;
    leaf no-install {
      type empty;
    }
    container match {
      uses flow-rule-qualifier-inet6;
    }
    container then {
      uses flow-rule-op;
    }
  }

  grouping flow-rule-op {
    uses apply-advanced;
    choice flow_op_action {
      case case_1 {
        leaf accept {
          type empty;
        }
      }
      case case_2 {
        leaf discard {
          type empty;
        }
      }
      case case_3 {
        leaf rate-limit {
          type string;
        }
      }
    }
  }

  grouping flow-rule-qualifier-inet {
    uses apply-advanced;
    leaf-list protocol {
      ordered-by user;
      type string;
    }
    leaf-list port {
      ordered-by user;
      type string;
    }
    leaf-list destination-port {
      ordered-by user;
      type string;
    }
    leaf-list source-port {
      ordered-by user;
      type string;
    }
    leaf destination {
      type ipv4prefix;
    }
    leaf source {
      type ipv4prefix;
    }
  }

  grouping flow-rule-qualifier-inet6 {
    uses apply-advanced;
    leaf-list protocol {
      ordered-by user;
      type string;
    }
    leaf-list port {
      ordered-by user;
      type string;
    }
    leaf-list destination-port {
      ordered-by user;
      type string;
    }
    leaf-list source-port {
      ordered-by user;
      type string;
    }
    container destination {
      presence "enable destination";
      uses flow-prefix-with-offset;
    }
    container source {
      presence "enable source";
      uses flow-prefix-with-offset;
    }
  }

  grouping flow-route-qualifier {
    uses apply-group;
    uses apply-macro;
    leaf destination {
      type ipprefix;
    }
    leaf source {
      type ipprefix;
    }
    leaf-list protocol {
      ordered-by user;
      type string;
    }
    leaf-list port {
      ordered-by user;
      type string;
    }
    leaf-list destination-port {
      ordered-by user;
      type string;
    }
    leaf-list source-port {
      ordered-by user;
      type string;
    }
    leaf-list icmp-type {
      ordered-by user;
      type string;
    }
    leaf-list icmp-code {
      ordered-by user;
      type string;
    }
    leaf-list tcp-flags {
      ordered-by user;
      type string;
    }
    leaf-list packet-length {
      type policy-algebra;
      ordered-by user;
    }
    leaf-list dscp {
      type policy-algebra;
      ordered-by user;
    }
    leaf-list fragment {
      ordered-by user;
      type string;
    }
  }

  grouping juniper-sampling-options {
    uses apply-group;
    uses apply-macro;
    choice choice-3 {
      leaf disable {
        type empty;
      }
    }
    container traceoptions {
      uses sampling-traceoptions-type;
    }
    leaf sample-once {
      type empty;
    }
    leaf pre-rewrite-tos {
      type empty;
    }
    container input {
      uses sampling-input-type;
      container undocumented {
        container family {
          container inet {
            uses sampling-input-type;
          }
        }
      }
    }
    container undocumented {
      container output {
        uses sampling-instance-inet-global-output-type;
      }
    }
    container family {
      uses apply-group;
      uses apply-macro;
      container inet {
        uses apply-group;
        uses apply-macro;
        choice choice-3 {
          leaf disable {
            type empty;
          }
        }
        container input {
          uses sampling-family-input-type;
        }
        container output {
          uses sampling-instance-inet-global-output-type;
        }
      }
      container inet6 {
        uses apply-group;
        uses apply-macro;
        choice choice-3 {
          leaf disable {
            type empty;
          }
        }
        container input {
          uses sampling-family-input-type;
        }
        container output {
          uses sampling-family-inet6-output-type;
        }
      }
      container mpls {
        uses apply-group;
        uses apply-macro;
        choice choice-3 {
          leaf disable {
            type empty;
          }
        }
        container input {
          uses sampling-family-input-type;
        }
        container output {
          presence "";
          uses sampling-instance-mpls-output-type;
        }
      }
    }
    list instance {
      key "name";
      ordered-by user;
      leaf name {
        type string;
      }
      uses apply-group;
      uses apply-macro;
      choice choice-3 {
        leaf disable {
          type empty;
        }
      }
      container input {
        uses sampling-instance-input-type;
      }
      container family {
        uses apply-group;
        uses apply-macro;
        container inet {
          uses apply-group;
          uses apply-macro;
          choice choice-3 {
            leaf disable {
              type empty;
            }
          }
          container input {
            uses sampling-family-input-type;
          }
          container output {
            uses sampling-instance-inet-output-type;
          }
        }
        container inet6 {
          uses apply-group;
          uses apply-macro;
          choice choice-3 {
            leaf disable {
              type empty;
            }
          }
          container input {
            uses sampling-family-input-type;
          }
          container output {
            uses sampling-instance-inet6-output-type;
          }
        }
        container mpls {
          uses apply-group;
          uses apply-macro;
          choice choice-3 {
            leaf disable {
              type empty;
            }
          }
          container input {
            uses sampling-family-input-type;
          }
          container output {
            presence "";
            uses sampling-instance-mpls-output-type;
          }
        }
        container vpls {
          uses apply-group;
          uses apply-macro;
          leaf enable-disable {
            type string;
          }
          container input {
            uses sampling-family-input-type;
          }
          container output {
            uses sampling-instance-vpls-output-type;
          }
        }
        container bridge {
          container apply-advanced {
            uses apply-group;
            uses apply-macro;
          }
          choice enable-disable {
            case case_1 {
              leaf disable {
                type empty;
              }
            }
          }
          container input {
            uses sampling-family-input-type;
          }
          container output {
            uses sampling-instance-bridge-output-type;
          }
        }
      }
    }
    container jflow-service {
      container apply-advanced {
        uses apply-group;
        uses apply-macro;
      }
      container traceoptions {
        uses jflow-service-traceoptions;
      }
    }
    container route-record {
      container apply-advanced {
        uses apply-group;
        uses apply-macro;
      }
      container traceoptions {
        uses route-record-traceoptions;
      }
    }
  }

  grouping jflow-service-traceoptions {
    container apply-advanced {
      uses apply-group;
      uses apply-macro;
    }
    leaf no-remote-trace {
      type empty;
    }
    container file {
      leaf filename {
        type string;
      }
      leaf size {
        type string;
      }
      leaf files {
        type string;
      }
      choice world-readable-choice {
        leaf world-readable {
          type empty;
        }
        leaf no-world-readable {
          type empty;
        }
      }
      leaf match {
        type regular-expression;
      }
    }
    leaf level {
      type string;
    }
    list flag {
      key "name";
      ordered-by user;
      leaf name {
        type string;
      }
    }
  }

  grouping route-record-traceoptions {
    container apply-advanced {
      uses apply-group;
      uses apply-macro;
    }
    leaf no-remote-trace {
      type empty;
    }
    container file {
      leaf filename {
        type string;
      }
      leaf size {
        type string;
      }
      leaf files {
        type string;
      }
      choice world-readable-choice {
        leaf world-readable {
          type empty;
        }
        leaf no-world-readable {
          type empty;
        }
      }
      leaf match {
        type regular-expression;
      }
    }
    leaf level {
      type string;
    }
    list flag {
      key "name";
      ordered-by user;
      leaf name {
        type string;
      }
    }
  }

  grouping juniper-system {
    uses apply-group;
    uses apply-macro;
    container undocumented {
      leaf dump-on-panic {
        type empty;
      }
    }
    container phone-home {
      leaf-list server {
        type string;
        ordered-by user;
      }
      leaf rfc-compliant {
        type empty;
      }
    }
    container autoinstallation {
      presence "enable autoinstallation";
      uses apply-group;
      uses apply-macro;
    }
    leaf host-name {
      type string;
    }
    leaf auto-snapshot {
      type empty;
    }
    leaf domain-name {
      type string;
    }
    leaf-list domain-search {
      type string;
      ordered-by user;
    }
    container backup-router {
      presence "";
      leaf address {
        type ipv4addr;
      }
      leaf-list destination {
        type ipv4prefix;
        ordered-by user;
      }
    }
    container inet6-backup-router {
      presence "";
      leaf address {
        type ipv6addr;
      }
      leaf destination {
        type ipv6prefix;
      }
    }
    leaf time-zone {
      type string;
    }
    leaf switchover-on-routing-crash {
      type empty;
    }
    leaf use-imported-time-zones {
      type empty;
    }
    leaf default-address-selection {
      type empty;
    }
    leaf nd-maxmcast-solicit {
      type int32;
    }
    leaf nd-retrasmit-timer {
      type int32;
    }
    leaf no-neighbor-learn {
      type empty;
    }
    leaf no-multicast-echo {
      type empty;
    }
    leaf no-redirects {
      type empty;
    }
    leaf no-redirects-ipv6 {
      type empty;
    }
    leaf nd-override-preferred-src {
      type empty;
    }
    leaf no-ping-record-route {
      type empty;
    }
    leaf no-ping-time-stamp {
      type empty;
    }
    choice choice-35;
    leaf dump-device {
      type string;
    }
    container arp {
      presence "enable arp";
      uses apply-group;
      uses apply-macro;
      leaf aging-timer {
        type int32;
      }
      container interfaces {
        uses apply-group;
        uses apply-macro;
        list arp-interface {
          key "name";
          uses arp-interface-type;
        }
      }
      leaf passive-learning {
        type empty;
      }
      leaf purging {
        type empty;
      }
      leaf gratuitous-arp-on-ifup {
        type empty;
      }
      leaf gratuitous-arp-delay {
        type int32;
      }
      leaf non-subscriber-no-reply {
        type empty;
      }
      leaf unicast-mode-on-expire {
        type empty;
      }
      leaf arp-retries {
        type string;
      }
      container undocumented {
        leaf arp-request-bump-priority {
          type empty;
        }
      }
    }
    leaf saved-core-files {
      type uint32;
    }
    leaf saved-core-context {
      type empty;
    }
    leaf no-saved-core-context {
      type empty;
    }
    container kernel-replication {
      presence "enable kernel-replication";
      uses apply-group;
      uses apply-macro;
    }
    leaf mirror-flash-on-disk {
      type empty;
    }
    container icmp-rate-limit {
      leaf packet-rate {
        type uint32;
      }
      leaf bucket-size {
        type uint32;
        units "seconds";
      }
    }
    leaf tcp-ack-rst-syn {
      type empty;
    }
    leaf management-instance {
      type empty;
    }
    container demux-options {
      uses apply-group;
      uses apply-macro;
      leaf use-underlying-interface-mac {
        type empty;
      }
    }
    container internet-options {
      uses apply-group;
      uses apply-macro;
      container undocumented {
        leaf tcp-reset-syn-acknowledge {
          type empty;
        }
      }
      container icmpv4-rate-limit {
        leaf packet-rate {
          type uint32;
        }
        leaf bucket-size {
          type uint32;
        }
      }
      container icmpv6-rate-limit {
        leaf packet-rate {
          type uint32;
        }
        leaf bucket-size {
          type uint32;
        }
      }
      leaf path-mtu-discovery {
        type empty;
      }
      leaf no-path-mtu-discovery {
        type empty;
      }
      leaf gre-path-mtu-discovery {
        type empty;
      }
      leaf no-gre-path-mtu-discovery {
        type empty;
      }
      leaf ipip-path-mtu-discovery {
        type empty;
      }
      leaf no-ipip-path-mtu-discovery {
        type empty;
      }
      container source-port {
        uses apply-group;
        uses apply-macro;
        leaf upper-limit {
          type uint32;
        }
      }
      leaf source-quench {
        type empty;
      }
      leaf no-source-quench {
        type empty;
      }
      leaf tcp-mss {
        type uint32;
      }
      leaf tcp-drop-synfin-set {
        type empty;
      }
      leaf no-tcp-rfc1323 {
        type empty;
      }
      leaf no-tcp-rfc1323-paws {
        type empty;
      }
      leaf ipv6-reject-zero-hop-limit {
        type empty;
      }
      leaf no-ipv6-reject-zero-hop-limit {
        type empty;
      }
      leaf ipv6-duplicate-addr-detection-transmits {
        type uint32;
      }
      leaf ipv6-path-mtu-discovery {
        type empty;
      }
      leaf no-ipv6-path-mtu-discovery {
        type empty;
      }
      leaf ipv6-path-mtu-discovery-timeout {
        type uint32;
      }
      leaf no-tcp-reset {
        type string;
      }
    }
    leaf-list authentication-order {
      ordered-by user;
      type string;
    }
    container location {
      uses apply-group;
      uses apply-macro;
      leaf country-code {
        type string;
      }
      leaf postal-code {
        type string;
      }
      leaf npa-nxx {
        type string;
      }
      leaf latitude {
        type string;
      }
      leaf longitude {
        type string;
      }
      leaf altitude {
        type int32;
      }
      leaf lata {
        type string;
      }
      leaf vcoord {
        type string;
      }
      leaf hcoord {
        type string;
      }
      leaf building {
        type string;
      }
      leaf floor {
        type int32;
      }
      leaf rack {
        type uint32;
      }
      list lcc {
        key "name";
        leaf name {
          type string;
        }
        uses apply-group;
        uses apply-macro;
        leaf floor {
          type int32;
        }
        leaf rack {
          type uint32;
        }
      }
    }
    container ports {
      uses apply-group;
      uses apply-macro;
      container console {
        uses tty-port-object;
      }
      container auxiliary {
        uses tty-port-object;
      }
    }
    container diag-port-authentication {
      uses apply-group;
      uses apply-macro;
      leaf plain-text-password-value {
        type string;
      }
      leaf encrypted-password {
        type string;
      }
    }
    container pic-console-authentication {
      uses apply-group;
      uses apply-macro;
      leaf plain-text-password-value {
        type string;
      }
      leaf encrypted-password {
        type string;
      }
    }
    container root-authentication {
      uses authentication-object;
    }
    list name-server {
      key "name";
      ordered-by user;
      uses nameserver-object;
    }
    list radius-server {
      key "name";
      ordered-by user;
      uses radius-server-object;
    }
    list tacplus-server {
      key "name";
      ordered-by user;
      uses tacplus-server-object;
    }
    container radius-options {
      uses apply-group;
      uses apply-macro;
      leaf password-protocol {
        type string;
      }
      container attributes {
        uses apply-group;
        uses apply-macro;
        leaf nas-ip-address {
          type ipv4addr;
        }
      }
    }
    container tacplus-options {
      uses apply-group;
      uses apply-macro;
      leaf service-name {
        type string;
      }
      leaf authorization-time-interval {
        units "minutes";
        type uint32;
      }
      leaf strict-authorization {
        type empty;
      }
      leaf no-strict-authorization {
        type empty;
      }
      choice choice-5 {
        leaf no-cmd-attribute-value {
          type empty;
        }
        leaf exclude-cmd-attribute {
          type empty;
        }
      }
      leaf enhanced-accounting {
        type empty;
      }
      leaf timestamp-and-timezone {
        type empty;
      }
    }
    container accounting {
      presence "";
      uses apply-group;
      uses apply-macro;
      leaf-list events {
        type string;
      }
      container traceoptions {
        uses apply-group;
        uses apply-macro;
        leaf no-remote-trace {
          type empty;
        }
        container file {
          leaf filename {
            type string;
          }
          leaf size {
            type string;
          }
          leaf files {
            type uint32;
          }
          leaf world-readable {
            type empty;
          }
          leaf no-world-readable {
            type empty;
          }
        }
        list flag {
          key "name";
          ordered-by user;
          leaf name {
            type string;
          }
        }
      }
      container destination {
        presence "enable destination";
        uses apply-group;
        uses apply-macro;
        container radius {
          presence "enable radius";
          uses apply-group;
          uses apply-macro;
          list server {
            key "name";
            ordered-by user;
            uses radius-server-object;
          }
        }
        container tacplus {
          presence "enable tacplus";
          uses apply-group;
          uses apply-macro;
          list server {
            key "name";
            ordered-by user;
            uses tacplus-server-object;
          }
        }
      }
    }
    leaf allow-v4mapped-packets {
      type empty;
    }
    container scripts {
      uses scripts-type;
    }
    container login {
      uses apply-group;
      uses apply-macro;
      leaf announcement {
        type string;
      }
      leaf message {
        type string;
      }
      container retry-options {
        uses apply-group;
        uses apply-macro;
        leaf tries-before-disconnect {
          type uint32;
        }
        leaf backoff-threshold {
          type uint32;
        }
        leaf backoff-factor {
          type uint32;
        }
        leaf minimum-time {
          type uint32;
        }
        leaf maximum-time {
          type uint32;
        }
        leaf lockout-period {
          units "minutes";
          type uint32;
        }
      }
      leaf idle-timeout {
        units "minutes";
        type uint32;
      }
      list class {
        key "name";
        uses login-class-object;
      }
      list user {
        key "name";
        uses login-user-object;
      }
      container password {
        uses apply-group;
        uses apply-macro;
        leaf minimum-character-changes {
          type int32;
        }
        leaf minimum-reuse {
          type int32;
        }
        leaf maximum-lifetime {
          type int32;
        }
        leaf minimum-lifetime {
          type int32;
        }
        leaf minimum-length {
          type int32;
        }
        leaf maximum-length {
          type int32;
        }
        leaf change-type {
          type string;
        }
        leaf minimum-changes {
          type int32;
        }
        leaf minimum-numerics {
          type int32;
        }
        leaf minimum-upper-cases {
          type int32;
        }
        leaf minimum-lower-cases {
          type int32;
        }
        leaf minimum-punctuations {
          type int32;
        }
        leaf format {
          type string;
        }
      }
      container deny-sources {
        uses apply-group;
        uses apply-macro;
        leaf-list address {
          type ipprefix-optional;
          ordered-by user;
        }
      }
    }
    container schema {
      uses apply-group;
      uses apply-macro;
      container openconfig {
        uses apply-group;
        uses apply-macro;
        leaf unhide {
          type empty;
        }
      }
    }
    list static-host-mapping {
      key "name";
      ordered-by user;
      leaf name {
        type string;
      }
      uses apply-group;
      uses apply-macro;
      leaf-list inet {
        type ipv4addr;
        ordered-by user;
      }
      leaf-list inet6 {
        type ipv6addr;
        ordered-by user;
      }
      leaf sysid {
        type sysid;
      }
      leaf-list alias {
        type string;
        ordered-by user;
      }
    }
    container services {
      presence "enable services";
      uses apply-group;
      uses apply-macro;
      container finger {
        presence "enable finger";
        uses apply-group;
        uses apply-macro;
        leaf connection-limit {
          type uint32;
        }
        leaf rate-limit {
          type uint32;
        }
      }
      container ftp {
        presence "enable ftp";
        uses apply-group;
        uses apply-macro;
        leaf connection-limit {
          type uint32;
        }
        leaf rate-limit {
          type uint32;
        }
      }
      container ssh {
        presence "enable ssh";
        uses apply-group;
        uses apply-macro;
        leaf-list authentication-order {
          ordered-by user;
          type string;
        }
        leaf root-login {
          type string;
        }
        leaf no-challenge-response {
          type empty;
        }
        leaf no-password-authentication {
          type empty;
        }
        leaf no-passwords {
          type empty;
        }
        leaf no-public-keys {
          type empty;
        }
        choice choice-tcp-forwarding {
          leaf tcp-forwarding {
            type empty;
          }
          leaf no-tcp-forwarding {
            type empty;
          }
        }
        leaf-list protocol-version {
          ordered-by user;
          type string;
        }
        leaf max-sessions-per-connection {
          type int32;
        }
        leaf max-pre-authentication-packets {
          type int32;
        }
        leaf sftp-server {
          type empty;
        }
        leaf-list ciphers {
          ordered-by user;
          type string;
        }
        leaf-list macs {
          ordered-by user;
          type string;
        }
        leaf-list key-exchange {
          ordered-by user;
          type string;
        }
        leaf client-alive-count-max {
          type uint32;
        }
        leaf client-alive-interval {
          units "seconds";
          type uint32;
        }
        container hostkey-algorithm {
          presence "enable hostkey-algorithm";
          uses apply-group;
          uses apply-macro;
          choice choice-no-ssh-dss {
            leaf no-ssh-dss {
              type empty;
            }
            container ssh-dss {
              presence "enable ssh-dss";
              uses apply-group;
              uses apply-macro;
              choice choice-allow {
                leaf allow {
                  type empty;
                }
                leaf deny {
                  type empty;
                }
              }
            }
          }
          choice choice-no-ssh-rsa {
            leaf no-ssh-rsa {
              type empty;
            }
            container ssh-rsa {
              presence "enable ssh-rsa";
              uses apply-group;
              uses apply-macro;
              choice choice-allow {
                leaf allow {
                  type empty;
                }
                leaf deny {
                  type empty;
                }
              }
            }
          }
          choice choice-no-ssh-ecdsa {
            leaf no-ssh-ecdsa {
              type empty;
            }
            container ssh-ecdsa {
              presence "enable ssh-ecdsa";
              uses apply-group;
              uses apply-macro;
              choice choice-allow {
                leaf allow {
                  type empty;
                }
                leaf deny {
                  type empty;
                }
              }
            }
          }
          choice choice-no-ssh-ed25519 {
            leaf no-ssh-ed25519 {
              type empty;
            }
            leaf ssh-ed25519 {
              type empty;
            }
          }
        }
        leaf fingerprint-hash {
          type string;
        }
        leaf authorized-keys-command {
          type string;
        }
        leaf authorized-keys-command-user {
          type string;
        }
        container rekey {
          uses apply-group;
          uses apply-macro;
          leaf data-limit {
            type string;
            units "bytes";
          }
          leaf time-limit {
            units "minutes";
            type uint32;
          }
        }
        leaf port {
          type uint32;
        }
        leaf log-key-changes {
          type empty;
        }
        leaf connection-limit {
          type uint32;
        }
        leaf rate-limit {
          type uint32;
        }
      }
      container telnet {
        presence "enable telnet";
        uses apply-group;
        uses apply-macro;
        leaf connection-limit {
          type uint32;
        }
        leaf rate-limit {
          type uint32;
        }
      }
      container xnm-clear-text {
        presence "enable xnm-clear-text";
        uses apply-group;
        uses apply-macro;
        leaf connection-limit {
          type uint32;
        }
        leaf rate-limit {
          type uint32;
        }
      }
      container xnm-ssl {
        presence "";
        uses apply-group;
        uses apply-macro;
        leaf local-certificate {
          type string;
        }
        leaf connection-limit {
          type uint32;
        }
        leaf rate-limit {
          type uint32;
        }
      }
      container extension-service {
        uses apply-group;
        uses apply-macro;
        container request-response {
          uses apply-group;
          uses apply-macro;
          container grpc {
            uses apply-group;
            uses apply-macro;
            container ssl {
              presence "";
              uses apply-group;
              uses apply-macro;
              leaf address {
                type ipaddr;
              }
              leaf port {
                type uint32;
              }
              leaf-list local-certificate {
                type string;
                ordered-by user;
              }
              container mutual-authentication {
                presence "";
                uses apply-group;
                uses apply-macro;
                leaf certificate-authority {
                  type string;
                  mandatory true;
                }
                leaf client-certificate-request {
                  type string;
                }
              }
              leaf hot-reloading {
                type empty;
              }
            }
            leaf max-connections {
              type uint32;
            }
            leaf routing-instance {
              type string;
            }
            container undocumented {
              presence "true";
              container clear-text {
                presence "true";
                leaf address {
                  type ipaddr;
                }
                leaf port {
                  type uint16;
                }
              }
              leaf skip-authentication {
                type empty;
              }
            }
          }
        }
        container notification {
          presence "enable notification";
          uses apply-group;
          uses apply-macro;
          leaf port {
            type uint32;
          }
          leaf max-connections {
            type uint32;
          }
          leaf broker-socket-send-buffer-size {
            type uint32;
          }
          container allow-clients {
            uses apply-group;
            uses apply-macro;
            leaf-list address {
              type ipprefix-optional;
              ordered-by user;
            }
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
      }
      container netconf {
        uses apply-group;
        uses apply-macro;
        container ssh {
          presence "enable ssh";
          uses apply-group;
          uses apply-macro;
          leaf connection-limit {
            type uint32;
          }
          leaf rate-limit {
            type uint32;
          }
          leaf port {
            type int32;
          }
        }
        leaf rfc-compliant {
          type empty;
        }
        leaf yang-compliant {
          type empty;
        }
        container version-1.1 {
          presence "enable version-1.1";
        }
        container yang-modules {
          uses apply-group;
          uses apply-macro;
          leaf device-specific {
            type empty;
          }
          leaf emit-extensions {
            type empty;
          }
          leaf emit-anyxml-in-rpc-output {
            type empty;
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
          leaf on-demand {
            type empty;
          }
        }
        container hello-message {
          container yang-module-capabilities {
            leaf advertise-native-yang-modules {
              type empty;
            }
            leaf advertise-custom-yang-modules {
              type empty;
            }
            leaf advertise-standard-yang-modules {
              type empty;
            }
          }
        }
      }
      container flow-tap-dtcp {
        uses apply-group;
        uses apply-macro;
        container ssh {
          presence "enable ssh";
          uses apply-group;
          uses apply-macro;
          leaf connection-limit {
            type uint32;
          }
          leaf rate-limit {
            type uint32;
          }
        }
      }
      leaf dtcp-only {
        type empty;
      }
      container reverse {
        uses apply-group;
        uses apply-macro;
        container telnet {
          presence "enable telnet";
          uses apply-group;
          uses apply-macro;
          leaf port {
            type int32;
          }
        }
        container ssh {
          presence "enable ssh";
          uses apply-group;
          uses apply-macro;
          leaf port {
            type int32;
          }
        }
      }
      container dns {
        presence "enable dns";
        uses apply-group;
        uses apply-macro;
        leaf max-cache-ttl {
          type uint32;
        }
        leaf max-ncache-ttl {
          type uint32;
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
          }
          leaf debug-level {
            type uint32;
          }
          list category {
            key "name";
            leaf name {
              type string;
            }
          }
        }
        list forwarders {
          key "name";
          ordered-by user;
          leaf name {
            type ipaddr;
          }
          uses apply-group;
          uses apply-macro;
        }
        container dnssec {
          presence "enable dnssec";
          uses apply-group;
          uses apply-macro;
          leaf disable {
            type empty;
          }
          container trusted-keys {
            presence "enable trusted-keys";
            uses apply-group;
            uses apply-macro;
            list key {
              key "name";
              ordered-by user;
              leaf name {
                type string;
              }
              uses apply-group;
              uses apply-macro;
            }
          }
          list dlv {
            key "domain trusted-anchor";
            ordered-by user;
            leaf domain {
              type string;
            }
            leaf trusted-anchor {
              type string;
            }
          }
          list secure-domains {
            key "name";
            ordered-by user;
            leaf name {
              type string;
            }
            uses apply-group;
            uses apply-macro;
          }
        }
      }
      container service-deployment {
        uses apply-group;
        uses apply-macro;
        leaf local-certificate {
          type string;
        }
        leaf source-address {
          type ipv4addr;
        }
        list servers {
          key "name";
          ordered-by user;
          leaf name {
            type ipv4addr;
          }
          uses apply-group;
          uses apply-macro;
          leaf port {
            type uint16;
          }
          leaf user {
            type string;
          }
          container security-options {
            uses apply-group;
            uses apply-macro;
            choice choice-3 {
              leaf tls {
                type empty;
              }
              leaf ssl3 {
                type empty;
              }
            }
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
      }
      container outbound-ssh {
        uses apply-group;
        uses apply-macro;
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
        list client {
          key "name";
          ordered-by user;
          leaf name {
            type string;
          }
          uses apply-group;
          uses apply-macro;
          leaf device-id {
            type string;
          }
          leaf secret {
            type unreadable;
          }
          container keep-alive {
            presence "enable keep-alive";
            uses apply-group;
            uses apply-macro;
            leaf retry {
              type uint32;
            }
            leaf timeout {
              type uint32;
            }
          }
          leaf reconnect-strategy {
            type string;
          }
          leaf services {
            type string;
          }
          list servers {
            key "name";
            ordered-by user;
            leaf name {
              type string;
            }
            uses apply-group;
            uses apply-macro;
            leaf port {
              type uint16;
            }
            leaf retry {
              type uint32;
            }
            leaf timeout {
              type uint32;
            }
          }
        }
      }
      container grpc-tunnel {
        uses apply-advanced;
        container servers {
          uses apply-advanced;
          leaf retry-interval {
            units "seconds";
            type string;
          }
          list server {
            key "name";
            ordered-by user;
            leaf name {
              type string;
            }
            uses apply-advanced;
            leaf address {
              type hostname;
            }
            leaf port {
              type string;
            }
            leaf-list targets {
              ordered-by user;
              type string;
            }
            leaf routing-instance {
              type string;
            }
            leaf source-address {
              type ipaddr;
            }
            container credentials {
              uses apply-advanced;
              choice credential-type {
                case case_1 {
                  container tls {
                    presence "enable tls";
                    uses apply-advanced;
                    leaf certificate-id {
                      type string;
                    }
                    leaf-list ca-profiles {
                      ordered-by user;
                      type string;
                    }
                  }
                }
              }
              container undocumented {
                container clear-text {
                  presence "true";
                }
              }
            }
          }
        }
        container target-string-option {
          uses apply-advanced;
          leaf-list pattern {
            ordered-by user;
            type string;
          }
          leaf custom-string {
            type string;
          }
          leaf delimiter {
            type string;
          }
        }
        container traceoptions {
          uses apply-advanced;
          leaf no-remote-trace {
            type empty;
          }
          container file {
            leaf filename {
              type string;
            }
            leaf size {
              type string;
            }
            leaf files {
              type string;
            }
            choice world-readable-choice {
              leaf world-readable {
                type empty;
              }
              leaf no-world-readable {
                type empty;
              }
            }
            leaf match {
              type regular-expression;
            }
          }
          leaf level {
            type string;
          }
          list flag {
            key "name";
            ordered-by user;
            leaf name {
              type string;
            }
          }
        }
      }
      container rest {
        uses apply-group;
        uses apply-macro;
        container http {
          presence "enable http";
          uses apply-group;
          uses apply-macro;
          leaf port {
            type uint32;
          }
          leaf-list addresses {
            type ipv4addr;
            ordered-by user;
          }
        }
        container https {
          presence "";
          uses apply-group;
          uses apply-macro;
          leaf port {
            type uint32;
          }
          leaf-list addresses {
            type ipv4addr;
            ordered-by user;
          }
          leaf server-certificate {
            type string;
            mandatory true;
          }
          leaf-list cipher-list {
            ordered-by user;
            type string;
          }
          container mutual-authentication {
            uses apply-group;
            uses apply-macro;
            leaf certificate-authority {
              type string;
            }
          }
        }
        container control {
          uses apply-group;
          uses apply-macro;
          leaf-list allowed-sources {
            type ipv4addr;
            ordered-by user;
          }
          leaf connection-limit {
            type int32;
          }
        }
        container traceoptions {
          uses apply-group;
          uses apply-macro;
          leaf flag {
            type string;
          }
        }
        leaf enable-explorer {
          type empty;
        }
      }
      container dhcp-local-server {
        uses jdhcp-local-server-type;
      }
      container database-replication {
        uses bdbrepd-type;
      }
      container web-management {
        uses apply-group;
        uses apply-macro;
        leaf management-url {
          type string;
        }
        container http {
          presence "enable http";
          uses apply-group;
          uses apply-macro;
          leaf port {
            type uint16;
          }
          leaf-list interface {
            type interface-name;
            ordered-by user;
          }
        }
        container https {
          presence "enable https";
          uses apply-group;
          uses apply-macro;
          leaf port {
            type uint16;
          }
          choice choice-5 {
            leaf local-certificate {
              type string;
            }
            leaf pki-local-certificate {
              type string;
            }
            leaf system-generated-certificate {
              type empty;
            }
          }
          leaf-list interface {
            type interface-name;
            ordered-by user;
          }
        }
        container control {
          uses apply-group;
          uses apply-macro;
          leaf max-threads {
            type uint32;
          }
        }
        container session {
          uses apply-group;
          uses apply-macro;
          leaf idle-timeout {
            type uint32;
          }
          leaf session-limit {
            type uint32;
          }
        }
      }
      container packet-triggered-subscribers {
        uses apply-group;
        uses apply-macro;
        container traceoptions {
          uses jptspd-traceoptions-type;
        }
        list partition {
          key "name";
          ordered-by user;
          leaf name {
            type key-attribute-string-type;
          }
          uses apply-group;
          uses apply-macro;
          leaf diameter-instance {
            type string;
          }
          leaf destination-realm {
            type string;
          }
          leaf destination-host {
            type string;
          }
        }
      }
      container static-subscribers {
        uses jsscd-static-subscribers-type;
      }
      container local-policy-decision-function {
        presence "enable local-policy-decision-function";
        uses apply-group;
        uses apply-macro;
        container traceoptions {
          uses lpdf-trace-options-type;
        }
        container statistics {
          presence "enable statistics";
          uses apply-group;
          uses apply-macro;
          list file {
            key "name";
            ordered-by user;
            leaf name {
              type string;
            }
            uses apply-group;
            uses apply-macro;
            leaf size {
              type string;
            }
            leaf files {
              type uint32;
            }
            leaf transfer-interval {
              type uint32;
            }
            list archive-sites {
              key "name";
              ordered-by user;
              leaf name {
                type string;
              }
              leaf password {
                type unreadable;
              }
            }
          }
          leaf record-type {
            type string;
          }
          list aacl-statistics-profile {
            key "name";
            ordered-by user;
            leaf name {
              type key-attribute-string-type;
            }
            uses apply-group;
            uses apply-macro;
            leaf file {
              type string;
            }
            leaf record-mode {
              type string;
            }
            leaf report-interval {
              type uint32;
            }
            container aacl-fields {
              uses apply-group;
              uses apply-macro;
              leaf address {
                type empty;
              }
              leaf all-fields {
                type empty;
              }
              leaf application {
                type empty;
              }
              leaf application-group {
                type empty;
              }
              leaf input-bytes {
                type empty;
              }
              leaf input-interface {
                type empty;
              }
              leaf input-packets {
                type empty;
              }
              leaf mask {
                type empty;
              }
              leaf output-bytes {
                type empty;
              }
              leaf output-packets {
                type empty;
              }
              leaf subscriber-name {
                type empty;
              }
              leaf timestamp {
                type empty;
              }
              leaf vrf-name {
                type empty;
              }
            }
          }
        }
      }
      container dhcp {
        uses apply-group;
        uses apply-macro;
        leaf maximum-lease-time {
          type string;
        }
        leaf default-lease-time {
          type string;
        }
        leaf domain-name {
          type string;
        }
        list name-server {
          key "name";
          ordered-by user;
          leaf name {
            type ipv4addr;
          }
          uses apply-group;
          uses apply-macro;
        }
        list domain-search {
          key "name";
          ordered-by user;
          leaf name {
            type string;
          }
          uses apply-group;
          uses apply-macro;
        }
        list wins-server {
          key "name";
          ordered-by user;
          leaf name {
            type ipv4addr;
          }
          uses apply-group;
          uses apply-macro;
        }
        list router {
          key "name";
          ordered-by user;
          leaf name {
            type ipv4addr;
          }
          uses apply-group;
          uses apply-macro;
        }
        leaf boot-file {
          type string;
        }
        leaf boot-server {
          type string;
        }
        leaf next-server {
          type ipv4addr;
        }
        leaf server-identifier {
          type ipv4addr;
        }
        list option {
          key "name";
          ordered-by user;
          leaf name {
            type string;
          }
          choice choice-3 {
            leaf flag {
              type string;
            }
            leaf byte {
              type uint8;
            }
            leaf short {
              type int16;
            }
            leaf unsigned-short {
              type uint16;
            }
            leaf integer {
              type int32;
            }
            leaf unsigned-integer {
              type uint32;
            }
            leaf string {
              type string;
            }
            leaf ip-address {
              type ipv4addr;
            }
            container array {
              presence "enable array";
              uses apply-group;
              uses apply-macro;
              choice choice-3 {
                leaf-list flag {
                  ordered-by user;
                  type string;
                }
                leaf-list byte {
                  type uint8;
                  ordered-by user;
                }
                leaf-list short {
                  type int16;
                  ordered-by user;
                }
                leaf-list unsigned-short {
                  type uint16;
                  ordered-by user;
                }
                leaf-list integer {
                  type int32;
                  ordered-by user;
                }
                leaf-list unsigned-integer {
                  type uint32;
                  ordered-by user;
                }
                leaf-list string {
                  ordered-by user;
                  type string;
                }
                leaf-list ip-address {
                  type ipv4addr;
                  ordered-by user;
                }
              }
            }
            leaf byte-stream {
              type string;
            }
          }
        }
        container sip-server {
          uses apply-group;
          uses apply-macro;
          list name {
            key "name";
            ordered-by user;
            leaf name {
              type string;
            }
            uses apply-group;
            uses apply-macro;
          }
          list address {
            key "name";
            ordered-by user;
            leaf name {
              type ipv4addr;
            }
            uses apply-group;
            uses apply-macro;
          }
        }
        container traceoptions {
          uses dhcp-traceoptions-type;
        }
        list pool {
          key "name";
          ordered-by user;
          leaf name {
            type ipprefix;
          }
          uses apply-group;
          uses apply-macro;
          container address-range {
            presence "";
            leaf low {
              type ipv4addr;
            }
            leaf high {
              type ipv4addr;
            }
          }
          list exclude-address {
            key "name";
            ordered-by user;
            leaf name {
              type ipv4addr;
            }
            uses apply-group;
            uses apply-macro;
          }
          leaf maximum-lease-time {
            type string;
          }
          leaf default-lease-time {
            type string;
          }
          leaf domain-name {
            type string;
          }
          list name-server {
            key "name";
            ordered-by user;
            leaf name {
              type ipv4addr;
            }
            uses apply-group;
            uses apply-macro;
          }
          list domain-search {
            key "name";
            ordered-by user;
            leaf name {
              type string;
            }
            uses apply-group;
            uses apply-macro;
          }
          list wins-server {
            key "name";
            ordered-by user;
            leaf name {
              type ipv4addr;
            }
            uses apply-group;
            uses apply-macro;
          }
          list router {
            key "name";
            ordered-by user;
            leaf name {
              type ipv4addr;
            }
            uses apply-group;
            uses apply-macro;
          }
          leaf boot-file {
            type string;
          }
          leaf boot-server {
            type string;
          }
          leaf next-server {
            type ipv4addr;
          }
          leaf server-identifier {
            type ipv4addr;
          }
          list option {
            key "name";
            ordered-by user;
            leaf name {
              type string;
            }
            choice choice-3 {
              leaf flag {
                type string;
              }
              leaf byte {
                type uint8;
              }
              leaf short {
                type int16;
              }
              leaf unsigned-short {
                type uint16;
              }
              leaf integer {
                type int32;
              }
              leaf unsigned-integer {
                type uint32;
              }
              leaf string {
                type string;
              }
              leaf ip-address {
                type ipv4addr;
              }
              container array {
                presence "enable array";
                uses apply-group;
                uses apply-macro;
                choice choice-3 {
                  leaf-list flag {
                    ordered-by user;
                    type string;
                  }
                  leaf-list byte {
                    type uint8;
                    ordered-by user;
                  }
                  leaf-list short {
                    type int16;
                    ordered-by user;
                  }
                  leaf-list unsigned-short {
                    type uint16;
                    ordered-by user;
                  }
                  leaf-list integer {
                    type int32;
                    ordered-by user;
                  }
                  leaf-list unsigned-integer {
                    type uint32;
                    ordered-by user;
                  }
                  leaf-list string {
                    ordered-by user;
                    type string;
                  }
                  leaf-list ip-address {
                    type ipv4addr;
                    ordered-by user;
                  }
                }
              }
              leaf byte-stream {
                type string;
              }
            }
          }
          container sip-server {
            uses apply-group;
            uses apply-macro;
            list name {
              key "name";
              ordered-by user;
              leaf name {
                type string;
              }
              uses apply-group;
              uses apply-macro;
            }
            list address {
              key "name";
              ordered-by user;
              leaf name {
                type ipv4addr;
              }
              uses apply-group;
              uses apply-macro;
            }
          }
          leaf propagate-settings {
            type string;
          }
        }
        list static-binding {
          key "name";
          ordered-by user;
          leaf name {
            type mac-addr;
          }
          uses apply-group;
          uses apply-macro;
          list fixed-address {
            key "name";
            ordered-by user;
            leaf name {
              type ipaddr;
            }
            uses apply-group;
            uses apply-macro;
          }
          leaf host-name {
            type string;
          }
          container client-identifier {
            choice choice-3 {
              leaf ascii {
                type string;
              }
              leaf hexadecimal {
                type string;
              }
            }
          }
          leaf domain-name {
            type string;
          }
          list name-server {
            key "name";
            ordered-by user;
            leaf name {
              type ipv4addr;
            }
            uses apply-group;
            uses apply-macro;
          }
          list domain-search {
            key "name";
            ordered-by user;
            leaf name {
              type string;
            }
            uses apply-group;
            uses apply-macro;
          }
          list wins-server {
            key "name";
            ordered-by user;
            leaf name {
              type ipv4addr;
            }
            uses apply-group;
            uses apply-macro;
          }
          list router {
            key "name";
            ordered-by user;
            leaf name {
              type ipv4addr;
            }
            uses apply-group;
            uses apply-macro;
          }
          leaf boot-file {
            type string;
          }
          leaf boot-server {
            type string;
          }
          leaf next-server {
            type ipv4addr;
          }
          leaf server-identifier {
            type ipv4addr;
          }
          list option {
            key "name";
            ordered-by user;
            leaf name {
              type string;
            }
            choice choice-3 {
              leaf flag {
                type string;
              }
              leaf byte {
                type uint8;
              }
              leaf short {
                type int16;
              }
              leaf unsigned-short {
                type uint16;
              }
              leaf integer {
                type int32;
              }
              leaf unsigned-integer {
                type uint32;
              }
              leaf string {
                type string;
              }
              leaf ip-address {
                type ipv4addr;
              }
              container array {
                presence "enable array";
                uses apply-group;
                uses apply-macro;
                choice choice-3 {
                  leaf-list flag {
                    ordered-by user;
                    type string;
                  }
                  leaf-list byte {
                    type uint8;
                    ordered-by user;
                  }
                  leaf-list short {
                    type int16;
                    ordered-by user;
                  }
                  leaf-list unsigned-short {
                    type uint16;
                    ordered-by user;
                  }
                  leaf-list integer {
                    type int32;
                    ordered-by user;
                  }
                  leaf-list unsigned-integer {
                    type uint32;
                    ordered-by user;
                  }
                  leaf-list string {
                    ordered-by user;
                    type string;
                  }
                  leaf-list ip-address {
                    type ipv4addr;
                    ordered-by user;
                  }
                }
              }
              leaf byte-stream {
                type string;
              }
            }
          }
          container sip-server {
            uses apply-group;
            uses apply-macro;
            list name {
              key "name";
              ordered-by user;
              leaf name {
                type string;
              }
              uses apply-group;
              uses apply-macro;
            }
            list address {
              key "name";
              ordered-by user;
              leaf name {
                type ipv4addr;
              }
              uses apply-group;
              uses apply-macro;
            }
          }
        }
        leaf propagate-settings {
          type string;
        }
      }
      container subscriber-management {
        uses smid-type;
      }
      container resource-monitor {
        uses resource-monitor-type;
      }
      container undocumented {
        container rlogin {
          presence "true";
        }
        container rsh {
          presence "true";
        }
      }
    }
    container syslog {
      uses apply-group;
      uses apply-macro;
      container archive {
        presence "enable archive";
        uses archive-object;
      }
      list user {
        key "name";
        ordered-by user;
        leaf name {
          type string;
        }
        uses apply-group;
        uses apply-macro;
        list contents {
          key "name";
          uses syslog-object;
        }
        leaf match {
          type regular-expression;
        }
        leaf allow-duplicates {
          type empty;
        }
        leaf-list match-strings {
          type string;
          ordered-by user;
        }
      }
      list host {
        key "name";
        ordered-by user;
        leaf name {
          type string;
        }
        uses apply-group;
        uses apply-macro;
        list contents {
          key "name";
          uses syslog-object;
        }
        leaf match {
          type regular-expression;
        }
        leaf allow-duplicates {
          type empty;
        }
        leaf port {
          type uint16;
        }
        leaf facility-override {
          type string;
        }
        leaf log-prefix {
          type string;
        }
        leaf source-address {
          type ipaddr;
        }
        leaf routing-instance {
          type string;
        }
        leaf explicit-priority {
          type empty;
        }
        leaf exclude-hostname {
          type empty;
        }
        leaf transport {
          type string;
        }
        container tlsdetails {
          presence "enable tlsdetails";
          uses apply-advanced;
          leaf local-certificate {
            type string;
          }
          container mutual-authentication {
            uses apply-advanced;
            leaf certificate-authority {
              type string;
            }
          }
          list trusted-ca-group {
            key "name";
            ordered-by user;
            leaf name {
              type string;
            }
            uses apply-advanced;
            leaf-list ca-profiles {
              ordered-by user;
              type string;
            }
          }
        }
        leaf-list match-strings {
          type string;
          ordered-by user;
        }
        container structured-data {
          presence "enable structured-data";
          uses apply-group;
          uses apply-macro;
          leaf brief {
            type empty;
          }
        }
      }
      leaf allow-duplicates {
        type empty;
      }
      list file {
        key "name";
        ordered-by user;
        leaf name {
          type key-attribute-string-type;
        }
        uses apply-group;
        uses apply-macro;
        list contents {
          key "name";
          uses syslog-object;
        }
        leaf match {
          type regular-expression;
        }
        leaf allow-duplicates {
          type empty;
        }
        container archive {
          presence "enable archive";
          uses archive-object;
        }
        leaf explicit-priority {
          type empty;
        }
        leaf-list match-strings {
          type string;
          ordered-by user;
        }
        container structured-data {
          presence "enable structured-data";
          uses apply-group;
          uses apply-macro;
          choice choice-3 {
            leaf brief {
              type empty;
            }
          }
        }
      }
      list console {
        key "name";
        leaf name {
          type string;
        }
        choice choice-3 {
          leaf any {
            type empty;
          }
          leaf emergency {
            type empty;
          }
          leaf alert {
            type empty;
          }
          leaf critical {
            type empty;
          }
          leaf error {
            type empty;
          }
          leaf warning {
            type empty;
          }
          leaf notice {
            type empty;
          }
          leaf info {
            type empty;
          }
          leaf none {
            type empty;
          }
        }
      }
      container time-format {
        presence "enable time-format";
        leaf year {
          type empty;
        }
        leaf millisecond {
          type empty;
        }
      }
      leaf source-address {
        type ipaddr;
      }
      leaf routing-instance {
        type string;
      }
      leaf log-rotate-frequency {
        units "minutes";
        type string;
      }
      container server {
        presence "enable server";
        uses apply-advanced;
        list routing-instances {
          key "name";
          ordered-by user;
          leaf name {
            type string;
          }
          uses apply-advanced;
          container disable {
            presence "enable disable";
          }
        }
      }
      leaf alternate-format {
        type empty;
      }
      container grpc-replay {
        uses apply-advanced;
        list contents {
          key "name";
          uses syslog-object;
        }
        leaf-list match-strings {
          ordered-by user;
          type string;
        }
        leaf last {
          units "minutes";
          type string;
        }
      }
    }
    container tracing {
      container destination-override {
        container syslog {
          presence "";
          leaf host {
            type ipv4addr;
          }
        }
      }
    }
    leaf encrypt-configuration-files {
      type empty;
    }
    leaf compress-configuration-files {
      type empty;
    }
    leaf no-compress-configuration-files {
      type empty;
    }
    leaf max-configurations-on-flash {
      type uint32;
    }
    leaf max-configuration-rollbacks {
      type uint32;
    }
    container archival {
      uses apply-group;
      uses apply-macro;
      container configuration {
        presence "";
        uses apply-group;
        uses apply-macro;
        choice choice-3 {
          leaf transfer-interval {
            type uint32;
          }
          leaf transfer-on-commit {
            type empty;
          }
        }
        leaf routing-instance {
          type string;
        }
        list archive-sites {
          key "name";
          ordered-by user;
          leaf name {
            type string;
          }
          leaf password {
            type unreadable;
          }
        }
      }
    }
    container extensions {
      presence "enable extensions";
      uses apply-group;
      uses apply-macro;
      list providers {
        key "name";
        ordered-by user;
        leaf name {
          type string;
        }
        uses apply-group;
        uses apply-macro;
        list license-type {
          key "name";
          ordered-by user;
          leaf name {
            type string;
          }
          leaf-list deployment-scope {
            type string;
            ordered-by user;
          }
        }
      }
      container resource-limits {
        uses apply-group;
        uses apply-macro;
        list process {
          key "name";
          ordered-by user;
          leaf name {
            type string;
          }
          uses apply-group;
          uses apply-macro;
          container resources {
            presence "enable resources";
            uses resources-type;
          }
        }
        list package {
          key "name";
          ordered-by user;
          leaf name {
            type string;
          }
          uses apply-group;
          uses apply-macro;
          container resources {
            presence "enable resources";
            uses resources-type;
          }
        }
      }
    }
    container license {
      uses license-object;
    }
    container packet-forwarding-options {
      uses apply-advanced;
      leaf multicast-statistics {
        type empty;
      }
      container warm-boot {
        presence "enable warm-boot";
      }
      container no-ip-tos-rewrite {
        presence "enable no-ip-tos-rewrite";
      }
      container mef-forwarding-profile {
        presence "enable mef-forwarding-profile";
      }
      container eracl-ip6-match {
        presence "enable eracl-ip6-match";
        uses apply-advanced;
        choice ip6-match {
          case case_1 {
            leaf srcip6-only {
              type empty;
            }
          }
          case case_2 {
            leaf srcip6-and-destip6 {
              type empty;
            }
          }
        }
      }
      container firewall-profile {
        presence "enable firewall-profile";
        uses apply-advanced;
        choice rio-profile-list {
          case case_1 {
            leaf evpn-mh-profile {
              type empty;
            }
          }
          case case_2 {
            leaf default-profile {
              type empty;
            }
          }
          case case_3 {
            leaf mef-profile {
              type empty;
            }
          }
        }
        choice odin-profile-list {
          case case_1 {
            leaf profile-one {
              type empty;
            }
          }
          case case_2 {
            leaf profile-two {
              type empty;
            }
          }
        }
        choice filter-modify-type {
          case case_1 {
            container filter-modify {
              presence "enable filter-modify";
              uses apply-advanced;
              choice filter-modify-attr {
                case case_1 {
                  leaf make-before-break {
                    type empty;
                  }
                }
                case case_2 {
                  leaf full-scale {
                    type empty;
                  }
                }
              }
            }
          }
        }
        container ingress {
          presence "enable ingress";
          uses apply-advanced;
          container lo0-inet6 {
            presence "enable lo0-inet6";
            uses apply-advanced;
            choice lo0-profile-list {
              case case_1 {
                leaf profile-one {
                  type empty;
                }
              }
              case case_2 {
                leaf profile-two {
                  type empty;
                }
              }
            }
          }
        }
        container egress {
          presence "enable egress";
          uses apply-advanced;
          container inet6 {
            presence "enable inet6";
            uses apply-advanced;
            choice inet6-profile-list {
              case case_1 {
                leaf profile-one {
                  type empty;
                }
              }
              case case_2 {
                leaf profile-two {
                  type empty;
                }
              }
            }
          }
        }
      }
      container mpls {
        uses apply-advanced;
        leaf lsp-ingress-stats-enable {
          type empty;
        }
        leaf lsp-transit-stats-enable {
          type empty;
        }
      }
      container system-profile {
        uses apply-advanced;
        choice system-profile-set {
          case case_1 {
            leaf vxlan-extended {
              type empty;
            }
          }
          case case_2 {
            leaf vxlan-stitching {
              type empty;
            }
          }
          case case_3 {
            leaf default-profile {
              type empty;
            }
          }
        }
      }
      container hw-db-profile {
        uses apply-advanced;
        choice hwdb-profile-object {
          case case_1 {
            leaf balanced {
              type empty;
            }
          }
          case case_2 {
            leaf balanced-exem {
              type empty;
            }
          }
          case case_3 {
            leaf l2-xl {
              type empty;
            }
          }
          case case_4 {
            leaf l3-xl {
              type empty;
            }
          }
        }
        leaf lpm-distribution {
          type string;
        }
      }
      container mcast-repl-type {
        uses apply-advanced;
        choice repl-type-obj {
          case case_1 {
            leaf ingress-only {
              type empty;
            }
          }
          case case_2 {
            leaf ingress-egress-recycle {
              type empty;
            }
          }
        }
      }
      container internal-forwarding-bandwidth {
        uses apply-advanced;
        leaf internal-forwarding-bandwidth-value {
          type string;
        }
        container reserve {
          uses apply-advanced;
          container ingress-egress-mcast {
            leaf percent {
              type string;
            }
          }
        }
      }
    }
    container commit {
      uses apply-group;
      uses apply-macro;
      container server {
        uses apply-group;
        uses apply-macro;
        leaf maximum-aggregate-pool {
          type uint32;
        }
        leaf maximum-entries {
          type uint32;
        }
        leaf commit-interval {
          type uint32;
        }
        leaf retry-attempts {
          type uint32;
        }
        leaf retry-interval {
          type uint32;
        }
        leaf days-to-keep-error-logs {
          type uint32;
        }
        leaf redirect-completion-status {
          type string;
        }
        list commit-schedule-profile {
          key "name";
          ordered-by user;
          leaf name {
            type key-attribute-string-type;
          }
          uses apply-group;
          uses apply-macro;
          leaf start-time {
            type string;
            mandatory true;
          }
          leaf end-time {
            type string;
            mandatory true;
          }
          leaf interruptible {
            type empty;
          }
          leaf load-average {
            type unsigned-float;
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf microsecond-stamp {
              type empty;
            }
          }
          list flag {
            key "name";
            leaf name {
              type string;
            }
          }
        }
      }
      leaf fast-synchronize {
        type empty;
      }
      leaf synchronize {
        type empty;
      }
      leaf delta-export {
        type empty;
      }
      container undocumented {
        leaf no-delta-synchronize {
          type empty;
        }
        container private {
          leaf no-fast-diff {
            type empty;
          }
        }
      }
      leaf persist-groups-inheritance {
        type empty;
      }
    }
    container configuration-database {
      uses apply-group;
      uses apply-macro;
      container ephemeral {
        presence "enable ephemeral";
        uses apply-group;
        uses apply-macro;
        list instance {
          key "name";
          ordered-by user;
          leaf name {
            type key-attribute-string-type;
          }
          uses apply-group;
          uses apply-macro;
        }
        leaf ignore-ephemeral-default {
          type empty;
        }
        leaf allow-commit-synchronize-with-gres {
          type empty;
        }
        container undocumented {
          leaf purge-on-version {
            type uint32;
          }
        }
      }
      container virtual-memory-mapping {
        uses apply-group;
        uses apply-macro;
        container process-set {
          uses apply-group;
          uses apply-macro;
          container subscriber-management {
            presence "";
            uses apply-group;
            uses apply-macro;
            leaf fixed-size {
              mandatory true;
              units "kilobytes";
              type uint32;
            }
            leaf page-pooling-size {
              mandatory true;
              units "kilobytes";
              type uint32;
            }
          }
        }
      }
      leaf extend-size {
        type empty;
      }
      leaf max-db-size {
        type uint32;
      }
    }
    container auto-configuration {
      presence "enable auto-configuration";
      uses apply-group;
      uses apply-macro;
      container traceoptions {
        uses autoconf-traceoptions-type;
      }
    }
    container processes {
      uses apply-group;
      uses apply-macro;
      container routing {
        container undocumented {
          leaf force-64-bit {
            type empty;
          }
        }
        choice choice-3 {
          leaf disable {
            type empty;
          }
        }
        leaf failover {
          type string;
        }
        choice mode {
          case case_1 {
            leaf force-32-bit {
              type empty;
            }
          }
          case case_2 {
            leaf force-64-bit {
              type empty;
            }
          }
          case case_3 {
            leaf auto-64-bit {
              type empty;
            }
          }
        }
        container bgp {
          uses apply-group;
          uses apply-macro;
          container rib-sharding {
            presence "enable rib-sharding";
            uses apply-group;
            uses apply-macro;
            leaf number-of-shards {
              type uint32;
            }
          }
          container update-threading {
            presence "enable update-threading";
            uses apply-group;
            uses apply-macro;
            leaf number-of-threads {
              type uint32;
            }
          }
        }
      }
      container chassis-control {
        choice choice-3 {
          leaf disable {
            type empty;
          }
        }
        leaf failover {
          type string;
        }
      }
      container service-pics {
        choice choice-3 {
          leaf disable {
            type empty;
          }
        }
        leaf failover {
          type string;
        }
      }
      container ntp {
        choice choice-3 {
          leaf disable {
            type empty;
          }
        }
        leaf enable-disable {
          type string;
        }
        leaf failover {
          type string;
        }
      }
      container watchdog {
        choice choice-3 {
          leaf enable {
            type empty;
          }
          leaf disable {
            type empty;
          }
        }
        leaf timeout {
          type uint32;
        }
      }
      container process-monitor {
        uses apply-group;
        uses apply-macro;
        choice choice-3 {
          leaf disable {
            type empty;
          }
        }
        container traceoptions {
          uses pmond-traceoptions-type;
        }
      }
      container resource-cleanup {
        uses apply-group;
        uses apply-macro;
        choice choice-3 {
          leaf disable {
            type empty;
          }
        }
        container traceoptions {
          uses res-cleanupd-traceoptions-type;
        }
      }
      container routing-socket-proxy {
        choice choice-3 {
          leaf disable {
            type empty;
          }
        }
        leaf failover {
          type string;
        }
      }
      container web-management {
        choice choice-3 {
          leaf disable {
            type empty;
          }
        }
        leaf failover {
          type string;
        }
      }
      container named-service {
        presence "enable named-service";
        uses apply-group;
        uses apply-macro;
        choice choice-3 {
          leaf disable {
            type empty;
          }
        }
        leaf failover {
          type string;
        }
      }
      container cfm {
        choice choice-3 {
          leaf disable {
            type empty;
          }
        }
      }
      container general-authentication-service {
        uses apply-group;
        uses apply-macro;
        choice choice-3 {
          leaf disable {
            type empty;
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
      }
      container smg-service {
        presence "enable smg-service";
        uses apply-group;
        uses apply-macro;
        container apply-advanced {
          uses apply-group;
          uses apply-macro;
        }
        leaf enable-disable {
          type string;
        }
        leaf failover {
          type string;
        }
        container traceoptions {
          uses bbe-smgd-traceoptions-type;
        }
      }
      container dhcp-service {
        uses apply-group;
        uses apply-macro;
        leaf enable-disable {
          type string;
        }
        leaf disable {
          type empty;
        }
        leaf failover {
          type string;
        }
        container persistent-storage {
          uses apply-group;
          uses apply-macro;
          leaf file-name {
            type string;
          }
          leaf backup-interval {
            type uint32;
          }
        }
        container traceoptions {
          uses jdhcp-traceoptions-level-type;
        }
        container interface-traceoptions {
          uses jdhcp-interface-traceoptions-level-type;
        }
        container dhcp-snooping-file {
          presence "";
          uses apply-group;
          uses apply-macro;
          leaf location {
            mandatory true;
            type filename;
          }
          leaf write-interval {
            mandatory true;
            units "seconds";
            type uint32;
          }
        }
        container dhcpv6-snooping-file {
          presence "";
          uses apply-group;
          uses apply-macro;
          leaf location {
            mandatory true;
            type filename;
          }
          leaf write-interval {
            mandatory true;
            units "seconds";
            type uint32;
          }
        }
        container ltv-syslog-interval {
          uses apply-group;
          uses apply-macro;
          leaf syslog-interval {
            units "seconds";
            type uint32;
          }
        }
        leaf accept-max-tcp-connections {
          type uint32;
        }
        leaf request-max-tcp-connections {
          type uint32;
        }
      }
      container diameter-service {
        uses apply-group;
        uses apply-macro;
        choice choice-3 {
          leaf disable {
            type empty;
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          leaf level {
            type string;
          }
          list flag {
            key "name";
            ordered-by user;
            leaf name {
              type string;
            }
          }
        }
      }
      container mac-validation {
        uses apply-group;
        uses apply-macro;
        choice choice-3 {
          leaf disable {
            type empty;
          }
        }
        container traceoptions {
          uses jsavald-traceoptions-type;
        }
      }
      container sbc-configuration-process {
        uses apply-group;
        uses apply-macro;
        choice choice-3 {
          leaf disable {
            type empty;
          }
        }
        leaf failover {
          type string;
        }
        container traceoptions {
          uses sbc-traceoptions;
        }
      }
      container sdk-service {
        uses apply-group;
        uses apply-macro;
        choice choice-3 {
          leaf disable {
            type empty;
          }
        }
        container traceoptions {
          uses ssd-traceoptions-type;
        }
      }
      container app-engine-virtual-machine-management-service {
        uses apply-group;
        uses apply-macro;
        leaf enable-disable {
          type string;
        }
        container traceoptions {
          uses sdk-vmmd-traceoptions-type;
        }
      }
      container datapath-trace-service {
        uses apply-group;
        uses apply-macro;
        choice choice-3 {
          leaf disable {
            type empty;
          }
        }
        container traceoptions {
          uses datapath-traced-traceoptions-type;
        }
      }
      container send {
        choice choice-3 {
          leaf disable {
            type empty;
          }
        }
      }
      container static-subscribers {
        uses apply-group;
        uses apply-macro;
        choice choice-3 {
          leaf disable {
            type empty;
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
      }
      list daemon-process {
        key "name";
        ordered-by user;
        uses daemon-process;
      }
      container network-security {
        choice choice-3 {
          leaf disable {
            type empty;
          }
        }
      }
      container firewall-authentication-service {
        choice choice-3 {
          leaf disable {
            type empty;
          }
        }
      }
      container jsrp-service {
        choice choice-3 {
          leaf disable {
            type empty;
          }
        }
      }
      container wan-acceleration {
        uses apply-group;
        uses apply-macro;
        choice choice-3 {
          leaf disable {
            type empty;
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
      }
      container smtpd-service {
        choice choice-3 {
          leaf disable {
            type empty;
          }
        }
      }
      container logical-system-service {
        uses apply-group;
        uses apply-macro;
        choice choice-3 {
          leaf disable {
            type empty;
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
      }
      container rtmd {
        uses apply-group;
        uses apply-macro;
        choice choice-3 {
          leaf disable {
            type empty;
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
      }
      container wireless-wan-service {
        uses apply-group;
        uses apply-macro;
        choice choice-3 {
          leaf disable {
            type empty;
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
      }
      container wireless-lan-service {
        uses apply-group;
        uses apply-macro;
        choice choice-3 {
          leaf disable {
            type empty;
          }
        }
        container traceoptions {
          uses apply-group;
          uses apply-macro;
          leaf no-remote-trace {
            type empty;
          }
          container file {
            leaf filename {
              type string;
            }
            leaf size {
              type string;
            }
            leaf files {
              type uint32;
            }
            leaf world-readable {
              type empty;
            }
            leaf no-world-readable {
              type empty;
            }
            leaf match {
              type regular-expression;
            }
          }
          list flag {
            key "name";
            ordered-by user;
            leaf name {
              type string;
            }
          }
        }
      }
    }
    container ddos-protection {
      uses apply-group;
      uses apply-macro;
      container traceoptions {
        uses ddos-traceoptions-type;
      }
      container global {
        uses apply-group;
        uses apply-macro;
        leaf disable-routing-engine {
          type empty;
        }
        leaf disable-fpc {
          type empty;
        }
        leaf disable-logging {
          type empty;
        }
        leaf flow-detection {
          type empty;
        }
        leaf violation-report-rate {
          units "reports per second";
          type uint32;
        }
        leaf flow-report-rate {
          units "reports per second";
          type uint32;
        }
        leaf flow-detection-mode {
          type string;
        }
        leaf flow-level-control {
          type string;
        }
      }
      container protocols {
        uses apply-group;
        uses apply-macro;
        container ipv4-unclassified {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container ipv6-unclassified {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container resolve {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container other {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container ucast-v4 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container mcast-v4 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container ucast-v6 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container mcast-v6 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container filter-action {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container other {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container filter-v4 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container filter-v6 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container dynamic-vlan {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container ppp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container unclassified {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container lcp {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container authentication {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container ipcp {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container ipv6cp {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container mplscp {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container isis {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container echo-req {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container echo-rep {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container mlppp-lcp {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container pppoe {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container padi {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container pado {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container padr {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container pads {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container padt {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container padm {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container padn {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container dhcpv4 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container unclassified {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container discover {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container offer {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container request {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container decline {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container ack {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container nak {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container release {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container inform {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container renew {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container force-renew {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container lease-query {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container lease-unassigned {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container lease-unknown {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container lease-active {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container bootp {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container no-message-type {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container bad-packets {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container dhcpv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container unclassified {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container solicit {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container advertise {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container request {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container confirm {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container renew {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container rebind {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container reply {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container release {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container decline {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container reconfigure {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container information-request {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container relay-forward {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container relay-reply {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container leasequery {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container leasequery-reply {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container leasequery-done {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container leasequery-data {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container virtual-chassis {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container unclassified {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container control-high {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container control-low {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container vc-packets {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container vc-ttl-errors {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container icmp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container igmp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container ospf {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container rsvp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container pim {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container rip {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container ptp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container bfd {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container lmp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container ldp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container msdp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container bgp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container vrrp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container telnet {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container ftp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container ssh {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container snmp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container ancp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container igmpv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container egpv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container rsvpv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container igmpv4v6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container ripv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container bfdv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container lmpv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container ldpv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container msdpv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container bgpv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container vrrpv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container telnetv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container ftpv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container sshv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container snmpv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container ancpv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container ospfv3v6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container lacp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container stp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container esmc {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container oam-lfm {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container eoam {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container lldp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container mvrp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container pmvrp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container arp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
          container unclassified {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf bypass-aggregate {
              type empty;
            }
            leaf priority {
              type string;
            }
            leaf hostbound-queue {
              type uint32;
            }
          }
          container arp-snoop {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf bypass-aggregate {
              type empty;
            }
            leaf priority {
              type string;
            }
            leaf hostbound-queue {
              type uint32;
            }
          }
        }
        container pvstp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container isis {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container pos {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container mlp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container unclassified {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container lookup {
            uses apply-advanced;
            leaf bandwidth {
              units "packets per second";
              type string;
            }
            leaf burst {
              units "packets";
              type string;
            }
            leaf recover-time {
              units "seconds";
              type string;
            }
            leaf disable-routing-engine {
              type empty;
            }
            leaf disable-fpc {
              type empty;
            }
            leaf disable-logging {
              type empty;
            }
            container violation {
              status deprecated;
              uses apply-advanced;
              leaf disable-logging {
                type empty;
              }
            }
            leaf flow-detection-mode {
              type string;
            }
            container flow-level-bandwidth {
              uses apply-advanced;
              leaf subscriber {
                units "packets per second";
                type string;
              }
              leaf logical-interface {
                units "packets per second";
                type string;
              }
              leaf physical-interface {
                units "packets per second";
                type string;
              }
            }
            container flow-level-detection {
              uses apply-advanced;
              leaf subscriber {
                type string;
              }
              leaf logical-interface {
                type string;
              }
              leaf physical-interface {
                type string;
              }
            }
            container flow-level-control {
              uses apply-advanced;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type string;
            }
            leaf flow-recover-time {
              units "seconds";
              type string;
            }
            leaf flow-timeout-time {
              units "seconds";
              type string;
            }
            list fpc {
              key "name";
              ordered-by user;
              leaf name {
                type string;
              }
              uses apply-advanced;
              leaf disable-fpc {
                type empty;
              }
              leaf bandwidth-scale {
                units "percent";
                type string;
              }
              leaf burst-scale {
                units "percent";
                type string;
              }
              leaf hostbound-queue {
                type string;
              }
            }
            leaf bypass-aggregate {
              type empty;
            }
            leaf priority {
              type string;
            }
            leaf hostbound-queue {
              type string;
            }
          }
          container add {
            uses apply-advanced;
            leaf bandwidth {
              units "packets per second";
              type string;
            }
            leaf burst {
              units "packets";
              type string;
            }
            leaf recover-time {
              units "seconds";
              type string;
            }
            leaf disable-routing-engine {
              type empty;
            }
            leaf disable-fpc {
              type empty;
            }
            leaf disable-logging {
              type empty;
            }
            container violation {
              status deprecated;
              uses apply-advanced;
              leaf disable-logging {
                type empty;
              }
            }
            leaf flow-detection-mode {
              type string;
            }
            container flow-level-bandwidth {
              uses apply-advanced;
              leaf subscriber {
                units "packets per second";
                type string;
              }
              leaf logical-interface {
                units "packets per second";
                type string;
              }
              leaf physical-interface {
                units "packets per second";
                type string;
              }
            }
            container flow-level-detection {
              uses apply-advanced;
              leaf subscriber {
                type string;
              }
              leaf logical-interface {
                type string;
              }
              leaf physical-interface {
                type string;
              }
            }
            container flow-level-control {
              uses apply-advanced;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type string;
            }
            leaf flow-recover-time {
              units "seconds";
              type string;
            }
            leaf flow-timeout-time {
              units "seconds";
              type string;
            }
            list fpc {
              key "name";
              ordered-by user;
              leaf name {
                type string;
              }
              uses apply-advanced;
              leaf disable-fpc {
                type empty;
              }
              leaf bandwidth-scale {
                units "percent";
                type string;
              }
              leaf burst-scale {
                units "percent";
                type string;
              }
              leaf hostbound-queue {
                type string;
              }
            }
            leaf bypass-aggregate {
              type empty;
            }
            leaf priority {
              type string;
            }
            leaf hostbound-queue {
              type string;
            }
          }
          container delete {
            uses apply-advanced;
            leaf bandwidth {
              units "packets per second";
              type string;
            }
            leaf burst {
              units "packets";
              type string;
            }
            leaf recover-time {
              units "seconds";
              type string;
            }
            leaf disable-routing-engine {
              type empty;
            }
            leaf disable-fpc {
              type empty;
            }
            leaf disable-logging {
              type empty;
            }
            container violation {
              status deprecated;
              uses apply-advanced;
              leaf disable-logging {
                type empty;
              }
            }
            leaf flow-detection-mode {
              type string;
            }
            container flow-level-bandwidth {
              uses apply-advanced;
              leaf subscriber {
                units "packets per second";
                type string;
              }
              leaf logical-interface {
                units "packets per second";
                type string;
              }
              leaf physical-interface {
                units "packets per second";
                type string;
              }
            }
            container flow-level-detection {
              uses apply-advanced;
              leaf subscriber {
                type string;
              }
              leaf logical-interface {
                type string;
              }
              leaf physical-interface {
                type string;
              }
            }
            container flow-level-control {
              uses apply-advanced;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type string;
            }
            leaf flow-recover-time {
              units "seconds";
              type string;
            }
            leaf flow-timeout-time {
              units "seconds";
              type string;
            }
            list fpc {
              key "name";
              ordered-by user;
              leaf name {
                type string;
              }
              uses apply-advanced;
              leaf disable-fpc {
                type empty;
              }
              leaf bandwidth-scale {
                units "percent";
                type string;
              }
              leaf burst-scale {
                units "percent";
                type string;
              }
              leaf hostbound-queue {
                type string;
              }
            }
            leaf bypass-aggregate {
              type empty;
            }
            leaf priority {
              type string;
            }
            leaf hostbound-queue {
              type string;
            }
          }
          container macpin-exception {
            uses apply-advanced;
            leaf bandwidth {
              units "packets per second";
              type string;
            }
            leaf burst {
              units "packets";
              type string;
            }
            leaf recover-time {
              units "seconds";
              type string;
            }
            leaf disable-routing-engine {
              type empty;
            }
            leaf disable-fpc {
              type empty;
            }
            leaf disable-logging {
              type empty;
            }
            container violation {
              status deprecated;
              uses apply-advanced;
              leaf disable-logging {
                type empty;
              }
            }
            leaf flow-detection-mode {
              type string;
            }
            container flow-level-bandwidth {
              uses apply-advanced;
              leaf subscriber {
                units "packets per second";
                type string;
              }
              leaf logical-interface {
                units "packets per second";
                type string;
              }
              leaf physical-interface {
                units "packets per second";
                type string;
              }
            }
            container flow-level-detection {
              uses apply-advanced;
              leaf subscriber {
                type string;
              }
              leaf logical-interface {
                type string;
              }
              leaf physical-interface {
                type string;
              }
            }
            container flow-level-control {
              uses apply-advanced;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type string;
            }
            leaf flow-recover-time {
              units "seconds";
              type string;
            }
            leaf flow-timeout-time {
              units "seconds";
              type string;
            }
            list fpc {
              key "name";
              ordered-by user;
              leaf name {
                type string;
              }
              uses apply-advanced;
              leaf disable-fpc {
                type empty;
              }
              leaf bandwidth-scale {
                units "percent";
                type string;
              }
              leaf burst-scale {
                units "percent";
                type string;
              }
              leaf hostbound-queue {
                type string;
              }
            }
            leaf bypass-aggregate {
              type empty;
            }
            leaf priority {
              type string;
            }
            leaf hostbound-queue {
              type string;
            }
          }
          container packets {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container aging-exception {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container jfm {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container atm {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container pfe-alive {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container ttl {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container ip-options {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container unclassified {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container router-alert {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container non-v4v6 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container redirect {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container multicast-copy {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container exceptions {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container unclassified {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf bypass-aggregate {
              type empty;
            }
            leaf priority {
              type string;
            }
            leaf hostbound-queue {
              type uint32;
            }
          }
          container mtu-exceeded {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf bypass-aggregate {
              type empty;
            }
            leaf priority {
              type string;
            }
            leaf hostbound-queue {
              type uint32;
            }
          }
          container mcast-rpf-err {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf bypass-aggregate {
              type empty;
            }
            leaf priority {
              type string;
            }
            leaf hostbound-queue {
              type uint32;
            }
          }
        }
        container mac-host {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container tunnel-fragment {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container mcast-snoop {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container unclassified {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container igmp {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container pim {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container services {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container packet {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container bsdt {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container demux-autosense {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container reject {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container firewall-host {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container tcp-flags {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container unclassified {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container initial {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container established {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container dtcp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container radius {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container server {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container accounting {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container authorization {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container ntp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container tacacs {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container dns {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container diameter {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container ip-fragments {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container first-fragment {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container trail-fragment {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container l2tp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container gre {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container pimv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container icmpv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container ndpv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container router-solicitation {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf bypass-aggregate {
              type empty;
            }
            leaf priority {
              type string;
            }
            leaf hostbound-queue {
              type uint32;
            }
          }
          container router-advertisement {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf bypass-aggregate {
              type empty;
            }
            leaf priority {
              type string;
            }
            leaf hostbound-queue {
              type uint32;
            }
          }
          container neighbor-solicitation {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf bypass-aggregate {
              type empty;
            }
            leaf priority {
              type string;
            }
            leaf hostbound-queue {
              type uint32;
            }
          }
          container neighbor-advertisement {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf bypass-aggregate {
              type empty;
            }
            leaf priority {
              type string;
            }
            leaf hostbound-queue {
              type uint32;
            }
          }
          container redirect {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf bypass-aggregate {
              type empty;
            }
            leaf priority {
              type string;
            }
            leaf hostbound-queue {
              type uint32;
            }
          }
          container invalid-hop-limit {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf bypass-aggregate {
              type empty;
            }
            leaf priority {
              type string;
            }
            leaf hostbound-queue {
              type uint32;
            }
          }
        }
        container sample {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container syslog {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container host {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container pfe {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container tap {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container sflow {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container re-services {
          uses apply-group;
          uses apply-macro;
          container apply-advanced {
            uses apply-group;
            uses apply-macro;
          }
          container aggregate {
            uses apply-group;
            uses apply-macro;
            container apply-advanced {
              uses apply-group;
              uses apply-macro;
            }
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              container apply-advanced {
                uses apply-group;
                uses apply-macro;
              }
              leaf disable-logging {
                type empty;
              }
            }
            leaf flow-detection-mode {
              type string;
            }
            container flow-level-bandwidth {
              uses apply-group;
              uses apply-macro;
              container apply-advanced {
                uses apply-group;
                uses apply-macro;
              }
              leaf subscriber {
                units "packets per second";
                type uint32;
              }
              leaf logical-interface {
                units "packets per second";
                type uint32;
              }
              leaf physical-interface {
                units "packets per second";
                type uint32;
              }
            }
            container flow-level-detection {
              uses apply-group;
              uses apply-macro;
              container apply-advanced {
                uses apply-group;
                uses apply-macro;
              }
              leaf subscriber {
                type string;
              }
              leaf logical-interface {
                type string;
              }
              leaf physical-interface {
                type string;
              }
            }
            container flow-level-control {
              uses apply-group;
              uses apply-macro;
              container apply-advanced {
                uses apply-group;
                uses apply-macro;
              }
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              container apply-advanced {
                uses apply-group;
                uses apply-macro;
              }
              leaf disable-fpc {
                type empty;
              }
              leaf bandwidth-scale {
                units "percent";
                type uint32;
              }
              leaf burst-scale {
                units "percent";
                type uint32;
              }
            }
          }
          container captive-portal {
            uses apply-group;
            uses apply-macro;
            container apply-advanced {
              uses apply-group;
              uses apply-macro;
            }
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              container apply-advanced {
                uses apply-group;
                uses apply-macro;
              }
              leaf disable-logging {
                type empty;
              }
            }
            leaf flow-detection-mode {
              type string;
            }
            container flow-level-bandwidth {
              uses apply-group;
              uses apply-macro;
              container apply-advanced {
                uses apply-group;
                uses apply-macro;
              }
              leaf subscriber {
                units "packets per second";
                type uint32;
              }
              leaf logical-interface {
                units "packets per second";
                type uint32;
              }
              leaf physical-interface {
                units "packets per second";
                type uint32;
              }
            }
            container flow-level-detection {
              uses apply-group;
              uses apply-macro;
              container apply-advanced {
                uses apply-group;
                uses apply-macro;
              }
              leaf subscriber {
                type string;
              }
              leaf logical-interface {
                type string;
              }
              leaf physical-interface {
                type string;
              }
            }
            container flow-level-control {
              uses apply-group;
              uses apply-macro;
              container apply-advanced {
                uses apply-group;
                uses apply-macro;
              }
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              container apply-advanced {
                uses apply-group;
                uses apply-macro;
              }
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container re-services-v6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
          container captive-portal {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf bypass-aggregate {
              type empty;
            }
            leaf priority {
              type string;
            }
            leaf hostbound-queue {
              type uint32;
            }
          }
        }
        container fab-probe {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container unclassified {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container other {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container resolve-v4 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container resolve-v6 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container control-v4 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container control-v6 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container host-route-v4 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container host-route-v6 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container filter-v4 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container filter-v6 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container control-layer2 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container fw-host {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container mcast-copy {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container rejectv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container l2pt {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container keepalive {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container tunnel-ka {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container inline-ka {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container inline-svcs {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container frame-relay {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
          container frf15 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
          container frf16 {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
            leaf bypass-aggregate {
              type empty;
            }
            leaf priority {
              type string;
            }
          }
        }
        container amtv4 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container amtv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
            }
          }
        }
        container syslog {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container pim-ctrl {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container ospf-hello {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container pim-data {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container fip-snooping {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container unknown-l2mc {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container nonucast-switch {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container ipmcast-miss {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container urpf-fail {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container l3nhop {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container martian-address {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container l3mc-sgv-hit-icl {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container l3dest-miss {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container ipmc-reserved {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container garp-reply {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container l3mtu-fail {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container sample-dest {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container sample-source {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container vcipc-udp {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container vxlan {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
          container bfd {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf bypass-aggregate {
              type empty;
            }
            leaf priority {
              type string;
            }
            leaf hostbound-queue {
              type uint32;
            }
          }
        }
        container dhcpv4v6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container localnh {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container proto-802-1x {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container all-fiber-channel-enode {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container tcc {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
          container unclassified {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf bypass-aggregate {
              type empty;
            }
            leaf priority {
              type string;
            }
            leaf hostbound-queue {
              type uint32;
            }
          }
          container ethernet-tcc {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf bypass-aggregate {
              type empty;
            }
            leaf priority {
              type string;
            }
            leaf hostbound-queue {
              type uint32;
            }
          }
          container iso-tcc {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf bypass-aggregate {
              type empty;
            }
            leaf priority {
              type string;
            }
            leaf hostbound-queue {
              type uint32;
            }
          }
        }
        container pkt-inject {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
        container ptpv6 {
          uses apply-group;
          uses apply-macro;
          container aggregate {
            uses apply-group;
            uses apply-macro;
            leaf bandwidth {
              units "packets per second";
              type uint32;
            }
            leaf burst {
              units "packets";
              type uint32;
            }
            leaf recover-time {
              units "seconds";
              type uint32;
            }
            leaf disable-routing-engine {
              type empty;
            }
            leaf disable-fpc {
              type empty;
            }
            leaf disable-logging {
              type empty;
            }
            container violation {
              uses apply-group;
              uses apply-macro;
              leaf disable-logging {
                type empty;
              }
            }
            leaf flow-detection-mode {
              type string;
            }
            container flow-level-bandwidth {
              uses apply-group;
              uses apply-macro;
              leaf subscriber {
                units "packets per second";
                type uint32;
              }
              leaf logical-interface {
                units "packets per second";
                type uint32;
              }
              leaf physical-interface {
                units "packets per second";
                type uint32;
              }
            }
            container flow-level-detection {
              uses apply-group;
              uses apply-macro;
              leaf subscriber {
                type string;
              }
              leaf logical-interface {
                type string;
              }
              leaf physical-interface {
                type string;
              }
            }
            container flow-level-control {
              uses apply-group;
              uses apply-macro;
              leaf subscriber {
                type string;
              }
              leaf logical-interface {
                type string;
              }
              leaf physical-interface {
                type string;
              }
            }
            leaf no-flow-logging {
              type empty;
            }
            leaf timeout-active-flows {
              type empty;
            }
            leaf flow-detect-time {
              units "seconds";
              type uint32;
            }
            leaf flow-recover-time {
              units "seconds";
              type uint32;
            }
            leaf flow-timeout-time {
              units "seconds";
              type uint32;
            }
            list fpc {
              key "name";
              ordered-by user;
              leaf name {
                type key-attribute-ulong-type;
              }
              uses apply-group;
              uses apply-macro;
              leaf disable-fpc {
                type empty;
              }
              leaf bandwidth-scale {
                units "percent";
                type uint32;
              }
              leaf burst-scale {
                units "percent";
                type uint32;
              }
              leaf hostbound-queue {
                type uint32;
              }
            }
            leaf hostbound-queue {
              type uint32;
            }
          }
        }
      }
    }
    container packet-triggered-subscribers-partition {
      uses apply-group;
      uses apply-macro;
      leaf partition-name {
        type string;
      }
    }
    container ntp {
      presence "enable ntp";
      uses apply-group;
      uses apply-macro;
      leaf boot-server {
        type string;
      }
      list authentication-key {
        key "name";
        ordered-by user;
        leaf name {
          type uint32;
        }
        leaf type {
          type string;
        }
        leaf value {
          type unreadable;
        }
      }
      list peer {
        key "name";
        ordered-by user;
        leaf name {
          type ipaddr;
        }
        leaf key {
          type uint32;
        }
        leaf version {
          type uint32;
        }
        leaf prefer {
          type empty;
        }
      }
      list server {
        key "name";
        ordered-by user;
        leaf name {
          type hostname;
        }
        leaf key {
          type string;
        }
        leaf version {
          type uint32;
        }
        leaf prefer {
          type empty;
        }
        leaf routing-instance {
          type string;
        }
      }
      list broadcast {
        key "name";
        ordered-by user;
        leaf name {
          type ipaddr;
        }
        leaf routing-instance-name {
          type string;
        }
        leaf key {
          type uint32;
        }
        leaf version {
          type uint32;
        }
        leaf ttl {
          type uint32;
        }
      }
      leaf broadcast-client {
        type empty;
      }
      container multicast-client {
        presence "enable multicast-client";
        leaf address {
          type ipaddr;
        }
      }
      leaf-list trusted-key {
        type uint32;
        ordered-by user;
      }
      list restrict {
        key "name";
        ordered-by user;
        leaf name {
          type string;
        }
        leaf mask {
          type string;
        }
        leaf noquery {
          type empty;
        }
      }
      list source-address {
        key "name";
        ordered-by user;
        leaf name {
          type ipaddr;
        }
        leaf-list routing-instance {
          type string;
          ordered-by user;
        }
      }
    }
    container security-profile {
      uses apply-group;
      uses apply-macro;
      container resources {
        presence "enable resources";
        uses apply-group;
        uses apply-macro;
        leaf cpu-control {
          type empty;
        }
        leaf cpu-control-target {
          units "percent";
          type string;
        }
      }
      list profile {
        key "name";
        uses profile-type;
      }
    }
    container dynamic-profile-options {
      presence "";
      uses dynamic-profile-option-object;
    }
    container auto-sw-sync {
      leaf enable {
        type empty;
      }
    }
  }

  grouping archive-object {
    uses apply-group;
    uses apply-macro;
    leaf size {
      type string;
    }
    leaf files {
      type string;
    }
    leaf world-readable {
      type empty;
    }
    leaf no-world-readable {
      type empty;
    }
    leaf transfer-interval {
      type uint32;
    }
    leaf start-time {
      type time;
    }
    list archive-sites {
      key "name";
      ordered-by user;
      leaf name {
        type string;
      }
      leaf password {
        type unreadable;
      }
    }
  }

  grouping arp-interface-type {
    leaf name {
      type interface-name;
    }
    uses apply-group;
    uses apply-macro;
    leaf aging-timer {
      type uint32;
    }
  }

  grouping authentication-object {
    uses apply-group;
    uses apply-macro;
    leaf plain-text-password-value {
      type string;
    }
    leaf encrypted-password {
      type string;
    }
    leaf no-public-keys {
      type empty;
    }
    list ssh-rsa {
      key "name";
      ordered-by user;
      leaf name {
        type string;
      }
      leaf from {
        type string;
      }
    }
    list ssh-dsa {
      key "name";
      ordered-by user;
      leaf name {
        type string;
      }
      leaf from {
        type string;
      }
    }
    list ssh-ecdsa {
      key "name";
      ordered-by user;
      leaf name {
        type string;
      }
      leaf from {
        type string;
      }
    }
    list ssh-ed25519 {
      key "name";
      ordered-by user;
      leaf name {
        type string;
      }
      leaf from {
        type string;
      }
    }
  }

  grouping autoconf-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping bbe-smgd-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping bdbrepd-type {
    uses apply-group;
    uses apply-macro;
    container traceoptions {
      uses bdbrepd-traceoptions-type;
    }
  }

  grouping bdbrepd-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    list flag {
      key "name";
      ordered-by user;
      leaf name {
        type string;
      }
    }
  }

  grouping daemon-process {
    leaf name {
      type string;
    }
    uses apply-group;
    uses apply-macro;
    choice choice-3 {
      leaf disable {
        type empty;
      }
    }
    leaf failover {
      type string;
    }
    leaf command {
      type string;
    }
  }

  grouping datapath-traced-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping ddos-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping dhcp-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping jptspd-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    list flag {
      key "name";
      ordered-by user;
      leaf name {
        type string;
      }
    }
  }

  grouping jsavald-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping juniper-transport-profiles {
    leaf name {
      type key-attribute-string-type;
    }
    uses apply-group;
    uses apply-macro;
    leaf description {
      type string;
    }
    container online {
      presence "";
      uses apply-group;
      uses apply-macro;
      leaf tx-timeout {
        type uint32;
      }
      leaf session-failover-not-supported {
        type empty;
      }
      leaf diameter-profile {
        type string;
      }
      leaf service-context-id {
        type string;
      }
      leaf charging-function-name {
        type string;
      }
      leaf single-mscc {
        type empty;
      }
      leaf no-mscc-in-ccrt {
        type empty;
      }
      leaf no-initiate-session-on-activation {
        type empty;
      }
      leaf quota-request-on-activation {
        type empty;
      }
      leaf all-rgs-on-termination {
        type empty;
      }
    }
    container offline {
      presence "enable offline";
      uses apply-group;
      uses apply-macro;
      container charging-gateways {
        presence "enable charging-gateways";
        uses apply-group;
        uses apply-macro;
        leaf cdr-release {
          type string;
        }
        container peer-order {
          presence "enable peer-order";
          uses apply-group;
          uses apply-macro;
          list peer {
            key "name";
            ordered-by user;
            leaf name {
              type key-attribute-string-type;
            }
            uses apply-group;
            uses apply-macro;
          }
        }
        container persistent-storage-order {
          presence "enable persistent-storage-order";
          uses apply-group;
          uses apply-macro;
          leaf local-storage {
            type empty;
          }
        }
        leaf switch-back-time {
          units "seconds";
          type uint16;
        }
        leaf cdr-aggregation-limit {
          type uint16;
        }
        leaf mtu {
          type uint16;
        }
      }
      leaf charging-function-name {
        type string;
      }
      leaf container-limit {
        type uint16;
      }
      leaf sgsn-mme-change-limit {
        type uint16;
      }
    }
    leaf service-mode {
      type string;
    }
  }

  grouping juniper-trigger-profiles {
    leaf name {
      type key-attribute-string-type;
    }
    uses apply-group;
    uses apply-macro;
    leaf description {
      type string;
    }
    list tariff-time-list {
      key "name";
      leaf name {
        type time;
      }
      uses apply-group;
      uses apply-macro;
    }
    container offline {
      presence "enable offline";
      uses apply-group;
      uses apply-macro;
      container volume-limit {
        presence "";
        leaf vlimit {
          type string;
        }
        leaf direction {
          type string;
        }
      }
      leaf time-limit {
        units "seconds";
        type uint32;
      }
      container exclude {
        uses apply-group;
        uses apply-macro;
        leaf plmn-change {
          type empty;
        }
        leaf qos-change {
          type empty;
        }
        leaf rat-change {
          type empty;
        }
        leaf sgsn-sgw-change {
          type empty;
        }
        leaf user-location-change {
          type empty;
        }
        leaf ms-timezone-change {
          type empty;
        }
        leaf dcca-events {
          type empty;
        }
      }
    }
    leaf charging-method {
      type string;
    }
    container online {
      presence "enable online";
      uses apply-group;
      uses apply-macro;
      container reporting-level {
        presence "enable reporting-level";
        uses apply-group;
        uses apply-macro;
        choice choice-rating-group {
          leaf rating-group {
            type empty;
          }
          leaf service-identifier {
            type empty;
          }
        }
        leaf override {
          type empty;
        }
      }
      leaf measurement-method {
        type string;
      }
      container quota-threshold {
        presence "enable quota-threshold";
        uses apply-group;
        uses apply-macro;
        leaf threshold {
          units "percent";
          type uint32;
        }
        leaf override {
          type empty;
        }
      }
      leaf quota-validity-time {
        units "seconds";
        type uint32;
      }
      leaf quota-holding-time {
        units "seconds";
        type uint32;
      }
      container grant-quota {
        presence "enable grant-quota";
        uses apply-group;
        uses apply-macro;
        leaf cc-time {
          units "seconds";
          type uint32;
        }
        leaf cc-octet-uplink {
          units "bytes";
          type uint64;
        }
        leaf cc-octet-downlink {
          units "bytes";
          type uint64;
        }
        leaf cc-octet-both {
          units "bytes";
          type uint64;
        }
      }
      container requested-service-unit {
        presence "enable requested-service-unit";
        uses apply-group;
        uses apply-macro;
        leaf include-quota-holding-time {
          type empty;
        }
        leaf cc-time {
          units "seconds";
          type uint32;
        }
        leaf cc-octet-uplink {
          units "bytes";
          type uint64;
        }
        leaf cc-octet-downlink {
          units "bytes";
          type uint64;
        }
        leaf cc-octet-both {
          units "bytes";
          type uint64;
        }
      }
      container cc-failure-handling {
        uses apply-group;
        uses apply-macro;
        leaf block-traffic-pending-reauth-no-quota {
          type empty;
        }
        leaf override {
          type empty;
        }
        container result-code-based-action {
          uses apply-group;
          uses apply-macro;
          container authorization-rejected {
            uses apply-group;
            uses apply-macro;
            container blacklist {
              presence "enable blacklist";
              leaf retry-timer {
                units "seconds";
                type uint32;
              }
            }
          }
          container credit-control-not-applicable {
            uses apply-group;
            uses apply-macro;
            container convert-to-offline {
              presence "enable convert-to-offline";
              uses apply-group;
              uses apply-macro;
              leaf grant-grace-quota {
                type empty;
              }
            }
          }
          container end-user-service-denied {
            uses apply-group;
            uses apply-macro;
            choice choice-disable-online-charging {
              leaf disable-online-charging {
                type empty;
              }
              container convert-to-offline {
                presence "enable convert-to-offline";
                uses apply-group;
                uses apply-macro;
                leaf grant-grace-quota {
                  type empty;
                }
              }
            }
          }
          container user-unknown {
            uses apply-group;
            uses apply-macro;
            choice choice-disable-online-charging {
              leaf disable-online-charging {
                type empty;
              }
              container convert-to-offline {
                presence "enable convert-to-offline";
                uses apply-group;
                uses apply-macro;
                leaf grant-grace-quota {
                  type empty;
                }
              }
            }
          }
          container credit-limit-reached {
            uses apply-group;
            uses apply-macro;
            container blacklist {
              presence "enable blacklist";
              leaf retry-timer {
                units "seconds";
                type uint32;
              }
            }
          }
        }
        container initial-request {
          presence "enable initial-request";
          uses apply-group;
          uses apply-macro;
          choice choice-grant-grace-quota {
            leaf grant-grace-quota {
              type empty;
            }
            leaf disable-online-charging {
              type empty;
            }
            container convert-to-offline {
              presence "enable convert-to-offline";
              uses apply-group;
              uses apply-macro;
              leaf grant-grace-quota {
                type empty;
              }
            }
          }
        }
        container update-request {
          presence "enable update-request";
          uses apply-group;
          uses apply-macro;
          choice choice-grant-grace-quota {
            leaf grant-grace-quota {
              type empty;
            }
            leaf disable-online-charging {
              type empty;
            }
            container convert-to-offline {
              presence "enable convert-to-offline";
              uses apply-group;
              uses apply-macro;
              leaf grant-grace-quota {
                type empty;
              }
            }
          }
        }
      }
    }
  }

  grouping juniper-unified-edge-cos-options {
    uses apply-group;
    uses apply-macro;
    list classifier-profiles {
      key "name";
      ordered-by user;
      leaf name {
        type string;
      }
      uses apply-group;
      uses apply-macro;
      leaf description {
        type string;
      }
      list qos-class-identifier {
        key "name";
        ordered-by user;
        leaf name {
          type key-attribute-ulong-type;
        }
        leaf forwarding-class {
          type string;
        }
        leaf loss-priority {
          type string;
        }
      }
    }
    list gbr-bandwidth-pools {
      key "name";
      ordered-by user;
      leaf name {
        type string;
      }
      uses apply-group;
      uses apply-macro;
      leaf maximum-bandwidth {
        units "mega-bits per second";
        type uint32;
      }
      leaf downgrade-gtp-v1-gbr-bearers {
        type empty;
      }
    }
    list resource-threshold-profiles {
      key "name";
      ordered-by user;
      leaf name {
        type string;
      }
      uses apply-group;
      uses apply-macro;
      leaf description {
        type string;
      }
      container bearers-load {
        uses apply-group;
        uses apply-macro;
        container low {
          presence "";
          uses apply-group;
          uses apply-macro;
          leaf percentage {
            units "Percentage";
            type uint32;
          }
          leaf priority-level {
            type uint32;
          }
        }
        container high {
          presence "";
          uses apply-group;
          uses apply-macro;
          leaf percentage {
            units "Percentage";
            type uint32;
          }
          leaf priority-level {
            type uint32;
          }
        }
      }
      container memory {
        uses apply-group;
        uses apply-macro;
        container low {
          presence "";
          uses apply-group;
          uses apply-macro;
          leaf percentage {
            units "Percentage";
            type uint32;
          }
          leaf priority-level {
            type uint32;
          }
        }
        container high {
          presence "";
          uses apply-group;
          uses apply-macro;
          leaf percentage {
            units "Percentage";
            type uint32;
          }
          leaf priority-level {
            type uint32;
          }
        }
      }
      container cpu {
        uses apply-group;
        uses apply-macro;
        container low {
          presence "";
          uses apply-group;
          uses apply-macro;
          leaf percentage {
            units "Percentage";
            type uint32;
          }
          leaf priority-level {
            type uint32;
          }
        }
        container high {
          presence "";
          uses apply-group;
          uses apply-macro;
          leaf percentage {
            units "Percentage";
            type uint32;
          }
          leaf priority-level {
            type uint32;
          }
        }
      }
    }
    list cos-policy-profiles {
      key "name";
      ordered-by user;
      leaf name {
        type string;
      }
      uses apply-group;
      uses apply-macro;
      leaf description {
        type string;
      }
      container default-bearer-qci {
        presence "";
        leaf qci-value {
          type uint8;
        }
        leaf upgrade {
          type empty;
        }
        leaf reject {
          type empty;
        }
      }
      container allocation-retention-priority {
        leaf priority-value {
          type uint8;
        }
        leaf reject {
          type empty;
        }
      }
      container aggregated-qos-control {
        uses apply-group;
        uses apply-macro;
        container maximum-bit-rate-uplink {
          presence "";
          leaf mbr-uplink {
            units "kbps";
            type uint32;
          }
          leaf upgrade {
            type empty;
          }
          leaf reject {
            type empty;
          }
        }
        container maximum-bit-rate-downlink {
          presence "";
          leaf mbr-downlink {
            units "kbps";
            type uint32;
          }
          leaf upgrade {
            type empty;
          }
          leaf reject {
            type empty;
          }
        }
      }
      container pdp-qos-control {
        uses apply-group;
        uses apply-macro;
        container maximum-bit-rate-uplink {
          presence "";
          leaf mbr-uplink {
            units "kbps";
            type uint32;
          }
          leaf upgrade {
            type empty;
          }
          leaf reject {
            type empty;
          }
        }
        container maximum-bit-rate-downlink {
          presence "";
          leaf mbr-downlink {
            units "kbps";
            type uint32;
          }
          leaf upgrade {
            type empty;
          }
          leaf reject {
            type empty;
          }
        }
        container guaranteed-bit-rate-uplink {
          presence "";
          leaf gbr-uplink {
            units "kbps";
            type uint32;
          }
          leaf upgrade {
            type empty;
          }
          leaf reject {
            type empty;
          }
        }
        container guaranteed-bit-rate-downlink {
          presence "";
          leaf gbr-downlink {
            units "kbps";
            type uint32;
          }
          leaf upgrade {
            type empty;
          }
          leaf reject {
            type empty;
          }
        }
        list qci {
          key "name";
          ordered-by user;
          leaf name {
            type key-attribute-ulong-type;
          }
          uses apply-group;
          uses apply-macro;
          container maximum-bit-rate-uplink {
            presence "";
            leaf mbr-uplink {
              units "kbps";
              type uint32;
            }
            leaf upgrade {
              type empty;
            }
            leaf reject {
              type empty;
            }
          }
          container maximum-bit-rate-downlink {
            presence "";
            leaf mbr-downlink {
              units "kbps";
              type uint32;
            }
            leaf upgrade {
              type empty;
            }
            leaf reject {
              type empty;
            }
          }
        }
      }
      container policer-action {
        uses apply-group;
        uses apply-macro;
        container non-gbr-bearer {
          uses apply-group;
          uses apply-macro;
          leaf violate-action {
            type string;
          }
        }
        container gbr-bearer {
          uses apply-group;
          uses apply-macro;
          leaf exceed-action {
            type string;
          }
          leaf violate-action {
            type string;
          }
        }
      }
    }
  }

  grouping juniper-virtual-chassis-traceoptions {
    uses apply-group;
    uses apply-macro;
    container file {
      presence "";
      uses vchassis-trace-file-type;
    }
    list flag {
      key "name";
      ordered-by user;
      leaf name {
        type string;
      }
      leaf send {
        type empty;
      }
      leaf receive {
        type empty;
      }
      leaf detail {
        type empty;
      }
      leaf disable {
        type empty;
      }
    }
  }

  grouping juniper-accounting-options {
    uses apply-group;
    uses apply-macro;
    container selective-aggregate-interface-stats {
      leaf enable-disable {
        type string;
      }
      leaf disable {
        type empty;
      }
    }
    container periodic-refresh {
      leaf enable-disable {
        type string;
      }
      leaf disable {
        type empty;
      }
    }
    list policy-decision-statistics-profile {
      key "name";
      ordered-by user;
      leaf name {
        type key-attribute-string-type;
      }
      uses apply-group;
      uses apply-macro;
      leaf file {
        type string;
      }
      container application-aware-access-list-fields {
        uses apply-group;
        uses apply-macro;
        leaf address {
          type empty;
        }
        leaf application {
          type empty;
        }
        leaf application-group {
          type empty;
        }
        leaf input-bytes {
          type empty;
        }
        leaf input-interface {
          type empty;
        }
        leaf input-packets {
          type empty;
        }
        leaf mask {
          type empty;
        }
        leaf output-bytes {
          type empty;
        }
        leaf output-packets {
          type empty;
        }
        leaf subscriber-name {
          type empty;
        }
        leaf timestamp {
          type empty;
        }
        leaf vrf-name {
          type empty;
        }
      }
    }
    list file {
      key "name";
      ordered-by user;
      leaf name {
        type string;
      }
      uses apply-group;
      uses apply-macro;
      leaf nonpersistent {
        type empty;
      }
      leaf size {
        type string;
      }
      leaf files {
        type uint32;
      }
      leaf transfer-interval {
        type uint32;
      }
      leaf start-time {
        type time;
      }
      list archive-sites {
        key "name";
        ordered-by user;
        leaf name {
          type string;
        }
        leaf password {
          type unreadable;
        }
      }
    }
    list interface-profile {
      key "name";
      ordered-by user;
      leaf name {
        type string;
      }
      uses apply-group;
      uses apply-macro;
      leaf file {
        type string;
      }
      leaf interval {
        type uint32;
      }
      container fields {
        uses apply-group;
        uses apply-macro;
        leaf input-bytes {
          type empty;
        }
        leaf output-bytes {
          type empty;
        }
        leaf input-packets {
          type empty;
        }
        leaf output-packets {
          type empty;
        }
        leaf input-errors {
          type empty;
        }
        leaf output-errors {
          type empty;
        }
        leaf input-multicast {
          type empty;
        }
        leaf output-multicast {
          type empty;
        }
        leaf input-unicast {
          type empty;
        }
        leaf output-unicast {
          type empty;
        }
        leaf unsupported-protocol {
          type empty;
        }
        leaf rpf-check-bytes {
          type empty;
        }
        leaf rpf-check-packets {
          type empty;
        }
        leaf rpf-check6-bytes {
          type empty;
        }
        leaf rpf-check6-packets {
          type empty;
        }
      }
    }
    list filter-profile {
      key "name";
      ordered-by user;
      leaf name {
        type string;
      }
      uses apply-group;
      uses apply-macro;
      leaf file {
        type string;
      }
      leaf interval {
        type uint32;
      }
      list counters {
        key "name";
        ordered-by user;
        uses counter-object;
      }
    }
    list class-usage-profile {
      key "name";
      ordered-by user;
      leaf name {
        type string;
      }
      uses apply-group;
      uses apply-macro;
      leaf file {
        type string;
      }
      leaf interval {
        type uint32;
      }
      choice choice-7 {
        list destination-classes {
          key "name";
          ordered-by user;
          uses dest-class-name-object;
        }
        list source-classes {
          key "name";
          ordered-by user;
          uses source-class-name-object;
        }
      }
    }
    list routing-engine-profile {
      key "name";
      ordered-by user;
      leaf name {
        type string;
      }
      uses apply-group;
      uses apply-macro;
      leaf file {
        type string;
      }
      leaf interval {
        type uint32;
      }
      container fields {
        uses apply-group;
        uses apply-macro;
        leaf host-name {
          type empty;
        }
        leaf date {
          type empty;
        }
        leaf time-of-day {
          type empty;
        }
        leaf uptime {
          type empty;
        }
        leaf cpu-load-1 {
          type empty;
        }
        leaf cpu-load-5 {
          type empty;
        }
        leaf cpu-load-15 {
          type empty;
        }
        leaf memory-usage {
          type empty;
        }
        leaf total-cpu-usage {
          type empty;
        }
      }
    }
    list mib-profile {
      key "name";
      ordered-by user;
      leaf name {
        type string;
      }
      uses apply-group;
      uses apply-macro;
      leaf file {
        type string;
      }
      leaf interval {
        type uint32;
      }
      leaf operation {
        type string;
      }
      list object-names {
        key "name";
        ordered-by user;
        uses mib-variable-name-object;
      }
    }
  }

  grouping counter-object {
    leaf name {
      type string;
    }
    uses apply-group;
    uses apply-macro;
  }

  grouping dest-class-name-object {
    leaf name {
      type string;
    }
    uses apply-group;
    uses apply-macro;
  }

  grouping junos-hash-key {
    uses apply-group;
    uses apply-macro;
    container family {
      uses apply-group;
      uses apply-macro;
      container fcoe {
        uses apply-group;
        uses apply-macro;
        container ethernet-interfaces {
          uses apply-group;
          uses apply-macro;
          leaf oxid {
            type string;
          }
        }
        container fabric-interfaces {
          uses apply-group;
          uses apply-macro;
          leaf oxid {
            type string;
          }
        }
        leaf oxid {
          type string;
        }
      }
      container inet {
        uses apply-group;
        uses apply-macro;
        container layer-3 {
          presence "enable layer-3";
          uses apply-group;
          uses apply-macro;
          leaf destination-address {
            type empty;
          }
        }
        container layer-4 {
          presence "enable layer-4";
          uses apply-group;
          uses apply-macro;
          leaf gtp-tunnel-endpoint-identifier {
            type empty;
          }
        }
        leaf session-id {
          type empty;
        }
        container symmetric-hash {
          presence "enable symmetric-hash";
          uses apply-group;
          uses apply-macro;
          leaf complement {
            type empty;
          }
        }
      }
      container inet6 {
        uses apply-group;
        uses apply-macro;
        container layer-3 {
          presence "enable layer-3";
          uses apply-group;
          uses apply-macro;
          leaf destination-address {
            type empty;
          }
          leaf incoming-interface-index {
            type empty;
          }
          leaf next-header {
            type empty;
          }
          leaf source-address {
            type empty;
          }
          leaf traffic-class {
            type empty;
          }
          leaf ipv6-flow-label {
            type empty;
          }
        }
        container layer-4 {
          presence "enable layer-4";
          uses apply-group;
          uses apply-macro;
          leaf destination-port {
            type empty;
          }
          leaf source-port {
            type empty;
          }
          leaf gtp-tunnel-endpoint-identifier {
            type empty;
          }
        }
        leaf session-id {
          type empty;
        }
      }
      container mpls {
        uses apply-group;
        uses apply-macro;
        choice choice-label-1 {
          leaf label-1 {
            type empty;
          }
          leaf all-labels {
            type empty;
          }
          leaf no-labels {
            type empty;
          }
          leaf bottom-label-1 {
            type empty;
          }
        }
        leaf label-2 {
          type empty;
        }
        leaf label-3 {
          type empty;
        }
        leaf bottom-label-2 {
          type empty;
        }
        leaf bottom-label-3 {
          type empty;
        }
        leaf no-label-1-exp {
          type empty;
        }
        container payload {
          uses apply-group;
          uses apply-macro;
          container ether-pseudowire {
            presence "enable ether-pseudowire";
            uses apply-group;
            uses apply-macro;
            leaf zero-control-word {
              type empty;
            }
          }
          container ip {
            presence "enable ip";
            uses apply-group;
            uses apply-macro;
            choice choice-port-data {
              leaf layer-3-only {
                type empty;
              }
              leaf enable {
                type empty;
              }
              leaf disable {
                type empty;
              }
              container port-data {
                presence "enable port-data";
                uses apply-group;
                uses apply-macro;
                leaf source-msb {
                  type empty;
                }
                leaf source-lsb {
                  type empty;
                }
                leaf destination-msb {
                  type empty;
                }
                leaf destination-lsb {
                  type empty;
                }
              }
            }
          }
        }
      }
      container multiservice {
        uses apply-group;
        uses apply-macro;
        leaf source-mac {
          type empty;
        }
        leaf destination-mac {
          type empty;
        }
        leaf label-1 {
          type empty;
        }
        leaf label-2 {
          type empty;
        }
        container payload {
          uses apply-group;
          uses apply-macro;
          container ip {
            uses apply-group;
            uses apply-macro;
            container layer-3 {
              presence "enable layer-3";
              uses apply-group;
              uses apply-macro;
              choice choice-source-ip-only {
                leaf source-ip-only {
                  type empty;
                }
                leaf destination-ip-only {
                  type empty;
                }
              }
            }
            leaf layer-4 {
              type empty;
            }
            leaf layer-3-only {
              type empty;
            }
          }
        }
        container symmetric-hash {
          presence "enable symmetric-hash";
          uses apply-group;
          uses apply-macro;
          leaf complement {
            type empty;
          }
        }
      }
    }
  }

  grouping keepalives-type {
    uses apply-group;
    uses apply-macro;
    leaf interval {
      type uint16;
    }
    leaf up-count {
      type uint16;
    }
    leaf down-count {
      type uint16;
    }
  }

  grouping l2tp-destination-object {
    uses apply-group;
    uses apply-macro;
    leaf lockout-timeout {
      type uint16;
    }
    list address {
      key "name";
      ordered-by user;
      leaf name {
        type ipv4addr;
      }
      container access-line-information {
        presence "enable access-line-information";
        uses apply-group;
        uses apply-macro;
        leaf connection-speed-update {
          type empty;
        }
      }
      list routing-instance {
        key "name";
        ordered-by user;
        leaf name {
          type string;
        }
        leaf drain {
          type empty;
        }
      }
      leaf drain {
        type empty;
      }
    }
    list name {
      key "name";
      ordered-by user;
      leaf name {
        type key-attribute-string-type;
      }
      leaf drain {
        type empty;
      }
    }
  }

  grouping l2tp-interface-traceoptions {
    leaf name {
      type interface-device;
    }
    uses apply-group;
    uses apply-macro;
    list flag {
      key "name";
      ordered-by user;
      leaf name {
        type string;
      }
    }
    leaf debug-level {
      type string;
    }
  }

  grouping l2tp-tunnel-group-object {
    leaf name {
      type key-attribute-string-type;
    }
    uses apply-group;
    uses apply-macro;
    leaf l2tp-access-profile {
      type string;
    }
    leaf ppp-access-profile {
      type string;
    }
    leaf aaa-access-profile {
      type string;
    }
    leaf receive-window {
      type uint16;
    }
    leaf maximum-send-window {
      type uint16;
    }
    leaf retransmit-interval {
      type uint16;
    }
    leaf hello-interval {
      type uint16;
    }
    leaf hide-avps {
      type empty;
    }
    leaf no-tos-reflect {
      type empty;
    }
    leaf tos-reflect {
      type empty;
    }
    leaf tunnel-timeout {
      type uint16;
    }
    container local-gateway {
      presence "enable local-gateway";
      uses apply-group;
      uses apply-macro;
      leaf address {
        type ipv4addr;
      }
      leaf gateway-name {
        type string;
      }
    }
    choice choice-service-interface {
      leaf service-interface {
        type interface-unit;
      }
      leaf service-device-pool {
        type string;
      }
    }
    leaf dynamic-profile {
      type string;
    }
    leaf tunnel-switch-profile {
      type string;
    }
    container syslog {
      uses service-set-syslog-object;
    }
    leaf maximum-sessions {
      type uint32;
    }
    leaf service-profile {
      type string;
    }
  }

  grouping layer2-pm-family-output-type {
    uses apply-group;
    uses apply-macro;
    choice choice-3 {
      leaf interface {
        type interface-name;
      }
      leaf next-hop-group {
        type string;
      }
    }
    leaf no-filter-check {
      type empty;
    }
  }

  grouping ldap-server-object {
    leaf name {
      type string;
    }
    uses apply-group;
    uses apply-macro;
    leaf port {
      type uint16;
    }
    leaf source-address {
      type ipv4addr;
    }
    leaf routing-instance {
      type string;
    }
    leaf retry {
      type uint32;
    }
    leaf timeout {
      type uint32;
    }
  }

  grouping ldp-sync-obj {
    uses apply-group;
    uses apply-macro;
    choice choice-3 {
      leaf disable {
        type empty;
      }
    }
    leaf enable-disable {
      type string;
    }
    leaf hold-time {
      type string;
    }
  }

  grouping ldp-filter-obj {
    uses apply-group;
    uses apply-macro;
    leaf match-on {
      type string;
    }
    leaf-list policy {
      type policy-algebra;
      ordered-by user;
    }
  }

  grouping license-object {
    uses apply-group;
    uses apply-macro;
    container autoupdate {
      presence "enable autoupdate";
      uses apply-group;
      uses apply-macro;
      list url {
        key "name";
        ordered-by user;
        leaf name {
          type string;
        }
        leaf password {
          type string;
        }
      }
    }
    container renew {
      presence "";
      leaf before-expiration {
        type uint32;
      }
      leaf interval {
        type uint32;
      }
    }
    container traceoptions {
      uses apply-group;
      uses apply-macro;
      leaf no-remote-trace {
        type empty;
      }
      container file {
        leaf filename {
          type string;
        }
        leaf size {
          type string;
        }
        leaf files {
          type uint32;
        }
        leaf world-readable {
          type empty;
        }
        leaf no-world-readable {
          type empty;
        }
        leaf match {
          type regular-expression;
        }
      }
      list flag {
        key "name";
        ordered-by user;
        leaf name {
          type string;
        }
      }
    }
    container keys {
      presence "enable keys";
      uses apply-group;
      uses apply-macro;
      list key {
        key "name";
        ordered-by user;
        leaf name {
          type string;
        }
        uses apply-group;
        uses apply-macro;
      }
    }
  }

  grouping lmp-control-channel-type {
    leaf name {
      type interface-name;
    }
    uses apply-group;
    uses apply-macro;
    leaf remote-address {
      type ipaddr;
    }
  }

  grouping login-class-object {
    leaf name {
      type string;
    }
    uses apply-group;
    uses apply-macro;
    leaf-list allowed-days {
      ordered-by user;
      type string;
    }
    leaf access-start {
      type time;
    }
    leaf access-end {
      type time;
    }
    leaf idle-timeout {
      type uint32;
    }
    leaf logical-system {
      type string;
    }
    leaf login-alarms {
      type empty;
    }
    leaf login-script {
      type string;
    }
    leaf login-tip {
      type empty;
    }
    leaf-list permissions {
      type string;
    }
    leaf allow-commands {
      type regular-expression;
    }
    leaf deny-commands {
      type regular-expression;
    }
    leaf allow-configuration {
      type regular-expression;
    }
    leaf deny-configuration {
      type regular-expression;
    }
    leaf-list allow-commands-regexps {
      type string;
      ordered-by user;
    }
    leaf-list deny-commands-regexps {
      type string;
      ordered-by user;
    }
    leaf-list allow-configuration-regexps {
      type string;
      ordered-by user;
    }
    leaf-list deny-configuration-regexps {
      type string;
      ordered-by user;
    }
    leaf configuration-breadcrumbs {
      type empty;
    }
    list confirm-commands {
      key "name";
      ordered-by user;
      leaf name {
        type regular-expression;
      }
      uses apply-group;
      uses apply-macro;
      leaf message {
        type string;
      }
    }
    choice choice-allow-hidden-commands {
      leaf allow-hidden-commands {
        type empty;
      }
      container no-hidden-commands {
        uses apply-group;
        uses apply-macro;
        list except {
          key "name";
          ordered-by user;
          leaf name {
            type string;
          }
          uses apply-group;
          uses apply-macro;
        }
      }
    }
    container cli {
      uses apply-group;
      uses apply-macro;
      leaf prompt {
        type string;
      }
    }
    leaf security-role {
      type string;
    }
    leaf satellite {
      type string;
    }
  }

  grouping login-object {
    leaf name {
      type string;
    }
    uses apply-group;
    uses apply-macro;
    leaf password {
      type unreadable;
    }
  }

  grouping login-user-object {
    leaf name {
      type string;
    }
    uses apply-group;
    uses apply-macro;
    leaf full-name {
      type string;
    }
    container cli {
      uses apply-group;
      uses apply-macro;
      leaf prompt {
        type string;
      }
    }
    leaf uid {
      type uint32;
    }
    leaf class {
      type string;
    }
    container authentication {
      uses authentication-object;
    }
  }

  grouping lpdf-trace-options-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    list flag {
      key "name";
      ordered-by user;
      leaf name {
        type string;
      }
    }
  }

  grouping lr-interfaces-type {
    leaf name {
      type interface-unit;
    }
    uses apply-group;
    uses apply-macro;
    list unit {
      key "name";
      leaf name {
        type string;
      }
      uses apply-group;
      uses apply-macro;
      container peer-psd {
        presence "";
        leaf psd-name {
          type string;
        }
      }
      container peer-interface {
        presence "enable peer-interface";
        uses apply-group;
        uses apply-macro;
        leaf interface-name {
          type interface-unit;
        }
      }
      container interface-shared-with {
        presence "";
        uses apply-group;
        uses apply-macro;
        leaf psd-name {
          type string;
        }
      }
      choice choice-9 {
        leaf disable {
          type empty;
        }
      }
      leaf passive-monitor-mode {
        type empty;
      }
      leaf per-session-scheduler {
        type empty;
      }
      leaf clear-dont-fragment-bit {
        type empty;
      }
      leaf reassemble-packets {
        type empty;
      }
      container rpm {
        uses apply-group;
        uses apply-macro;
        choice choice-3 {
          leaf client {
            type empty;
          }
          leaf server {
            type empty;
          }
          leaf twamp-server {
            type empty;
          }
        }
      }
      leaf description {
        type string;
      }
      container dial-options {
        uses apply-group;
        uses apply-macro;
        choice choice-3 {
          leaf l2tp-interface-id {
            type string;
          }
          leaf ipsec-interface-id {
            type string;
          }
        }
        choice choice-4 {
          leaf dedicated {
            type empty;
          }
          leaf shared {
            type empty;
          }
        }
      }
      leaf-list demux-source {
        ordered-by user;
        type string;
      }
      leaf-list demux-destination {
        ordered-by user;
        type string;
      }
      leaf encapsulation {
        type string;
      }
      leaf mtu {
        type uint32;
      }
      choice choice-32 {
        leaf point-to-point {
          type empty;
        }
        leaf multipoint {
          type empty;
        }
      }
      leaf bandwidth {
        type string;
      }
      container radio-router {
        presence "enable radio-router";
        uses dynamic-ifbw-parms-type;
      }
      leaf traps {
        type empty;
      }
      leaf no-traps {
        type empty;
      }
      container arp-resp {
        presence "enable arp-resp";
        choice choice-3 {
          leaf unrestricted {
            type empty;
          }
          leaf restricted {
            type empty;
          }
        }
      }
      container proxy-arp {
        presence "enable proxy-arp";
        choice choice-3 {
          leaf unrestricted {
            type empty;
          }
          leaf restricted {
            type empty;
          }
        }
      }
      choice choice-45 {
        leaf vlan-id {
          type string;
        }
        leaf vlan-id-range {
          type string;
        }
        leaf-list vlan-id-list {
          type string;
        }
        container vlan-tags {
          presence "";
          leaf outer {
            type string;
          }
          choice choice-5 {
            leaf inner {
              type string;
            }
            leaf inner-range {
              type string;
            }
            leaf-list inner-list {
              type string;
            }
          }
        }
      }
      leaf native-inner-vlan-id {
        type uint32;
      }
      container inner-vlan-id-range {
        presence "";
        leaf start {
          type uint32;
        }
        leaf end {
          type uint32;
        }
      }
      container accept-source-mac {
        uses apply-group;
        uses apply-macro;
        list mac-address {
          key "name";
          uses mac-list;
        }
      }
      container input-vlan-map {
        uses vlan-map;
      }
      container output-vlan-map {
        uses vlan-map;
      }
      leaf receive-lsp {
        type string;
      }
      leaf transmit-lsp {
        type string;
      }
      leaf dlci {
        type uint32;
      }
      leaf multicast-dlci {
        type uint32;
      }
      choice choice-64 {
        leaf vci {
          type atm-vci;
        }
        leaf allow-any-vci {
          type empty;
        }
        leaf vpi {
          type uint32;
        }
        leaf trunk-id {
          type uint32;
        }
      }
      container atm-l2circuit-mode {
        choice choice-3 {
          leaf cell {
            type empty;
          }
          leaf aal5 {
            type empty;
          }
        }
      }
      container vci-range {
        presence "";
        leaf start {
          type uint16;
        }
        leaf end {
          type uint16;
        }
      }
      leaf trunk-bandwidth {
        type string;
      }
      leaf multicast-vci {
        type atm-vci;
      }
      container shaping {
        uses dcd-shaping-config;
      }
      container oam-period {
        choice choice-3 {
          leaf oam-period {
            type uint32;
          }
          container disable {
            presence "enable disable";
          }
        }
      }
      container oam-liveness {
        uses apply-group;
        uses apply-macro;
        leaf up-count {
          type uint32;
        }
        leaf down-count {
          type uint32;
        }
      }
      container ppp-options {
        uses ppp-options-type;
      }
      container pppoe-options {
        presence "";
        uses pppoe-options-type;
      }
      container pppoe-underlying-options {
        uses pppoe-underlying-options-type;
      }
      container demux-options {
        presence "";
        uses demux-options-type;
      }
      choice choice-87 {
        container keepalives {
          presence "enable keepalives";
          uses keepalives-type;
        }
        leaf no-keepalives {
          type empty;
        }
      }
      leaf inverse-arp {
        type empty;
      }
      leaf transmit-weight {
        type uint16;
      }
      container epd-threshold {
        presence "";
        uses epd-threshold-config;
      }
      leaf cell-bundle-size {
        type uint32;
      }
      leaf plp-to-clp {
        type empty;
      }
      leaf atm-scheduler-map {
        type string;
      }
      leaf mrru {
        type uint16;
      }
      leaf short-sequence {
        type empty;
      }
      leaf fragment-threshold {
        type uint32;
      }
      leaf drop-timeout {
        type uint16;
      }
      leaf disable-mlppp-inner-ppp-pfc {
        type empty;
      }
      leaf minimum-links {
        type uint16;
      }
      leaf multilink-max-classes {
        type uint16;
      }
      container compression {
        presence "enable compression";
        uses apply-group;
        uses apply-macro;
        container rtp {
          presence "enable rtp";
          uses apply-group;
          uses apply-macro;
          leaf f-max-period {
            type uint32;
          }
          leaf-list queues {
            ordered-by user;
            type string;
          }
          container port {
            presence "";
            leaf minimum {
              type uint32;
            }
            leaf maximum {
              type uint32;
            }
          }
          container maximum-contexts {
            leaf number {
              type uint32;
            }
          }
        }
      }
      leaf interleave-fragments {
        type empty;
      }
      leaf link-layer-overhead {
        type unsigned-float;
      }
      leaf accounting-profile {
        type string;
      }
      leaf peer-unit {
        type uint32;
      }
      container tunnel {
        presence "";
        uses apply-group;
        uses apply-macro;
        leaf source {
          type ipv4addr;
        }
        leaf destination {
          type ipv4addr;
        }
        leaf key {
          type uint32;
        }
        leaf backup-destination {
          type ipv4addr;
        }
        choice choice-11 {
          leaf allow-fragmentation {
            type empty;
          }
          leaf do-not-fragment {
            type empty;
          }
        }
        leaf ttl {
          type uint32;
        }
        leaf path-mtu-discovery {
          type empty;
        }
        leaf no-path-mtu-discovery {
          type empty;
        }
        container routing-instance {
          uses apply-group;
          uses apply-macro;
          leaf destination {
            type string;
          }
        }
      }
      leaf compression-device {
        type interface-unit;
      }
      container layer2-policer {
        uses apply-group;
        uses apply-macro;
        choice choice-3 {
          leaf input-policer {
            type string;
          }
          leaf input-hierarchical-policer {
            type string;
          }
          leaf input-three-color {
            type string;
          }
        }
        choice choice-4 {
          leaf output-policer {
            type string;
          }
          leaf output-three-color {
            type string;
          }
        }
      }
      container filter {
        uses apply-group;
        uses apply-macro;
        leaf input {
          type string;
        }
        leaf output {
          type string;
        }
      }
      leaf statistics {
        type empty;
      }
      container esi {
        presence "";
        uses apply-group;
        uses apply-macro;
        container apply-advanced {
          uses apply-group;
          uses apply-macro;
        }
        leaf identifier {
          mandatory true;
          type string;
        }
        choice choice-single-active {
          leaf single-active {
            type empty;
          }
          leaf all-active {
            type empty;
          }
        }
      }
      container family {
        uses apply-group;
        uses apply-macro;
        container inet {
          presence "enable inet";
          uses apply-group;
          uses apply-macro;
          container targeted-broadcast {
            presence "enable targeted-broadcast";
            uses apply-group;
            uses apply-macro;
            choice choice-3 {
              leaf forward-and-send-to-re {
                type empty;
              }
              leaf forward-only {
                type empty;
              }
            }
          }
          leaf receive-options-packets {
            type empty;
          }
          leaf receive-ttl-exceeded {
            type empty;
          }
          container accounting {
            uses apply-group;
            uses apply-macro;
            container source-class-usage {
              uses apply-group;
              uses apply-macro;
              leaf input {
                type empty;
              }
              leaf output {
                type empty;
              }
            }
            leaf destination-class-usage {
              type empty;
            }
          }
          leaf mac-validate {
            type string;
          }
          container rpf-check {
            presence "enable rpf-check";
            uses apply-group;
            uses apply-macro;
            leaf fail-filter {
              type string;
            }
            container mode {
              leaf loose {
                type empty;
              }
            }
          }
          leaf mtu {
            type uint32;
          }
          leaf no-redirects {
            type empty;
          }
          leaf no-neighbor-learn {
            type empty;
          }
          leaf multicast-only {
            type empty;
          }
          leaf primary {
            type empty;
          }
          leaf ipsec-sa {
            type string;
          }
          list demux-source {
            key "name";
            ordered-by user;
            leaf name {
              type string;
            }
            uses apply-group;
            uses apply-macro;
          }
          list demux-destination {
            key "name";
            ordered-by user;
            leaf name {
              type string;
            }
            uses apply-group;
            uses apply-macro;
          }
          container filter {
            uses apply-group;
            uses apply-macro;
            choice choice-3 {
              container input {
                presence "";
                leaf filter-name {
                  type string;
                }
                leaf precedence {
                  type uint32;
                }
              }
              leaf-list input-list {
                type string;
                ordered-by user;
              }
            }
            choice choice-4 {
              container output {
                presence "";
                leaf filter-name {
                  type string;
                }
                leaf precedence {
                  type uint32;
                }
              }
              leaf-list output-list {
                type string;
                ordered-by user;
              }
            }
            container adf {
              presence "";
              uses apply-group;
              uses apply-macro;
              list rule {
                key "name";
                ordered-by user;
                leaf name {
                  type string;
                }
                uses apply-group;
                uses apply-macro;
              }
              leaf counter {
                type empty;
              }
              leaf input-precedence {
                type uint32;
              }
              leaf output-precedence {
                type uint32;
              }
            }
            leaf group {
              type uint32;
            }
          }
          container simple-filter {
            uses apply-group;
            uses apply-macro;
            leaf input {
              type string;
            }
          }
          leaf input-hierarchical-policer {
            type string;
          }
          container policer {
            uses apply-group;
            uses apply-macro;
            leaf arp {
              type string;
            }
            leaf input {
              type string;
            }
            leaf output {
              type string;
            }
          }
          container sampling {
            uses apply-group;
            uses apply-macro;
            leaf input {
              type empty;
            }
            leaf output {
              type empty;
            }
          }
          list next-hop-tunnel {
            key "name";
            ordered-by user;
            leaf name {
              type string;
            }
            uses apply-group;
            uses apply-macro;
            leaf ipsec-vpn {
              type string;
            }
          }
          list address {
            key "name";
            ordered-by user;
            leaf name {
              type ipv4prefix;
            }
            uses apply-group;
            uses apply-macro;
            leaf destination {
              type ipv4addr;
            }
            leaf destination-profile {
              type string;
            }
            leaf broadcast {
              type ipv4addr;
            }
            leaf primary {
              type empty;
            }
            leaf preferred {
              type empty;
            }
            leaf master-only {
              type empty;
            }
            list multipoint-destination {
              key "name";
              ordered-by user;
              leaf name {
                type ipv4addr;
              }
              uses apply-group;
              uses apply-macro;
              choice choice-3 {
                leaf dlci {
                  type uint32;
                }
                leaf vci {
                  type atm-vci;
                }
              }
              container shaping {
                uses dcd-shaping-config;
              }
              container oam-period {
                choice choice-3 {
                  leaf oam_period {
                    type uint32;
                  }
                  container disable {
                    presence "enable disable";
                  }
                }
              }
              container oam-liveness {
                uses apply-group;
                uses apply-macro;
                leaf up-count {
                  type uint32;
                }
                leaf down-count {
                  type uint32;
                }
              }
              leaf inverse-arp {
                type empty;
              }
              leaf transmit-weight {
                type uint16;
              }
              container epd-threshold {
                presence "";
                uses epd-threshold-config;
              }
            }
            list arp {
              key "name";
              ordered-by user;
              leaf name {
                type ipv4addr;
              }
              leaf l2-interface {
                type interface-name;
              }
              choice choice-5 {
                leaf mac {
                  type mac-unicaset;
                }
                leaf multicast-mac {
                  type mac-multicast;
                }
              }
              leaf publish {
                type empty;
              }
            }
            container web-authentication {
              uses apply-group;
              uses apply-macro;
              leaf http {
                type empty;
              }
            }
            list vrrp-group {
              key "name";
              ordered-by user;
              uses vrrp-group;
            }
          }
          container unnumbered-address {
            presence "";
            leaf source {
              type interface-unit;
            }
            leaf preferred-source-address {
              type string;
            }
            leaf destination {
              type ipv4addr;
            }
            leaf destination-profile {
              type string;
            }
          }
          container location-pool-address {
            presence "enable location-pool-address";
            uses apply-group;
            uses apply-macro;
            leaf pool-name {
              type string;
            }
          }
          leaf negotiate-address {
            type empty;
          }
          container dhcp {
            presence "enable dhcp";
            uses apply-group;
            uses apply-macro;
            container client-identifier {
              choice choice-3 {
                leaf ascii {
                  type string;
                }
                leaf hexadecimal {
                  type string;
                }
              }
            }
            leaf lease-time {
              type string;
            }
            leaf retransmission-attempt {
              type uint32;
            }
            leaf retransmission-interval {
              type uint32;
            }
            leaf server-address {
              type ipv4addr;
            }
            leaf update-server {
              type empty;
            }
            leaf vendor-id {
              type string;
            }
          }
        }
        container iso {
          presence "enable iso";
          uses apply-group;
          uses apply-macro;
          list address {
            key "name";
            ordered-by user;
            leaf name {
              type isoaddr;
            }
            uses apply-group;
            uses apply-macro;
          }
          leaf mtu {
            type uint32;
          }
        }
        container inet6 {
          presence "enable inet6";
          uses apply-group;
          uses apply-macro;
          container rpf-check {
            presence "enable rpf-check";
            uses apply-group;
            uses apply-macro;
            leaf fail-filter {
              type string;
            }
            container mode {
              leaf loose {
                type empty;
              }
            }
          }
          container accounting {
            uses apply-group;
            uses apply-macro;
            container source-class-usage {
              uses apply-group;
              uses apply-macro;
              leaf input {
                type empty;
              }
              leaf output {
                type empty;
              }
            }
            leaf destination-class-usage {
              type empty;
            }
          }
          leaf mtu {
            type uint32;
          }
          leaf no-neighbor-learn {
            type empty;
          }
          container filter {
            uses apply-group;
            uses apply-macro;
            choice choice-3 {
              container input {
                presence "";
                leaf filter-name {
                  type string;
                }
                leaf precedence {
                  type uint32;
                }
              }
              leaf-list input-list {
                type string;
                ordered-by user;
              }
            }
            choice choice-4 {
              container output {
                presence "";
                leaf filter-name {
                  type string;
                }
                leaf precedence {
                  type uint32;
                }
              }
              leaf-list output-list {
                type string;
                ordered-by user;
              }
            }
            container adf {
              presence "";
              uses apply-group;
              uses apply-macro;
              list rule {
                key "name";
                ordered-by user;
                leaf name {
                  type string;
                }
                uses apply-group;
                uses apply-macro;
              }
              leaf counter {
                type empty;
              }
              leaf input-precedence {
                type uint32;
              }
              leaf output-precedence {
                type uint32;
              }
            }
            leaf group {
              type uint32;
            }
          }
          leaf input-hierarchical-policer {
            type string;
          }
          container policer {
            uses apply-group;
            uses apply-macro;
            leaf input {
              type string;
            }
            leaf output {
              type string;
            }
          }
          container sampling {
            uses apply-group;
            uses apply-macro;
            leaf input {
              type empty;
            }
            leaf output {
              type empty;
            }
          }
          list address {
            key "name";
            ordered-by user;
            leaf name {
              type ipv6prefix;
            }
            uses apply-group;
            uses apply-macro;
            leaf destination {
              type ipv6addr;
            }
            leaf eui-64 {
              type empty;
            }
            leaf primary {
              type empty;
            }
            leaf preferred {
              type empty;
            }
            leaf master-only {
              type empty;
            }
            list ndp {
              key "name";
              ordered-by user;
              leaf name {
                type ipv6addr;
              }
              leaf l2-interface {
                type interface-name;
              }
              choice choice-5 {
                leaf mac {
                  type mac-unicaset;
                }
                leaf multicast-mac {
                  type mac-multicast;
                }
              }
              leaf publish {
                type empty;
              }
            }
            list vrrp-inet6-group {
              key "name";
              ordered-by user;
              uses vrrp-group;
            }
            container web-authentication {
              uses apply-group;
              uses apply-macro;
              leaf http {
                type empty;
              }
            }
            leaf virtual-gateway-address {
              type ipv6addr;
            }
          }
          list demux-source {
            key "name";
            ordered-by user;
            leaf name {
              type string;
            }
            uses apply-group;
            uses apply-macro;
          }
          list demux-destination {
            key "name";
            ordered-by user;
            leaf name {
              type string;
            }
            uses apply-group;
            uses apply-macro;
          }
          container unnumbered-address {
            presence "";
            leaf source {
              type interface-unit;
            }
            leaf preferred-source-address {
              type string;
            }
          }
          leaf dad-disable {
            type empty;
          }
          leaf no-dad-disable {
            type empty;
          }
        }
        container mpls {
          presence "enable mpls";
          uses apply-group;
          uses apply-macro;
          leaf mtu {
            type uint32;
          }
          leaf maximum-labels {
            type uint32;
          }
          container filter {
            uses apply-group;
            uses apply-macro;
            choice choice-3 {
              leaf input {
                type string;
              }
              leaf-list input-list {
                type string;
                ordered-by user;
              }
            }
            choice choice-4 {
              leaf output {
                type string;
              }
              leaf-list output-list {
                type string;
                ordered-by user;
              }
            }
            leaf group {
              type uint32;
            }
          }
          leaf input-hierarchical-policer {
            type string;
          }
          container policer {
            uses apply-group;
            uses apply-macro;
            leaf input {
              type string;
            }
            leaf output {
              type string;
            }
          }
        }
        container mlppp {
          presence "";
          uses apply-group;
          uses apply-macro;
          leaf bundle {
            type interface-unit;
          }
        }
        container mlfr-end-to-end {
          presence "";
          uses apply-group;
          uses apply-macro;
          leaf bundle {
            type interface-unit;
          }
        }
        container mlfr-uni-nni {
          presence "";
          uses apply-group;
          uses apply-macro;
          leaf bundle {
            type interface-unit;
          }
        }
        container ccc {
          presence "enable ccc";
          uses apply-group;
          uses apply-macro;
          container filter {
            uses apply-group;
            uses apply-macro;
            choice choice-3 {
              leaf input {
                type string;
              }
              leaf-list input-list {
                type string;
                ordered-by user;
              }
            }
            choice choice-4 {
              leaf output {
                type string;
              }
              leaf-list output-list {
                type string;
                ordered-by user;
              }
            }
            leaf group {
              type uint32;
            }
          }
          container policer {
            uses apply-group;
            uses apply-macro;
            leaf input {
              type string;
            }
            leaf output {
              type string;
            }
          }
          leaf translate-fecn-and-becn {
            type empty;
          }
          choice choice-9 {
            leaf translate-discard-eligible {
              type empty;
            }
            leaf translate-plp-control-word-de {
              type empty;
            }
          }
          leaf keep-address-and-control {
            type empty;
          }
        }
        container tcc {
          presence "enable tcc";
          uses apply-group;
          uses apply-macro;
          container policer {
            uses apply-group;
            uses apply-macro;
            leaf input {
              type string;
            }
            leaf output {
              type string;
            }
          }
          container proxy {
            presence "enable proxy";
            uses apply-group;
            uses apply-macro;
            leaf inet-address {
              type ipv4addr;
            }
          }
          container remote {
            presence "enable remote";
            uses apply-group;
            uses apply-macro;
            leaf inet-address {
              type ipv4addr;
            }
            leaf mac-address {
              type mac-addr;
            }
          }
          leaf-list protocols {
            ordered-by user;
            type string;
          }
        }
        container vpls {
          presence "enable vpls";
          uses apply-group;
          uses apply-macro;
          leaf core-facing {
            type empty;
          }
          container filter {
            uses apply-group;
            uses apply-macro;
            choice choice-3 {
              container input {
                presence "";
                leaf filter-name {
                  type string;
                }
                leaf precedence {
                  type uint32;
                }
              }
              leaf-list input-list {
                type string;
                ordered-by user;
              }
            }
            choice choice-4 {
              container output {
                presence "";
                leaf filter-name {
                  type string;
                }
                leaf precedence {
                  type uint32;
                }
              }
              leaf-list output-list {
                type string;
                ordered-by user;
              }
            }
            container adf {
              presence "";
              uses apply-group;
              uses apply-macro;
              list rule {
                key "name";
                ordered-by user;
                leaf name {
                  type string;
                }
                uses apply-group;
                uses apply-macro;
              }
              leaf counter {
                type empty;
              }
              leaf input-precedence {
                type uint32;
              }
              leaf output-precedence {
                type uint32;
              }
            }
            leaf group {
              type uint32;
            }
          }
          container policer {
            uses apply-group;
            uses apply-macro;
            leaf input {
              type string;
            }
            leaf output {
              type string;
            }
          }
        }
        container bridge {
          presence "enable bridge";
          uses apply-group;
          uses apply-macro;
          leaf core-facing {
            type empty;
          }
          container filter {
            uses apply-group;
            uses apply-macro;
            choice choice-3 {
              container input {
                presence "";
                leaf filter-name {
                  type string;
                }
                leaf precedence {
                  type uint32;
                }
              }
              leaf-list input-list {
                type string;
                ordered-by user;
              }
            }
            choice choice-4 {
              container output {
                presence "";
                leaf filter-name {
                  type string;
                }
                leaf precedence {
                  type uint32;
                }
              }
              leaf-list output-list {
                type string;
                ordered-by user;
              }
            }
            container adf {
              presence "";
              uses apply-group;
              uses apply-macro;
              list rule {
                key "name";
                ordered-by user;
                leaf name {
                  type string;
                }
                uses apply-group;
                uses apply-macro;
              }
              leaf counter {
                type empty;
              }
              leaf input-precedence {
                type uint32;
              }
              leaf output-precedence {
                type uint32;
              }
            }
            leaf group {
              type uint32;
            }
          }
          container policer {
            uses apply-group;
            uses apply-macro;
            leaf input {
              type string;
            }
            leaf output {
              type string;
            }
          }
          leaf interface-mode {
            type string;
          }
          leaf bridge-domain-type {
            type string;
          }
          choice choice-13 {
            leaf vlan-id {
              type uint32;
            }
            leaf-list vlan-id-list {
              type string;
              ordered-by user;
            }
            leaf-list inner-vlan-id-list {
              type string;
              ordered-by user;
            }
          }
          container vlan-rewrite {
            uses apply-group;
            uses apply-macro;
            list translate {
              key "name";
              ordered-by user;
              leaf name {
                type string;
              }
              leaf to-vlan-id {
                type uint32;
              }
            }
          }
          choice choice-16 {
            leaf isid-list {
              type string;
            }
          }
        }
        container ethernet-switching {
          presence "enable ethernet-switching";
          uses ethernet-switching-type;
        }
        container fibre-channel {
          presence "enable fibre-channel";
          uses fibre-channel-type;
        }
        container any {
          presence "enable any";
          uses apply-group;
          uses apply-macro;
          container filter {
            uses apply-group;
            uses apply-macro;
            leaf input {
              type string;
            }
            leaf group {
              type uint32;
            }
          }
        }
      }
      leaf service-domain {
        type string;
      }
      leaf copy-tos-to-outer-ip-header {
        type empty;
      }
    }
  }

  grouping lsp-nh-obj {
    leaf name {
      type string;
    }
    uses apply-group;
    uses apply-macro;
    leaf preference {
      type uint32;
    }
    leaf metric {
      type uint32;
    }
  }

  grouping mac-aging-time-config {
    uses apply-group;
    uses apply-macro;
    choice choice-3 {
      leaf time {
        type uint32;
      }
      leaf unlimited {
        type empty;
      }
    }
  }

  grouping mac-list {
    leaf name {
      type mac-addr;
    }
    uses apply-group;
    uses apply-macro;
    container policer {
      uses apply-group;
      uses apply-macro;
      leaf input {
        type string;
      }
      leaf output {
        type string;
      }
    }
  }

  grouping martian-type {
    leaf address {
      type ipprefix;
    }
    leaf key2 {
      type string;
    }
    leaf key2-arg {
      type string;
    }
    uses apply-group;
    uses apply-macro;
    leaf allow {
      type empty;
    }
  }

  grouping match-L2-flexible-mask {
    uses apply-group;
    uses apply-macro;
    leaf match-start {
      type string;
    }
    leaf byte-offset {
      type uint32;
    }
    leaf bit-offset {
      type uint32;
    }
    leaf bit-length {
      type uint32;
    }
    leaf mask-in-hex {
      type string;
    }
    leaf prefix {
      type string;
      mandatory true;
    }
    leaf flexible-mask-name {
      type string;
    }
  }

  grouping match-L2-flexible-range {
    uses apply-group;
    uses apply-macro;
    leaf match-start {
      type string;
    }
    leaf byte-offset {
      type uint32;
    }
    leaf bit-offset {
      type uint32;
    }
    leaf bit-length {
      type uint32;
    }
    choice choice-range {
      leaf range {
        type string;
      }
      leaf range-except {
        type string;
      }
    }
    leaf flexible-range-name {
      type string;
    }
  }

  grouping match_L3_flexible_mask {
    uses apply-advanced;
    leaf match-start {
      type string;
    }
    leaf byte-offset {
      type string;
    }
    leaf bit-offset {
      type string;
    }
    leaf bit-length {
      type string;
    }
    leaf mask-in-hex {
      type string;
    }
    leaf prefix {
      type string;
    }
    leaf flexible-mask-name {
      type string;
    }
  }

  grouping match_L3_flexible_range {
    uses apply-advanced;
    leaf match-start {
      type string;
    }
    leaf byte-offset {
      type string;
    }
    leaf bit-offset {
      type string;
    }
    leaf bit-length {
      type string;
    }
    choice range_choice {
      case case_1 {
        leaf range {
          type string;
        }
      }
      case case_2 {
        leaf range-except {
          type string;
        }
      }
    }
    leaf flexible-range-name {
      type string;
    }
  }

  grouping match-flags-value {
    uses apply-group;
    uses apply-macro;
    leaf value {
      type string;
    }
    leaf mask-in-hex {
      type string;
    }
  }

  grouping match-interface-object {
    leaf name {
      type interface-wildcard;
    }
    uses apply-group;
    uses apply-macro;
  }

  grouping match-interface-object-oam {
    leaf name {
      type interface-wildcard;
    }
    uses apply-group;
    uses apply-macro;
  }

  grouping match-interface-set-object {
    leaf name {
      type string;
    }
    uses apply-group;
    uses apply-macro;
  }

  grouping match-simple-dscp-value {
    uses apply-group;
    uses apply-macro;
    choice choice-3 {
      leaf af11 {
        type empty;
      }
      leaf af12 {
        type empty;
      }
      leaf af13 {
        type empty;
      }
      leaf af21 {
        type empty;
      }
      leaf af22 {
        type empty;
      }
      leaf af23 {
        type empty;
      }
      leaf af31 {
        type empty;
      }
      leaf af32 {
        type empty;
      }
      leaf af33 {
        type empty;
      }
      leaf af41 {
        type empty;
      }
      leaf af42 {
        type empty;
      }
      leaf af43 {
        type empty;
      }
      leaf ef {
        type empty;
      }
      leaf cs0 {
        type empty;
      }
      leaf cs1 {
        type empty;
      }
      leaf cs2 {
        type empty;
      }
      leaf cs3 {
        type empty;
      }
      leaf cs4 {
        type empty;
      }
      leaf cs5 {
        type empty;
      }
      leaf cs6 {
        type empty;
      }
      leaf cs7 {
        type empty;
      }
      leaf be {
        type empty;
      }
      leaf range {
        type empty;
      }
    }
  }

  grouping match-simple-port-value {
    uses apply-group;
    uses apply-macro;
    choice choice-3 {
      leaf ftp-data {
        type empty;
      }
      leaf ftp {
        type empty;
      }
      leaf ssh {
        type empty;
      }
      leaf telnet {
        type empty;
      }
      leaf smtp {
        type empty;
      }
      leaf tacacs {
        type empty;
      }
      leaf tacacs-ds {
        type empty;
      }
      leaf domain {
        type empty;
      }
      leaf dhcp {
        type empty;
      }
      leaf bootps {
        type empty;
      }
      leaf bootpc {
        type empty;
      }
      leaf tftp {
        type empty;
      }
      leaf finger {
        type empty;
      }
      leaf http {
        type empty;
      }
      leaf kerberos-sec {
        type empty;
      }
      leaf pop3 {
        type empty;
      }
      leaf sunrpc {
        type empty;
      }
      leaf ident {
        type empty;
      }
      leaf nntp {
        type empty;
      }
      leaf ntp {
        type empty;
      }
      leaf netbios-ns {
        type empty;
      }
      leaf netbios-dgm {
        type empty;
      }
      leaf netbios-ssn {
        type empty;
      }
      leaf imap {
        type empty;
      }
      leaf snmp {
        type empty;
      }
      leaf snmptrap {
        type empty;
      }
      leaf xdmcp {
        type empty;
      }
      leaf bgp {
        type empty;
      }
      leaf ldap {
        type empty;
      }
      leaf mobileip-agent {
        type empty;
      }
      leaf mobilip-mn {
        type empty;
      }
      leaf msdp {
        type empty;
      }
      leaf https {
        type empty;
      }
      leaf snpp {
        type empty;
      }
      leaf biff {
        type empty;
      }
      leaf exec {
        type empty;
      }
      leaf login {
        type empty;
      }
      leaf who {
        type empty;
      }
      leaf cmd {
        type empty;
      }
      leaf syslog {
        type empty;
      }
      leaf printer {
        type empty;
      }
      leaf talk {
        type empty;
      }
      leaf ntalk {
        type empty;
      }
      leaf rip {
        type empty;
      }
      leaf timed {
        type empty;
      }
      leaf klogin {
        type empty;
      }
      leaf kshell {
        type empty;
      }
      leaf ldp {
        type empty;
      }
      leaf krb-prop {
        type empty;
      }
      leaf krbupdate {
        type empty;
      }
      leaf kpasswd {
        type empty;
      }
      leaf socks {
        type empty;
      }
      leaf afs {
        type empty;
      }
      leaf pptp {
        type empty;
      }
      leaf radius {
        type empty;
      }
      leaf radacct {
        type empty;
      }
      leaf nfsd {
        type empty;
      }
      leaf eklogin {
        type empty;
      }
      leaf ekshell {
        type empty;
      }
      leaf rkinit {
        type empty;
      }
      leaf cvspserver {
        type empty;
      }
      leaf range {
        type empty;
      }
    }
  }

  grouping match-simple-protocol-value {
    uses apply-group;
    uses apply-macro;
    choice choice-3 {
      leaf icmp {
        type empty;
      }
      leaf igmp {
        type empty;
      }
      leaf ipip {
        type empty;
      }
      leaf tcp {
        type empty;
      }
      leaf egp {
        type empty;
      }
      leaf udp {
        type empty;
      }
      leaf rsvp {
        type empty;
      }
      leaf gre {
        type empty;
      }
      leaf esp {
        type empty;
      }
      leaf ah {
        type empty;
      }
      leaf icmp6 {
        type empty;
      }
      leaf ospf {
        type empty;
      }
      leaf pim {
        type empty;
      }
      leaf sctp {
        type empty;
      }
      leaf icmpv6 {
        type empty;
      }
      leaf ipv6 {
        type empty;
      }
      leaf dstopts {
        type empty;
      }
      leaf routing {
        type empty;
      }
      leaf fragment {
        type empty;
      }
      leaf no-next-header {
        type empty;
      }
      leaf hop-by-hop {
        type empty;
      }
      leaf vrrp {
        type empty;
      }
      leaf range {
        type empty;
      }
    }
  }

  grouping mac-addr-list-items {
    leaf name {
      type mac-addr;
    }
    uses apply-advanced;
  }

  grouping metric-expression-type {
    uses apply-group;
    uses apply-macro;
    container metric {
      leaf multiplier {
        type float;
      }
      leaf offset {
        type int32;
      }
    }
    container metric2 {
      leaf multiplier {
        type float;
      }
      leaf offset {
        type int32;
      }
    }
  }

  grouping mib-variable-name-object {
    leaf name {
      type string;
    }
    uses apply-group;
    uses apply-macro;
  }

  grouping mobile-diameter-profiles {
    uses apply-group;
    uses apply-macro;
    list gy-profile {
      key "name";
      ordered-by user;
      uses mobile-diameter-profile-type-gy;
    }
    list gx-profile {
      key "name";
      ordered-by user;
      uses mobile-diameter-profile-type-gx;
    }
  }

  grouping mobile-diameter-profile-type-gx {
    leaf name {
      type key-attribute-string-type;
    }
    uses apply-group;
    uses apply-macro;
    list targets {
      key "name";
      ordered-by user;
      uses mobile-diameter-target;
    }
    leaf request-timeout {
      units "seconds";
      type uint32;
    }
    container attributes {
      uses mobile-diameter-gx-profile-attr-type;
    }
  }

  grouping mobile-diameter-gx-profile-attr-type {
    uses apply-group;
    uses apply-macro;
    container include {
      uses apply-group;
      uses apply-macro;
      leaf gx-capability-list {
        type uint32;
      }
      leaf rule-suggestion {
        type string;
      }
      leaf rai {
        type empty;
      }
      leaf qos-negotiation {
        type empty;
      }
      leaf qos-upgrade {
        type empty;
      }
    }
    container exclude {
      uses apply-group;
      uses apply-macro;
      leaf packet-filter-information {
        type empty;
      }
      leaf packet-filter-operation {
        type empty;
      }
      leaf rat-type {
        type empty;
      }
      leaf default-eps-bearer-qos {
        type empty;
      }
      leaf an-gw-address {
        type empty;
      }
      leaf network-request-support {
        type empty;
      }
      leaf event-trigger {
        type empty;
      }
      leaf threegpp-rat-type {
        type empty;
      }
      leaf offline {
        type empty;
      }
      leaf qos-negotiation {
        type empty;
      }
      leaf qos-upgrade {
        type empty;
      }
    }
  }

  grouping mobile-diameter-profile-type-gy {
    leaf name {
      type key-attribute-string-type;
    }
    uses apply-group;
    uses apply-macro;
    list targets {
      key "name";
      ordered-by user;
      uses mobile-diameter-target;
    }
    leaf request-timeout {
      units "seconds";
      type uint32;
    }
    container attributes {
      uses mobile-diameter-gy-profile-attr-type;
    }
  }

  grouping mobile-diameter-gy-profile-attr-type {
    uses apply-group;
    uses apply-macro;
    container include {
      uses apply-group;
      uses apply-macro;
      leaf cumulative-used-service-unit {
        type empty;
      }
      leaf credit-instance-id {
        type empty;
      }
      leaf service-start-timestamp {
        type empty;
      }
      leaf mscc-qos-information {
        type empty;
      }
      leaf framed-ip-address {
        type empty;
      }
      leaf framed-ipv6-prefix {
        type empty;
      }
      leaf gprs-negotiated-qos {
        type empty;
      }
    }
    container exclude {
      uses apply-group;
      uses apply-macro;
      leaf ps-information {
        type empty;
      }
      leaf username {
        type empty;
      }
      leaf user-equipment-info {
        type empty;
      }
      leaf all-3gpp-avps {
        type empty;
      }
      leaf qos-information {
        type empty;
      }
      leaf pdn-connection-id {
        type empty;
      }
      leaf dynamic-address-flag {
        type empty;
      }
      leaf serving-node-type {
        type empty;
      }
      leaf cc-selection-mode {
        type empty;
      }
      leaf start-time {
        type empty;
      }
      leaf stop-time {
        type empty;
      }
      leaf user-location-information {
        type empty;
      }
    }
  }

  grouping mobile-diameter-target {
    leaf name {
      type key-attribute-string-type;
    }
    uses apply-group;
    uses apply-macro;
    leaf destination-realm {
      type string;
    }
    leaf destination-host {
      type string;
    }
    leaf priority {
      type uint32;
    }
    leaf network-element {
      type string;
    }
  }

  grouping mobile-gateway-config-gtp {
    uses apply-group;
    uses apply-macro;
    leaf peer-history {
      type uint16;
    }
    container interface {
      presence "";
      leaf intf-name {
        type interface-name;
      }
      leaf v4-address {
        type ipv4addr;
      }
    }
    leaf echo-interval {
      units "seconds";
      type uint16;
    }
    leaf path-management {
      type string;
    }
    leaf echo-n3-requests {
      type uint16;
    }
    leaf echo-t3-response {
      units "seconds";
      type uint16;
    }
    leaf path-failure {
      type string;
    }
    leaf number-of-msgs-for-response-time {
      type uint16;
    }
    container control {
      uses apply-group;
      uses apply-macro;
      container interface {
        presence "";
        leaf intf-name {
          type interface-name;
        }
        leaf v4-address {
          type ipv4addr;
        }
      }
      leaf echo-interval {
        units "seconds";
        type uint16;
      }
      leaf path-management {
        type string;
      }
      leaf echo-n3-requests {
        type uint16;
      }
      leaf echo-t3-response {
        units "seconds";
        type uint16;
      }
      leaf path-failure {
        type string;
      }
      leaf number-of-msgs-for-response-time {
        type uint16;
      }
      leaf forwarding-class {
        type string;
      }
      leaf n3-requests {
        type uint16;
      }
      leaf t3-response {
        units "seconds";
        type uint16;
      }
      leaf dscp-code-point {
        type uint8;
      }
      leaf no-response-cache {
        type empty;
      }
      leaf response-cache-timeout {
        units "seconds";
        type uint8;
      }
      leaf no-piggyback-support {
        type empty;
      }
    }
    container data {
      uses apply-group;
      uses apply-macro;
      container interface {
        presence "";
        leaf intf-name {
          type interface-name;
        }
        leaf v4-address {
          type ipv4addr;
        }
      }
      leaf echo-interval {
        units "seconds";
        type uint16;
      }
      leaf path-management {
        type string;
      }
      leaf echo-n3-requests {
        type uint16;
      }
      leaf echo-t3-response {
        units "seconds";
        type uint16;
      }
      leaf path-failure {
        type string;
      }
      leaf error-indication-interval {
        units "seconds";
        type uint16;
      }
    }
    container gn {
      uses apply-group;
      uses apply-macro;
      container interface {
        presence "";
        leaf intf-name {
          type interface-name;
        }
        leaf v4-address {
          type ipv4addr;
        }
      }
      leaf echo-interval {
        units "seconds";
        type uint16;
      }
      leaf path-management {
        type string;
      }
      leaf echo-n3-requests {
        type uint16;
      }
      leaf echo-t3-response {
        units "seconds";
        type uint16;
      }
      leaf path-failure {
        type string;
      }
      leaf number-of-msgs-for-response-time {
        type uint16;
      }
      container control {
        uses apply-group;
        uses apply-macro;
        container interface {
          presence "";
          leaf intf-name {
            type interface-name;
          }
          leaf v4-address {
            type ipv4addr;
          }
        }
        leaf echo-interval {
          units "seconds";
          type uint16;
        }
        leaf path-management {
          type string;
        }
        leaf echo-n3-requests {
          type uint16;
        }
        leaf echo-t3-response {
          units "seconds";
          type uint16;
        }
        leaf path-failure {
          type string;
        }
        leaf number-of-msgs-for-response-time {
          type uint16;
        }
        leaf forwarding-class {
          type string;
        }
        leaf n3-requests {
          type uint16;
        }
        leaf t3-response {
          units "seconds";
          type uint16;
        }
        leaf dscp-code-point {
          type uint8;
        }
      }
      container data {
        uses apply-group;
        uses apply-macro;
        container interface {
          presence "";
          leaf echo-interval {
            units "seconds";
            type uint16;
          }
          leaf path-management {
            type string;
          }
          leaf echo-n3-requests {
            type uint16;
          }
          leaf echo-t3-response {
            units "seconds";
            type uint16;
          }
          leaf path-failure {
            type string;
          }
          leaf intf-name {
            type interface-name;
          }
          leaf v4-address {
            type ipv4addr;
          }
        }
        leaf echo-interval {
          units "seconds";
          type uint16;
        }
        leaf path-management {
          type string;
        }
        leaf echo-n3-requests {
          type uint16;
        }
        leaf echo-t3-response {
          units "seconds";
          type uint16;
        }
        leaf path-failure {
          type string;
        }
        leaf number-of-msgs-for-response-time {
          type uint16;
        }
      }
    }
    container gp {
      uses apply-group;
      uses apply-macro;
      container interface {
        presence "";
        leaf intf-name {
          type interface-name;
        }
        leaf v4-address {
          type ipv4addr;
        }
      }
      leaf echo-interval {
        units "seconds";
        type uint16;
      }
      leaf path-management {
        type string;
      }
      leaf echo-n3-requests {
        type uint16;
      }
      leaf echo-t3-response {
        units "seconds";
        type uint16;
      }
      leaf path-failure {
        type string;
      }
      leaf number-of-msgs-for-response-time {
        type uint16;
      }
      container control {
        uses apply-group;
        uses apply-macro;
        container interface {
          presence "";
          leaf intf-name {
            type interface-name;
          }
          leaf v4-address {
            type ipv4addr;
          }
        }
        leaf echo-interval {
          units "seconds";
          type uint16;
        }
        leaf path-management {
          type string;
        }
        leaf echo-n3-requests {
          type uint16;
        }
        leaf echo-t3-response {
          units "seconds";
          type uint16;
        }
        leaf path-failure {
          type string;
        }
        leaf number-of-msgs-for-response-time {
          type uint16;
        }
        leaf forwarding-class {
          type string;
        }
        leaf n3-requests {
          type uint16;
        }
        leaf t3-response {
          units "seconds";
          type uint16;
        }
        leaf dscp-code-point {
          type uint8;
        }
      }
      container data {
        uses apply-group;
        uses apply-macro;
        container interface {
          presence "";
          leaf echo-interval {
            units "seconds";
            type uint16;
          }
          leaf path-management {
            type string;
          }
          leaf echo-n3-requests {
            type uint16;
          }
          leaf echo-t3-response {
            units "seconds";
            type uint16;
          }
          leaf path-failure {
            type string;
          }
          leaf intf-name {
            type interface-name;
          }
          leaf v4-address {
            type ipv4addr;
          }
        }
        leaf echo-interval {
          units "seconds";
          type uint16;
        }
        leaf path-management {
          type string;
        }
        leaf echo-n3-requests {
          type uint16;
        }
        leaf echo-t3-response {
          units "seconds";
          type uint16;
        }
        leaf path-failure {
          type string;
        }
        leaf number-of-msgs-for-response-time {
          type uint16;
        }
      }
    }
    container s5 {
      uses apply-group;
      uses apply-macro;
      container interface {
        presence "";
        leaf intf-name {
          type interface-name;
        }
        leaf v4-address {
          type ipv4addr;
        }
      }
      leaf echo-interval {
        units "seconds";
        type uint16;
      }
      leaf path-management {
        type string;
      }
      leaf echo-n3-requests {
        type uint16;
      }
      leaf echo-t3-response {
        units "seconds";
        type uint16;
      }
      leaf path-failure {
        type string;
      }
      leaf number-of-msgs-for-response-time {
        type uint16;
      }
      container control {
        uses apply-group;
        uses apply-macro;
        container interface {
          presence "";
          leaf intf-name {
            type interface-name;
          }
          leaf v4-address {
            type ipv4addr;
          }
        }
        leaf echo-interval {
          units "seconds";
          type uint16;
        }
        leaf path-management {
          type string;
        }
        leaf echo-n3-requests {
          type uint16;
        }
        leaf echo-t3-response {
          units "seconds";
          type uint16;
        }
        leaf path-failure {
          type string;
        }
        leaf number-of-msgs-for-response-time {
          type uint16;
        }
        leaf forwarding-class {
          type string;
        }
        leaf n3-requests {
          type uint16;
        }
        leaf t3-response {
          units "seconds";
          type uint16;
        }
        leaf dscp-code-point {
          type uint8;
        }
        leaf support-16-bit-sequence {
          type empty;
        }
      }
      container data {
        uses apply-group;
        uses apply-macro;
        container interface {
          presence "";
          leaf echo-interval {
            units "seconds";
            type uint16;
          }
          leaf path-management {
            type string;
          }
          leaf echo-n3-requests {
            type uint16;
          }
          leaf echo-t3-response {
            units "seconds";
            type uint16;
          }
          leaf path-failure {
            type string;
          }
          leaf intf-name {
            type interface-name;
          }
          leaf v4-address {
            type ipv4addr;
          }
        }
        leaf echo-interval {
          units "seconds";
          type uint16;
        }
        leaf path-management {
          type string;
        }
        leaf echo-n3-requests {
          type uint16;
        }
        leaf echo-t3-response {
          units "seconds";
          type uint16;
        }
        leaf path-failure {
          type string;
        }
        leaf number-of-msgs-for-response-time {
          type uint16;
        }
      }
    }
    container s8 {
      uses apply-group;
      uses apply-macro;
      container interface {
        presence "";
        leaf intf-name {
          type interface-name;
        }
        leaf v4-address {
          type ipv4addr;
        }
      }
      leaf echo-interval {
        units "seconds";
        type uint16;
      }
      leaf path-management {
        type string;
      }
      leaf echo-n3-requests {
        type uint16;
      }
      leaf echo-t3-response {
        units "seconds";
        type uint16;
      }
      leaf path-failure {
        type string;
      }
      leaf number-of-msgs-for-response-time {
        type uint16;
      }
      container control {
        uses apply-group;
        uses apply-macro;
        container interface {
          presence "";
          leaf intf-name {
            type interface-name;
          }
          leaf v4-address {
            type ipv4addr;
          }
        }
        leaf echo-interval {
          units "seconds";
          type uint16;
        }
        leaf path-management {
          type string;
        }
        leaf echo-n3-requests {
          type uint16;
        }
        leaf echo-t3-response {
          units "seconds";
          type uint16;
        }
        leaf path-failure {
          type string;
        }
        leaf number-of-msgs-for-response-time {
          type uint16;
        }
        leaf forwarding-class {
          type string;
        }
        leaf n3-requests {
          type uint16;
        }
        leaf t3-response {
          units "seconds";
          type uint16;
        }
        leaf dscp-code-point {
          type uint8;
        }
        leaf support-16-bit-sequence {
          type empty;
        }
      }
      container data {
        uses apply-group;
        uses apply-macro;
        container interface {
          presence "";
          leaf echo-interval {
            units "seconds";
            type uint16;
          }
          leaf path-management {
            type string;
          }
          leaf echo-n3-requests {
            type uint16;
          }
          leaf echo-t3-response {
            units "seconds";
            type uint16;
          }
          leaf path-failure {
            type string;
          }
          leaf intf-name {
            type interface-name;
          }
          leaf v4-address {
            type ipv4addr;
          }
        }
        leaf echo-interval {
          units "seconds";
          type uint16;
        }
        leaf path-management {
          type string;
        }
        leaf echo-n3-requests {
          type uint16;
        }
        leaf echo-t3-response {
          units "seconds";
          type uint16;
        }
        leaf path-failure {
          type string;
        }
        leaf number-of-msgs-for-response-time {
          type uint16;
        }
      }
    }
    list peer-group {
      key "name";
      ordered-by user;
      leaf name {
        type key-attribute-string-type;
      }
      uses apply-group;
      uses apply-macro;
      leaf routing-instance {
        type string;
      }
      leaf echo-interval {
        units "seconds";
        type uint16;
      }
      leaf path-management {
        type string;
      }
      leaf echo-n3-requests {
        type uint16;
      }
      leaf echo-t3-response {
        units "seconds";
        type uint16;
      }
      leaf path-failure {
        type string;
      }
      leaf number-of-msgs-for-response-time {
        type uint16;
      }
      container control {
        uses apply-group;
        uses apply-macro;
        leaf support-16-bit-sequence {
          type empty;
        }
        leaf no-piggyback-support {
          type empty;
        }
      }
      container gn {
        uses apply-group;
        uses apply-macro;
      }
      container gp {
        uses apply-group;
        uses apply-macro;
      }
      list peer {
        key "name";
        ordered-by user;
        leaf name {
          type ipprefix-mandatory;
        }
      }
    }
    container traceoptions {
      uses gtp-traceoptions;
    }
  }

  grouping gtp-traceoptions {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
    }
    leaf level {
      type string;
    }
    list flag {
      key "name";
      ordered-by user;
      leaf name {
        type string;
      }
    }
  }

  grouping mobile-gateways-ipv6-router-advertisement {
    uses apply-group;
    uses apply-macro;
    leaf disable {
      type empty;
    }
    leaf maximum-advertisement-interval {
      units "seconds";
      type uint32;
    }
    leaf minimum-advertisement-interval {
      units "seconds";
      type uint32;
    }
    leaf maximum-initial-advertisement-interval {
      units "seconds";
      type uint32;
    }
    leaf maximum-initial-advertisements {
      type uint32;
    }
    leaf reachable-time {
      units "milliseconds";
      type uint32;
    }
    leaf retransmission-timer {
      type uint32;
      units "milliseconds";
    }
    leaf router-lifetime {
      units "seconds";
      type uint32;
    }
    leaf current-hop-limit {
      type uint32;
    }
  }

  grouping mobile-smd-traceoptions {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
    }
    leaf level {
      type string;
    }
    list flag {
      key "name";
      ordered-by user;
      leaf name {
        type string;
      }
    }
  }

  grouping mime-list-type {
    leaf name {
      type key-attribute-string-type;
    }
    uses apply-group;
    uses apply-macro;
    leaf-list value {
      ordered-by user;
      type string;
    }
  }

  grouping mip-access-type {
    uses apply-group;
    uses apply-macro;
    choice choice-3 {
      container wimax {
        presence "enable wimax";
        uses apply-group;
        uses apply-macro;
      }
      container generic {
        presence "enable generic";
        uses apply-group;
        uses apply-macro;
      }
    }
  }

  grouping mip-home-agent-type {
    uses apply-group;
    uses apply-macro;
    container virtual-network {
      uses mip-virtual-home-agent-address-type;
    }
    list enable-service {
      key "name";
      ordered-by user;
      leaf name {
        type interface-name;
      }
    }
    list pool-match-order {
      key "name";
      ordered-by user;
      leaf name {
        type string;
      }
    }
  }

  grouping mip-peer-type {
    uses apply-group;
    uses apply-macro;
    list ip-address {
      key "name";
      ordered-by user;
      leaf name {
        type ipv4addr;
      }
      list spi {
        key "name";
        ordered-by user;
        uses spi-type;
      }
    }
    list nai {
      key "name";
      ordered-by user;
      leaf name {
        type key-attribute-string-type;
      }
      list spi {
        key "name";
        ordered-by user;
        uses spi-type;
      }
    }
  }

  grouping mip-trace-options-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping mip-virtual-home-agent-address-type {
    uses apply-group;
    uses apply-macro;
    list home-agent-address {
      key "name";
      ordered-by user;
      leaf name {
        type ipv4addr;
      }
      leaf registration-lifetime {
        type uint32;
      }
      leaf timestamp-tolerance {
        type uint32;
      }
      leaf starting-ip-address {
        type ipv4addr;
      }
      leaf ending-ip-address {
        type ipv4addr;
      }
      leaf revocation-required {
        type empty;
      }
    }
  }

  grouping monitoring-output-type {
    uses apply-group;
    uses apply-macro;
    leaf export-format {
      type string;
    }
    leaf flow-active-timeout {
      type uint32;
    }
    leaf flow-inactive-timeout {
      type uint32;
    }
    leaf flow-export-destination {
      type string;
    }
    list cflowd {
      key "name";
      uses cflowd-monitoring-type;
    }
    list interface {
      key "name";
      uses monitor-export-intf-type;
    }
  }

  grouping cflowd-monitoring-type {
    leaf name {
      type ipv4addr;
    }
    uses apply-group;
    uses apply-macro;
    leaf port {
      type uint16;
    }
  }

  grouping monitor-export-intf-type {
    leaf name {
      type interface-name;
    }
    uses apply-group;
    uses apply-macro;
    leaf engine-id {
      type uint8;
    }
    leaf engine-type {
      type uint8;
    }
    leaf input-interface-index {
      type uint32;
    }
    leaf output-interface-index {
      type uint32;
    }
    leaf source-address {
      type ipv4addr;
    }
  }

  grouping mpls-dialer-filter {
    leaf name {
      type string;
    }
    uses apply-group;
    uses apply-macro;
    leaf-list accounting-profile {
      type string;
      ordered-by user;
    }
    list term {
      key "name";
      ordered-by user;
      leaf name {
        type string;
      }
      uses apply-group;
      uses apply-macro;
      container from {
        uses apply-group;
        uses apply-macro;
        choice choice-3 {
          leaf-list exp {
            type string;
            ordered-by user;
          }
          leaf-list exp-except {
            type string;
            ordered-by user;
          }
        }
      }
      container then {
        uses apply-group;
        uses apply-macro;
        leaf log {
          type empty;
        }
        leaf syslog {
          type empty;
        }
        leaf sample {
          type empty;
        }
        choice choice-9 {
          leaf note {
            type empty;
          }
          leaf ignore {
            type empty;
          }
        }
      }
    }
  }

  grouping mpls-filter {
    leaf name {
      type string;
    }
    uses apply-group;
    uses apply-macro;
    leaf-list accounting-profile {
      type string;
      ordered-by user;
    }
    leaf fast-lookup-filter {
      type empty;
    }
    leaf interface-specific {
      type empty;
    }
    leaf physical-interface-filter {
      type empty;
    }
    leaf instance-shared {
      type empty;
    }
    list term {
      key "name";
      ordered-by user;
      leaf name {
        type string;
      }
      uses apply-group;
      uses apply-macro;
      leaf filter {
        type string;
      }
      container from {
        uses apply-group;
        uses apply-macro;
        choice choice-interface-group {
          leaf-list interface-group {
            type string;
            ordered-by user;
          }
          leaf-list interface-group-except {
            type string;
            ordered-by user;
          }
        }
        container ip-version {
          uses apply-group;
          uses apply-macro;
          container ipv4 {
            presence "enable ipv4";
            uses apply-group;
            uses apply-macro;
            list protocol {
              key "name";
              ordered-by user;
              leaf name {
                type string;
              }
              uses apply-group;
              uses apply-macro;
              choice choice-source-port {
                leaf-list source-port {
                  ordered-by user;
                  type string;
                }
                leaf-list source-port-except {
                  ordered-by user;
                  type string;
                }
              }
              choice choice-destination-port {
                leaf-list destination-port {
                  ordered-by user;
                  type string;
                }
                leaf-list destination-port-except {
                  ordered-by user;
                  type string;
                }
              }
            }
            list source-address {
              key "name";
              ordered-by user;
              uses firewall-addr-object;
            }
            list destination-address {
              key "name";
              ordered-by user;
              uses firewall-addr-object;
            }
          }
          container ipv6 {
            presence "enable ipv6";
            uses apply-group;
            uses apply-macro;
            list protocol {
              key "name";
              ordered-by user;
              leaf name {
                type string;
              }
              uses apply-group;
              uses apply-macro;
              choice choice-source-port {
                leaf-list source-port {
                  ordered-by user;
                  type string;
                }
                leaf-list source-port-except {
                  ordered-by user;
                  type string;
                }
              }
              choice choice-destination-port {
                leaf-list destination-port {
                  ordered-by user;
                  type string;
                }
                leaf-list destination-port-except {
                  ordered-by user;
                  type string;
                }
              }
            }
            list source-address {
              key "name";
              ordered-by user;
              uses firewall-addr6-object;
            }
            list destination-address {
              key "name";
              ordered-by user;
              uses firewall-addr6-object;
            }
          }
        }
        list label {
          key "name";
          ordered-by user;
          leaf name {
            type string;
          }
          uses apply-group;
          uses apply-macro;
        }
        choice choice-5 {
          leaf-list exp {
            type string;
            ordered-by user;
          }
          leaf-list exp-except {
            type string;
            ordered-by user;
          }
        }
        choice exp0_choice {
          case case_1 {
            leaf-list exp0 {
              ordered-by user;
              type string;
            }
          }
          case case_2 {
            leaf-list exp0-except {
              ordered-by user;
              type string;
            }
          }
        }
        list interface {
          key "name";
          ordered-by user;
          uses match-interface-object;
        }
        list interface-set {
          key "name";
          ordered-by user;
          uses match-interface-set-object;
        }
        choice choice-10 {
          leaf-list forwarding-class {
            type string;
            ordered-by user;
          }
          leaf-list forwarding-class-except {
            type string;
            ordered-by user;
          }
        }
        choice choice-ttl {
          leaf-list ttl {
            type string;
            ordered-by user;
          }
          leaf-list ttl-except {
            type string;
            ordered-by user;
          }
        }
        choice choice-11 {
          leaf-list loss-priority {
            ordered-by user;
            type string;
          }
          leaf-list loss-priority-except {
            ordered-by user;
            type string;
          }
        }
        container flexible-match-mask {
          presence "";
          uses match-mpls-flexible-mask;
        }
        container flexible-match-range {
          presence "enable flexible-match-range";
          uses match-mpls-flexible-range;
        }
        choice choice-policy-map {
          leaf-list policy-map {
            type string;
            ordered-by user;
          }
          leaf-list policy-map-except {
            type string;
            ordered-by user;
          }
        }
      }
      container then {
        uses apply-group;
        uses apply-macro;
        choice choice-3 {
          leaf policer {
            type string;
          }
          container three-color-policer {
            uses apply-group;
            uses apply-macro;
            choice choice-3 {
              leaf single-rate {
                type string;
              }
              leaf two-rate {
                type string;
              }
            }
          }
          leaf hierarchical-policer {
            type string;
          }
        }
        choice policy-map-choice {
          case case_1 {
            leaf clear-policy-map {
              type empty;
            }
          }
          case case_2 {
            leaf policy-map {
              type string;
            }
          }
        }
        container encapsulate {
          presence "";
          leaf tunnel-end-point {
            type string;
            mandatory true;
          }
        }
        leaf count {
          type string;
        }
        leaf sample {
          type empty;
        }
        leaf loss-priority {
          type string;
        }
        leaf forwarding-class {
          type string;
        }
        leaf port-mirror-instance {
          type string;
        }
        leaf port-mirror {
          type empty;
        }
        leaf inline-monitoring-instance {
          type string;
        }
        leaf packet-mode {
          type empty;
        }
        choice choice-14 {
          leaf accept {
            type empty;
          }
          leaf discard {
            type empty;
          }
          leaf next {
            type string;
          }
        }
      }
    }
  }

  grouping match-mpls-flexible-mask {
    uses apply-group;
    uses apply-macro;
    leaf match-start {
      type string;
    }
    leaf byte-offset {
      type uint32;
    }
    leaf bit-offset {
      type uint32;
    }
    leaf bit-length {
      type uint32;
    }
    leaf mask-in-hex {
      type string;
    }
    leaf prefix {
      type string;
      mandatory true;
    }
    leaf flexible-mask-name {
      type string;
    }
  }

  grouping match-mpls-flexible-range {
    uses apply-group;
    uses apply-macro;
    leaf match-start {
      type string;
    }
    leaf byte-offset {
      type uint32;
    }
    leaf bit-offset {
      type uint32;
    }
    leaf bit-length {
      type uint32;
    }
    choice choice-range {
      leaf range {
        type string;
      }
      leaf range-except {
        type string;
      }
    }
    leaf flexible-range-name {
      type string;
    }
  }

  grouping mpls-ifd-options {
    uses apply-group;
    uses apply-macro;
    container pop-all-labels {
      presence "enable pop-all-labels";
      uses apply-group;
      uses apply-macro;
      leaf-list required-depth {
        ordered-by user;
        type string;
      }
    }
  }

  grouping mpls-pm-family-output-type {
    uses apply-group;
    uses apply-macro;
    leaf server-profile {
      type string;
    }
  }

  grouping mrp-trace-options {
    uses apply-group;
    uses apply-macro;
    container file {
      presence "";
      uses trace-file-type;
    }
    list flag {
      key "name";
      ordered-by user;
      leaf name {
        type string;
      }
      leaf disable {
        type empty;
      }
    }
  }

  grouping multi-chassis-protection-group {
    leaf name {
      mandatory true;
      type ipv4addr;
    }
    uses apply-group;
    uses apply-macro;
    leaf interface {
      mandatory true;
      type string;
    }
  }

  grouping multicast-interface-options-type {
    leaf name {
      type interface-unit;
    }
    uses apply-group;
    uses apply-macro;
    container maximum-bandwidth {
      presence "enable maximum-bandwidth";
      leaf bandwidth-limit {
        type string;
      }
    }
    choice choice-5;
    container reverse-oif-mapping {
      presence "enable reverse-oif-mapping";
      uses apply-group;
      uses apply-macro;
      leaf no-qos-adjust {
        type empty;
      }
    }
    leaf subscriber-leave-timer {
      type uint32;
    }
    leaf no-qos-adjust {
      type empty;
    }
  }

  grouping multilink-object {
    uses apply-group;
    uses apply-macro;
    leaf fragment-threshold {
      type uint16;
    }
    leaf drop-timeout {
      type uint16;
    }
  }

  grouping name-resolution-cache-type {
    uses apply-group;
    uses apply-macro;
    container maximum-time-in-cache {
      presence "enable maximum-time-in-cache";
      choice choice-3 {
        leaf unlimited {
          type empty;
        }
        leaf time {
          type uint32;
        }
      }
    }
    leaf maximum-records-in-cache {
      type uint32;
    }
    leaf blacklist-period {
      type uint32;
    }
    container accelerations {
      presence "enable accelerations";
      uses apply-group;
      uses apply-macro;
      leaf no-refresh-before-ttl-expiry {
        type empty;
      }
      leaf initiate-next-queries {
        type empty;
      }
      leaf initiate-alternative-queries {
        type empty;
      }
    }
  }

  grouping nameserver-object {
    leaf name {
      type ipaddr;
    }
    leaf routing-instance {
      type string;
    }
    leaf source-address {
      type ipaddr;
    }
    uses apply-group;
    uses apply-macro;
  }

  grouping nat-pool-object {
    leaf name {
      type key-attribute-string-type;
    }
    uses apply-group;
    uses apply-macro;
    container pgcp {
      presence "enable pgcp";
      uses apply-group;
      uses apply-macro;
      leaf remotely-controlled {
        type empty;
      }
      leaf ports-per-session {
        type uint8;
      }
      leaf-list hint {
        type string;
        ordered-by user;
      }
      leaf-list transport {
        ordered-by user;
        type string;
      }
    }
    list address {
      key "name";
      ordered-by user;
      leaf name {
        type ipprefix-only;
      }
      uses apply-group;
      uses apply-macro;
    }
    list address-range {
      key "low high";
      ordered-by user;
      leaf low {
        type ipaddr;
      }
      leaf high {
        type ipaddr;
      }
    }
    container port {
      uses apply-group;
      uses apply-macro;
      choice choice-3 {
        container automatic {
          presence "enable automatic";
          uses apply-group;
          uses apply-macro;
          leaf auto {
            type empty;
          }
          leaf random-allocation {
            type empty;
          }
        }
        container range {
          presence "";
          leaf low {
            type uint16;
          }
          leaf high {
            type uint16;
          }
          leaf random-allocation {
            type empty;
          }
        }
      }
      choice choice-secured-port-block-allocation {
        container secured-port-block-allocation {
          presence "enable secured-port-block-allocation";
          leaf block-size {
            type uint16;
          }
          leaf max-blocks-per-address {
            type uint16;
          }
          leaf active-block-timeout {
            type uint32;
          }
        }
        container deterministic-port-block-allocation {
          presence "enable deterministic-port-block-allocation";
          leaf block-size {
            type uint16;
          }
          leaf include-boundary-addresses {
            type empty;
          }
        }
      }
      leaf preserve-parity {
        type empty;
      }
      leaf preserve-range {
        type empty;
      }
    }
    container address-allocation {
      presence "enable address-allocation";
      uses apply-group;
      uses apply-macro;
      leaf round-robin {
        type empty;
      }
    }
    leaf mapping-timeout {
      type int32;
    }
    leaf ei-mapping-timeout {
      units "second";
      type int32;
    }
    leaf app-mapping-timeout {
      units "second";
      type int32;
    }
    leaf limit-ports-per-address {
      units "connections";
      type int32;
    }
    container snmp-trap-thresholds {
      presence "enable snmp-trap-thresholds";
      uses apply-group;
      uses apply-macro;
      container address-port {
        presence "";
        leaf low {
          mandatory true;
          units "percent";
          type uint16;
        }
        leaf high {
          mandatory true;
          units "percent";
          type uint16;
        }
      }
    }
  }

  grouping nat-rule-object {
    leaf name {
      type key-attribute-string-type;
    }
    uses apply-group;
    uses apply-macro;
    leaf match-direction {
      type string;
    }
    list term {
      key "name";
      ordered-by user;
      leaf name {
        type key-attribute-string-type;
      }
      uses apply-group;
      uses apply-macro;
      leaf nat-type {
        type string;
      }
      container from {
        uses sfw-match-object;
      }
      container then {
        uses apply-group;
        uses apply-macro;
        leaf no-translation {
          type empty;
        }
        leaf port-forwarding-mappings {
          type string;
        }
        container translated {
          presence "";
          uses apply-group;
          uses apply-macro;
          choice choice-3 {
            leaf source-pool {
              type string;
            }
            leaf source-prefix {
              type ipprefix-only;
            }
          }
          choice choice-4 {
            leaf destination-pool {
              type string;
            }
            leaf destination-prefix {
              type ipprefix-only;
            }
          }
          choice choice-5 {
            leaf dns-alg-pool {
              type string;
            }
            leaf dns-alg-prefix {
              type ipprefix-only;
            }
          }
          choice choice-6 {
            leaf use-dns-map-for-destination-translation {
              type empty;
            }
          }
          choice choice-7 {
            leaf overload-pool {
              type string;
            }
            leaf overload-prefix {
              type ipprefix-only;
            }
          }
          container translation-type {
            uses apply-group;
            uses apply-macro;
            leaf source {
              type string;
            }
            leaf destination {
              type string;
            }
            container basic-nat44 {
              presence "enable basic-nat44";
              uses apply-group;
              uses apply-macro;
            }
            container dynamic-nat44 {
              presence "enable dynamic-nat44";
              uses apply-group;
              uses apply-macro;
            }
            container napt-44 {
              presence "enable napt-44";
              uses apply-group;
              uses apply-macro;
            }
            container dnat-44 {
              presence "enable dnat-44";
              uses apply-group;
              uses apply-macro;
            }
            container stateful-nat64 {
              presence "enable stateful-nat64";
              uses apply-group;
              uses apply-macro;
            }
            container basic-nat-pt {
              presence "enable basic-nat-pt";
              uses apply-group;
              uses apply-macro;
            }
            container napt-pt {
              presence "enable napt-pt";
              uses apply-group;
              uses apply-macro;
            }
            container basic-nat66 {
              presence "enable basic-nat66";
              uses apply-group;
              uses apply-macro;
            }
            container nptv6 {
              presence "enable nptv6";
              uses apply-group;
              uses apply-macro;
            }
            container napt-66 {
              presence "enable napt-66";
              uses apply-group;
              uses apply-macro;
            }
            container twice-napt-44 {
              presence "enable twice-napt-44";
              uses apply-group;
              uses apply-macro;
            }
            container twice-basic-nat-44 {
              presence "enable twice-basic-nat-44";
              uses apply-group;
              uses apply-macro;
            }
            container twice-dynamic-nat-44 {
              presence "enable twice-dynamic-nat-44";
              uses apply-group;
              uses apply-macro;
            }
            container deterministic-napt44 {
              presence "enable deterministic-napt44";
              uses apply-group;
              uses apply-macro;
            }
          }
          leaf mapping-type {
            type string;
          }
          container secure-nat-mapping {
            presence "enable secure-nat-mapping";
            uses apply-group;
            uses apply-macro;
            leaf eif-flow-limit {
              type uint16;
            }
            leaf mapping-refresh {
              type string;
            }
          }
          container filtering-type {
            uses apply-group;
            uses apply-macro;
            container endpoint-independent {
              presence "enable endpoint-independent";
              uses apply-group;
              uses apply-macro;
              list prefix-list {
                key "name";
                ordered-by user;
                leaf name {
                  type string;
                }
                leaf except {
                  type empty;
                }
              }
            }
          }
          leaf address-pooling {
            type string;
          }
        }
        leaf syslog {
          type empty;
        }
      }
    }
  }

  grouping network-type {
    leaf name {
      type ipprefix;
    }
    uses apply-group;
    uses apply-macro;
  }

  grouping new-call-then-type {
    uses apply-group;
    uses apply-macro;
    leaf trace {
      type empty;
    }
    container media-policy {
      uses apply-group;
      uses apply-macro;
      choice choice-3 {
        leaf no-anchoring {
          type empty;
        }
        leaf media-release {
          type empty;
        }
      }
      container nat-traversal {
        presence "enable nat-traversal";
        uses apply-group;
        uses apply-macro;
        leaf nat-traversal-strategy {
          type string;
        }
        leaf force-bidirectional-media {
          type empty;
        }
      }
      container data-inactivity-detection {
        uses apply-group;
        uses apply-macro;
        leaf inactivity-duration {
          type uint16;
        }
      }
      leaf service-class {
        type string;
      }
    }
  }

  grouping new-call-usage-set-type {
    leaf name {
      type string;
    }
    uses apply-group;
    uses apply-macro;
    leaf-list policy-name {
      ordered-by user;
      type string;
    }
  }

  grouping new-registration-set-type {
    leaf name {
      type string;
    }
    uses apply-group;
    uses apply-macro;
    leaf-list policy-name {
      ordered-by user;
      type string;
    }
  }

  grouping new-transaction-set-type {
    leaf name {
      type string;
    }
    uses apply-group;
    uses apply-macro;
    leaf-list policy-name {
      ordered-by user;
      type string;
    }
  }

  grouping next-hop-group-intf-type {
    leaf name {
      type interface-name;
    }
    uses apply-group;
    uses apply-macro;
    list next-hop {
      key "name";
      ordered-by user;
      uses inet-next-hop-type;
    }
  }

  grouping next-hop-subgroup-intf-type {
    leaf name {
      type interface-name;
    }
    uses apply-group;
    uses apply-macro;
    list next-hop {
      key "name";
      ordered-by user;
      uses inet-next-hop-type;
    }
  }

  grouping otn-options-type {
    uses apply-group;
    uses apply-macro;
    leaf laser-enable {
      type empty;
    }
    leaf no-laser-enable {
      type empty;
    }
    leaf line-loopback {
      type empty;
    }
    leaf no-line-loopback {
      type empty;
    }
    leaf fec {
      type string;
    }
    leaf rate {
      type string;
    }
    container bytes {
      uses apply-group;
      uses apply-macro;
      leaf transmit-payload-type {
        type uint32;
      }
    }
    container tti {
      uses apply-group;
      uses apply-macro;
      leaf otu-dapi {
        type string;
      }
      leaf otu-sapi {
        type string;
      }
      leaf otu-expected-receive-dapi {
        type string;
      }
      leaf otu-expected-receive-sapi {
        type string;
      }
      leaf odu-dapi {
        type string;
      }
      leaf odu-sapi {
        type string;
      }
      leaf odu-expected-receive-dapi {
        type string;
      }
      leaf odu-expected-receive-sapi {
        type string;
      }
    }
    container trigger {
      uses apply-group;
      uses apply-macro;
      container oc-los {
        choice choice-3 {
          leaf ignore {
            type empty;
          }
          container hold-time {
            presence "";
            leaf up {
              type uint32;
            }
            leaf down {
              type uint32;
            }
          }
        }
      }
      container oc-lof {
        choice choice-3 {
          leaf ignore {
            type empty;
          }
          container hold-time {
            presence "";
            leaf up {
              type uint32;
            }
            leaf down {
              type uint32;
            }
          }
        }
      }
      container oc-lom {
        choice choice-3 {
          leaf ignore {
            type empty;
          }
          container hold-time {
            presence "";
            leaf up {
              type uint32;
            }
            leaf down {
              type uint32;
            }
          }
        }
      }
      container oc-wavelength-lock {
        choice choice-3 {
          leaf ignore {
            type empty;
          }
          container hold-time {
            presence "";
            leaf up {
              type uint32;
            }
            leaf down {
              type uint32;
            }
          }
        }
      }
      container otu-ais {
        choice choice-3 {
          leaf ignore {
            type empty;
          }
          container hold-time {
            presence "";
            leaf up {
              type uint32;
            }
            leaf down {
              type uint32;
            }
          }
        }
      }
      container otu-bdi {
        choice choice-3 {
          leaf ignore {
            type empty;
          }
          container hold-time {
            presence "";
            leaf up {
              type uint32;
            }
            leaf down {
              type uint32;
            }
          }
        }
      }
      container otu-iae {
        choice choice-3 {
          leaf ignore {
            type empty;
          }
          container hold-time {
            presence "";
            leaf up {
              type uint32;
            }
            leaf down {
              type uint32;
            }
          }
        }
      }
      container otu-ttim {
        choice choice-3 {
          leaf ignore {
            type empty;
          }
          container hold-time {
            presence "";
            leaf up {
              type uint32;
            }
            leaf down {
              type uint32;
            }
          }
        }
      }
      container otu-sd {
        choice choice-3 {
          leaf ignore {
            type empty;
          }
          container hold-time {
            presence "";
            leaf up {
              type uint32;
            }
            leaf down {
              type uint32;
            }
          }
        }
      }
      container otu-fec-deg {
        choice choice-3 {
          leaf ignore {
            type empty;
          }
          container hold-time {
            presence "";
            leaf up {
              type uint32;
            }
            leaf down {
              type uint32;
            }
          }
        }
      }
      container otu-fec-exe {
        choice choice-3 {
          leaf ignore {
            type empty;
          }
          container hold-time {
            presence "";
            leaf up {
              type uint32;
            }
            leaf down {
              type uint32;
            }
          }
        }
      }
      container otu-tca-es {
        choice choice-3 {
          leaf ignore {
            type empty;
          }
          container hold-time {
            presence "";
            leaf up {
              type uint32;
            }
            leaf down {
              type uint32;
            }
          }
        }
      }
      container otu-tca-ses {
        choice choice-3 {
          leaf ignore {
            type empty;
          }
          container hold-time {
            presence "";
            leaf up {
              type uint32;
            }
            leaf down {
              type uint32;
            }
          }
        }
      }
      container otu-tca-uas {
        choice choice-3 {
          leaf ignore {
            type empty;
          }
          container hold-time {
            presence "";
            leaf up {
              type uint32;
            }
            leaf down {
              type uint32;
            }
          }
        }
      }
      container otu-tca-bbe {
        choice choice-3 {
          leaf ignore {
            type empty;
          }
          container hold-time {
            presence "";
            leaf up {
              type uint32;
            }
            leaf down {
              type uint32;
            }
          }
        }
      }
      container odu-ais {
        choice choice-3 {
          leaf ignore {
            type empty;
          }
          container hold-time {
            presence "";
            leaf up {
              type uint32;
            }
            leaf down {
              type uint32;
            }
          }
        }
      }
      container odu-bdi {
        choice choice-3 {
          leaf ignore {
            type empty;
          }
          container hold-time {
            presence "";
            leaf up {
              type uint32;
            }
            leaf down {
              type uint32;
            }
          }
        }
      }
      container odu-oci {
        choice choice-3 {
          leaf ignore {
            type empty;
          }
          container hold-time {
            presence "";
            leaf up {
              type uint32;
            }
            leaf down {
              type uint32;
            }
          }
        }
      }
      container odu-lck {
        choice choice-3 {
          leaf ignore {
            type empty;
          }
          container hold-time {
            presence "";
            leaf up {
              type uint32;
            }
            leaf down {
              type uint32;
            }
          }
        }
      }
      container odu-ttim {
        choice choice-3 {
          leaf ignore {
            type empty;
          }
          container hold-time {
            presence "";
            leaf up {
              type uint32;
            }
            leaf down {
              type uint32;
            }
          }
        }
      }
      container odu-sd {
        choice choice-3 {
          leaf ignore {
            type empty;
          }
          container hold-time {
            presence "";
            leaf up {
              type uint32;
            }
            leaf down {
              type uint32;
            }
          }
        }
      }
      container odu-tca-es {
        choice choice-3 {
          leaf ignore {
            type empty;
          }
          container hold-time {
            presence "";
            leaf up {
              type uint32;
            }
            leaf down {
              type uint32;
            }
          }
        }
      }
      container odu-tca-ses {
        choice choice-3 {
          leaf ignore {
            type empty;
          }
          container hold-time {
            presence "";
            leaf up {
              type uint32;
            }
            leaf down {
              type uint32;
            }
          }
        }
      }
      container odu-tca-uas {
        choice choice-3 {
          leaf ignore {
            type empty;
          }
          container hold-time {
            presence "";
            leaf up {
              type uint32;
            }
            leaf down {
              type uint32;
            }
          }
        }
      }
      container odu-tca-bbe {
        choice choice-3 {
          leaf ignore {
            type empty;
          }
          container hold-time {
            presence "";
            leaf up {
              type uint32;
            }
            leaf down {
              type uint32;
            }
          }
        }
      }
      container opu-ptim {
        choice choice-3 {
          leaf ignore {
            type empty;
          }
          container hold-time {
            presence "";
            leaf up {
              type uint32;
            }
            leaf down {
              type uint32;
            }
          }
        }
      }
    }
  }

  grouping output-plugin {
    leaf name {
      type string;
    }
    uses apply-group;
    uses apply-macro;
    list parameters {
      key "name";
      ordered-by user;
      uses parameter-pair;
    }
  }

  grouping override-local-server-type {
    uses apply-group;
    uses apply-macro;
    leaf interface-client-limit {
      type uint32;
    }
    leaf no-arp {
      type empty;
    }
    container client-discover-match {
      presence "enable client-discover-match";
      choice choice-3 {
        leaf option60-and-option82 {
          type empty;
        }
      }
    }
  }

  grouping override-type {
    uses apply-group;
    uses apply-macro;
    leaf no-unicast-replies {
      type empty;
    }
    leaf allow-snooped-clients {
      type empty;
    }
    leaf no-allow-snooped-clients {
      type empty;
    }
    leaf allow-no-end-option {
      type empty;
    }
    leaf always-write-giaddr {
      type empty;
    }
    container always-write-option-82 {
      presence "enable always-write-option-82";
      uses write-option-82-type;
    }
    leaf user-defined-option-82 {
      type string;
    }
    leaf layer2-unicast-replies {
      type empty;
    }
    leaf trust-option-82 {
      type empty;
    }
    leaf delay-authentication {
      type empty;
    }
    leaf disable-relay {
      type empty;
    }
    leaf no-bind-on-request {
      type empty;
    }
    leaf interface-client-limit {
      type uint32;
    }
    leaf no-arp {
      type empty;
    }
    leaf bootp-support {
      type empty;
    }
    leaf dual-stack {
      type string;
    }
    container client-discover-match {
      presence "enable client-discover-match";
      choice choice-option60-and-option82 {
        leaf option60-and-option82 {
          type empty;
        }
        leaf incoming-interface {
          type empty;
        }
      }
    }
    container proxy-mode {
      presence "enable proxy-mode";
      container undocumented {
        leaf single-proxy {
          type empty;
        }
      }
    }
    leaf asymmetric-lease-time {
      units "seconds";
      type uint32;
    }
    container replace-ip-source-with {
      leaf giaddr {
        type empty;
      }
    }
    leaf send-release-on-delete {
      type empty;
    }
    leaf apply-secondary-as-giaddr {
      type empty;
    }
    leaf relay-source {
      type interface-name;
    }
    leaf delete-binding-on-renegotiation {
      type empty;
    }
  }

  grouping p2mp-ldp-lsp-nh-obj {
    uses apply-group;
    uses apply-macro;
    list root-address {
      key "name";
      leaf name {
        type ipaddr;
      }
      uses apply-group;
      uses apply-macro;
      leaf lsp-id {
        type uint32;
      }
      list group-address {
        key "name";
        leaf name {
          type ipaddr;
        }
        uses apply-group;
        uses apply-macro;
        list source-address {
          key "name";
          leaf name {
            type ipaddr;
          }
          uses apply-group;
          uses apply-macro;
        }
      }
    }
  }

  grouping packet-accounting-output-type {
    uses apply-group;
    uses apply-macro;
    leaf aggregate-export-interval {
      type uint32;
    }
    leaf flow-inactive-timeout {
      type uint32;
    }
    leaf flow-active-timeout {
      type uint32;
    }
    list cflowd {
      key "name";
      uses cflowd-packet-accounting-type;
    }
    list interface {
      key "name";
      uses packet-export-intf-type;
    }
  }

  grouping cflowd-packet-accounting-type {
    leaf name {
      type ipv4addr;
    }
    uses apply-group;
    uses apply-macro;
    leaf port {
      type uint16;
    }
    leaf version {
      type string;
    }
    leaf autonomous-system-type {
      type string;
    }
    container aggregation {
      uses aggregation-type;
    }
  }

  grouping aggregation-type {
    uses apply-group;
    uses apply-macro;
    leaf autonomous-system {
      type empty;
    }
    leaf protocol-port {
      type empty;
    }
    leaf source-prefix {
      type empty;
    }
    leaf destination-prefix {
      type empty;
    }
    container source-destination-prefix {
      presence "enable source-destination-prefix";
      uses apply-group;
      uses apply-macro;
      leaf caida-compliant {
        type empty;
      }
    }
  }

  grouping packet-export-intf-type {
    leaf name {
      type interface-device;
    }
    uses apply-group;
    uses apply-macro;
    leaf engine-id {
      type uint8;
    }
    leaf engine-type {
      type uint8;
    }
    leaf source-address {
      type ipv4addr;
    }
    container export-port {
      presence "enable export-port";
      uses export-port-address-type;
    }
  }

  grouping export-port-address-type {
    uses apply-group;
    uses apply-macro;
    leaf address {
      type ipv4prefix;
    }
    leaf gateway {
      type ipv4addr;
    }
  }

  grouping parameter-pair {
    leaf name {
      type string;
    }
    uses apply-group;
    uses apply-macro;
    leaf value {
      type string;
    }
  }

  grouping pccd-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    list flag {
      key "name";
      ordered-by user;
      leaf name {
        type string;
      }
    }
  }

  grouping peer-group {
    leaf name {
      type ipv4addr;
    }
    uses apply-group;
    uses apply-macro;
    leaf local-ip-addr {
      type ipv4addr;
    }
    leaf session-establishment-hold-time {
      type uint32;
    }
    leaf-list redundancy-group-id-list {
      type uint32;
      ordered-by user;
    }
    container liveness-detection {
      presence "enable liveness-detection";
      uses apply-group;
      uses apply-macro;
      leaf version {
        type string;
      }
      leaf minimum-interval {
        type uint32;
      }
      leaf minimum-receive-interval {
        type uint32;
      }
      leaf multiplier {
        type uint32;
      }
      choice choice-11 {
        leaf no-adaptation {
          type empty;
        }
      }
      container transmit-interval {
        uses apply-group;
        uses apply-macro;
        leaf minimum-interval {
          type uint32;
        }
        leaf threshold {
          type uint32;
        }
      }
      container detection-time {
        uses apply-group;
        uses apply-macro;
        leaf threshold {
          type uint32;
        }
      }
    }
    leaf authentication-key {
      type unreadable;
    }
    container undocumented {
      container tcp-ka {
        leaf detection-time {
          type uint32;
        }
      }
    }
  }

  grouping periodic-oam {
    uses apply-group;
    uses apply-macro;
    container mpls-tp-mode {
      presence "enable mpls-tp-mode";
      uses apply-advanced;
      container lsping-channel-type {
        uses apply-advanced;
        choice action-choice {
          case case_1 {
            leaf ipv4 {
              type empty;
            }
          }
          case case_2 {
            leaf on-demand-cv {
              type empty;
            }
          }
        }
      }
    }
    container bfd-port {
      uses apply-group;
      uses apply-macro;
      leaf-list import {
        type policy-algebra;
        ordered-by user;
      }
    }
    container bfd-liveness-detection {
      uses apply-group;
      uses apply-macro;
      leaf version {
        type string;
      }
      leaf minimum-interval {
        type uint32;
      }
      leaf minimum-transmit-interval {
        units "milliseconds";
        type uint32;
      }
      leaf minimum-receive-interval {
        type uint32;
      }
      leaf multiplier {
        type uint32;
      }
      choice choice-11 {
        leaf no-adaptation {
          type empty;
        }
      }
      container transmit-interval {
        uses apply-group;
        uses apply-macro;
        leaf minimum-interval {
          type uint32;
        }
        leaf threshold {
          type uint32;
        }
      }
      container detection-time {
        uses apply-group;
        uses apply-macro;
        leaf threshold {
          type uint32;
        }
      }
      container failure-action {
        choice choice-3 {
          leaf teardown {
            type empty;
          }
          container make-before-break {
            presence "enable make-before-break";
            uses apply-group;
            uses apply-macro;
            leaf teardown-timeout {
              type uint32;
            }
          }
        }
      }
    }
    container performance-monitoring {
      uses apply-group;
      uses apply-macro;
      container traceoptions {
        uses apply-group;
        uses apply-macro;
        container file {
          presence "";
          uses trace-file-type;
        }
        list flag {
          key "name";
          ordered-by user;
          leaf name {
            type string;
          }
        }
      }
      container querier {
        uses apply-group;
        uses apply-macro;
        container loss {
          uses apply-group;
          uses apply-macro;
          list traffic-class {
            key "name";
            leaf name {
              type string;
            }
            uses apply-group;
            uses apply-macro;
            leaf query-interval {
              units "milliseconds";
              type uint32;
            }
            leaf measurement-quantity {
              type string;
            }
            leaf average-sample-size {
              type uint16;
            }
            leaf loss-threshold {
              type uint32;
            }
            leaf loss-threshold-window {
              type uint32;
            }
          }
        }
        container delay {
          uses apply-group;
          uses apply-macro;
          list traffic-class {
            key "name";
            leaf name {
              type string;
            }
            uses apply-group;
            uses apply-macro;
            leaf query-interval {
              units "milliseconds";
              type uint32;
            }
            leaf padding-size {
              type uint16;
            }
            leaf average-sample-size {
              type uint16;
            }
            leaf twcd-delay-threshold {
              units "microseconds";
              type uint32;
            }
            leaf rtt-delay-threshold {
              units "microseconds";
              type uint32;
            }
          }
        }
        container loss-delay {
          uses apply-group;
          uses apply-macro;
          list traffic-class {
            key "name";
            leaf name {
              type string;
            }
            uses apply-group;
            uses apply-macro;
            leaf query-interval {
              units "milliseconds";
              type uint32;
            }
            leaf measurement-quantity {
              type string;
            }
            leaf padding-size {
              type uint16;
            }
            leaf average-sample-size {
              type uint16;
            }
            leaf loss-threshold {
              type uint32;
            }
            leaf loss-threshold-window {
              type uint32;
            }
            leaf twcd-delay-threshold {
              units "microseconds";
              type uint32;
            }
            leaf rtt-delay-threshold {
              units "microseconds";
              type uint32;
            }
          }
        }
      }
      container responder {
        uses apply-group;
        uses apply-macro;
        container loss {
          uses apply-group;
          uses apply-macro;
          leaf min-query-interval {
            units "milliseconds";
            type uint32;
          }
        }
        container delay {
          uses apply-group;
          uses apply-macro;
          leaf min-query-interval {
            units "milliseconds";
            type uint32;
          }
        }
      }
    }
    leaf lsp-ping-interval {
      type uint16;
    }
    leaf lsp-ping-multiplier {
      type uint16;
    }
    container traceoptions {
      uses apply-group;
      uses apply-macro;
      leaf no-remote-trace {
        type empty;
      }
      container file {
        leaf filename {
          type string;
        }
        leaf size {
          type string;
        }
        leaf files {
          type uint32;
        }
        leaf world-readable {
          type empty;
        }
        leaf no-world-readable {
          type empty;
        }
        leaf match {
          type regular-expression;
        }
      }
      list flag {
        key "name";
        ordered-by user;
        leaf name {
          type string;
        }
      }
    }
  }

  grouping pf-mapping {
    leaf name {
      type key-attribute-string-type;
    }
    uses apply-group;
    uses apply-macro;
    list destined-port {
      key "port translated-port";
      ordered-by user;
      leaf port {
        type key-attribute-ulong-type;
      }
      leaf translated-port {
        type key-attribute-ulong-type;
      }
    }
  }

  grouping pgcp-gateway-object {
    leaf name {
      type key-attribute-string-type;
    }
    uses apply-group;
    uses apply-macro;
    leaf gateway-address {
      type ipv4addr;
    }
    leaf routing-instance {
      type string;
    }
    leaf gateway-port {
      type uint16;
    }
    leaf cleanup-timeout {
      type uint16;
    }
    leaf service-state {
      type string;
    }
    container h248-timers {
      presence "enable h248-timers";
      uses pgcp-h248-timers-object;
    }
    container h248-properties {
      presence "enable h248-properties";
      uses pgcp-h248-properties-object;
    }
    container h248-options {
      presence "enable h248-options";
      uses pgcp-h248-options-object;
    }
    leaf max-concurrent-calls {
      type uint32;
    }
    list gateway-controller {
      key "name";
      ordered-by user;
      uses pgcp-controller-object;
    }
    container monitor {
      uses apply-group;
      uses apply-macro;
      container media {
        presence "enable media";
        uses apply-group;
        uses apply-macro;
        leaf rtp {
          type empty;
        }
        leaf rtcp {
          type empty;
        }
      }
    }
    container graceful-restart {
      presence "enable graceful-restart";
      uses apply-group;
      uses apply-macro;
      leaf maximum-synchronization-mismatches {
        type uint32;
      }
      leaf no-synchronization {
        type empty;
      }
      leaf catchup-replication-delay {
        type uint16;
      }
    }
    container fast-update-filters {
      presence "enable fast-update-filters";
      uses apply-group;
      uses apply-macro;
      leaf maximum-terms {
        type uint64;
      }
      leaf maximum-term-percentage {
        type uint8;
      }
    }
    container session-mirroring {
      presence "enable session-mirroring";
      uses pgcp-gateway-session-mirroring-object;
    }
    container data-inactivity-detection {
      uses apply-group;
      uses apply-macro;
      leaf inactivity-delay {
        type uint16;
      }
      leaf latch-deadlock-delay {
        type uint16;
      }
      leaf send-notification-on-delay {
        type empty;
      }
      leaf inactivity-duration {
        type uint32;
      }
      leaf stop-detection-on-drop {
        type empty;
      }
      leaf no-rtcp-check {
        type empty;
      }
      container report-service-change {
        presence "";
        uses apply-group;
        uses apply-macro;
        leaf service-change-type {
          type string;
        }
      }
    }
    container overload-control {
      presence "enable overload-control";
      uses apply-group;
      uses apply-macro;
      leaf queue-limit-percentage {
        type uint8;
      }
      leaf reject-new-calls-threshold {
        type uint8;
      }
      leaf reject-all-commands-threshold {
        type uint8;
      }
      leaf queue-maximum-length {
        type uint16;
      }
      leaf error-code {
        type uint16;
      }
    }
    container platform {
      presence "enable platform";
      uses apply-group;
      uses apply-macro;
      choice choice-3 {
        leaf routing-engine {
          type empty;
        }
        leaf device {
          type interface-device;
        }
      }
    }
    leaf ipsec-transport-security-association {
      type string;
    }
  }

  grouping pgcp-controller-object {
    leaf name {
      type key-attribute-string-type;
    }
    uses apply-group;
    uses apply-macro;
    leaf controller-address {
      type ipv4addr;
    }
    leaf controller-port {
      type uint16;
    }
    container interim-ah-scheme {
      presence "";
      uses pgcp-interim-ah-scheme-object;
    }
    choice choice-9 {
      leaf remote-controller {
        type empty;
      }
      leaf local-controller {
        type string;
      }
    }
  }

  grouping pgcp-gateway-session-mirroring-object {
    uses apply-group;
    uses apply-macro;
    leaf-list delivery-function {
      type string;
      ordered-by user;
    }
    leaf disable-session-mirroring {
      type empty;
    }
  }

  grouping pgcp-h248-options-object {
    uses apply-group;
    uses apply-macro;
    container service-change {
      presence "enable service-change";
      uses pgcp-h248-service-change-object;
    }
    leaf audit-observed-events-returns {
      type empty;
    }
    container encoding {
      presence "enable encoding";
      uses apply-group;
      uses apply-macro;
      leaf no-octet-string-bit-mirroring {
        type empty;
      }
      leaf use-lower-case {
        type empty;
      }
    }
    container h248-profile {
      presence "";
      uses apply-group;
      uses apply-macro;
      leaf profile-name {
        type string;
      }
      leaf profile-version {
        type uint32;
      }
    }
    leaf accept-emergency-calls-while-graceful {
      type empty;
    }
    leaf implicit-tcp-latch {
      type empty;
    }
    leaf implicit-tcp-source-filter {
      type empty;
    }
  }

  grouping pgcp-h248-service-change-object {
    uses apply-group;
    uses apply-macro;
    container control-association-indications {
      presence "enable control-association-indications";
      uses control-association-indications-object;
    }
    container virtual-interface-indications {
      presence "enable virtual-interface-indications";
      uses virtual-interface-indications-object;
    }
    container context-indications {
      presence "enable context-indications";
      uses context-indications-object;
    }
    leaf use-wildcard-response {
      type empty;
    }
  }

  grouping context-indications-object {
    uses apply-group;
    uses apply-macro;
    leaf state-loss {
      type string;
    }
  }

  grouping control-association-indications-object {
    uses apply-group;
    uses apply-macro;
    container up {
      presence "enable up";
      uses pgcp-association-up-object;
    }
    container down {
      presence "enable down";
      uses pgcp-association-down-object;
    }
    container disconnect {
      presence "enable disconnect";
      uses pgcp-association-disconnect-object;
    }
  }

  grouping pgcp-association-disconnect-object {
    uses apply-group;
    uses apply-macro;
    leaf reconnect {
      type string;
    }
    leaf controller-failure {
      type string;
    }
  }

  grouping pgcp-association-down-object {
    uses apply-group;
    uses apply-macro;
    leaf administrative {
      type string;
    }
    leaf failure {
      type string;
    }
    leaf graceful {
      type string;
    }
  }

  grouping pgcp-association-up-object {
    uses apply-group;
    uses apply-macro;
    leaf failover-cold {
      type string;
    }
    leaf failover-warm {
      type string;
    }
    leaf cancel-graceful {
      type string;
    }
  }

  grouping pgcp-h248-properties-object {
    uses apply-group;
    uses apply-macro;
    container base-root {
      presence "enable base-root";
      uses pgcp-h248-base-root-object;
    }
    container segmentation {
      presence "enable segmentation";
      uses pgcp-h248-segmentation-object;
    }
    container diffserv {
      presence "enable diffserv";
      uses pgcp-h248-diffserv-object;
    }
    container hanging-termination-detection {
      presence "enable hanging-termination-detection";
      uses pgcp-h248-hangterm-object;
    }
    container traffic-management {
      presence "enable traffic-management";
      uses pgcp-h248-traffic-management-object;
    }
    container notification-behavior {
      presence "enable notification-behavior";
      uses pgcp-h248-notification-behavior-object;
    }
    container application-data-inactivity-detection {
      presence "enable application-data-inactivity-detection";
      uses pgcp-h248-application-data-inactivity-detection-object;
    }
    container event-timestamp-notification {
      presence "enable event-timestamp-notification";
      uses pgcp-h248-event-timestamp-notification-object;
    }
    container inactivity-timer {
      presence "enable inactivity-timer";
      uses pgcp-h248-inactivity-timer-object;
    }
  }

  grouping pgcp-h248-application-data-inactivity-detection-object {
    uses apply-group;
    uses apply-macro;
    leaf ip-flow-stop-detection {
      type string;
    }
  }

  grouping pgcp-h248-event-timestamp-notification-object {
    uses apply-group;
    uses apply-macro;
    leaf request-timestamp {
      type string;
    }
  }

  grouping pgcp-h248-hangterm-object {
    uses apply-group;
    uses apply-macro;
    leaf timerx {
      type uint32;
    }
  }

  grouping pgcp-h248-inactivity-timer-object {
    uses apply-group;
    uses apply-macro;
    container inactivity-timeout {
      presence "enable inactivity-timeout";
      uses apply-group;
      uses apply-macro;
      leaf detect {
        type empty;
      }
      container maximum-inactivity-time {
        uses apply-group;
        uses apply-macro;
        leaf default {
          type uint16;
        }
        leaf minimum {
          type uint16;
        }
        leaf maximum {
          type uint16;
        }
      }
    }
  }

  grouping pgcp-h248-notification-behavior-object {
    uses apply-group;
    uses apply-macro;
    container notification-regulation {
      presence "enable notification-regulation";
      uses apply-group;
      uses apply-macro;
      leaf default {
        type string;
      }
    }
  }

  grouping pgcp-h248-base-root-object {
    uses apply-group;
    uses apply-macro;
    container normal-mg-execution-time {
      presence "enable normal-mg-execution-time";
      uses apply-group;
      uses apply-macro;
      leaf default {
        type uint16;
      }
      leaf minimum {
        type uint16;
      }
      leaf maximum {
        type uint16;
      }
    }
    container mg-provisional-response-timer-value {
      presence "enable mg-provisional-response-timer-value";
      uses apply-group;
      uses apply-macro;
      leaf default {
        type uint16;
      }
      leaf minimum {
        type uint16;
      }
      leaf maximum {
        type uint16;
      }
    }
    container mg-originated-pending-limit {
      presence "enable mg-originated-pending-limit";
      uses apply-group;
      uses apply-macro;
      leaf default {
        type uint16;
      }
      leaf minimum {
        type uint16;
      }
      leaf maximum {
        type uint16;
      }
    }
    container normal-mgc-execution-time {
      presence "enable normal-mgc-execution-time";
      uses apply-group;
      uses apply-macro;
      leaf default {
        type uint16;
      }
      leaf minimum {
        type uint16;
      }
      leaf maximum {
        type uint16;
      }
    }
    container mgc-provisional-response-timer-value {
      presence "enable mgc-provisional-response-timer-value";
      uses apply-group;
      uses apply-macro;
      leaf default {
        type uint16;
      }
      leaf minimum {
        type uint16;
      }
      leaf maximum {
        type uint16;
      }
    }
    container mgc-originated-pending-limit {
      presence "enable mgc-originated-pending-limit";
      uses apply-group;
      uses apply-macro;
      leaf default {
        type uint16;
      }
      leaf minimum {
        type uint16;
      }
      leaf maximum {
        type uint16;
      }
    }
  }

  grouping pgcp-h248-diffserv-object {
    uses apply-group;
    uses apply-macro;
    container dscp {
      presence "enable dscp";
      uses apply-group;
      uses apply-macro;
      leaf default {
        type string;
      }
      leaf ignore-signaled-value {
        type empty;
      }
    }
  }

  grouping pgcp-h248-segmentation-object {
    uses apply-group;
    uses apply-macro;
    container mgc-segmentation-timer {
      presence "enable mgc-segmentation-timer";
      uses apply-group;
      uses apply-macro;
      leaf default {
        type int32;
      }
      leaf minimum {
        type int32;
      }
      leaf maximum {
        type int32;
      }
    }
    container mgc-maximum-pdu-size {
      presence "enable mgc-maximum-pdu-size";
      uses apply-group;
      uses apply-macro;
      leaf default {
        type int32;
      }
      leaf minimum {
        type int32;
      }
      leaf maximum {
        type int32;
      }
    }
    container mg-segmentation-timer {
      presence "enable mg-segmentation-timer";
      uses apply-group;
      uses apply-macro;
      leaf default {
        type int32;
      }
      leaf minimum {
        type int32;
      }
      leaf maximum {
        type int32;
      }
    }
    container mg-maximum-pdu-size {
      presence "enable mg-maximum-pdu-size";
      uses apply-group;
      uses apply-macro;
      leaf default {
        type int32;
      }
      leaf minimum {
        type int32;
      }
      leaf maximum {
        type int32;
      }
    }
  }

  grouping pgcp-h248-timers-object {
    uses apply-group;
    uses apply-macro;
    leaf maximum-waiting-delay {
      type uint32;
    }
    leaf tmax-retransmission-delay {
      type uint16;
    }
    leaf initial-average-ack-delay {
      type uint16;
    }
    leaf maximum-net-propagation-delay {
      type uint16;
    }
  }

  grouping pgcp-h248-traffic-management-object {
    uses apply-group;
    uses apply-macro;
    container sustained-data-rate {
      presence "enable sustained-data-rate";
      uses apply-group;
      uses apply-macro;
      leaf default {
        type uint32;
      }
      leaf minimum {
        type uint32;
      }
      leaf maximum {
        type uint32;
      }
      container rtcp {
        presence "enable rtcp";
        uses pgcp-h248-rtcp-rate-units-object;
      }
      leaf rtcp-include {
        type empty;
      }
    }
    container peak-data-rate {
      presence "enable peak-data-rate";
      uses apply-group;
      uses apply-macro;
      leaf default {
        type uint32;
      }
      leaf minimum {
        type uint32;
      }
      leaf maximum {
        type uint32;
      }
      container rtcp {
        presence "enable rtcp";
        uses pgcp-h248-rtcp-rate-units-object;
      }
    }
    container max-burst-size {
      presence "enable max-burst-size";
      uses apply-group;
      uses apply-macro;
      leaf default {
        type uint32;
      }
      leaf minimum {
        type uint32;
      }
      leaf maximum {
        type uint32;
      }
      container rtcp {
        presence "enable rtcp";
        uses pgcp-h248-rtcp-burst-units-object;
      }
    }
  }

  grouping pgcp-h248-rtcp-burst-units-object {
    uses apply-group;
    uses apply-macro;
    choice choice-3 {
      leaf percentage {
        type uint32;
      }
      leaf fixed-value {
        type uint32;
      }
    }
  }

  grouping pgcp-h248-rtcp-rate-units-object {
    uses apply-group;
    uses apply-macro;
    choice choice-3 {
      leaf percentage {
        type uint32;
      }
      leaf fixed-value {
        type uint32;
      }
    }
  }

  grouping pgcp-interim-ah-scheme-object {
    uses apply-group;
    uses apply-macro;
    leaf algorithm {
      type string;
    }
  }

  grouping pgcp-rule-object {
    leaf name {
      type key-attribute-string-type;
    }
    uses apply-group;
    uses apply-macro;
    leaf gateway {
      type string;
    }
    choice choice-5 {
      leaf-list nat-pool {
        type string;
        ordered-by user;
      }
    }
  }

  grouping pgcp-session-mirroring-object {
    uses apply-group;
    uses apply-macro;
    list delivery-function {
      key "name";
      ordered-by user;
      uses pgcp-delivery-function-object;
    }
    leaf disable-session-mirroring {
      type empty;
    }
  }

  grouping pgcp-delivery-function-object {
    leaf name {
      type key-attribute-string-type;
    }
    uses apply-group;
    uses apply-macro;
    leaf destination-address {
      type ipv4addr;
    }
    leaf destination-port {
      type uint16;
    }
    leaf network-operator-id {
      type string;
    }
    leaf source-address {
      type ipv4addr;
    }
    leaf source-port {
      type uint16;
    }
    container memory-managment {
      presence "enable memory-managment";
      uses pgcp-debug-mem-mgmt-object;
    }
  }

  grouping pgcp-debug-mem-mgmt-object {
    uses apply-group;
    uses apply-macro;
    leaf operational-mode {
      type string;
    }
  }

  grouping pgcp-virtual-interface-object {
    leaf name {
      type key-attribute-string-type;
    }
    uses apply-group;
    uses apply-macro;
    leaf routing-instance {
      type string;
    }
    leaf service-state {
      type string;
    }
    choice choice-7 {
      leaf-list nat-pool {
        type string;
        ordered-by user;
      }
    }
  }

  grouping pim-bootstrap-options-type {
    uses apply-group;
    uses apply-macro;
    leaf priority {
      type uint32;
    }
    leaf-list import {
      type policy-algebra;
      ordered-by user;
    }
    leaf-list export {
      type policy-algebra;
      ordered-by user;
    }
  }

  grouping pim-dense-group-type {
    leaf name {
      type ipprefix;
    }
    uses apply-group;
    uses apply-macro;
    choice choice-3 {
      leaf reject {
        type empty;
      }
      leaf announce {
        type empty;
      }
    }
  }

  grouping pim-filter-obj {
    uses apply-group;
    uses apply-macro;
    leaf match-on {
      type string;
    }
    leaf-list policy {
      type policy-algebra;
      ordered-by user;
    }
  }

  grouping pim-rp-group-range-type {
    leaf name {
      type ipprefix;
    }
    uses apply-group;
    uses apply-macro;
    leaf nexthop-hold-time {
      type uint32;
    }
  }

  grouping pm-rspan-bridge-domain {
    leaf name {
      type string;
    }
    uses apply-group;
    uses apply-macro;
  }

  grouping pm-rspan-vlan {
    leaf name {
      type string;
    }
    uses apply-group;
    uses apply-macro;
    leaf no-tag {
      type empty;
    }
  }

  grouping pm-family-input-type {
    uses apply-group;
    uses apply-macro;
    leaf rate {
      type uint16;
    }
    leaf run-length {
      type uint32;
    }
    leaf maximum-packet-length {
      type uint32;
    }
  }

  grouping pmond-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping policy-object-type {
    uses apply-group;
    uses apply-macro;
    container traceoptions {
      uses apply-group;
      uses apply-macro;
      leaf no-remote-trace {
        type empty;
      }
      container file {
        leaf filename {
          type string;
        }
        leaf size {
          type string;
        }
        leaf files {
          type uint32;
        }
        leaf world-readable {
          type empty;
        }
        leaf no-world-readable {
          type empty;
        }
        leaf match {
          type regular-expression;
        }
      }
      list flag {
        key "name";
        ordered-by user;
        leaf name {
          type string;
        }
      }
    }
    list policy {
      key "from-zone-name to-zone-name";
      ordered-by user;
      leaf from-zone-name {
        type key-attribute-string-type;
      }
      leaf to-zone-name {
        type key-attribute-string-type;
      }
      uses apply-group;
      uses apply-macro;
      list policy {
        key "name";
        ordered-by user;
        uses policy-type;
      }
      container application-services {
        uses context-application-services-type;
      }
    }
    container global {
      presence "";
      uses apply-group;
      uses apply-macro;
      list policy {
        key "name";
        ordered-by user;
        uses policy-type;
      }
    }
    list policy-set {
      key "name";
      ordered-by user;
      leaf name {
        type key-attribute-string-type;
      }
      uses apply-group;
      uses apply-macro;
      list policy {
        key "name";
        ordered-by user;
        uses policy-type;
      }
    }
    container default-policy {
      uses apply-group;
      uses apply-macro;
      choice choice-permit-all {
        leaf permit-all {
          type empty;
        }
        leaf deny-all {
          type empty;
        }
      }
    }
    leaf policy-rematch {
      type empty;
    }
    container policy-stats {
      presence "enable policy-stats";
      uses apply-group;
      uses apply-macro;
      leaf system-wide {
        type string;
      }
    }
    container pre-id-default-policy {
      presence "";
      uses apply-group;
      uses apply-macro;
      container then {
        uses apply-group;
        uses apply-macro;
        container log {
          uses log-type;
        }
        container session-timeout {
          uses session-timeout-type;
        }
      }
    }
    container unified-policy {
      uses apply-group;
      uses apply-macro;
      leaf max-lookups {
        type uint32;
      }
    }
    container dns-cache {
      uses apply-group;
      uses apply-macro;
      container error-response-delete-ip {
        presence "enable error-response-delete-ip";
        uses apply-group;
        uses apply-macro;
        leaf retry-interval {
          units "seconds";
          type uint32;
        }
      }
    }
    list stateful-firewall-rule {
      key "name";
      ordered-by user;
      leaf name {
        type key-attribute-string-type;
      }
      uses apply-group;
      uses apply-macro;
      leaf match-direction {
        type string;
      }
      list policy {
        key "name";
        ordered-by user;
        uses policy-type;
      }
    }
    list stateful-firewall-rule-set {
      key "name";
      ordered-by user;
      leaf name {
        type key-attribute-string-type;
      }
      uses apply-group;
      uses apply-macro;
      list stateful-firewall-rule {
        key "name";
        ordered-by user;
        leaf name {
          type string;
        }
        uses apply-group;
        uses apply-macro;
      }
    }
  }

  grouping context-application-services-type {
    uses apply-group;
    uses apply-macro;
    leaf security-metadata-streaming-policy {
      type string;
    }
  }

  grouping log-type {
    uses apply-group;
    uses apply-macro;
    leaf session-init {
      type empty;
    }
    leaf session-close {
      type empty;
    }
    leaf sfw {
      type empty;
    }
    leaf profile {
      type string;
    }
  }

  grouping policy-type {
    leaf name {
      type key-attribute-string-type;
    }
    uses apply-group;
    uses apply-macro;
    leaf description {
      type string;
    }
    container match {
      presence "enable match";
      uses apply-group;
      uses apply-macro;
      leaf-list source-address {
        ordered-by user;
        type string;
      }
      leaf-list destination-address {
        ordered-by user;
        type string;
      }
      leaf source-address-excluded {
        type empty;
      }
      leaf destination-address-excluded {
        type empty;
      }
      leaf-list application {
        type string;
        ordered-by user;
      }
      leaf-list source-identity {
        ordered-by user;
        type string;
      }
      container source-end-user-profile {
        uses match-source-end-user-profile-value;
      }
      leaf-list dynamic-application {
        ordered-by user;
        type string;
      }
      leaf-list url-category {
        ordered-by user;
        type string;
      }
      leaf-list from-zone {
        ordered-by user;
        type string;
      }
      leaf-list to-zone {
        ordered-by user;
        type string;
      }
      leaf-list source-l3vpn-vrf-group {
        type string;
        ordered-by user;
      }
      leaf-list destination-l3vpn-vrf-group {
        type string;
        ordered-by user;
      }
    }
    container then {
      presence "enable then";
      uses apply-group;
      uses apply-macro;
      choice choice-3 {
        leaf deny {
          type empty;
        }
        leaf reject {
          type empty;
        }
        container permit {
          presence "enable permit";
          uses apply-group;
          uses apply-macro;
          container tunnel {
            uses tunnel-type;
          }
          container firewall-authentication {
            uses firewall-authentication-type;
          }
          container destination-address {
            presence "enable destination-address";
            uses destination-nat-enable-type;
          }
          container application-services {
            uses application-services-type;
          }
          container tcp-options {
            uses apply-group;
            uses apply-macro;
            leaf syn-check-required {
              type empty;
            }
            leaf sequence-check-required {
              type empty;
            }
          }
          leaf services-offload {
            type empty;
          }
        }
      }
      container log {
        uses log-type;
      }
      container count {
        presence "enable count";
        uses count-type;
      }
    }
    leaf scheduler-name {
      type string;
    }
  }

  grouping application-services-type {
    uses apply-group;
    uses apply-macro;
    leaf gprs-gtp-profile {
      type string;
    }
    leaf gprs-sctp-profile {
      type string;
    }
    leaf idp {
      type empty;
    }
    container ssl-proxy {
      presence "enable ssl-proxy";
      uses apply-group;
      uses apply-macro;
    }
    container uac-policy {
      presence "enable uac-policy";
      uses apply-group;
      uses apply-macro;
      leaf captive-portal {
        type string;
      }
    }
    leaf utm-policy {
      type string;
    }
    container application-firewall {
      uses jsf-service-rule-set-type;
    }
    container application-traffic-control {
      uses jsf-application-traffic-control-rule-set-type;
    }
    container wan-optimization {
      uses jsf-service-profile-type;
    }
    choice choice-15 {
      leaf redirect-wx {
        type empty;
      }
      leaf reverse-redirect-wx {
        type empty;
      }
    }
    leaf security-intelligence-policy {
      type string;
    }
  }

  grouping count-type {
    uses apply-group;
    uses apply-macro;
    container alarm {
      leaf per-second-threshold {
        type uint32;
      }
      leaf per-minute-threshold {
        type uint32;
      }
    }
  }

  grouping destination-nat-enable-type {
    uses apply-group;
    uses apply-macro;
    choice choice-3 {
      leaf drop-translated {
        type empty;
      }
      leaf drop-untranslated {
        type empty;
      }
    }
  }

  grouping firewall-authentication-type {
    uses apply-group;
    uses apply-macro;
    choice choice-3 {
      container pass-through {
        presence "enable pass-through";
        uses apply-group;
        uses apply-macro;
        leaf access-profile {
          type string;
        }
        leaf client-match {
          type string;
        }
        leaf web-redirect {
          type empty;
        }
      }
      container web-authentication {
        presence "enable web-authentication";
        uses apply-group;
        uses apply-macro;
        leaf client-match {
          type string;
        }
      }
    }
  }

  grouping jsf-application-traffic-control-rule-set-type {
    uses apply-group;
    uses apply-macro;
    leaf rule-set {
      type string;
    }
  }

  grouping jsf-service-rule-set-type {
    uses apply-group;
    uses apply-macro;
    leaf rule-set {
      type string;
    }
  }

  grouping jsf-service-profile-type {
    uses apply-group;
    uses apply-macro;
    leaf profile-name {
      type string;
    }
    leaf service-options {
      type string;
    }
  }

  grouping match-source-end-user-profile-value {
    uses apply-group;
    uses apply-macro;
    leaf source-end-user-profile-name {
      type string;
    }
  }

  grouping port-range {
    leaf name {
      type string;
    }
    uses apply-group;
    uses apply-macro;
    leaf maximum-port {
      type uint32;
    }
  }

  grouping ppp-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping ppp-options-type {
    uses apply-group;
    uses apply-macro;
    leaf dynamic-profile {
      type string;
    }
    container chap {
      presence "enable chap";
      uses apply-group;
      uses apply-macro;
      choice choice-access-profile {
        leaf access-profile {
          type string;
        }
        leaf default-chap-secret {
          type unreadable;
        }
      }
      leaf local-name {
        type string;
      }
      leaf no-rfc2486 {
        type empty;
      }
      leaf passive {
        type empty;
      }
      container challenge-length {
        leaf minimum {
          units "bytes";
          type uint8;
        }
        leaf maximum {
          units "bytes";
          type uint8;
        }
      }
    }
    container pap {
      presence "enable pap";
      uses apply-group;
      uses apply-macro;
      choice choice-access-profile {
        leaf access-profile {
          type string;
        }
        leaf default-password {
          type unreadable;
        }
      }
      leaf local-name {
        type string;
      }
      leaf no-rfc2486 {
        type empty;
      }
      leaf local-password {
        type unreadable;
      }
      leaf passive {
        type empty;
      }
    }
    leaf-list authentication {
      ordered-by user;
      type string;
    }
    container compression {
      leaf acfc {
        type empty;
      }
      leaf pfc {
        type empty;
      }
    }
    leaf lcp-restart-timer {
      units "milliseconds";
      type uint16;
    }
    leaf ncp-restart-timer {
      units "milliseconds";
      type uint16;
    }
    leaf no-termination-request {
      type empty;
    }
    leaf loopback-clear-timer {
      units "seconds";
      type uint8;
    }
    leaf lcp-max-conf-req {
      type uint32;
    }
    leaf ncp-max-conf-req {
      type uint32;
    }
    leaf on-demand-ip-address {
      type empty;
    }
    leaf aaa-options {
      type string;
    }
    container initiate-ncp {
      uses apply-group;
      uses apply-macro;
      leaf ip {
        type empty;
      }
      leaf ipv6 {
        type empty;
      }
      leaf dual-stack-passive {
        type empty;
      }
    }
    leaf mru {
      type uint32;
    }
    leaf mtu {
      type string;
    }
    leaf peer-ip-address-optional {
      type empty;
    }
    leaf ipcp-suggest-dns-option {
      type empty;
    }
    leaf ignore-magic-number-mismatch {
      type empty;
    }
    container local-authentication {
      uses local-auth-type;
    }
  }

  grouping local-auth-type {
    uses apply-group;
    uses apply-macro;
    leaf password {
      type string;
    }
    container username-include {
      uses apply-group;
      uses apply-macro;
      leaf mac-address {
        type empty;
      }
      leaf circuit-id {
        type empty;
      }
      leaf remote-id {
        type empty;
      }
      leaf domain-name {
        type string;
      }
      leaf delimiter {
        type string;
      }
    }
  }

  grouping pppoe-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
    container filter {
      presence "enable filter";
      uses apply-group;
      uses apply-macro;
      leaf aci {
        type string;
      }
      leaf ari {
        type string;
      }
      leaf service-name {
        type string;
      }
      leaf underlying-interface {
        type string;
      }
      container user {
        presence "enable user";
        uses apply-group;
        uses apply-macro;
        leaf username {
          type string;
        }
      }
    }
  }

  grouping pppoe-options-type {
    uses apply-group;
    uses apply-macro;
    leaf underlying-interface {
      type string;
    }
    leaf idle-timeout {
      type uint32;
    }
    leaf access-concentrator {
      type string;
    }
    leaf service-name {
      type string;
    }
    leaf auto-reconnect {
      type uint32;
    }
    choice choice-13 {
      leaf server {
        type empty;
      }
      leaf client {
        type empty;
      }
    }
    leaf ppp-max-payload {
      type uint32;
    }
  }

  grouping pppoe-underlying-options-type {
    uses apply-group;
    uses apply-macro;
    leaf access-concentrator {
      type string;
    }
    leaf direct-connect {
      type empty;
    }
    leaf duplicate-protection {
      type empty;
    }
    leaf dynamic-profile {
      type string;
    }
    leaf max-sessions {
      type uint32;
    }
    leaf max-sessions-vsa-ignore {
      type empty;
    }
    leaf service-name-table {
      type string;
    }
    container short-cycle-protection {
      presence "enable short-cycle-protection";
      uses apply-group;
      uses apply-macro;
      leaf lockout-time-min {
        units "seconds";
        type uint32;
      }
      leaf lockout-time-max {
        units "seconds";
        type uint32;
      }
      leaf filter {
        type string;
      }
    }
  }

  grouping prefix-action {
    leaf name {
      type string;
    }
    uses apply-group;
    uses apply-macro;
    leaf policer {
      type string;
    }
    leaf count {
      type empty;
    }
    leaf filter-specific {
      type empty;
    }
    leaf subnet-prefix-length {
      type uint32;
    }
    choice choice-11 {
      leaf source-prefix-length {
        type uint32;
      }
      leaf destination-prefix-length {
        type uint32;
      }
    }
  }

  grouping prefix-list-items {
    leaf name {
      type ipprefix-only;
    }
    uses apply-group;
    uses apply-macro;
  }

  grouping profile-radius-server-object {
    leaf name {
      type ipv4addr;
    }
    uses apply-group;
    uses apply-macro;
    leaf port {
      type uint16;
    }
    leaf accounting-port {
      type uint16;
    }
    leaf secret {
      type unreadable;
    }
    leaf timeout {
      units "seconds";
      type string;
    }
    leaf retry {
      type string;
    }
    leaf accounting-timeout {
      units "seconds";
      type string;
    }
    leaf accounting-retry {
      type string;
    }
    leaf max-outstanding-requests {
      type string;
    }
    leaf source-address {
      type ipv4addr;
    }
    leaf routing-instance {
      type string;
    }
  }

  grouping profile-setting {
    leaf name {
      type key-attribute-string-type;
    }
    uses apply-group;
    uses apply-macro;
    container anti-virus {
      uses apply-group;
      uses apply-macro;
      leaf http-profile {
        type string;
      }
      container ftp {
        uses apply-group;
        uses apply-macro;
        leaf upload-profile {
          type string;
        }
        leaf download-profile {
          type string;
        }
      }
      leaf smtp-profile {
        type string;
      }
      leaf pop3-profile {
        type string;
      }
      leaf imap-profile {
        type string;
      }
    }
    container content-filtering {
      uses apply-group;
      uses apply-macro;
      leaf http-profile {
        type string;
      }
      container ftp {
        uses apply-group;
        uses apply-macro;
        leaf upload-profile {
          type string;
        }
        leaf download-profile {
          type string;
        }
      }
      leaf smtp-profile {
        type string;
      }
      leaf pop3-profile {
        type string;
      }
      leaf imap-profile {
        type string;
      }
    }
    container web-filtering {
      uses apply-group;
      uses apply-macro;
      leaf http-profile {
        type string;
      }
    }
    container anti-spam {
      uses apply-group;
      uses apply-macro;
      leaf smtp-profile {
        type string;
      }
    }
    container traffic-options {
      uses apply-group;
      uses apply-macro;
      container sessions-per-client {
        uses apply-group;
        uses apply-macro;
        leaf limit {
          type uint32;
        }
        leaf over-limit {
          type string;
        }
      }
    }
  }

  grouping profile-type {
    leaf name {
      type key-attribute-string-type;
    }
    uses apply-group;
    uses apply-macro;
    container appfw-rule-set {
      presence "enable appfw-rule-set";
      uses apply-group;
      uses apply-macro;
      leaf maximum {
        type uint32;
      }
      leaf reserved {
        type uint32;
      }
    }
    container appfw-rule {
      presence "enable appfw-rule";
      uses apply-group;
      uses apply-macro;
      leaf maximum {
        type uint32;
      }
      leaf reserved {
        type uint32;
      }
    }
    container appfw-profile {
      presence "enable appfw-profile";
      uses apply-group;
      uses apply-macro;
      leaf maximum {
        type uint32;
      }
      leaf reserved {
        type uint32;
      }
    }
    container auth-entry {
      presence "enable auth-entry";
      uses apply-group;
      uses apply-macro;
      leaf maximum {
        type uint32;
      }
      leaf reserved {
        type uint32;
      }
    }
    container policy {
      presence "enable policy";
      uses apply-group;
      uses apply-macro;
      leaf maximum {
        type uint32;
      }
      leaf reserved {
        type uint32;
      }
    }
    container policy-with-count {
      presence "enable policy-with-count";
      uses apply-group;
      uses apply-macro;
      leaf maximum {
        type uint32;
      }
      leaf reserved {
        type uint32;
      }
    }
    container scheduler {
      presence "enable scheduler";
      uses apply-group;
      uses apply-macro;
      leaf maximum {
        type uint32;
      }
      leaf reserved {
        type uint32;
      }
    }
    container address-book {
      presence "enable address-book";
      uses apply-group;
      uses apply-macro;
      leaf maximum {
        type uint32;
      }
      leaf reserved {
        type uint32;
      }
    }
    container zone {
      presence "enable zone";
      uses apply-group;
      uses apply-macro;
      leaf maximum {
        type uint32;
      }
      leaf reserved {
        type uint32;
      }
    }
    container flow-session {
      presence "enable flow-session";
      uses apply-group;
      uses apply-macro;
      leaf maximum {
        type uint32;
      }
      leaf reserved {
        type uint32;
      }
    }
    container cpu {
      presence "enable cpu";
      uses apply-group;
      uses apply-macro;
      leaf reserved {
        units "percent";
        type string;
      }
    }
    container flow-gate {
      presence "enable flow-gate";
      uses apply-group;
      uses apply-macro;
      leaf maximum {
        type uint32;
      }
      leaf reserved {
        type uint32;
      }
    }
    container nat-source-pool {
      presence "enable nat-source-pool";
      uses apply-group;
      uses apply-macro;
      leaf maximum {
        type uint32;
      }
      leaf reserved {
        type uint32;
      }
    }
    container nat-destination-pool {
      presence "enable nat-destination-pool";
      uses apply-group;
      uses apply-macro;
      leaf maximum {
        type uint32;
      }
      leaf reserved {
        type uint32;
      }
    }
    container nat-pat-address {
      presence "enable nat-pat-address";
      uses apply-group;
      uses apply-macro;
      leaf maximum {
        type uint32;
      }
      leaf reserved {
        type uint32;
      }
    }
    container nat-nopat-address {
      presence "enable nat-nopat-address";
      uses apply-group;
      uses apply-macro;
      leaf maximum {
        type uint32;
      }
      leaf reserved {
        type uint32;
      }
    }
    container nat-pat-portnum {
      presence "enable nat-pat-portnum";
      uses apply-group;
      uses apply-macro;
      leaf maximum {
        type uint32;
      }
      leaf reserved {
        type uint32;
      }
    }
    container nat-source-rule {
      presence "enable nat-source-rule";
      uses apply-group;
      uses apply-macro;
      leaf maximum {
        type uint32;
      }
      leaf reserved {
        type uint32;
      }
    }
    container nat-destination-rule {
      presence "enable nat-destination-rule";
      uses apply-group;
      uses apply-macro;
      leaf maximum {
        type uint32;
      }
      leaf reserved {
        type uint32;
      }
    }
    container nat-static-rule {
      presence "enable nat-static-rule";
      uses apply-group;
      uses apply-macro;
      leaf maximum {
        type uint32;
      }
      leaf reserved {
        type uint32;
      }
    }
    container nat-rule-referenced-prefix {
      presence "enable nat-rule-referenced-prefix";
      uses apply-group;
      uses apply-macro;
      leaf maximum {
        type uint32;
      }
      leaf reserved {
        type uint32;
      }
    }
    container nat-cone-binding {
      presence "enable nat-cone-binding";
      uses apply-group;
      uses apply-macro;
      leaf maximum {
        type uint32;
      }
      leaf reserved {
        type uint32;
      }
    }
    container nat-port-ol-ipnumber {
      presence "enable nat-port-ol-ipnumber";
      uses apply-group;
      uses apply-macro;
      leaf maximum {
        type uint32;
      }
      leaf reserved {
        type uint32;
      }
    }
    container nat-interface-port-ol {
      presence "enable nat-interface-port-ol";
      uses apply-group;
      uses apply-macro;
      leaf maximum {
        type uint32;
      }
      leaf reserved {
        type uint32;
      }
    }
    container dslite-softwire-initiator {
      presence "enable dslite-softwire-initiator";
      uses apply-group;
      uses apply-macro;
      leaf maximum {
        type uint32;
      }
      leaf reserved {
        type uint32;
      }
    }
    leaf idp-policy {
      type string;
    }
    leaf root-logical-system {
      type empty;
    }
    leaf-list logical-system {
      ordered-by user;
      type string;
    }
  }

  grouping proto-object {
    leaf name {
      type string;
    }
    uses apply-group;
    uses apply-macro;
    list tunable-name {
      key "name";
      ordered-by user;
      uses tunable-object;
    }
  }

  grouping ptsp-forward-rule-object {
    leaf name {
      type key-attribute-string-type;
    }
    uses apply-group;
    uses apply-macro;
    list term {
      key "name";
      ordered-by user;
      leaf name {
        type string;
      }
      uses apply-group;
      uses apply-macro;
      container from {
        presence "enable from";
        uses ptsp-forward-match-object;
      }
      container then {
        presence "";
        uses apply-group;
        uses apply-macro;
        leaf forwarding-instance {
          type string;
        }
        leaf unit-number {
          type uint16;
        }
      }
    }
  }

  grouping ptsp-forward-match-object {
    uses apply-group;
    uses apply-macro;
    list local-address {
      key "name";
      ordered-by user;
      uses sfw-addr-object;
    }
    list local-address-range {
      key "low high";
      ordered-by user;
      leaf low {
        type ipaddr;
      }
      leaf high {
        type ipaddr;
      }
      leaf except {
        type empty;
      }
    }
    list local-prefix-list {
      key "name";
      ordered-by user;
      leaf name {
        type string;
      }
      leaf except {
        type empty;
      }
    }
    choice choice-9 {
      leaf-list applications {
        type string;
        ordered-by user;
      }
      leaf-list application-groups {
        type string;
        ordered-by user;
      }
    }
  }

  grouping ptsp-rule-object {
    leaf name {
      type key-attribute-string-type;
    }
    uses apply-group;
    uses apply-macro;
    leaf match-direction {
      type string;
    }
    leaf demux {
      type string;
    }
    leaf count-type {
      type string;
    }
    leaf forward-rule {
      type string;
    }
    list term {
      key "name";
      ordered-by user;
      leaf name {
        type string;
      }
      uses apply-group;
      uses apply-macro;
      container from {
        presence "enable from";
        uses ptsp-match-object;
      }
      container then {
        uses apply-group;
        uses apply-macro;
        leaf forwarding-class {
          type string;
        }
        leaf count {
          type string;
        }
        leaf police {
          type string;
        }
        choice choice-9 {
          leaf accept {
            type empty;
          }
          leaf discard {
            type empty;
          }
        }
      }
    }
  }

  grouping ptsp-match-object {
    uses apply-group;
    uses apply-macro;
    list remote-address {
      key "name";
      ordered-by user;
      uses sfw-addr-object;
    }
    list remote-address-range {
      key "low high";
      ordered-by user;
      leaf low {
        type ipaddr;
      }
      leaf high {
        type ipaddr;
      }
      leaf except {
        type empty;
      }
    }
    list remote-prefix-list {
      key "name";
      ordered-by user;
      leaf name {
        type string;
      }
      leaf except {
        type empty;
      }
    }
    leaf protocol {
      type uint16;
    }
    leaf-list local-ports {
      ordered-by user;
      type uint32;
    }
    list local-port-range {
      key "low high";
      ordered-by user;
      leaf low {
        type string;
      }
      leaf high {
        type string;
      }
    }
    leaf-list remote-ports {
      ordered-by user;
      type uint32;
    }
    list remote-port-range {
      key "low high";
      ordered-by user;
      leaf low {
        type string;
      }
      leaf high {
        type string;
      }
    }
    choice choice-19 {
      leaf application-group-any {
        type empty;
      }
      leaf-list applications {
        type string;
        ordered-by user;
      }
      leaf-list application-groups {
        type string;
        ordered-by user;
      }
    }
  }

  grouping qos-parameter-type {
    uses apply-group;
    uses apply-macro;
    leaf no-wifi-multimedia {
      type empty;
    }
    leaf no-acknowledgement {
      type empty;
    }
    leaf no-auto-power-save {
      type empty;
    }
    container access-point-queues {
      uses apply-group;
      uses apply-macro;
      container voice-queue {
        uses access-point-queue-type;
      }
      container video-queue {
        uses access-point-queue-type;
      }
      container best-effort-queue {
        uses access-point-queue-type;
      }
      container background-queue {
        uses access-point-queue-type;
      }
    }
    container station-queues {
      uses apply-group;
      uses apply-macro;
      container voice-queue {
        uses station-queue-type;
      }
      container video-queue {
        uses station-queue-type;
      }
      container best-effort-queue {
        uses station-queue-type;
      }
      container background-queue {
        uses station-queue-type;
      }
    }
  }

  grouping access-point-queue-type {
    uses apply-group;
    uses apply-macro;
    leaf arbitration-inter-frame-space {
      type int32;
    }
    container minimum-contention-window {
      uses contention-window;
    }
    container maximum-contention-window {
      uses contention-window;
    }
    leaf maximum-burst {
      type int32;
    }
  }

  grouping contention-window {
    uses apply-group;
    uses apply-macro;
    leaf window-size {
      type int32;
    }
  }

  grouping programmable-rpd-type {
    uses apply-advanced;
    container traceoptions {
      uses apply-advanced;
      container file {
        leaf filename {
          type string;
        }
        leaf replace {
          status deprecated;
          type empty;
        }
        leaf size {
          type string;
        }
        leaf files {
          type string;
        }
        leaf no-stamp {
          status deprecated;
          type empty;
        }
        choice world-readable-choice {
          leaf world-readable {
            type empty;
          }
          leaf no-world-readable {
            type empty;
          }
        }
      }
      list flag {
        key "name";
        ordered-by user;
        leaf name {
          type string;
        }
      }
    }
    container purge-timeout {
      presence "enable purge-timeout";
      choice purge-parm {
        case case_1 {
          leaf never {
            type empty;
          }
        }
        case case_2 {
          leaf timeout {
            units "seconds";
            type string;
          }
        }
      }
    }
    list client {
      key "name";
      ordered-by user;
      leaf name {
        type string;
      }
      uses apply-advanced;
      list interface-notification {
        key "name";
        ordered-by user;
        leaf name {
          type string;
        }
        uses apply-advanced;
      }
    }
    container rib-service {
      presence "enable rib-service";
      uses apply-advanced;
      container dynamic-next-hop-interface {
        presence "enable dynamic-next-hop-interface";
        uses apply-advanced;
        choice enable-disable {
          case case_1 {
            leaf disable {
              type empty;
            }
          }
        }
      }
    }
    leaf stats-sampling-interval {
      units "seconds";
      type string;
    }
    leaf stats-aggregation-interval {
      units "seconds";
      type string;
    }
  }

  grouping qualified-nh-obj {
    leaf name {
      type ipaddr-or-interface;
    }
    uses apply-group;
    uses apply-macro;
    leaf preference {
      type uint32;
    }
    leaf metric {
      type uint32;
    }
    leaf interface {
      type interface-name;
    }
    leaf mac-address {
      type mac-unicaset;
    }
    leaf tag {
      type string;
    }
    container bfd-liveness-detection {
      uses apply-group;
      uses apply-macro;
      leaf version {
        type string;
      }
      leaf minimum-interval {
        type uint32;
      }
      leaf minimum-receive-interval {
        type uint32;
      }
      leaf multiplier {
        type uint32;
      }
      choice choice-11 {
        leaf no-adaptation {
          type empty;
        }
      }
      container transmit-interval {
        uses apply-group;
        uses apply-macro;
        leaf minimum-interval {
          type uint32;
        }
        leaf threshold {
          type uint32;
        }
      }
      container detection-time {
        uses apply-group;
        uses apply-macro;
        leaf threshold {
          type uint32;
        }
      }
      container authentication {
        uses apply-group;
        uses apply-macro;
        leaf key-chain {
          type string;
        }
        leaf algorithm {
          type string;
        }
        leaf loose-check {
          type empty;
        }
      }
      leaf neighbor {
        type ipaddr;
      }
      leaf local-address {
        type ipaddr;
      }
      leaf holddown-interval {
        type uint32;
      }
      leaf minimum-receive-ttl {
        type uint8;
      }
    }
  }

  grouping r2cp-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping radius-disconnect-object {
    leaf name {
      type ipv4addr;
    }
    uses apply-group;
    uses apply-macro;
    leaf secret {
      type unreadable;
    }
  }

  grouping radius-server-object {
    leaf name {
      type hostname;
    }
    uses apply-group;
    uses apply-macro;
    leaf port {
      type uint16;
    }
    leaf accounting-port {
      type uint16;
    }
    leaf secret {
      type unreadable;
    }
    leaf timeout {
      type uint32;
    }
    leaf retry {
      type uint32;
    }
    leaf source-address {
      type ipv4addr;
    }
  }

  grouping range-address-type {
    leaf name {
      mandatory true;
      type ipv4addr;
    }
    uses apply-group;
    uses apply-macro;
    container to {
      presence "";
      uses apply-group;
      uses apply-macro;
      leaf range-high {
        mandatory true;
        type ipv4addr;
      }
    }
  }

  grouping reconfigure-trigger-type {
    uses apply-group;
    uses apply-macro;
    leaf radius-disconnect {
      type empty;
    }
  }

  grouping reconfigure-type {
    uses apply-group;
    uses apply-macro;
    leaf clear-on-abort {
      type empty;
    }
    leaf attempts {
      type uint32;
    }
    leaf timeout {
      type uint32;
    }
    leaf token {
      type string;
    }
    container trigger {
      uses reconfigure-trigger-type;
    }
  }

  grouping registration-policy-type {
    leaf name {
      type string;
    }
    uses apply-group;
    uses apply-macro;
    list term {
      key "name";
      ordered-by user;
      leaf name {
        type string;
      }
      uses apply-group;
      uses apply-macro;
      container from {
        presence "enable from";
        uses new-transaction-from-type;
      }
      container then {
        presence "enable then";
        uses new-registration-then-type;
      }
    }
  }

  grouping new-registration-then-type {
    uses apply-group;
    uses apply-macro;
    container nat-traversal {
      uses nat-traversal-action;
    }
  }

  grouping nat-traversal-action {
    uses apply-group;
    uses apply-macro;
    leaf nat-traversal-strategy {
      type string;
    }
    leaf keepalive-interval {
      type uint32;
    }
    leaf minimum-registration-interval {
      type uint32;
    }
    container keepalive-mechanisms {
      uses apply-group;
      uses apply-macro;
      leaf register-fast-expiration {
        type empty;
      }
    }
  }

  grouping new-transaction-from-type {
    uses apply-group;
    uses apply-macro;
    leaf-list source-address {
      type ipaddr;
      ordered-by user;
    }
    list method {
      key "name";
      ordered-by user;
      uses transaction-method-type;
    }
    container request-uri {
      leaf-list regular-expression {
        type regular-expression;
        ordered-by user;
      }
      leaf registration-state {
        type string;
      }
      leaf uri-hiding {
        type string;
      }
    }
    container contact {
      leaf-list regular-expression {
        type regular-expression;
        ordered-by user;
      }
      leaf registration-state {
        type string;
      }
      leaf uri-hiding {
        type string;
      }
    }
  }

  grouping relay-active-leasequery-v6-type {
    uses apply-advanced;
    leaf topology-discover {
      type empty;
    }
    leaf timeout {
      units "seconds";
      type string;
    }
    leaf idle-timeout {
      units "seconds";
      type string;
    }
    list peer-address {
      key "name";
      ordered-by user;
      leaf name {
        type ipv6addr;
      }
      uses apply-advanced;
    }
  }

  grouping relay-bulk-leasequery-v4-type {
    uses apply-group;
    uses apply-macro;
    leaf attempts {
      type uint32;
    }
    leaf timeout {
      units "seconds";
      type uint32;
    }
  }

  grouping relay-bulk-leasequery-v6-type {
    uses apply-advanced;
    leaf attempts {
      type string;
    }
    leaf timeout {
      units "seconds";
      type string;
    }
    container trigger {
      leaf automatic {
        type empty;
      }
    }
  }

  grouping relay-leasequery-type {
    uses apply-group;
    uses apply-macro;
    leaf attempts {
      type uint32;
    }
    leaf timeout {
      units "seconds";
      type uint32;
    }
  }

  grouping relay-option-60-type-group {
    uses apply-group;
    uses apply-macro;
    container vendor-option {
      uses apply-group;
      uses apply-macro;
      container equals {
        uses relay-option-60-match-group;
      }
      container starts-with {
        uses relay-option-60-match-group;
      }
      choice choice-7 {
        leaf default-relay-server-group {
          type string;
        }
        leaf default-local-server-group {
          type string;
        }
        leaf drop {
          type empty;
        }
      }
    }
  }

  grouping relay-option-60-match-group {
    uses apply-group;
    uses apply-macro;
    list ascii {
      key "name";
      leaf name {
        type key-attribute-string-type;
      }
      uses apply-group;
      uses apply-macro;
      choice choice-3 {
        leaf relay-server-group {
          type string;
        }
        leaf local-server-group {
          type string;
        }
        leaf drop {
          type empty;
        }
      }
    }
    list hexadecimal {
      key "name";
      leaf name {
        type key-attribute-string-type;
      }
      uses apply-group;
      uses apply-macro;
      choice choice-3 {
        leaf relay-server-group {
          type string;
        }
        leaf local-server-group {
          type string;
        }
        leaf drop {
          type empty;
        }
      }
    }
  }

  grouping relay-option-60-type-top {
    uses apply-group;
    uses apply-macro;
    container vendor-option {
      uses apply-group;
      uses apply-macro;
      container equals {
        uses relay-option-60-match-top;
      }
      container starts-with {
        uses relay-option-60-match-top;
      }
      choice choice-7 {
        leaf default-relay-server-group {
          type string;
        }
        leaf default-local-server-group {
          type string;
        }
        leaf drop {
          type empty;
        }
      }
    }
  }

  grouping relay-option-60-match-top {
    uses apply-group;
    uses apply-macro;
    list ascii {
      key "name";
      leaf name {
        type key-attribute-string-type;
      }
      uses apply-group;
      uses apply-macro;
      choice choice-3 {
        leaf relay-server-group {
          type string;
        }
        leaf local-server-group {
          type string;
        }
        leaf drop {
          type empty;
        }
        leaf forward-only {
          type empty;
        }
      }
    }
    list hexadecimal {
      key "name";
      leaf name {
        type key-attribute-string-type;
      }
      uses apply-group;
      uses apply-macro;
      choice choice-3 {
        leaf relay-server-group {
          type string;
        }
        leaf local-server-group {
          type string;
        }
        leaf drop {
          type empty;
        }
        leaf forward-only {
          type empty;
        }
      }
    }
  }

  grouping relay-option-82-type {
    uses apply-group;
    uses apply-macro;
    container circuit-id {
      presence "enable circuit-id";
      uses apply-group;
      uses apply-macro;
      container prefix {
        uses apply-group;
        uses apply-macro;
        leaf host-name {
          type empty;
        }
        leaf logical-system-name {
          type empty;
        }
        leaf routing-instance-name {
          type empty;
        }
      }
      leaf use-interface-description {
        type string;
      }
      leaf use-vlan-id {
        type empty;
      }
      leaf no-vlan-interface-name {
        type empty;
      }
      leaf include-irb-and-l2 {
        type empty;
      }
      leaf user-defined {
        type empty;
      }
      leaf keep-incoming-circuit-id {
        type empty;
      }
    }
    container remote-id {
      presence "enable remote-id";
      uses apply-group;
      uses apply-macro;
      container prefix {
        uses apply-group;
        uses apply-macro;
        leaf host-name {
          type empty;
        }
        leaf logical-system-name {
          type empty;
        }
        leaf routing-instance-name {
          type empty;
        }
      }
      leaf use-interface-description {
        type string;
      }
      leaf use-vlan-id {
        type empty;
      }
      leaf no-vlan-interface-name {
        type empty;
      }
      leaf include-irb-and-l2 {
        type empty;
      }
      leaf keep-incoming-remote-id {
        type empty;
      }
      leaf use-string {
        type string;
      }
    }
    leaf server-id-override {
      type empty;
    }
  }

  grouping relay-v4-option-ascii-hex {
    uses apply-group;
    uses apply-macro;
    list ascii {
      key "name";
      leaf name {
        type key-attribute-string-type;
      }
      uses apply-group;
      uses apply-macro;
      choice choice-relay-server-group {
        leaf relay-server-group {
          type string;
        }
        leaf local-server-group {
          type string;
        }
        leaf drop {
          type empty;
        }
        leaf forward-only {
          type empty;
        }
        container relay-config {
          presence "enable relay-config";
          uses apply-group;
          uses apply-macro;
          leaf relay-server-group {
            type string;
          }
          container dynamic-profile {
            presence "";
            uses dynamic-profile-type;
          }
          leaf giaddr {
            type ipaddr;
          }
        }
      }
    }
    list hexadecimal {
      key "name";
      leaf name {
        type key-attribute-string-type;
      }
      uses apply-group;
      uses apply-macro;
      choice choice-relay-server-group {
        leaf relay-server-group {
          type string;
        }
        leaf local-server-group {
          type string;
        }
        leaf drop {
          type empty;
        }
        leaf forward-only {
          type empty;
        }
        container relay-config {
          presence "enable relay-config";
          uses apply-group;
          uses apply-macro;
          leaf relay-server-group {
            type string;
          }
          container dynamic-profile {
            presence "";
            uses dynamic-profile-type;
          }
          leaf giaddr {
            type ipaddr;
          }
        }
      }
    }
  }

  grouping relay-v6-option-ascii-hex {
    uses apply-group;
    uses apply-macro;
    list ascii {
      key "name";
      leaf name {
        type key-attribute-string-type;
      }
      uses apply-group;
      uses apply-macro;
      choice choice-relay-server-group {
        leaf relay-server-group {
          type string;
        }
        leaf drop {
          type empty;
        }
        leaf forward-only {
          type empty;
        }
      }
    }
    list hexadecimal {
      key "name";
      leaf name {
        type key-attribute-string-type;
      }
      uses apply-group;
      uses apply-macro;
      choice choice-relay-server-group {
        leaf relay-server-group {
          type string;
        }
        leaf drop {
          type empty;
        }
        leaf forward-only {
          type empty;
        }
      }
    }
  }

  grouping dhcp-liveness-detection-type {
    uses apply-group;
    uses apply-macro;
    container failure-action {
      uses dhcp-liveness-detection-failure-action-type;
    }
    container method {
      uses apply-group;
      uses apply-macro;
      choice choice-bfd {
        container bfd {
          uses dhcp-bfd-liveness-detection-type;
        }
        container layer2-liveness-detection {
          uses dhcp-arp-nud-liveness-detection-type;
        }
      }
    }
  }

  grouping dhcp-bfd-liveness-detection-type {
    uses apply-group;
    uses apply-macro;
    leaf version {
      type string;
    }
    leaf minimum-interval {
      units "milliseconds";
      type uint32;
    }
    leaf minimum-transmit-interval {
      units "milliseconds";
      type uint32;
    }
    leaf minimum-receive-interval {
      units "milliseconds";
      type uint32;
    }
    leaf multiplier {
      type uint32;
    }
    leaf no-adaptation {
      type empty;
    }
    container transmit-interval {
      uses apply-group;
      uses apply-macro;
      leaf minimum-interval {
        units "milliseconds";
        type uint32;
      }
      leaf threshold {
        type uint32;
        units "milliseconds";
      }
    }
    container detection-time {
      uses apply-group;
      uses apply-macro;
      leaf threshold {
        type uint32;
        units "milliseconds";
      }
    }
    leaf session-mode {
      type string;
    }
    leaf holddown-interval {
      units "milliseconds";
      type uint32;
    }
  }

  grouping dhcp-arp-nud-liveness-detection-type {
    uses apply-group;
    uses apply-macro;
    leaf transmit-interval {
      units "seconds";
      type uint32;
    }
    leaf max-consecutive-retries {
      type uint32;
    }
  }

  grouping dhcp-liveness-detection-failure-action-type {
    uses apply-group;
    uses apply-macro;
    choice choice-clear-binding {
      leaf clear-binding {
        type empty;
      }
      leaf clear-binding-if-interface-up {
        type empty;
      }
      leaf log-only {
        type empty;
      }
    }
  }

  grouping dhcp-remote-id-mismatch-type {
    uses apply-group;
    uses apply-macro;
    leaf disconnect {
      mandatory true;
      type empty;
    }
  }

  grouping dhcp-route-suppression-type {
    uses apply-group;
    uses apply-macro;
    choice choice-access-internal {
      leaf access-internal {
        type empty;
      }
      leaf destination {
        type empty;
      }
    }
  }

  grouping dhcp-v4-option-default-action {
    uses apply-group;
    uses apply-macro;
    choice choice-relay-server-group {
      leaf relay-server-group {
        type string;
      }
      leaf local-server-group {
        type string;
      }
      leaf drop {
        type empty;
      }
      leaf forward-only {
        type empty;
      }
    }
  }

  grouping dhcpv4-gbl-active-sg-type {
    uses apply-group;
    uses apply-macro;
    leaf active-server-group {
      type string;
    }
    leaf allow-server-change {
      type empty;
    }
  }

  grouping res-cleanupd-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping resource-monitor-type {
    uses apply-group;
    uses apply-macro;
    list resource-category {
      key "name";
      ordered-by user;
      leaf name {
        type string;
      }
      uses apply-group;
      uses apply-macro;
      list resource-type {
        key "name";
        ordered-by user;
        leaf name {
          type string;
        }
        uses apply-group;
        uses apply-macro;
        leaf low-watermark {
          type uint32;
        }
        leaf high-watermark {
          type uint32;
        }
      }
    }
    container traceoptions {
      uses resource-monitor-traceoptions-type;
    }
    leaf no-throttle {
      type empty;
    }
    leaf no-load-throttle {
      type empty;
    }
    leaf no-logging {
      type empty;
    }
    leaf high-threshold {
      units "percentage";
      type uint32;
    }
    leaf high-cos-queue-threshold {
      units "percentage";
      type uint32;
    }
    leaf free-heap-memory-watermark {
      units "percentage";
      type uint32;
    }
    leaf free-nh-memory-watermark {
      units "percentage";
      type uint32;
    }
    leaf free-fw-memory-watermark {
      units "percentage";
      type uint32;
    }
    container subscribers-limit {
      uses apply-group;
      uses apply-macro;
      list client-type {
        key "name";
        ordered-by user;
        leaf name {
          type string;
        }
        uses apply-group;
        uses apply-macro;
        container chassis {
          uses apply-group;
          uses apply-macro;
          leaf limit {
            type uint32;
          }
        }
        list fpc {
          key "name";
          uses rsmon-fpc-type;
        }
      }
    }
  }

  grouping resource-monitor-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    list flag {
      key "name";
      ordered-by user;
      leaf name {
        type string;
      }
    }
  }

  grouping resources-type {
    uses apply-group;
    uses apply-macro;
    container cpu {
      uses apply-group;
      uses apply-macro;
      leaf priority {
        type int32;
      }
      leaf time {
        type uint64;
      }
    }
    container memory {
      uses apply-group;
      uses apply-macro;
      leaf data-size {
        type string;
      }
      leaf locked-in {
        type string;
      }
      leaf resident-set-size {
        type string;
      }
      leaf socket-buffers {
        type string;
      }
      leaf stack-size {
        type string;
      }
    }
    container file {
      uses apply-group;
      uses apply-macro;
      leaf size {
        type string;
      }
      leaf open {
        type uint64;
      }
      leaf core-size {
        type string;
      }
    }
  }

  grouping rib-aggregate-type {
    uses apply-group;
    uses apply-macro;
    container defaults {
      uses apply-group;
      uses apply-macro;
      container metric {
        presence "";
        uses rib-static-metric-type;
      }
      container metric2 {
        presence "";
        uses rib-static-metric-type;
      }
      container metric3 {
        presence "";
        uses rib-static-metric-type;
      }
      container metric4 {
        presence "";
        uses rib-static-metric-type;
      }
      container tag {
        presence "";
        uses rib-static-metric-type;
      }
      container tag2 {
        presence "";
        uses rib-static-metric-type;
      }
      container preference {
        presence "";
        uses rib-static-metric-type;
      }
      container preference2 {
        presence "";
        uses rib-static-metric-type;
      }
      container color {
        presence "";
        uses rib-static-metric-type;
      }
      container color2 {
        presence "";
        uses rib-static-metric-type;
      }
      leaf-list community {
        type community;
        ordered-by user;
      }
      container as-path {
        uses apply-group;
        uses apply-macro;
        leaf path {
          type string;
        }
        leaf origin {
          type string;
        }
        leaf atomic-aggregate {
          type empty;
        }
        choice aggregator {
          case aggregator {
            leaf as-number {
              type string;
              mandatory true;
            }
            leaf address {
              mandatory true;
              type ipv4addr;
            }
          }
        }
      }
      leaf discard {
        type empty;
      }
      choice choice-brief {
        leaf brief {
          type empty;
        }
        leaf full {
          type empty;
        }
      }
      choice choice-active {
        leaf active {
          type empty;
        }
        leaf passive {
          type empty;
        }
      }
    }
    list route {
      key "name";
      ordered-by user;
      leaf name {
        type ipprefix;
      }
      uses apply-group;
      uses apply-macro;
      leaf-list policy {
        type policy-algebra;
        ordered-by user;
      }
      container metric {
        presence "";
        uses rib-static-metric-type;
      }
      container metric2 {
        presence "";
        uses rib-static-metric-type;
      }
      container metric3 {
        presence "";
        uses rib-static-metric-type;
      }
      container metric4 {
        presence "";
        uses rib-static-metric-type;
      }
      container tag {
        presence "";
        uses rib-static-metric-type;
      }
      container tag2 {
        presence "";
        uses rib-static-metric-type;
      }
      container preference {
        presence "";
        uses rib-static-metric-type;
      }
      container preference2 {
        presence "";
        uses rib-static-metric-type;
      }
      container color {
        presence "";
        uses rib-static-metric-type;
      }
      container color2 {
        presence "";
        uses rib-static-metric-type;
      }
      leaf-list community {
        type community;
        ordered-by user;
      }
      container as-path {
        uses apply-group;
        uses apply-macro;
        leaf path {
          type string;
        }
        leaf origin {
          type string;
        }
        leaf atomic-aggregate {
          type empty;
        }
        choice aggregator {
          case aggregator {
            leaf as-number {
              type string;
              mandatory true;
            }
            leaf address {
              mandatory true;
              type ipv4addr;
            }
          }
        }
      }
      leaf discard {
        type empty;
      }
      choice choice-brief {
        leaf brief {
          type empty;
        }
        leaf full {
          type empty;
        }
      }
      choice choice-active {
        leaf active {
          type empty;
        }
        leaf passive {
          type empty;
        }
      }
    }
  }

  grouping rib-inet3 {
    uses apply-advanced;
    container inet.3 {
      presence "enable inet.3";
      uses apply-advanced;
    }
  }

  grouping rib-group-inet-type {
    uses apply-group;
    uses apply-macro;
    leaf ribgroup-name {
      type string;
    }
  }

  grouping rib-group-type {
    uses apply-group;
    uses apply-macro;
    leaf inet-old-style {
      status deprecated;
      type string;
    }
    leaf inet {
      type string;
    }
    leaf inet3 {
      type string;
    }
    leaf inet6 {
      type string;
    }
    leaf inet63 {
      type string;
    }
  }

  grouping rib-static-metric-type {
    uses apply-group;
    uses apply-macro;
    leaf metric-value {
      type string;
    }
    leaf type {
      type string;
    }
  }

  grouping rip-filter-obj {
    uses apply-group;
    uses apply-macro;
    leaf match-on {
      type string;
    }
    leaf-list policy {
      type policy-algebra;
      ordered-by user;
    }
  }

  grouping rmopd-traceoptions {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping rmps-clnt-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping rmpsd-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping route-filter-list-items {
    leaf address {
      type ipprefix;
    }
    leaf key2 {
      type string;
    }
    leaf key2-arg {
      type string;
    }
    uses apply-group;
    uses apply-macro;
    container metric {
      uses apply-group;
      uses apply-macro;
      choice choice-metric {
        leaf metric {
          type uint32;
        }
        leaf add {
          type uint32;
        }
        leaf subtract {
          type uint32;
        }
        container igp {
          presence "enable igp";
          leaf metric_offset {
            type int32;
          }
        }
        container minimum-igp {
          presence "enable minimum-igp";
          leaf metric_offset {
            type int32;
          }
        }
        container expression {
          uses metric-expression-type;
        }
        leaf aigp {
          type empty;
        }
      }
    }
    container metric2 {
      uses apply-group;
      uses apply-macro;
      choice choice-metric2 {
        leaf metric2 {
          type uint32;
        }
        leaf add {
          type uint32;
        }
        leaf subtract {
          type uint32;
        }
      }
    }
    container metric3 {
      uses apply-group;
      uses apply-macro;
      choice choice-metric3 {
        leaf metric3 {
          type uint32;
        }
        leaf add {
          type uint32;
        }
        leaf subtract {
          type uint32;
        }
      }
    }
    container metric4 {
      uses apply-group;
      uses apply-macro;
      choice choice-metric4 {
        leaf metric4 {
          type uint32;
        }
        leaf add {
          type uint32;
        }
        leaf subtract {
          type uint32;
        }
      }
    }
    container tag {
      uses apply-group;
      uses apply-macro;
      choice choice-tag {
        leaf tag {
          type uint32;
        }
        leaf add {
          type uint32;
        }
        leaf subtract {
          type uint32;
        }
      }
    }
    container tag2 {
      uses apply-group;
      uses apply-macro;
      choice choice-tag2 {
        leaf tag2 {
          type uint32;
        }
        leaf add {
          type uint32;
        }
        leaf subtract {
          type uint32;
        }
      }
    }
    container preference {
      uses apply-group;
      uses apply-macro;
      choice choice-preference {
        leaf preference {
          type uint32;
        }
        leaf add {
          type uint32;
        }
        leaf subtract {
          type uint32;
        }
      }
    }
    container preference2 {
      uses apply-group;
      uses apply-macro;
      choice choice-preference2 {
        leaf preference2 {
          type uint32;
        }
        leaf add {
          type uint32;
        }
        leaf subtract {
          type uint32;
        }
      }
    }
    container color {
      uses apply-group;
      uses apply-macro;
      choice choice-color {
        leaf color {
          type uint32;
        }
        leaf add {
          type uint32;
        }
        leaf subtract {
          type uint32;
        }
      }
    }
    container color2 {
      uses apply-group;
      uses apply-macro;
      choice choice-color2 {
        leaf color2 {
          type uint32;
        }
        leaf add {
          type uint32;
        }
        leaf subtract {
          type uint32;
        }
      }
    }
    container local-preference {
      uses apply-group;
      uses apply-macro;
      choice choice-local-preference {
        leaf local-preference {
          type uint32;
        }
        leaf add {
          type uint32;
        }
        leaf subtract {
          type uint32;
        }
      }
    }
    leaf priority {
      type string;
    }
    container prefix-segment {
      list algorithm {
        key "name";
        leaf name {
          type string;
        }
        leaf index {
          type string;
        }
        leaf node-segment {
          type empty;
        }
      }
      leaf index {
        type string;
      }
      leaf node-segment {
        type empty;
      }
    }
    leaf label-allocation {
      type string;
    }
    container add-path {
      leaf send-count {
        type uint32;
      }
    }
    leaf validation-state {
      type string;
    }
    leaf origin {
      type string;
    }
    container aigp-originate {
      presence "enable aigp-originate";
      leaf distance {
        type uint32;
      }
    }
    container aigp-adjust {
      choice choice-add {
        leaf add {
          type empty;
        }
        leaf subtract {
          type empty;
        }
        leaf multiply {
          type empty;
        }
        leaf divide {
          type empty;
        }
      }
      choice choice-user-value {
        leaf user-value {
          type uint64;
        }
        leaf distance-to-protocol-nexthop {
          type empty;
        }
      }
    }
    list community {
      key "key1 community-name";
      ordered-by user;
      leaf key1 {
        type string;
      }
      leaf community-name {
        type string;
      }
    }
    leaf damping {
      type string;
    }
    leaf aggregate-bandwidth {
      type empty;
    }
    leaf limit-bandwidth {
      type uint32;
    }
    leaf no-entropy-label-capability {
      type empty;
    }
    leaf as-path-prepend {
      type string;
    }
    container as-path-expand {
      choice choice-last-as {
        container last-as {
          presence "enable last-as";
          leaf count {
            type uint32;
          }
        }
        leaf aspath {
          type string;
        }
      }
    }
    container next-hop {
      choice choice-self {
        leaf self {
          type empty;
        }
        leaf peer-address {
          type empty;
        }
        leaf address {
          type ipaddr;
        }
        leaf reject {
          type empty;
        }
        leaf discard {
          type empty;
        }
        leaf next-table {
          type string;
        }
      }
    }
    container install-nexthop {
      leaf strict {
        type empty;
      }
      choice choice-lsp {
        leaf-list lsp {
          type string;
          ordered-by user;
        }
        leaf-list lsp-regex {
          type string;
          ordered-by user;
        }
        leaf-list static-lsp {
          type string;
          ordered-by user;
        }
        leaf-list static-lsp-regex {
          type string;
          ordered-by user;
        }
      }
      container except {
        uses apply-group;
        uses apply-macro;
        choice choice-lsp {
          leaf-list lsp {
            type string;
            ordered-by user;
          }
          leaf-list lsp-regex {
            type string;
            ordered-by user;
          }
          leaf-list static-lsp {
            type string;
            ordered-by user;
          }
          leaf-list static-lsp-regex {
            type string;
            ordered-by user;
          }
        }
      }
    }
    leaf trace {
      type empty;
    }
    container external {
      presence "enable external";
      uses apply-group;
      uses apply-macro;
      leaf type {
        type int32;
      }
      leaf nssa-only {
        type empty;
      }
    }
    container load-balance {
      choice choice-per-packet {
        leaf per-packet {
          type empty;
        }
        leaf random {
          type empty;
        }
        leaf per-prefix {
          type empty;
        }
        leaf consistent-hash {
          type empty;
        }
        leaf source-ip-only {
          type empty;
        }
        leaf destination-ip-only {
          type empty;
        }
      }
    }
    leaf no-route-localize {
      type empty;
    }
    leaf install-to-fib {
      type empty;
    }
    leaf no-install-to-fib {
      type empty;
    }
    leaf analyze {
      type empty;
    }
    leaf class {
      type string;
    }
    leaf destination-class {
      type string;
    }
    leaf source-class {
      type string;
    }
    leaf forwarding-class {
      type string;
    }
    container map-to-interface {
      choice choice-self {
        leaf self {
          type empty;
        }
        leaf interface {
          type interface-name;
        }
      }
    }
    leaf-list ssm-source {
      type ipaddr;
      ordered-by user;
    }
    container p2mp-lsp-root {
      uses apply-group;
      uses apply-macro;
      leaf address {
        type ipv4addr;
      }
    }
    leaf cos-next-hop-map {
      type string;
    }
    leaf dynamic-tunnel-attributes {
      type string;
    }
    leaf selected-mldp-egress {
      type empty;
    }
    leaf mhop-bfd-port {
      type empty;
    }
    leaf default-action {
      type string;
    }
    leaf next {
      type string;
    }
    choice choice-accept {
      leaf accept {
        type empty;
      }
      leaf reject {
        type empty;
      }
    }
    container bgp-output-queue-priority {
      choice choice-priority {
        leaf priority {
          type uint32;
        }
        leaf expedited {
          type empty;
        }
      }
    }
    leaf multipath-resolve {
      type empty;
    }
    leaf sr-te-template {
      type string;
    }
    leaf label-allocation-fallback-reject {
      type empty;
    }
    leaf resolution-map {
      type string;
    }
  }

  grouping routing-destinations {
    uses apply-group;
    uses apply-macro;
    leaf default-availability-check-profile {
      type string;
    }
    list availability-check-profiles {
      key "name";
      ordered-by user;
      uses availability-check-profile;
    }
    list servers {
      key "name";
      ordered-by user;
      uses routing-destination-server;
    }
    list clusters {
      key "name";
      ordered-by user;
      uses routing-destination-cluster;
    }
  }

  grouping availability-check-profile {
    leaf name {
      type key-attribute-string-type;
    }
    uses apply-group;
    uses apply-macro;
    container keepalive-method {
      choice choice-3 {
        leaf sip-options {
          type empty;
        }
      }
    }
    container keepalive-strategy {
      presence "enable keepalive-strategy";
      choice choice-3 {
        container send-always {
          presence "enable send-always";
          uses apply-group;
          uses apply-macro;
          leaf failures-before-unavailable {
            type uint32;
          }
          leaf successes-before-available {
            type uint32;
          }
        }
        container send-when-unavailable {
          presence "enable send-when-unavailable";
          leaf successes-before-available {
            type uint32;
          }
        }
        container do-not-send {
          presence "enable do-not-send";
          leaf blackout-period {
            type uint32;
          }
        }
      }
    }
    container keepalive-interval {
      uses apply-group;
      uses apply-macro;
      leaf available-server {
        type uint32;
      }
      leaf unavailable-server {
        type uint32;
      }
    }
    leaf transaction-timeout {
      type uint32;
    }
  }

  grouping routing-destination-cluster {
    leaf name {
      type key-attribute-string-type;
    }
    uses apply-group;
    uses apply-macro;
    list server {
      key "name";
      ordered-by user;
      leaf name {
        type key-attribute-string-type;
      }
      uses apply-group;
      uses apply-macro;
      leaf priority {
        type uint16;
      }
      leaf weight {
        type uint16;
      }
    }
  }

  grouping routing-destination-server {
    leaf name {
      type key-attribute-string-type;
    }
    uses apply-group;
    uses apply-macro;
    container address {
      presence "";
      uses routing-destination-address;
    }
    leaf service-point {
      type string;
    }
    leaf admission-control {
      type string;
    }
    leaf availability-check-profile {
      type string;
    }
  }

  grouping routing-destination-address {
    uses apply-group;
    uses apply-macro;
    leaf ip4-address {
      type ipaddr;
    }
    leaf port {
      type uint32;
    }
    container transport-protocol {
      uses transport-protocol;
    }
  }

  grouping rpd-rib-group-type {
    leaf name {
      type string;
    }
    uses apply-group;
    uses apply-macro;
    leaf export-rib {
      type string;
    }
    leaf-list import-rib {
      type string;
      ordered-by user;
    }
    leaf-list import-policy {
      type policy-algebra;
      ordered-by user;
    }
  }

  grouping rsmon-fpc-type {
    leaf name {
      type key-attribute-ulong-type;
    }
    uses apply-group;
    uses apply-macro;
    list pic {
      key "name";
      uses rsmon-pic-type;
    }
    leaf limit {
      type uint32;
    }
  }

  grouping rsmon-pic-type {
    leaf name {
      type key-attribute-ulong-type;
    }
    uses apply-group;
    uses apply-macro;
    list port {
      key "name";
      uses rsmon-port-type;
    }
    leaf limit {
      type uint32;
    }
  }

  grouping rsmon-port-type {
    leaf name {
      type key-attribute-ulong-type;
    }
    uses apply-group;
    uses apply-macro;
    leaf limit {
      type uint32;
    }
  }

  grouping rtf-prefix-list-items {
    leaf name {
      type key-attribute-string-type;
    }
    uses apply-group;
    uses apply-macro;
  }

  grouping rtmd-dialplan-policy {
    leaf name {
      type string;
    }
    uses apply-group;
    uses apply-macro;
    list term {
      key "name";
      ordered-by user;
      leaf name {
        type string;
      }
      uses apply-group;
      uses apply-macro;
      container from {
        presence "enable from";
        uses apply-group;
        uses apply-macro;
        leaf trunk-group {
          type string;
        }
      }
      container then {
        presence "enable then";
        uses rtmd-dialplan-then;
      }
    }
  }

  grouping rtmd-dialplan-then {
    uses apply-group;
    uses apply-macro;
    container route {
      uses rtmd-dialplan-route-action;
    }
  }

  grouping rtmd-dialplan-route-action {
    uses apply-group;
    uses apply-macro;
    container next-hop {
      presence "enable next-hop";
      uses apply-group;
      uses apply-macro;
      choice choice-3 {
        leaf trunk-group {
          type string;
        }
        leaf peer-call-server {
          type string;
        }
      }
    }
  }

  grouping rtmd-mediapolicy {
    leaf name {
      type string;
    }
    uses apply-group;
    uses apply-macro;
    list term {
      key "name";
      ordered-by user;
      leaf name {
        type string;
      }
      uses apply-group;
      uses apply-macro;
      container from {
        presence "enable from";
        uses apply-group;
        uses apply-macro;
        container peer-address {
          presence "enable peer-address";
          uses apply-group;
          uses apply-macro;
          leaf fqdn {
            type string;
          }
          leaf ip-address {
            type ipprefix;
          }
        }
      }
      container then {
        presence "enable then";
        uses rtmd-mediapolicy-action;
      }
    }
  }

  grouping rtmd-mediapolicy-action {
    uses apply-group;
    uses apply-macro;
    leaf dscp {
      type string;
    }
  }

  grouping sampling-family-inet6-output-type {
    uses apply-group;
    uses apply-macro;
    leaf aggregate-export-interval {
      type uint32;
    }
    leaf flow-inactive-timeout {
      type uint32;
    }
    leaf flow-active-timeout {
      type uint32;
    }
    list flow-server {
      key "name";
      uses cflowd-sampling-inet6-sampling-type;
    }
    list interface {
      key "name";
      uses packet-export-intf-type;
    }
    container inline-jflow {
      presence "";
      uses packet-export-inline;
    }
  }

  grouping cflowd-sampling-inet6-sampling-type {
    leaf name {
      type ipv4addr;
    }
    uses apply-group;
    uses apply-macro;
    leaf port {
      type uint16;
    }
    leaf autonomous-system-type {
      type string;
    }
    container aggregation {
      uses aggregation-type;
    }
    leaf local-dump {
      type empty;
    }
    leaf no-local-dump {
      type empty;
    }
    leaf source-address {
      type ipv4addr;
    }
    container version9 {
      presence "";
      uses apply-group;
      uses apply-macro;
      container template {
        presence "";
        uses apply-group;
        uses apply-macro;
        leaf template-name {
          type string;
        }
      }
    }
  }

  grouping sampling-input-type {
    uses apply-group;
    uses apply-macro;
    leaf rate {
      type uint16;
    }
    leaf run-length {
      type uint32;
    }
    leaf max-packets-per-second {
      type uint16;
    }
    leaf maximum-packet-length {
      type uint32;
    }
  }

  grouping sampling-instance-bridge-output-type {
    container apply-advanced {
      uses apply-group;
      uses apply-macro;
    }
    list flow-server {
      key "name";
      uses cflowd-instance-bridge-sampling-type;
    }
    container inline-jflow {
      presence "enable inline-jflow";
      uses packet-export-inline-instance;
    }
  }

  grouping cflowd-instance-bridge-sampling-type {
    leaf name {
      type ipaddr;
    }
    container apply-advanced {
      uses apply-group;
      uses apply-macro;
    }
    leaf port {
      type string;
    }
    leaf dscp {
      type string;
    }
    leaf forwarding-class {
      type string;
    }
    leaf routing-instance {
      type string;
    }
    container version9 {
      presence "enable version9";
      container apply-advanced {
        uses apply-group;
        uses apply-macro;
      }
      container template {
        container apply-advanced {
          uses apply-group;
          uses apply-macro;
        }
        leaf template-name {
          type string;
        }
      }
    }
    container version-ipfix {
      presence "enable version-ipfix";
      container apply-advanced {
        uses apply-group;
        uses apply-macro;
      }
      container template {
        container apply-advanced {
          uses apply-group;
          uses apply-macro;
        }
        leaf template-name {
          type string;
        }
      }
    }
  }

  grouping packet-export-inline-instance {
    container apply-advanced {
      uses apply-group;
      uses apply-macro;
    }
    leaf source-address {
      type ipaddr;
    }
    leaf flow-export-rate {
      type string;
    }
  }

  grouping sampling-instance-inet6-output-type {
    uses apply-group;
    uses apply-macro;
    leaf aggregate-export-interval {
      type uint32;
    }
    leaf flow-inactive-timeout {
      type uint32;
    }
    leaf flow-active-timeout {
      type uint32;
    }
    list flow-server {
      key "name";
      uses cflowd-instance-inet6-sampling-type;
    }
    list interface {
      key "name";
      uses packet-export-intf-type;
    }
    container inline-jflow {
      presence "";
      uses packet-export-inline-instance;
    }
  }

  grouping cflowd-instance-inet6-sampling-type {
    leaf name {
      type ipv4addr;
    }
    uses apply-group;
    uses apply-macro;
    leaf port {
      type uint16;
    }
    leaf dscp {
      type uint8;
    }
    leaf forwarding-class {
      type string;
    }
    leaf routing-instance {
      type string;
    }
    leaf autonomous-system-type {
      type string;
    }
    container aggregation {
      uses aggregation-type;
    }
    leaf local-dump {
      type empty;
    }
    leaf no-local-dump {
      type empty;
    }
    leaf source-address {
      type ipv4addr;
    }
    container version9 {
      presence "";
      uses apply-group;
      uses apply-macro;
      container template {
        presence "";
        uses apply-group;
        uses apply-macro;
        leaf template-name {
          type string;
        }
      }
    }
    container version-ipfix {
      presence "";
      uses apply-group;
      uses apply-macro;
      container template {
        presence "";
        uses apply-group;
        uses apply-macro;
        leaf template-name {
          type string;
          mandatory true;
        }
      }
    }
  }

  grouping sampling-instance-inet-global-output-type {
    uses apply-group;
    uses apply-macro;
    leaf aggregate-export-interval {
      type uint32;
    }
    leaf flow-inactive-timeout {
      type uint32;
    }
    leaf flow-active-timeout {
      type uint32;
    }
    container file {
      presence "";
      choice choice-3 {
        leaf disable {
          type empty;
        }
      }
      leaf filename {
        type string;
      }
      leaf files {
        type uint32;
      }
      leaf size {
        type string;
      }
      leaf world-readable {
        type empty;
      }
      leaf no-world-readable {
        type empty;
      }
      leaf stamp {
        type empty;
      }
      leaf no-stamp {
        type empty;
      }
    }
    list flow-server {
      key "name";
      uses cflowd-sampling-inet-type;
    }
    list interface {
      key "name";
      uses packet-export-intf-type;
    }
    container inline-jflow {
      presence "";
      uses packet-export-inline;
    }
    list extension-service {
      key "name";
      ordered-by user;
      leaf name {
        type key-attribute-string-type;
      }
      uses apply-group;
      uses apply-macro;
    }
  }

  grouping cflowd-sampling-inet-type {
    leaf name {
      type ipv4addr;
    }
    uses apply-group;
    uses apply-macro;
    leaf port {
      type uint16;
    }
    leaf autonomous-system-type {
      type string;
    }
    container aggregation {
      uses aggregation-type;
    }
    leaf local-dump {
      type empty;
    }
    leaf no-local-dump {
      type empty;
    }
    leaf source-address {
      type ipv4addr;
    }
    container version9 {
      presence "";
      uses apply-group;
      uses apply-macro;
      container template {
        presence "";
        uses apply-group;
        uses apply-macro;
        leaf template-name {
          type string;
        }
      }
    }
    container version-ipfix {
      presence "";
      uses apply-group;
      uses apply-macro;
      container template {
        presence "";
        uses apply-group;
        uses apply-macro;
        leaf template-name {
          type string;
          mandatory true;
        }
      }
    }
    leaf version {
      type string;
    }
  }

  grouping packet-export-inline {
    uses apply-group;
    uses apply-macro;
    leaf source-address {
      type ipv4addr;
    }
    leaf flow-export-rate {
      type uint32;
    }
  }

  grouping sampling-family-input-type {
    container apply-advanced {
      uses apply-group;
      uses apply-macro;
    }
    leaf rate {
      type string;
    }
    leaf run-length {
      type string;
    }
    leaf max-packets-per-second {
      type string;
    }
    leaf maximum-packet-length {
      units "bytes";
      type string;
    }
  }

  grouping sampling-instance-inet-output-type {
    uses apply-group;
    uses apply-macro;
    leaf aggregate-export-interval {
      type uint32;
    }
    leaf flow-inactive-timeout {
      type uint32;
    }
    leaf flow-active-timeout {
      type uint32;
    }
    list flow-server {
      key "name";
      uses cflowd-instance-inet-sampling-type;
    }
    list interface {
      key "name";
      uses packet-export-intf-type;
    }
    container inline-jflow {
      presence "";
      uses packet-export-inline;
    }
    list extension-service {
      key "name";
      ordered-by user;
      leaf name {
        type key-attribute-string-type;
      }
      uses apply-group;
      uses apply-macro;
    }
  }

  grouping cflowd-instance-inet-sampling-type {
    leaf name {
      type ipv4addr;
    }
    uses apply-group;
    uses apply-macro;
    leaf port {
      type uint16;
    }
    leaf dscp {
      type uint8;
    }
    leaf forwarding-class {
      type string;
    }
    leaf routing-instance {
      type string;
    }
    leaf autonomous-system-type {
      type string;
    }
    container aggregation {
      uses aggregation-type;
    }
    leaf local-dump {
      type empty;
    }
    leaf no-local-dump {
      type empty;
    }
    leaf source-address {
      type ipv4addr;
    }
    container version9 {
      presence "";
      uses apply-group;
      uses apply-macro;
      container template {
        presence "";
        uses apply-group;
        uses apply-macro;
        leaf template-name {
          type string;
        }
      }
    }
    container version-ipfix {
      presence "";
      uses apply-group;
      uses apply-macro;
      container template {
        presence "";
        uses apply-group;
        uses apply-macro;
        leaf template-name {
          type string;
        }
      }
    }
    leaf version {
      type string;
    }
  }

  grouping sampling-instance-input-type {
    uses apply-group;
    uses apply-macro;
    leaf rate {
      type uint16;
    }
    leaf run-length {
      type uint32;
    }
    leaf max-packets-per-second {
      type uint16;
    }
    leaf maximum-packet-length {
      type uint32;
    }
  }

  grouping sampling-instance-mpls-output-type {
    uses apply-group;
    uses apply-macro;
    leaf aggregate-export-interval {
      type uint32;
    }
    leaf flow-inactive-timeout {
      type uint32;
    }
    leaf flow-active-timeout {
      type uint32;
    }
    list flow-server {
      key "name";
      uses cflowd-instance-mpls-sampling-type;
    }
    container inline-jflow {
      presence "";
      uses packet-export-inline;
    }
    list interface {
      key "name";
      uses packet-export-intf-type;
    }
  }

  grouping cflowd-instance-mpls-sampling-type {
    leaf name {
      type ipv4addr;
    }
    uses apply-group;
    uses apply-macro;
    leaf port {
      type uint16;
    }
    leaf dscp {
      type uint8;
    }
    leaf forwarding-class {
      type string;
    }
    leaf routing-instance {
      type string;
    }
    leaf autonomous-system-type {
      type string;
    }
    container aggregation {
      uses aggregation-type;
    }
    leaf local-dump {
      type empty;
    }
    leaf no-local-dump {
      type empty;
    }
    leaf source-address {
      type ipv4addr;
    }
    container version9 {
      presence "";
      uses apply-group;
      uses apply-macro;
      container template {
        presence "";
        uses apply-group;
        uses apply-macro;
        leaf template-name {
          type string;
        }
      }
    }
    container version-ipfix {
      presence "";
      uses apply-group;
      uses apply-macro;
      container template {
        presence "";
        uses apply-group;
        uses apply-macro;
        leaf template-name {
          type string;
          mandatory true;
        }
      }
    }
  }

  grouping sampling-instance-vpls-output-type {
    uses apply-group;
    uses apply-macro;
    list flow-server {
      key "name";
      uses cflowd-instance-vpls-sampling-type;
    }
    container inline-jflow {
      presence "";
      uses packet-export-inline-instance;
    }
  }

  grouping cflowd-instance-vpls-sampling-type {
    leaf name {
      type ipaddr;
    }
    uses apply-group;
    uses apply-macro;
    leaf port {
      type uint16;
      mandatory true;
    }
    leaf dscp {
      type uint8;
    }
    leaf forwarding-class {
      type string;
    }
    leaf routing-instance {
      type string;
    }
    container version9 {
      presence "";
      uses apply-group;
      uses apply-macro;
      container template {
        presence "";
        uses apply-group;
        uses apply-macro;
        leaf template-name {
          type string;
          mandatory true;
        }
      }
    }
    container version-ipfix {
      presence "";
      uses apply-group;
      uses apply-macro;
      container template {
        presence "";
        uses apply-group;
        uses apply-macro;
        leaf template-name {
          type string;
          mandatory true;
        }
      }
    }
  }

  grouping sampling-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
  }

  grouping satellite-bridge-filter {
    leaf name {
      type string;
    }
    uses apply-group;
    uses apply-macro;
    list term {
      key "name";
      ordered-by user;
      leaf name {
        type string;
      }
      uses apply-group;
      uses apply-macro;
      container from {
        uses apply-group;
        uses apply-macro;
        list source-mac-address {
          key "name";
          ordered-by user;
          uses firewall-mac-addr-object;
        }
        list destination-mac-address {
          key "name";
          ordered-by user;
          uses firewall-mac-addr-object;
        }
        list ip-source-address {
          key "name";
          ordered-by user;
          uses firewall-addr-object;
        }
        list ip-destination-address {
          key "name";
          ordered-by user;
          uses firewall-addr-object;
        }
        choice choice-ip-protocol {
          leaf-list ip-protocol {
            ordered-by user;
            type string;
          }
          leaf-list ip-protocol-except {
            ordered-by user;
            type string;
          }
        }
        choice choice-source-port {
          leaf-list source-port {
            ordered-by user;
            type string;
          }
          leaf-list source-port-except {
            ordered-by user;
            type string;
          }
        }
        choice choice-destination-port {
          leaf-list destination-port {
            ordered-by user;
            type string;
          }
          leaf-list destination-port-except {
            ordered-by user;
            type string;
          }
        }
        choice choice-user-vlan-id {
          leaf-list user-vlan-id {
            type string;
            ordered-by user;
          }
          leaf-list user-vlan-id-except {
            type string;
            ordered-by user;
          }
        }
      }
      container then {
        uses apply-group;
        uses apply-macro;
        choice choice-accept {
          leaf accept {
            type empty;
          }
          leaf discard {
            type empty;
          }
        }
        leaf next-hop-group {
          type string;
        }
      }
    }
  }

  grouping satellite-policy-options {
    uses apply-group;
    uses apply-macro;
    list extended-ports-template {
      key "name";
      ordered-by user;
      leaf name {
        type key-attribute-string-type;
      }
      uses apply-group;
      uses apply-macro;
      list pic {
        key "name";
        uses satellite-pic-type;
      }
    }
    list port-group-alias {
      key "name";
      ordered-by user;
      leaf name {
        type key-attribute-string-type;
      }
      uses apply-group;
      uses apply-macro;
      list pic {
        key "name";
        ordered-by user;
        leaf name {
          type int32;
        }
        uses apply-group;
        uses apply-macro;
        leaf-list port {
          ordered-by user;
          type uint32;
        }
      }
    }
    list chassis-group-alias {
      key "name";
      ordered-by user;
      leaf name {
        type key-attribute-string-type;
      }
      uses apply-group;
      uses apply-macro;
      leaf prefer-primary {
        type empty;
      }
      list chassis-id {
        key "name";
        ordered-by user;
        leaf name {
          type key-attribute-ulong-type;
        }
        uses apply-group;
        uses apply-macro;
        container mode {
          uses apply-group;
          uses apply-macro;
          choice choice-primary {
            leaf primary {
              type empty;
            }
            leaf backup {
              type empty;
            }
          }
        }
        list core-interface {
          key "name";
          ordered-by user;
          leaf name {
            type interface-device;
          }
          uses apply-group;
          uses apply-macro;
        }
      }
    }
    list extended-ports-policy {
      key "name";
      ordered-by user;
      leaf name {
        type key-attribute-string-type;
      }
      uses apply-group;
      uses apply-macro;
      list term {
        key "name";
        ordered-by user;
        leaf name {
          type key-attribute-string-type;
        }
        uses apply-group;
        uses apply-macro;
        container from {
          presence "";
          uses apply-group;
          uses apply-macro;
          leaf-list product-model {
            ordered-by user;
            type string;
          }
          leaf extended-ports-template {
            type string;
            mandatory true;
          }
        }
      }
    }
    list candidate-uplink-port-policy {
      key "name";
      ordered-by user;
      leaf name {
        type key-attribute-string-type;
      }
      uses apply-group;
      uses apply-macro;
      leaf uplink-port-group {
        type string;
      }
      leaf minimum-links {
        type uint16;
      }
      leaf holddown {
        units "seconds";
        type uint32;
      }
      list term {
        key "name";
        ordered-by user;
        leaf name {
          type key-attribute-string-type;
        }
        uses apply-group;
        uses apply-macro;
        container from {
          presence "";
          uses apply-group;
          uses apply-macro;
          leaf-list product-model {
            ordered-by user;
            type string;
          }
          leaf uplink-port-group {
            type string;
          }
          leaf minimum-links {
            type uint16;
          }
          leaf holddown {
            units "seconds";
            type uint32;
          }
        }
      }
    }
    list environment-monitoring-policy {
      key "name";
      ordered-by user;
      leaf name {
        type key-attribute-string-type;
      }
      uses apply-group;
      uses apply-macro;
      container alarm {
        presence "";
        uses apply-group;
        uses apply-macro;
        leaf linkdown {
          mandatory true;
          type string;
        }
      }
      list term {
        key "name";
        ordered-by user;
        leaf name {
          type key-attribute-string-type;
        }
        uses apply-group;
        uses apply-macro;
        container from {
          presence "";
          uses apply-group;
          uses apply-macro;
          leaf-list product-model {
            ordered-by user;
            type string;
          }
          container alarm {
            presence "";
            uses apply-group;
            uses apply-macro;
            leaf linkdown {
              mandatory true;
              type string;
            }
          }
        }
      }
    }
    list forwarding-policy {
      key "name";
      ordered-by user;
      leaf name {
        type key-attribute-string-type;
      }
      uses apply-group;
      uses apply-macro;
      list port-group-extended {
        key "name";
        ordered-by user;
        uses port-extend-type;
      }
      list term {
        key "name";
        ordered-by user;
        leaf name {
          type key-attribute-string-type;
        }
        uses apply-group;
        uses apply-macro;
        container from {
          presence "";
          uses apply-group;
          uses apply-macro;
          leaf-list product-model {
            ordered-by user;
            type string;
          }
          list port-group-extended {
            key "name";
            ordered-by user;
            uses port-extend-type;
          }
        }
      }
    }
  }

  grouping port-extend-type {
    leaf name {
      type string;
    }
    uses apply-group;
    uses apply-macro;
    leaf filter {
      type string;
    }
    container port-group-uplink {
      presence "";
      uses apply-group;
      uses apply-macro;
      leaf port-group-uplink-alias {
        type string;
        mandatory true;
      }
      leaf minimum-links {
        type uint16;
      }
      leaf holddown {
        units "seconds";
        type uint32;
      }
    }
    container mirror-ingress {
      uses apply-group;
      uses apply-macro;
      leaf port-group-mirror {
        type string;
      }
    }
    container mirror-egress {
      uses apply-group;
      uses apply-macro;
      leaf port-group-mirror {
        type string;
      }
    }
  }

  grouping satellite-pic-type {
    leaf name {
      type key-attribute-ulong-type;
    }
    uses apply-group;
    uses apply-macro;
    list port {
      key "name";
      uses satellite-pic-port-attr;
    }
    list port-range {
      key "port-range-low port-range-high";
      ordered-by user;
      leaf port-range-low {
        mandatory true;
        type key-attribute-ulong-type;
      }
      leaf port-range-high {
        mandatory true;
        type key-attribute-ulong-type;
      }
      uses apply-group;
      uses apply-macro;
      leaf channel-speed {
        type string;
      }
    }
  }

  grouping satellite-pic-port-attr {
    leaf name {
      type key-attribute-ulong-type;
    }
    uses apply-group;
    uses apply-macro;
    leaf channel-speed {
      type string;
    }
  }

  grouping sbc-traceoptions {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    container flag {
      presence "enable flag";
      uses apply-group;
      uses apply-macro;
      leaf configuration {
        type string;
      }
      leaf ipc {
        type string;
      }
      leaf device-monitor {
        type string;
      }
      leaf ui {
        type string;
      }
      leaf common {
        type string;
      }
      leaf memory-pool {
        type string;
      }
      leaf all {
        type string;
      }
    }
  }

  grouping sbl-type {
    uses apply-group;
    uses apply-macro;
    list profile {
      key "name";
      ordered-by user;
      leaf name {
        type key-attribute-string-type;
      }
      uses apply-group;
      uses apply-macro;
      leaf sbl-default-server {
        type empty;
      }
      leaf no-sbl-default-server {
        type empty;
      }
      leaf spam-action {
        type string;
      }
      leaf custom-tag-string {
        type string;
      }
    }
  }

  grouping scheduler-object-type {
    leaf name {
      type key-attribute-string-type;
    }
    uses apply-group;
    uses apply-macro;
    list start-date {
      key "start-date stop-date";
      ordered-by user;
      leaf start-date {
        type string;
      }
      leaf stop-date {
        type string;
      }
      uses apply-group;
      uses apply-macro;
    }
    container daily {
      uses daily-object;
    }
    container sunday {
      uses daily-object;
    }
    container monday {
      uses daily-object;
    }
    container tuesday {
      uses daily-object;
    }
    container wednesday {
      uses daily-object;
    }
    container thursday {
      uses daily-object;
    }
    container friday {
      uses daily-object;
    }
    container saturday {
      uses daily-object;
    }
  }

  grouping daily-object {
    uses apply-group;
    uses apply-macro;
    choice choice-3 {
      list start-time {
        key "start-time-value stop-time";
        leaf start-time-value {
          type string;
        }
        leaf stop-time {
          type string;
        }
        uses apply-group;
        uses apply-macro;
      }
      leaf exclude {
        type empty;
      }
      leaf all-day {
        type empty;
      }
    }
  }

  grouping scripts-type {
    uses apply-group;
    uses apply-macro;
    container commit {
      uses apply-group;
      uses apply-macro;
      leaf allow-transients {
        type empty;
      }
      container traceoptions {
        uses script-traceoptions;
      }
      leaf refresh {
        type empty;
      }
      leaf refresh-from {
        type string;
      }
      leaf max-datasize {
        type string;
        units "bytes";
      }
      leaf direct-access {
        type empty;
      }
      container dampen {
        presence "enable dampen";
        uses apply-group;
        uses apply-macro;
        container dampen-options {
          uses apply-group;
          uses apply-macro;
          leaf cpu-factor {
            type uint32;
          }
          leaf line-interval {
            type uint32;
          }
          leaf time-interval {
            units "microseconds";
            type uint32;
          }
        }
      }
      list file {
        key "name";
        ordered-by user;
        uses commit-scripts-file-type;
      }
    }
    container op {
      uses apply-group;
      uses apply-macro;
      leaf refresh {
        type empty;
      }
      leaf refresh-from {
        type string;
      }
      container traceoptions {
        uses script-traceoptions;
      }
      list file {
        key "name";
        uses op-scripts-file-type;
      }
      leaf no-allow-url {
        type empty;
      }
      leaf allow-url-for-python {
        type empty;
      }
      leaf max-datasize {
        type string;
        units "bytes";
      }
      container dampen {
        presence "enable dampen";
        uses apply-group;
        uses apply-macro;
        container dampen-options {
          uses apply-group;
          uses apply-macro;
          leaf cpu-factor {
            type uint32;
          }
          leaf line-interval {
            type uint32;
          }
          leaf time-interval {
            units "microseconds";
            type uint32;
          }
        }
      }
    }
    container snmp {
      uses apply-group;
      uses apply-macro;
      leaf refresh {
        type empty;
      }
      leaf refresh-from {
        type string;
      }
      list file {
        key "name";
        uses snmp-scripts-file-type;
      }
      container traceoptions {
        uses script-traceoptions;
      }
      leaf max-datasize {
        type string;
        units "bytes";
      }
    }
    container translation {
      uses apply-group;
      uses apply-macro;
      leaf max-datasize {
        type string;
        units "bytes";
      }
    }
    leaf load-scripts-from-flash {
      type empty;
    }
    leaf language {
      type string;
    }
    leaf synchronize {
      type empty;
    }
  }

  grouping snmp-scripts-file-type {
    leaf name {
      type key-attribute-string-type;
    }
    uses apply-group;
    uses apply-macro;
    list oid {
      key "name";
      ordered-by user;
      leaf name {
        type string;
      }
      uses apply-group;
      uses apply-macro;
      leaf priority {
        type uint32;
      }
    }
    leaf source {
      type string;
    }
    leaf routing-instance {
      type string;
    }
    leaf python-script-user {
      type string;
    }
    leaf refresh {
      type empty;
    }
    leaf refresh-from {
      type string;
    }
    container checksum {
      uses apply-group;
      uses apply-macro;
      leaf sha-256 {
        type string;
      }
    }
  }

  grouping commit-scripts-file-type {
    leaf name {
      type key-attribute-string-type;
    }
    uses apply-group;
    uses apply-macro;
    leaf optional {
      type empty;
    }
    leaf source {
      type string;
    }
    leaf refresh {
      type empty;
    }
    leaf refresh-from {
      type string;
    }
    container checksum {
      uses apply-group;
      uses apply-macro;
      leaf md5 {
        type string;
      }
      leaf sha1 {
        type string;
      }
      leaf sha-256 {
        type string;
      }
    }
  }

  grouping op-scripts-file-type {
    leaf name {
      type key-attribute-string-type;
    }
    uses apply-group;
    uses apply-macro;
    leaf command {
      type string;
    }
    leaf description {
      type string;
    }
    leaf source {
      type string;
    }
    leaf refresh {
      type empty;
    }
    leaf refresh-from {
      type string;
    }
    list arguments {
      key "name";
      leaf name {
        type key-attribute-string-type;
      }
      uses apply-group;
      uses apply-macro;
      leaf description {
        type string;
      }
    }
    container checksum {
      uses apply-group;
      uses apply-macro;
      leaf md5 {
        type string;
      }
      leaf sha1 {
        type string;
      }
      leaf sha-256 {
        type string;
      }
    }
  }

  grouping script-traceoptions {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
    }
    list flag {
      key "name";
      leaf name {
        type string;
      }
    }
  }

  grouping sdk-vmmd-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping securid-server-object {
    leaf name {
      type string;
    }
    uses apply-group;
    uses apply-macro;
    leaf configuration-file {
      type string;
    }
  }

  grouping security-authentication-key-chains {
    uses apply-group;
    uses apply-macro;
    container apply-advanced {
      uses apply-group;
      uses apply-macro;
    }
    list key-chain {
      key "name";
      leaf name {
        type string;
      }
      uses apply-group;
      uses apply-macro;
      container apply-advanced {
        uses apply-group;
        uses apply-macro;
      }
      leaf description {
        type string;
      }
      leaf tolerance {
        type uint32;
        units "seconds";
      }
      list key {
        key "name";
        leaf name {
          type key-attribute-ulong-type;
        }
        uses apply-group;
        uses apply-macro;
        container apply-advanced {
          uses apply-group;
          uses apply-macro;
        }
        leaf secret {
          mandatory true;
          type unreadable;
        }
        leaf key-name {
          type string;
        }
        leaf start-time {
          mandatory true;
          type time;
        }
        leaf algorithm {
          type string;
        }
        leaf options {
          type string;
        }
        container ao-attribute {
          uses apply-advanced;
          leaf send-id {
            type string;
          }
          leaf recv-id {
            type string;
          }
          leaf tcp-ao-option {
            type string;
          }
          leaf cryptographic-algorithm {
            type string;
          }
        }
      }
    }
  }

  grouping security-distribution-profile {
    leaf name {
      type key-attribute-string-type;
    }
    uses apply-group;
    uses apply-macro;
    leaf description {
      type string;
    }
    list fpc {
      key "name";
      uses fpc-type;
    }
  }

  grouping fpc-type {
    leaf name {
      type key-attribute-ulong-type;
    }
    uses apply-group;
    uses apply-macro;
    list pic {
      key "name";
      uses pic-type;
    }
  }

  grouping pic-type {
    leaf name {
      type key-attribute-ulong-type;
    }
    uses apply-group;
    uses apply-macro;
  }

  grouping security-group-vpn {
    uses apply-group;
    uses apply-macro;
    container member {
      uses gvpn-member;
    }
    container server {
      uses gvpn-server;
    }
    leaf co-location {
      type empty;
    }
  }

  grouping gvpn-member {
    uses apply-group;
    uses apply-macro;
    container ike {
      uses gvpn-member-ike;
    }
    container ipsec {
      uses gvpn-member-ipsec-vpn;
    }
  }

  grouping gvpn-member-ike {
    uses apply-group;
    uses apply-macro;
    list proposal {
      key "name";
      ordered-by user;
      uses gvpn-member-ike-proposal;
    }
    list policy {
      key "name";
      ordered-by user;
      uses gvpn-member-ike-policy;
    }
    list gateway {
      key "name";
      ordered-by user;
      leaf name {
        type key-attribute-string-type;
      }
      uses apply-group;
      uses apply-macro;
      leaf ike-policy {
        type string;
      }
      choice choice-5 {
        leaf-list address {
          type hostname;
          ordered-by user;
        }
      }
      container local-identity {
        choice choice-3 {
          container inet {
            uses apply-group;
            uses apply-macro;
            leaf identity-ipv4 {
              type ipv4addr;
            }
          }
          container hostname {
            uses apply-group;
            uses apply-macro;
            leaf identity-hostname {
              type string;
            }
          }
          container user-at-hostname {
            uses apply-group;
            uses apply-macro;
            leaf identity-user {
              type string;
            }
          }
          leaf distinguished-name {
            type empty;
          }
        }
      }
      container remote-identity {
        choice choice-3 {
          container inet {
            uses apply-group;
            uses apply-macro;
            leaf identity-ipv4 {
              type ipv4addr;
            }
          }
          container hostname {
            uses apply-group;
            uses apply-macro;
            leaf identity-hostname {
              type string;
            }
          }
          container user-at-hostname {
            uses apply-group;
            uses apply-macro;
            leaf identity-user {
              type string;
            }
          }
          container distinguished-name {
            presence "enable distinguished-name";
            uses apply-group;
            uses apply-macro;
            leaf container {
              type string;
            }
            leaf wildcard {
              type string;
            }
          }
        }
      }
      leaf local-address {
        type ipv4addr;
      }
    }
  }

  grouping gvpn-member-ike-policy {
    leaf name {
      type key-attribute-string-type;
    }
    uses apply-group;
    uses apply-macro;
    leaf mode {
      type string;
    }
    leaf description {
      type string;
    }
    leaf-list proposals {
      type string;
      ordered-by user;
    }
    container certificate {
      uses apply-group;
      uses apply-macro;
      leaf local-certificate {
        type string;
      }
      leaf peer-certificate-type {
        type string;
      }
    }
    leaf proposal-set {
      type string;
    }
    container pre-shared-key {
      choice choice-3 {
        leaf ascii-text {
          type unreadable;
        }
        leaf hexadecimal {
          type unreadable;
        }
      }
    }
  }

  grouping gvpn-member-ike-proposal {
    leaf name {
      type key-attribute-string-type;
    }
    uses apply-group;
    uses apply-macro;
    leaf description {
      type string;
    }
    leaf authentication-method {
      type string;
    }
    leaf dh-group {
      type string;
    }
    leaf authentication-algorithm {
      type string;
    }
    leaf encryption-algorithm {
      type string;
    }
    leaf lifetime-seconds {
      type uint32;
    }
  }

  grouping gvpn-member-ipsec-vpn {
    uses apply-group;
    uses apply-macro;
    list vpn {
      key "name";
      ordered-by user;
      uses ipsec-gvpn-member-template;
    }
  }

  grouping gvpn-server {
    uses apply-group;
    uses apply-macro;
    container traceoptions {
      uses gvpn-server-traceoptions;
    }
    container ike {
      uses gvpn-server-ike;
    }
    container ipsec {
      uses gvpn-server-ipsec-vpn;
    }
    list group {
      key "name";
      ordered-by user;
      uses gvpn-server-group-template;
    }
  }

  grouping gvpn-server-group-template {
    leaf name {
      type key-attribute-string-type;
    }
    uses apply-group;
    uses apply-macro;
    leaf description {
      type string;
    }
    leaf group-id {
      type uint32;
    }
    list ike-gateway {
      key "name";
      ordered-by user;
      uses gvpn-server-ike-gateway;
    }
    leaf activation-time-delay {
      type uint32;
    }
    choice choice-11 {
      leaf anti-replay-time-window {
        type uint32;
      }
      leaf no-anti-replay {
        type empty;
      }
    }
    leaf server-address {
      type ipv4addr;
    }
    container server-member-communication {
      presence "";
      uses gvpn-server-member-communication;
    }
    list ipsec-sa {
      key "name";
      ordered-by user;
      uses gvpn-server-group-ipsecsa;
    }
  }

  grouping gvpn-server-group-ipsecsa {
    leaf name {
      type key-attribute-string-type;
    }
    uses apply-group;
    uses apply-macro;
    leaf proposal {
      type string;
    }
    list match-policy {
      key "name";
      ordered-by user;
      uses gvpn-server-group-ipsecsa-match;
    }
  }

  grouping gvpn-server-group-ipsecsa-match {
    leaf name {
      type key-attribute-string-type;
    }
    uses apply-group;
    uses apply-macro;
    leaf source {
      type ipv4prefix-mandatory;
    }
    leaf destination {
      type ipv4prefix-mandatory;
    }
    leaf source-port {
      type uint32;
    }
    leaf destination-port {
      type uint32;
    }
    leaf protocol {
      type uint32;
    }
  }

  grouping gvpn-server-ike {
    uses apply-group;
    uses apply-macro;
    list proposal {
      key "name";
      ordered-by user;
      uses gvpn-server-ike-proposal;
    }
    list policy {
      key "name";
      ordered-by user;
      uses ike-policy;
    }
    list gateway {
      key "name";
      ordered-by user;
      leaf name {
        type key-attribute-string-type;
      }
      uses apply-group;
      uses apply-macro;
      leaf ike-policy {
        type string;
      }
      choice choice-5 {
        leaf address {
          type string;
        }
        container dynamic {
          uses apply-group;
          uses apply-macro;
          choice choice-3 {
            container distinguished-name {
              presence "enable distinguished-name";
              uses apply-group;
              uses apply-macro;
              leaf container {
                type string;
              }
              leaf wildcard {
                type string;
              }
            }
            leaf hostname {
              type string;
            }
            leaf inet {
              type ipv4addr;
            }
            leaf user-at-hostname {
              type string;
            }
          }
        }
      }
      container local-identity {
        choice choice-3 {
          container inet {
            uses apply-group;
            uses apply-macro;
            leaf identity-ipv4 {
              type ipv4addr;
            }
          }
          container hostname {
            uses apply-group;
            uses apply-macro;
            leaf identity-hostname {
              type string;
            }
          }
          container user-at-hostname {
            uses apply-group;
            uses apply-macro;
            leaf identity-user {
              type string;
            }
          }
          leaf distinguished-name {
            type empty;
          }
        }
      }
      container remote-identity {
        choice choice-3 {
          container inet {
            uses apply-group;
            uses apply-macro;
            leaf identity-ipv4 {
              type ipv4addr;
            }
          }
          container hostname {
            uses apply-group;
            uses apply-macro;
            leaf identity-hostname {
              type string;
            }
          }
          container user-at-hostname {
            uses apply-group;
            uses apply-macro;
            leaf identity-user {
              type string;
            }
          }
          container distinguished-name {
            presence "enable distinguished-name";
            uses apply-group;
            uses apply-macro;
            leaf container {
              type string;
            }
            leaf wildcard {
              type string;
            }
          }
        }
      }
    }
  }

  grouping gvpn-server-ike-gateway {
    leaf name {
      type key-attribute-string-type;
    }
    uses apply-group;
    uses apply-macro;
  }

  grouping gvpn-server-ike-proposal {
    leaf name {
      type key-attribute-string-type;
    }
    uses apply-group;
    uses apply-macro;
    leaf description {
      type string;
    }
    leaf authentication-method {
      type string;
    }
    leaf dh-group {
      type string;
    }
    leaf authentication-algorithm {
      type string;
    }
    leaf encryption-algorithm {
      type string;
    }
  }

  grouping gvpn-server-ipsec-vpn {
    uses apply-group;
    uses apply-macro;
    list proposal {
      key "name";
      ordered-by user;
      uses gvpn-server-ipsec-proposal;
    }
  }

  grouping gvpn-server-ipsec-proposal {
    leaf name {
      type key-attribute-string-type;
    }
    uses apply-group;
    uses apply-macro;
    leaf description {
      type string;
    }
    leaf authentication-algorithm {
      type string;
    }
    leaf encryption-algorithm {
      type string;
    }
    leaf lifetime-seconds {
      type uint32;
    }
  }

  grouping gvpn-server-member-communication {
    uses apply-group;
    uses apply-macro;
    leaf communication-type {
      type string;
    }
    leaf multicast-group {
      type ipv4addr;
    }
    list multicast-outgoing-interface {
      key "name";
      ordered-by user;
      uses gvpn-server-multicast-interface;
    }
    leaf lifetime-seconds {
      type uint32;
    }
    leaf retransmission-period {
      type uint32;
    }
    leaf number-of-retransmission {
      type uint32;
    }
    leaf heartbeat {
      type uint32;
    }
    leaf encryption-algorithm {
      type string;
    }
    leaf sig-hash-algorithm {
      type string;
    }
    leaf certificate {
      type string;
    }
  }

  grouping gvpn-server-multicast-interface {
    leaf name {
      type interface-name;
    }
    uses apply-group;
    uses apply-macro;
  }

  grouping gvpn-server-traceoptions {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    list flag {
      key "name";
      ordered-by user;
      leaf name {
        type string;
      }
    }
  }

  grouping ike-policy {
    leaf name {
      type key-attribute-string-type;
    }
    uses apply-group;
    uses apply-macro;
    leaf mode {
      type string;
    }
    leaf reauth-frequency {
      type uint32;
    }
    leaf description {
      type string;
    }
    leaf-list proposals {
      type string;
      ordered-by user;
    }
    container certificate {
      uses apply-group;
      uses apply-macro;
      leaf local-certificate {
        type string;
      }
      container trusted-ca {
        choice choice-ca-index {
          leaf ca-index {
            type uint32;
          }
          leaf use-all {
            type empty;
          }
          leaf ca-profile {
            type string;
          }
          leaf trusted-ca-group {
            type string;
          }
        }
      }
      leaf peer-certificate-type {
        type string;
      }
      leaf-list policy-oids {
        ordered-by user;
        type string;
      }
    }
    leaf proposal-set {
      type string;
    }
    container pre-shared-key {
      choice choice-3 {
        leaf ascii-text {
          type unreadable;
        }
        leaf hexadecimal {
          type unreadable;
        }
      }
    }
  }

  grouping ipsec-gvpn-member-template {
    leaf name {
      type key-attribute-string-type;
    }
    uses apply-group;
    uses apply-macro;
    leaf ike-gateway {
      type string;
    }
    leaf group-vpn-external-interface {
      type interface-name;
    }
    leaf group {
      type uint32;
    }
    leaf heartbeat-threshold {
      type uint32;
    }
  }

  grouping security-ike {
    uses apply-group;
    uses apply-macro;
    container traceoptions {
      uses security-traceoptions;
    }
    container respond-bad-spi {
      presence "enable respond-bad-spi";
      leaf max-responses {
        type uint32;
      }
    }
    list proposal {
      key "name";
      ordered-by user;
      uses ike-proposal;
    }
    list policy {
      key "name";
      ordered-by user;
      uses ike-policy;
    }
    list gateway {
      key "name";
      ordered-by user;
      leaf name {
        type key-attribute-string-type;
      }
      uses apply-group;
      uses apply-macro;
      leaf ike-policy {
        type string;
      }
      choice choice-5 {
        leaf-list address {
          type hostname;
          ordered-by user;
        }
        container dynamic {
          uses apply-group;
          uses apply-macro;
          choice choice-3 {
            container distinguished-name {
              presence "enable distinguished-name";
              uses apply-group;
              uses apply-macro;
              leaf container {
                type string;
              }
              leaf wildcard {
                type string;
              }
            }
            leaf hostname {
              type string;
            }
            leaf inet {
              type ipv4addr;
            }
            leaf user-at-hostname {
              type string;
            }
          }
          leaf connections-limit {
            type uint32;
          }
          leaf ike-user-type {
            type string;
          }
        }
      }
      container dead-peer-detection {
        presence "enable dead-peer-detection";
        uses apply-group;
        uses apply-macro;
        leaf probe-idle-tunnel {
          type empty;
        }
        leaf always-send {
          type empty;
        }
        leaf interval {
          type uint32;
        }
        leaf threshold {
          type uint32;
        }
        leaf optimized {
          type empty;
        }
      }
      leaf no-nat-traversal {
        type empty;
      }
      leaf nat-keepalive {
        type uint32;
      }
      container local-identity {
        choice choice-3 {
          container inet {
            uses apply-group;
            uses apply-macro;
            leaf identity-ipv4 {
              type ipv4addr;
            }
          }
          container inet6 {
            uses apply-group;
            uses apply-macro;
            leaf identity-ipv6 {
              type ipv6addr;
            }
          }
          container hostname {
            uses apply-group;
            uses apply-macro;
            leaf identity-hostname {
              type string;
            }
          }
          container user-at-hostname {
            uses apply-group;
            uses apply-macro;
            leaf identity-user {
              type string;
            }
          }
          leaf distinguished-name {
            type empty;
          }
          container key-id {
            uses apply-group;
            uses apply-macro;
            leaf string-key-id {
              type string;
            }
          }
        }
      }
      container remote-identity {
        choice choice-3 {
          container inet {
            uses apply-group;
            uses apply-macro;
            leaf identity-ipv4 {
              type ipv4addr;
            }
          }
          container inet6 {
            uses apply-group;
            uses apply-macro;
            leaf identity-ipv6 {
              type ipv6addr;
            }
          }
          container hostname {
            uses apply-group;
            uses apply-macro;
            leaf identity-hostname {
              type string;
            }
          }
          container user-at-hostname {
            uses apply-group;
            uses apply-macro;
            leaf identity-user {
              type string;
            }
          }
          container distinguished-name {
            presence "enable distinguished-name";
            uses apply-group;
            uses apply-macro;
            leaf container {
              type string;
            }
            leaf wildcard {
              type string;
            }
          }
          container key-id {
            uses apply-group;
            uses apply-macro;
            leaf string-key-id {
              type string;
            }
          }
        }
      }
      leaf external-interface {
        type interface-unit;
      }
      leaf local-address {
        type ipaddr;
      }
      container xauth {
        presence "";
        leaf access-profile {
          type string;
        }
      }
      leaf general-ikeid {
        type empty;
      }
      container advpn {
        presence "enable advpn";
        uses advpn-suggester-partner;
      }
      leaf version {
        type string;
      }
      container fragmentation {
        uses apply-group;
        uses apply-macro;
        leaf disable {
          type empty;
        }
        leaf size {
          type uint32;
        }
      }
      leaf tcp-encap-profile {
        type string;
      }
    }
  }

  grouping advpn-suggester-partner {
    uses apply-group;
    uses apply-macro;
    container suggester {
      presence "enable suggester";
      uses apply-group;
      uses apply-macro;
      leaf disable {
        type empty;
      }
    }
    container partner {
      presence "enable partner";
      uses apply-group;
      uses apply-macro;
      leaf connection-limit {
        type uint32;
      }
      leaf idle-time {
        units "seconds";
        type uint32;
      }
      leaf idle-threshold {
        type uint32;
      }
      leaf disable {
        type empty;
      }
    }
  }

  grouping ike-proposal {
    leaf name {
      type key-attribute-string-type;
    }
    uses apply-group;
    uses apply-macro;
    leaf description {
      type string;
    }
    leaf authentication-method {
      type string;
    }
    leaf dh-group {
      type string;
    }
    leaf authentication-algorithm {
      type string;
    }
    leaf encryption-algorithm {
      type string;
    }
    leaf lifetime-seconds {
      type uint32;
    }
  }

  grouping security-ipsec-vpn {
    uses apply-group;
    uses apply-macro;
    container internal {
      presence "enable internal";
      uses apply-group;
      uses apply-macro;
      container security-association {
        presence "enable security-association";
        uses ipsec-internal-sa;
      }
    }
    container traceoptions {
      uses ipsec-traceoptions;
    }
    container vpn-monitor-options {
      presence "enable vpn-monitor-options";
      uses ipsec-vpn-monitor;
    }
    list proposal {
      key "name";
      ordered-by user;
      uses ipsec-proposal;
    }
    list policy {
      key "name";
      ordered-by user;
      uses ipsec-policy;
    }
    list vpn {
      key "name";
      ordered-by user;
      uses ipsec-vpn-template;
    }
    list security-association {
      key "name";
      ordered-by user;
      uses ipsec-sa;
    }
    container trusted-channel {
      presence "enable trusted-channel";
      uses apply-group;
      uses apply-macro;
      container security-association {
        presence "enable security-association";
        uses ipsec-trusted-channel-sa;
      }
      leaf-list port-exclusion-list {
        ordered-by user;
        type uint32;
      }
    }
  }

  grouping ipsec-policy {
    leaf name {
      type key-attribute-string-type;
    }
    uses apply-group;
    uses apply-macro;
    leaf description {
      type string;
    }
    container perfect-forward-secrecy {
      uses apply-group;
      uses apply-macro;
      leaf keys {
        type string;
      }
    }
    leaf-list proposals {
      type string;
      ordered-by user;
    }
    leaf proposal-set {
      type string;
    }
  }

  grouping ipsec-proposal {
    leaf name {
      type key-attribute-string-type;
    }
    uses apply-group;
    uses apply-macro;
    leaf description {
      type string;
    }
    leaf protocol {
      type string;
    }
    leaf authentication-algorithm {
      type string;
    }
    leaf encryption-algorithm {
      type string;
    }
    leaf lifetime-seconds {
      type uint32;
    }
    leaf lifetime-kilobytes {
      type uint32;
    }
  }

  grouping ipsec-traceoptions {
    uses apply-group;
    uses apply-macro;
    list flag {
      key "name";
      ordered-by user;
      leaf name {
        type string;
      }
    }
  }

  grouping ipsec-vpn-monitor {
    uses apply-group;
    uses apply-macro;
    leaf interval {
      type uint32;
    }
    leaf threshold {
      type uint32;
    }
  }

  grouping ipsec-vpn-template {
    leaf name {
      type key-attribute-string-type;
    }
    uses apply-group;
    uses apply-macro;
    leaf bind-interface {
      type interface-name;
    }
    leaf df-bit {
      type string;
    }
    container multi-sa {
      presence "enable multi-sa";
      uses apply-group;
      uses apply-macro;
      list forwarding-class {
        key "name";
        ordered-by user;
        leaf name {
          type key-attribute-string-type;
        }
        uses apply-group;
        uses apply-macro;
      }
    }
    leaf copy-outer-dscp {
      type empty;
    }
    container vpn-monitor {
      presence "enable vpn-monitor";
      uses ipsec-template-monitor;
    }
    choice choice-9 {
      container manual {
        presence "";
        uses apply-group;
        uses apply-macro;
        leaf gateway {
          type hostname;
        }
        leaf external-interface {
          type interface-unit;
        }
        leaf protocol {
          type string;
        }
        leaf spi {
          type uint32;
        }
        container authentication {
          presence "";
          uses apply-group;
          uses apply-macro;
          leaf algorithm {
            type string;
          }
          container key {
            choice choice-3 {
              leaf ascii-text {
                type unreadable;
              }
              leaf hexadecimal {
                type unreadable;
              }
            }
          }
        }
        container encryption {
          presence "";
          uses apply-group;
          uses apply-macro;
          leaf algorithm {
            type string;
          }
          container key {
            choice choice-3 {
              leaf ascii-text {
                type unreadable;
              }
              leaf hexadecimal {
                type unreadable;
              }
            }
          }
        }
      }
      container ike {
        presence "";
        uses apply-group;
        uses apply-macro;
        leaf gateway {
          type string;
        }
        leaf idle-time {
          type uint32;
        }
        leaf no-anti-replay {
          type empty;
        }
        container proxy-identity {
          presence "enable proxy-identity";
          uses ipsec-template-proxy-id;
        }
        leaf ipsec-policy {
          type string;
        }
        leaf install-interval {
          type uint32;
        }
      }
    }
    list traffic-selector {
      key "name";
      ordered-by user;
      leaf name {
        type key-attribute-string-type;
      }
      uses apply-group;
      uses apply-macro;
      leaf local-ip {
        mandatory true;
        type ipprefix-mandatory;
      }
      leaf remote-ip {
        mandatory true;
        type ipprefix-mandatory;
      }
    }
    leaf establish-tunnels {
      type string;
    }
  }

  grouping ipsec-template-monitor {
    uses apply-group;
    uses apply-macro;
    leaf optimized {
      type empty;
    }
    leaf source-interface {
      type interface-unit;
    }
    leaf destination-ip {
      type ipv4addr;
    }
    container verify-path {
      presence "enable verify-path";
      uses apply-group;
      uses apply-macro;
      leaf destination-ip {
        type ipaddr;
      }
      leaf packet-size {
        type uint32;
      }
    }
  }

  grouping ipsec-template-proxy-id {
    uses apply-group;
    uses apply-macro;
    leaf local {
      type ipv4prefix-mandatory;
    }
    leaf remote {
      type ipv4prefix-mandatory;
    }
    leaf service {
      type string;
    }
  }

  grouping security-ipsec {
    uses apply-group;
    uses apply-macro;
    container apply-advanced {
      uses apply-group;
      uses apply-macro;
    }
    list proposal {
      key "name";
      ordered-by user;
      uses ipsec-proposal;
    }
    list policy {
      key "name";
      ordered-by user;
      uses ipsec-policy;
    }
    list security-association {
      key "name";
      ordered-by user;
      uses ipsec-sa;
    }
    container internal {
      presence "enable internal";
      uses apply-group;
      uses apply-macro;
      container apply-advanced {
        uses apply-group;
        uses apply-macro;
      }
      container security-association {
        presence "enable security-association";
        uses ipsec-internal-sa;
      }
    }
    container trusted-channel {
      presence "enable trusted-channel";
      uses apply-group;
      uses apply-macro;
      container apply-advanced {
        uses apply-group;
        uses apply-macro;
      }
      container security-association {
        presence "enable security-association";
        uses ipsec-trusted-channel-sa;
      }
      leaf-list port-exclusion-list {
        ordered-by user;
        type uint32;
      }
    }
  }

  grouping ipsec-internal-sa {
    uses apply-group;
    uses apply-macro;
    container apply-advanced {
      uses apply-group;
      uses apply-macro;
    }
    leaf description {
      type string;
    }
    container manual {
      uses apply-group;
      uses apply-macro;
      container apply-advanced {
        uses apply-group;
        uses apply-macro;
      }
      container encryption {
        presence "";
        uses apply-group;
        uses apply-macro;
        leaf algorithm {
          type string;
        }
        leaf ike-ha-link-encryption {
          type string;
        }
        container key {
          choice choice-3 {
            leaf ascii-text {
              type unreadable;
            }
            leaf hexadecimal {
              type unreadable;
            }
          }
        }
      }
      list direction {
        key "name";
        ordered-by user;
        leaf name {
          type string;
        }
        uses apply-group;
        uses apply-macro;
        container apply-advanced {
          uses apply-group;
          uses apply-macro;
        }
        leaf protocol {
          mandatory true;
          type string;
        }
        leaf spi {
          mandatory true;
          type uint32;
        }
        leaf auxiliary-spi {
          type uint32;
        }
        container authentication {
          presence "";
          uses apply-group;
          uses apply-macro;
          container apply-advanced {
            uses apply-group;
            uses apply-macro;
          }
          leaf algorithm {
            mandatory true;
            type string;
          }
          container key {
            choice choice-ascii-text {
              leaf ascii-text {
                type unreadable;
              }
              leaf hexadecimal {
                type unreadable;
              }
            }
          }
        }
        container encryption {
          presence "";
          uses apply-group;
          uses apply-macro;
          container apply-advanced {
            uses apply-group;
            uses apply-macro;
          }
          leaf algorithm {
            mandatory true;
            type string;
          }
          container key {
            choice choice-ascii-text {
              leaf ascii-text {
                type unreadable;
              }
              leaf hexadecimal {
                type unreadable;
              }
            }
          }
        }
      }
    }
  }

  grouping ipsec-sa {
    leaf name {
      type key-attribute-string-type;
    }
    uses apply-group;
    uses apply-macro;
    container apply-advanced {
      uses apply-group;
      uses apply-macro;
    }
    leaf description {
      type string;
    }
    leaf mode {
      type string;
    }
    choice choice-manual {
      container manual {
        uses apply-group;
        uses apply-macro;
        container apply-advanced {
          uses apply-group;
          uses apply-macro;
        }
        list direction {
          key "name";
          ordered-by user;
          leaf name {
            type string;
          }
          uses apply-group;
          uses apply-macro;
          container apply-advanced {
            uses apply-group;
            uses apply-macro;
          }
          leaf protocol {
            mandatory true;
            type string;
          }
          leaf spi {
            mandatory true;
            type uint32;
          }
          leaf auxiliary-spi {
            type uint32;
          }
          container authentication {
            presence "";
            uses apply-group;
            uses apply-macro;
            container apply-advanced {
              uses apply-group;
              uses apply-macro;
            }
            leaf algorithm {
              mandatory true;
              type string;
            }
            container key {
              choice choice-ascii-text {
                leaf ascii-text {
                  type unreadable;
                }
                leaf hexadecimal {
                  type unreadable;
                }
              }
            }
          }
          container encryption {
            presence "";
            uses apply-group;
            uses apply-macro;
            container apply-advanced {
              uses apply-group;
              uses apply-macro;
            }
            leaf algorithm {
              mandatory true;
              type string;
            }
            container key {
              choice choice-ascii-text {
                leaf ascii-text {
                  type unreadable;
                }
                leaf hexadecimal {
                  type unreadable;
                }
              }
            }
          }
        }
      }
      container dynamic {
        uses apply-group;
        uses apply-macro;
        container apply-advanced {
          uses apply-group;
          uses apply-macro;
        }
        leaf replay-window-size {
          type string;
        }
        leaf ipsec-policy {
          type string;
        }
      }
    }
  }

  grouping ipsec-trusted-channel-sa {
    uses apply-group;
    uses apply-macro;
    container apply-advanced {
      uses apply-group;
      uses apply-macro;
    }
    leaf description {
      type string;
    }
    container manual {
      uses apply-group;
      uses apply-macro;
      container apply-advanced {
        uses apply-group;
        uses apply-macro;
      }
      list direction {
        key "name";
        ordered-by user;
        leaf name {
          type string;
        }
        uses apply-group;
        uses apply-macro;
        container apply-advanced {
          uses apply-group;
          uses apply-macro;
        }
        leaf protocol {
          mandatory true;
          type string;
        }
        leaf spi {
          mandatory true;
          type uint32;
        }
        leaf auxiliary-spi {
          type uint32;
        }
        container authentication {
          presence "";
          uses apply-group;
          uses apply-macro;
          container apply-advanced {
            uses apply-group;
            uses apply-macro;
          }
          leaf algorithm {
            mandatory true;
            type string;
          }
          container key {
            choice choice-ascii-text {
              leaf ascii-text {
                type unreadable;
              }
              leaf hexadecimal {
                type unreadable;
              }
            }
          }
        }
        container encryption {
          presence "";
          uses apply-group;
          uses apply-macro;
          container apply-advanced {
            uses apply-group;
            uses apply-macro;
          }
          leaf algorithm {
            mandatory true;
            type string;
          }
          container key {
            choice choice-ascii-text {
              leaf ascii-text {
                type unreadable;
              }
              leaf hexadecimal {
                type unreadable;
              }
            }
          }
        }
      }
    }
  }

  grouping security-macsec {
    uses apply-group;
    uses apply-macro;
    container apply-advanced {
      uses apply-group;
      uses apply-macro;
    }
    container traceoptions {
      presence "enable traceoptions";
      uses macsec-trace-options;
    }
    list connectivity-association {
      key "name";
      ordered-by user;
      leaf name {
        type key-attribute-string-type;
      }
      uses apply-group;
      uses apply-macro;
      container apply-advanced {
        uses apply-group;
        uses apply-macro;
      }
      leaf cipher-suite {
        type string;
      }
      leaf security-mode {
        mandatory true;
        type string;
      }
      leaf sak-hash-128 {
        type empty;
      }
      list secure-channel {
        key "name";
        ordered-by user;
        leaf name {
          type string;
        }
        uses apply-group;
        uses apply-macro;
        container apply-advanced {
          uses apply-group;
          uses apply-macro;
        }
        container id {
          presence "";
          uses apply-group;
          uses apply-macro;
          container apply-advanced {
            uses apply-group;
            uses apply-macro;
          }
          leaf mac-address {
            mandatory true;
            type mac-addr;
          }
          leaf port-id {
            mandatory true;
            type string;
          }
        }
        leaf direction {
          type string;
        }
        leaf encryption {
          type empty;
        }
        leaf offset {
          type string;
        }
        leaf include-sci {
          type empty;
        }
        list security-association {
          key "name";
          ordered-by user;
          leaf name {
            type string;
          }
          uses apply-group;
          uses apply-macro;
          container apply-advanced {
            uses apply-group;
            uses apply-macro;
          }
          leaf key {
            type unreadable;
          }
        }
      }
      container mka {
        presence "enable mka";
        uses apply-group;
        uses apply-macro;
        container apply-advanced {
          uses apply-group;
          uses apply-macro;
        }
        leaf transmit-interval {
          units "milliseconds";
          type string;
        }
        leaf sak-rekey-interval {
          units "seconds";
          type string;
        }
        leaf bounded-delay {
          type empty;
        }
        leaf key-server-priority {
          type string;
        }
        leaf must-secure {
          type empty;
        }
        leaf should-secure {
          type empty;
        }
        leaf eapol-address {
          type string;
        }
      }
      container replay-protect {
        presence "";
        uses apply-group;
        uses apply-macro;
        container apply-advanced {
          uses apply-group;
          uses apply-macro;
        }
        leaf replay-window-size {
          mandatory true;
          units "packets";
          type string;
        }
      }
      leaf no-encryption {
        type empty;
      }
      leaf disable-preceding-key {
        type empty;
      }
      leaf offset {
        type string;
      }
      leaf include-sci {
        type empty;
      }
      container pre-shared-key {
        presence "";
        uses apply-group;
        uses apply-macro;
        container apply-advanced {
          uses apply-group;
          uses apply-macro;
        }
        leaf ckn {
          mandatory true;
          type string;
        }
        leaf cak {
          mandatory true;
          type unreadable;
        }
      }
      container fallback-key {
        presence "enable fallback-key";
        uses apply-advanced;
        leaf ckn {
          type string;
        }
        leaf cak {
          type unreadable;
        }
      }
      leaf pre-shared-key-chain {
        type string;
      }
      list exclude-protocol {
        key "name";
        ordered-by user;
        leaf name {
          type string;
        }
      }
    }
    list interfaces {
      key "name";
      leaf name {
        type string;
      }
      uses apply-group;
      uses apply-macro;
      container apply-advanced {
        uses apply-group;
        uses apply-macro;
      }
      list unit {
        key "name";
        leaf name {
          type string;
        }
        uses apply-advanced;
        leaf connectivity-association {
          type string;
        }
        container traceoptions {
          presence "enable traceoptions";
          uses mka-trace-options;
        }
      }
      leaf connectivity-association {
        type string;
      }
      leaf pre-shared-key-chain {
        type string;
      }
      container replay-protect {
        uses apply-advanced;
        leaf replay-window-size {
          units "packets";
          type string;
        }
      }
      container traceoptions {
        presence "enable traceoptions";
        uses mka-trace-options;
      }
    }
  }

  grouping macsec-trace-options {
    uses apply-group;
    uses apply-macro;
    container apply-advanced {
      uses apply-group;
      uses apply-macro;
    }
    container file {
      presence "";
      uses trace-file-type;
    }
    list flag {
      key "name";
      ordered-by user;
      leaf name {
        type string;
      }
    }
  }

  grouping mka-trace-options {
    uses apply-group;
    uses apply-macro;
    container apply-advanced {
      uses apply-group;
      uses apply-macro;
    }
    container file {
      presence "";
      uses trace-file-type;
    }
    list flag {
      key "name";
      ordered-by user;
      leaf name {
        type string;
      }
    }
  }

  grouping security-model-access {
    leaf name {
      type string;
    }
    uses apply-group;
    uses apply-macro;
    list security-level {
      key "name";
      ordered-by user;
      leaf name {
        type string;
      }
      uses apply-group;
      uses apply-macro;
      leaf context-match {
        type string;
      }
      leaf read-view {
        type string;
      }
      leaf write-view {
        type string;
      }
      leaf notify-view {
        type string;
      }
    }
  }

  grouping security-pki {
    uses apply-group;
    uses apply-macro;
    list ca-profile {
      key "name";
      ordered-by user;
      leaf name {
        type string;
      }
      uses apply-group;
      uses apply-macro;
      leaf ca-identity {
        type string;
      }
      leaf source-address {
        type ipaddr;
      }
      leaf proxy-profile {
        type string;
      }
      leaf routing-instance {
        type string;
      }
      container enrollment {
        uses apply-group;
        uses apply-macro;
        leaf url {
          type string;
        }
        leaf retry {
          type uint32;
        }
        leaf retry-interval {
          type uint32;
        }
      }
      container revocation-check {
        uses apply-group;
        uses apply-macro;
        leaf disable {
          type empty;
        }
        container crl {
          uses apply-group;
          uses apply-macro;
          container disable {
            leaf on-download-failure {
              type empty;
            }
          }
          list url {
            key "name";
            ordered-by user;
            leaf name {
              type key-attribute-string-type;
            }
            uses apply-group;
            uses apply-macro;
            leaf password {
              type unreadable;
            }
          }
          leaf refresh-interval {
            type uint32;
          }
        }
      }
      container administrator {
        uses apply-group;
        uses apply-macro;
        leaf email-address {
          type string;
        }
      }
    }
    list trusted-ca-group {
      key "name";
      ordered-by user;
      leaf name {
        type key-attribute-string-type;
      }
      uses apply-group;
      uses apply-macro;
      leaf-list ca-profiles {
        ordered-by user;
        type string;
      }
    }
    container auto-re-enrollment {
      uses apply-group;
      uses apply-macro;
      list certificate-id {
        key "name";
        ordered-by user;
        leaf name {
          type string;
        }
        uses apply-group;
        uses apply-macro;
        leaf ca-profile-name {
          type string;
        }
        leaf challenge-password {
          type unreadable;
        }
        leaf re-enroll-trigger-time-percentage {
          type uint32;
        }
        leaf re-generate-keypair {
          type empty;
        }
      }
    }
    container traceoptions {
      uses apply-group;
      uses apply-macro;
      leaf no-remote-trace {
        type empty;
      }
      container file {
        leaf filename {
          type string;
        }
        leaf size {
          type string;
        }
        leaf files {
          type uint32;
        }
        leaf world-readable {
          type empty;
        }
        leaf no-world-readable {
          type empty;
        }
        leaf match {
          type regular-expression;
        }
      }
      list flag {
        key "name";
        ordered-by user;
        leaf name {
          type string;
        }
      }
    }
    container undocumented {
      list ca-profile-group {
        key "name";
        leaf name {
          type string;
        }
        leaf cert-base-count {
          type uint8;
        }
      }
    }
  }

  grouping security-traceoptions {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf rate-limit {
      type uint32;
    }
    container filter {
      uses apply-group;
      uses apply-macro;
      leaf fpc {
        type uint32;
      }
      leaf pic {
        type uint32;
      }
    }
    list flag {
      key "name";
      ordered-by user;
      leaf name {
        type string;
      }
    }
    leaf level {
      type string;
    }
    container undocumented {
      leaf level {
        type uint8;
      }
    }
  }

  grouping security-zone-type {
    leaf name {
      type key-attribute-string-type;
    }
    uses apply-group;
    uses apply-macro;
    leaf description {
      type string;
    }
    leaf tcp-rst {
      type empty;
    }
    container address-book {
      uses address-book-type;
    }
    leaf screen {
      type string;
    }
    container host-inbound-traffic {
      uses zone-host-inbound-traffic-t;
    }
    list interfaces {
      key "name";
      ordered-by user;
      uses zone-interface-list-type;
    }
    leaf application-tracking {
      type empty;
    }
    leaf source-identity-log {
      type empty;
    }
    container advance-policy-based-routing-profile {
      uses apply-group;
      uses apply-macro;
      leaf profile {
        type string;
      }
    }
    leaf enable-reverse-reroute {
      type empty;
    }
  }

  grouping address-book-type {
    uses apply-group;
    uses apply-macro;
    list address {
      key "name";
      ordered-by user;
      uses address-type;
    }
    list address-set {
      key "name";
      ordered-by user;
      uses address-set-type;
    }
  }

  grouping named-address-book-type {
    leaf name {
      type string;
    }
    uses apply-group;
    uses apply-macro;
    leaf description {
      type string;
    }
    list address {
      key "name";
      ordered-by user;
      uses address-type;
    }
    list address-set {
      key "name";
      ordered-by user;
      uses address-set-type;
    }
    container attach {
      uses apply-group;
      uses apply-macro;
      list zone {
        key "name";
        ordered-by user;
        leaf name {
          type key-attribute-string-type;
        }
        uses apply-group;
        uses apply-macro;
      }
    }
  }

  grouping address-set-type {
    leaf name {
      type key-attribute-string-type;
    }
    uses apply-group;
    uses apply-macro;
    leaf description {
      type string;
    }
    list address {
      key "name";
      ordered-by user;
      leaf name {
        type key-attribute-string-type;
      }
      uses apply-group;
      uses apply-macro;
    }
    list address-set {
      key "name";
      ordered-by user;
      leaf name {
        type key-attribute-string-type;
      }
      uses apply-group;
      uses apply-macro;
    }
  }

  grouping address-type {
    leaf name {
      type key-attribute-string-type;
    }
    uses apply-group;
    uses apply-macro;
    leaf description {
      type string;
    }
    choice choice-ip-prefix {
      leaf ip-prefix {
        type ipprefix;
      }
      list dns-name {
        key "name";
        ordered-by user;
        uses dns-name-type;
      }
      list wildcard-address {
        key "name";
        ordered-by user;
        uses wildcard-address-type;
      }
      list range-address {
        key "name";
        ordered-by user;
        uses range-address-type;
      }
      list address-range {
        key "name";
        ordered-by user;
        uses usf-range-address-type;
      }
    }
  }

  grouping dns-name-type {
    leaf name {
      type key-attribute-string-type;
    }
    uses apply-group;
    uses apply-macro;
    leaf ipv4-only {
      type empty;
    }
    leaf ipv6-only {
      type empty;
    }
  }

  grouping server-group-type {
    uses apply-group;
    uses apply-macro;
    list server-group {
      key "name";
      ordered-by user;
      leaf name {
        type key-attribute-string-type;
      }
      uses apply-group;
      uses apply-macro;
      list address {
        key "name";
        ordered-by user;
        leaf name {
          type ipaddr;
        }
        uses apply-group;
        uses apply-macro;
      }
    }
  }

  grouping server-match-action-choice {
    uses apply-group;
    uses apply-macro;
    choice choice-forward-only {
      leaf forward-only {
        type empty;
      }
      leaf create-relay-entry {
        type empty;
      }
    }
  }

  grouping server-match-v6-ascii-hex {
    uses apply-group;
    uses apply-macro;
    list ascii {
      key "name";
      leaf name {
        type key-attribute-string-type;
      }
      uses apply-group;
      uses apply-macro;
      choice choice-forward-only {
        leaf forward-only {
          type empty;
        }
        leaf create-relay-entry {
          type empty;
        }
      }
    }
    list hexadecimal {
      key "name";
      leaf name {
        type key-attribute-string-type;
      }
      uses apply-group;
      uses apply-macro;
      choice choice-forward-only {
        leaf forward-only {
          type empty;
        }
        leaf create-relay-entry {
          type empty;
        }
      }
    }
  }

  grouping server-v6-option-ascii-hex {
    uses apply-group;
    uses apply-macro;
    list ascii {
      key "name";
      leaf name {
        type key-attribute-string-type;
      }
      uses apply-group;
      uses apply-macro;
    }
    list hexadecimal {
      key "name";
      leaf name {
        type key-attribute-string-type;
      }
      uses apply-group;
      uses apply-macro;
    }
  }

  grouping service-device-pool-object {
    leaf name {
      type key-attribute-string-type;
    }
    uses apply-group;
    uses apply-macro;
    list interface {
      key "name";
      ordered-by user;
      leaf name {
        type interface-unit;
      }
      uses apply-group;
      uses apply-macro;
    }
  }

  grouping service-interface-pool-object {
    leaf name {
      type key-attribute-string-type;
    }
    uses apply-group;
    uses apply-macro;
    list interface {
      key "name";
      ordered-by user;
      leaf name {
        type interface-unit;
      }
      uses apply-group;
      uses apply-macro;
    }
  }

  grouping service-point-type {
    leaf name {
      type string;
    }
    uses apply-group;
    uses apply-macro;
    leaf service-point-type {
      type string;
    }
    container transport-details {
      presence "enable transport-details";
      leaf port-number {
        type uint32;
      }
      leaf ip-address {
        type ipaddr;
      }
      leaf tcp {
        type empty;
      }
      leaf udp {
        type empty;
      }
    }
    leaf service-interface {
      type interface-unit;
    }
    container service-policies {
      presence "enable service-policies";
      uses service-policies-type;
    }
    leaf default-media-realm {
      type string;
    }
  }

  grouping service-policies-type {
    uses apply-group;
    uses apply-macro;
    leaf-list new-transaction-input-policies {
      type string;
      ordered-by user;
    }
    leaf-list new-transaction-output-policies {
      type string;
      ordered-by user;
    }
    leaf-list new-registration-input-policies {
      type string;
      ordered-by user;
    }
    leaf-list new-call-usage-input-policies {
      type string;
      ordered-by user;
    }
    leaf-list new-call-usage-output-policies {
      type string;
      ordered-by user;
    }
  }

  grouping service-set-ipsec-vpn-options-object {
    uses apply-group;
    uses apply-macro;
    leaf-list trusted-ca {
      type string;
      ordered-by user;
    }
    container local-gateway {
      presence "";
      leaf address {
        type ipaddr;
      }
      leaf routing-instance {
        type string;
      }
      leaf interface {
        type interface-unit;
      }
      leaf gw-interface {
        type interface-unit;
      }
    }
    leaf ike-access-profile {
      type string;
    }
    leaf passive-mode-tunneling {
      type empty;
    }
    leaf clear-dont-fragment-bit {
      type empty;
    }
    leaf copy-dont-fragment-bit {
      type empty;
    }
    leaf set-dont-fragment-bit {
      type empty;
    }
    leaf tunnel-mtu {
      type uint32;
    }
    leaf no-anti-replay {
      type empty;
    }
    leaf anti-replay-window-size {
      type uint32;
    }
    container udp-encapsulate {
      presence "enable udp-encapsulate";
      leaf dest-port {
        type uint32;
      }
    }
    leaf no-nat-traversal {
      type empty;
    }
    leaf nat-keepalive {
      type uint32;
    }
    leaf no-certificate-chain-in-ike {
      type empty;
    }
  }

  grouping service-set-syslog-object {
    uses apply-group;
    uses apply-macro;
    list host {
      key "name";
      ordered-by user;
      leaf name {
        type string;
      }
      uses apply-group;
      uses apply-macro;
      list contents {
        key "name";
        leaf name {
          type string;
        }
        choice choice-any {
          leaf any {
            type empty;
          }
          leaf emergency {
            type empty;
          }
          leaf alert {
            type empty;
          }
          leaf critical {
            type empty;
          }
          leaf error {
            type empty;
          }
          leaf warning {
            type empty;
          }
          leaf notice {
            type empty;
          }
          leaf info {
            type empty;
          }
          leaf none {
            type empty;
          }
        }
      }
      leaf facility-override {
        type string;
      }
      leaf log-prefix {
        type string;
      }
      leaf port {
        type uint16;
      }
      container class {
        uses apply-group;
        uses apply-macro;
        container session-logs {
          presence "enable session-logs";
          uses apply-group;
          uses apply-macro;
          container open {
            presence "enable open";
            uses apply-group;
            uses apply-macro;
          }
          container close {
            presence "enable close";
            uses apply-group;
            uses apply-macro;
          }
        }
        container packet-logs {
          presence "enable packet-logs";
          uses apply-group;
          uses apply-macro;
        }
        container stateful-firewall-logs {
          presence "enable stateful-firewall-logs";
          uses apply-group;
          uses apply-macro;
        }
        container alg-logs {
          presence "enable alg-logs";
          uses apply-group;
          uses apply-macro;
        }
        container nat-logs {
          presence "enable nat-logs";
          uses apply-group;
          uses apply-macro;
        }
        container ids-logs {
          presence "enable ids-logs";
          uses apply-group;
          uses apply-macro;
        }
        container pcp-logs {
          presence "enable pcp-logs";
          container map {
            presence "enable map";
            uses apply-group;
            uses apply-macro;
          }
          container debug {
            presence "enable debug";
            uses apply-group;
            uses apply-macro;
          }
        }
      }
      leaf source-address {
        type ipv4addr;
      }
    }
    leaf message-rate-limit {
      units "messages per second";
      type uint32;
    }
    leaf mode {
      type string;
    }
    choice source {
      case case_1 {
        leaf source-address {
          type ipaddr;
        }
      }
      case case_2 {
        leaf source-interface {
          type string;
        }
      }
    }
    container transport {
      presence "enable transport";
      uses apply-advanced;
      leaf tcp-connections {
        type string;
      }
      leaf protocol {
        type string;
      }
      leaf tls-profile {
        type string;
      }
    }
    leaf local-log-tag {
      type string;
    }
    leaf utc-timestamp {
      type empty;
    }
    leaf format {
      type string;
    }
    list local-category {
      key "name";
      ordered-by user;
      leaf name {
        type string;
      }
      uses apply-advanced;
    }
    list stream {
      key "name";
      ordered-by user;
      leaf name {
        type string;
      }
      uses apply-advanced;
      leaf severity {
        type string;
      }
      leaf format {
        type string;
      }
      list category {
        key "name";
        ordered-by user;
        leaf name {
          type string;
        }
        uses apply-advanced;
      }
      container host {
        uses host-object;
      }
    }
  }

  grouping services-ike {
    uses apply-group;
    uses apply-macro;
    list proposal {
      key "name";
      ordered-by user;
      uses ike-proposal;
    }
    list policy {
      key "name";
      ordered-by user;
      uses svc-ike-policy;
    }
  }

  grouping services-ipsec {
    uses apply-group;
    uses apply-macro;
    list proposal {
      key "name";
      ordered-by user;
      uses ipsec-proposal;
    }
    list policy {
      key "name";
      ordered-by user;
      uses ipsec-policy;
    }
  }

  grouping sfw-addr-object {
    leaf name {
      type string;
    }
    uses apply-group;
    uses apply-macro;
    leaf except {
      type empty;
    }
  }

  grouping session-timeout-type {
    uses apply-group;
    uses apply-macro;
    leaf tcp {
      units "seconds";
      type uint32;
    }
    leaf udp {
      units "seconds";
      type uint32;
    }
    leaf ospf {
      units "seconds";
      type uint32;
    }
    leaf icmp {
      units "seconds";
      type uint32;
    }
    leaf icmp6 {
      units "seconds";
      type uint32;
    }
    leaf others {
      units "seconds";
      type uint32;
    }
  }

  grouping sfw-match-object {
    uses apply-group;
    uses apply-macro;
    list source-address {
      key "name";
      ordered-by user;
      uses sfw-addr-object;
    }
    list destination-address {
      key "name";
      ordered-by user;
      uses sfw-addr-object;
    }
    container destination-port {
      presence "enable destination-port";
      uses apply-group;
      uses apply-macro;
      container range {
        presence "";
        leaf low {
          mandatory true;
          type uint16;
        }
        leaf high {
          mandatory true;
          type uint16;
        }
      }
    }
    list source-address-range {
      key "low high";
      ordered-by user;
      leaf low {
        type ipaddr;
      }
      leaf high {
        type ipaddr;
      }
      leaf except {
        type empty;
      }
    }
    list source-prefix-list {
      key "name";
      ordered-by user;
      leaf name {
        type string;
      }
      leaf except {
        type empty;
      }
    }
    list destination-address-range {
      key "low high";
      ordered-by user;
      leaf low {
        type ipaddr;
      }
      leaf high {
        type ipaddr;
      }
      leaf except {
        type empty;
      }
    }
    list destination-prefix-list {
      key "name";
      ordered-by user;
      leaf name {
        type string;
      }
      leaf except {
        type empty;
      }
    }
    leaf-list applications {
      type string;
      ordered-by user;
    }
    list application-sets {
      key "name";
      ordered-by user;
      leaf name {
        type key-attribute-string-type;
      }
      uses apply-group;
      uses apply-macro;
    }
  }

  grouping sfw-rule-object {
    leaf name {
      type key-attribute-string-type;
    }
    uses apply-group;
    uses apply-macro;
    leaf match-direction {
      type string;
    }
    list term {
      key "name";
      ordered-by user;
      leaf name {
        type key-attribute-string-type;
      }
      uses apply-group;
      uses apply-macro;
      container from {
        uses sfw-match-object;
      }
      container then {
        uses apply-group;
        uses apply-macro;
        choice choice-3 {
          leaf accept {
            type empty;
          }
          container discard {
            presence "enable discard";
            uses apply-group;
            uses apply-macro;
          }
          leaf reject {
            type empty;
          }
        }
        leaf-list allow-ip-options {
          ordered-by user;
          type string;
        }
        leaf syslog {
          type empty;
        }
      }
    }
  }

  grouping sgw-config-gtp {
    uses apply-group;
    uses apply-macro;
    leaf peer-history {
      type uint16;
    }
    container interface {
      presence "";
      leaf intf-name {
        type interface-name;
      }
      leaf v4-address {
        type ipv4addr;
      }
    }
    leaf echo-interval {
      units "seconds";
      type uint16;
    }
    leaf path-management {
      type string;
    }
    leaf echo-n3-requests {
      type uint16;
    }
    leaf echo-t3-response {
      units "seconds";
      type uint16;
    }
    leaf path-failure {
      type string;
    }
    leaf number-of-msgs-for-response-time {
      type uint16;
    }
    container control {
      uses apply-group;
      uses apply-macro;
      container interface {
        presence "";
        leaf intf-name {
          type interface-name;
        }
        leaf v4-address {
          type ipv4addr;
        }
      }
      leaf echo-interval {
        units "seconds";
        type uint16;
      }
      leaf path-management {
        type string;
      }
      leaf echo-n3-requests {
        type uint16;
      }
      leaf echo-t3-response {
        units "seconds";
        type uint16;
      }
      leaf path-failure {
        type string;
      }
      leaf number-of-msgs-for-response-time {
        type uint16;
      }
      leaf forwarding-class {
        type string;
      }
      leaf n3-requests {
        type uint16;
      }
      leaf t3-response {
        units "seconds";
        type uint16;
      }
      leaf dscp-code-point {
        type uint8;
      }
      leaf ttl-value {
        type uint8;
      }
      leaf ddn-delay-sync {
        type string;
      }
      leaf no-response-cache {
        type empty;
      }
      leaf response-cache-timeout {
        units "seconds";
        type uint8;
      }
      leaf no-piggyback-support {
        type empty;
      }
    }
    container data {
      uses apply-group;
      uses apply-macro;
      container interface {
        presence "";
        leaf intf-name {
          type interface-name;
        }
        leaf v4-address {
          type ipv4addr;
        }
      }
      leaf echo-interval {
        units "seconds";
        type uint16;
      }
      leaf path-management {
        type string;
      }
      leaf echo-n3-requests {
        type uint16;
      }
      leaf echo-t3-response {
        units "seconds";
        type uint16;
      }
      leaf path-failure {
        type string;
      }
      leaf num-gtpu-end-markers {
        type uint8;
      }
      leaf indirect-tunnel {
        type string;
      }
      leaf error-indication-interval {
        units "seconds";
        type uint16;
      }
    }
    container s1u {
      presence "enable s1u";
      uses apply-group;
      uses apply-macro;
      container interface {
        presence "";
        leaf intf-name {
          type interface-name;
        }
        leaf v4-address {
          type ipv4addr;
        }
      }
      leaf echo-interval {
        units "seconds";
        type uint16;
      }
      leaf path-management {
        type string;
      }
      leaf echo-n3-requests {
        type uint16;
      }
      leaf echo-t3-response {
        units "seconds";
        type uint16;
      }
      leaf path-failure {
        type string;
      }
    }
    container s11 {
      presence "enable s11";
      uses apply-group;
      uses apply-macro;
      container interface {
        presence "";
        leaf intf-name {
          type interface-name;
        }
        leaf v4-address {
          type ipv4addr;
        }
      }
      leaf echo-interval {
        units "seconds";
        type uint16;
      }
      leaf path-management {
        type string;
      }
      leaf echo-n3-requests {
        type uint16;
      }
      leaf echo-t3-response {
        units "seconds";
        type uint16;
      }
      leaf path-failure {
        type string;
      }
      leaf number-of-msgs-for-response-time {
        type uint16;
      }
      leaf forwarding-class {
        type string;
      }
      leaf n3-requests {
        type uint16;
      }
      leaf t3-response {
        units "seconds";
        type uint16;
      }
      leaf dscp-code-point {
        type uint8;
      }
      leaf ttl-value {
        type uint8;
      }
    }
    container s12 {
      presence "enable s12";
      uses apply-group;
      uses apply-macro;
      container interface {
        presence "";
        leaf intf-name {
          type interface-name;
        }
        leaf v4-address {
          type ipv4addr;
        }
      }
      leaf echo-interval {
        units "seconds";
        type uint16;
      }
      leaf path-management {
        type string;
      }
      leaf echo-n3-requests {
        type uint16;
      }
      leaf echo-t3-response {
        units "seconds";
        type uint16;
      }
      leaf path-failure {
        type string;
      }
    }
    container s4 {
      uses apply-group;
      uses apply-macro;
      container interface {
        presence "";
        leaf intf-name {
          type interface-name;
        }
        leaf v4-address {
          type ipv4addr;
        }
      }
      leaf echo-interval {
        units "seconds";
        type uint16;
      }
      leaf path-management {
        type string;
      }
      leaf echo-n3-requests {
        type uint16;
      }
      leaf echo-t3-response {
        units "seconds";
        type uint16;
      }
      leaf path-failure {
        type string;
      }
      leaf number-of-msgs-for-response-time {
        type uint16;
      }
      container control {
        uses apply-group;
        uses apply-macro;
        container interface {
          presence "";
          leaf intf-name {
            type interface-name;
          }
          leaf v4-address {
            type ipv4addr;
          }
        }
        leaf echo-interval {
          units "seconds";
          type uint16;
        }
        leaf path-management {
          type string;
        }
        leaf echo-n3-requests {
          type uint16;
        }
        leaf echo-t3-response {
          units "seconds";
          type uint16;
        }
        leaf path-failure {
          type string;
        }
        leaf number-of-msgs-for-response-time {
          type uint16;
        }
        leaf forwarding-class {
          type string;
        }
        leaf n3-requests {
          type uint16;
        }
        leaf t3-response {
          units "seconds";
          type uint16;
        }
        leaf dscp-code-point {
          type uint8;
        }
        leaf ttl-value {
          type uint8;
        }
      }
      container data {
        uses apply-group;
        uses apply-macro;
        container interface {
          presence "";
          leaf intf-name {
            type interface-name;
          }
          leaf v4-address {
            type ipv4addr;
          }
        }
        leaf echo-interval {
          units "seconds";
          type uint16;
        }
        leaf path-management {
          type string;
        }
        leaf echo-n3-requests {
          type uint16;
        }
        leaf echo-t3-response {
          units "seconds";
          type uint16;
        }
        leaf path-failure {
          type string;
        }
      }
    }
    container s5 {
      uses apply-group;
      uses apply-macro;
      container interface {
        presence "";
        leaf intf-name {
          type interface-name;
        }
        leaf v4-address {
          type ipv4addr;
        }
      }
      leaf echo-interval {
        units "seconds";
        type uint16;
      }
      leaf path-management {
        type string;
      }
      leaf echo-n3-requests {
        type uint16;
      }
      leaf echo-t3-response {
        units "seconds";
        type uint16;
      }
      leaf path-failure {
        type string;
      }
      leaf number-of-msgs-for-response-time {
        type uint16;
      }
      container control {
        uses apply-group;
        uses apply-macro;
        container interface {
          presence "";
          leaf intf-name {
            type interface-name;
          }
          leaf v4-address {
            type ipv4addr;
          }
        }
        leaf echo-interval {
          units "seconds";
          type uint16;
        }
        leaf path-management {
          type string;
        }
        leaf echo-n3-requests {
          type uint16;
        }
        leaf echo-t3-response {
          units "seconds";
          type uint16;
        }
        leaf path-failure {
          type string;
        }
        leaf number-of-msgs-for-response-time {
          type uint16;
        }
        leaf forwarding-class {
          type string;
        }
        leaf n3-requests {
          type uint16;
        }
        leaf t3-response {
          units "seconds";
          type uint16;
        }
        leaf dscp-code-point {
          type uint8;
        }
        leaf ttl-value {
          type uint8;
        }
      }
      container data {
        uses apply-group;
        uses apply-macro;
        container interface {
          presence "";
          leaf intf-name {
            type interface-name;
          }
          leaf v4-address {
            type ipv4addr;
          }
        }
        leaf echo-interval {
          units "seconds";
          type uint16;
        }
        leaf path-management {
          type string;
        }
        leaf echo-n3-requests {
          type uint16;
        }
        leaf echo-t3-response {
          units "seconds";
          type uint16;
        }
        leaf path-failure {
          type string;
        }
      }
    }
    container s8 {
      uses apply-group;
      uses apply-macro;
      container interface {
        presence "";
        leaf intf-name {
          type interface-name;
        }
        leaf v4-address {
          type ipv4addr;
        }
      }
      leaf echo-interval {
        units "seconds";
        type uint16;
      }
      leaf path-management {
        type string;
      }
      leaf echo-n3-requests {
        type uint16;
      }
      leaf echo-t3-response {
        units "seconds";
        type uint16;
      }
      leaf path-failure {
        type string;
      }
      leaf number-of-msgs-for-response-time {
        type uint16;
      }
      container control {
        uses apply-group;
        uses apply-macro;
        container interface {
          presence "";
          leaf intf-name {
            type interface-name;
          }
          leaf v4-address {
            type ipv4addr;
          }
        }
        leaf echo-interval {
          units "seconds";
          type uint16;
        }
        leaf path-management {
          type string;
        }
        leaf echo-n3-requests {
          type uint16;
        }
        leaf echo-t3-response {
          units "seconds";
          type uint16;
        }
        leaf path-failure {
          type string;
        }
        leaf number-of-msgs-for-response-time {
          type uint16;
        }
        leaf forwarding-class {
          type string;
        }
        leaf n3-requests {
          type uint16;
        }
        leaf t3-response {
          units "seconds";
          type uint16;
        }
        leaf dscp-code-point {
          type uint8;
        }
        leaf ttl-value {
          type uint8;
        }
      }
      container data {
        uses apply-group;
        uses apply-macro;
        container interface {
          presence "";
          leaf intf-name {
            type interface-name;
          }
          leaf v4-address {
            type ipv4addr;
          }
        }
        leaf echo-interval {
          units "seconds";
          type uint16;
        }
        leaf path-management {
          type string;
        }
        leaf echo-n3-requests {
          type uint16;
        }
        leaf echo-t3-response {
          units "seconds";
          type uint16;
        }
        leaf path-failure {
          type string;
        }
      }
    }
    container traceoptions {
      uses gtp-traceoptions;
    }
  }

  grouping sgw-idle-mode-buffering {
    uses apply-group;
    uses apply-macro;
    leaf disable {
      type empty;
    }
    leaf expire-timer {
      units "seconds";
      type uint32;
    }
  }

  grouping signaling-realm {
    leaf name {
      type string;
    }
    uses apply-group;
    uses apply-macro;
  }

  grouping sip-timers-type {
    uses apply-group;
    uses apply-macro;
    leaf inactive-call {
      type uint32;
    }
    leaf timer-c {
      type uint32;
    }
  }

  grouping sm-ippool-group {
    leaf name {
      type key-attribute-string-type;
    }
    uses apply-group;
    uses apply-macro;
    list pools {
      key "name";
      ordered-by user;
      uses sm-ippool-group-pools;
    }
  }

  grouping sm-ippool-group-pools {
    leaf name {
      type key-attribute-string-type;
    }
    uses apply-group;
    uses apply-macro;
  }

  grouping sm-ippool-pool {
    leaf name {
      type key-attribute-string-type;
    }
    uses apply-group;
    uses apply-macro;
    leaf service-mode {
      type string;
    }
    container family {
      presence "enable family";
      uses apply-group;
      uses apply-macro;
      choice choice-inet {
        container inet {
          presence "";
          uses apply-group;
          uses apply-macro;
          list network {
            key "name";
            ordered-by user;
            leaf name {
              type ipv4prefix-only;
            }
            uses apply-group;
            uses apply-macro;
            leaf external-assigned {
              type empty;
            }
            leaf allocation-prefix-length {
              type uint8;
            }
            list range {
              key "name";
              ordered-by user;
              leaf name {
                type key-attribute-string-type;
              }
              uses apply-group;
              uses apply-macro;
              leaf low {
                type ipv4addr;
              }
              leaf high {
                type ipv4addr;
              }
              leaf external-assigned {
                type empty;
              }
            }
          }
        }
        container inet6 {
          presence "";
          uses apply-group;
          uses apply-macro;
          list network {
            key "name";
            ordered-by user;
            leaf name {
              type ipv6prefix-only;
            }
            uses apply-group;
            uses apply-macro;
            leaf external-assigned {
              type empty;
            }
            leaf allocation-prefix-length {
              type uint8;
            }
            list range {
              key "name";
              ordered-by user;
              leaf name {
                type key-attribute-string-type;
              }
              uses apply-group;
              uses apply-macro;
              leaf low {
                type ipv6prefix-only;
              }
              leaf high {
                type ipv6prefix-only;
              }
              leaf external-assigned {
                type empty;
              }
            }
          }
        }
      }
    }
    leaf ageing-window {
      units "seconds";
      type uint16;
    }
    leaf pool-prefetch-threshold {
      units "percent";
      type uint8;
    }
    leaf pool-snmp-trap-threshold {
      units "percent";
      type uint8;
    }
    leaf default-pool {
      type empty;
    }
  }

  grouping smid-type {
    uses apply-group;
    uses apply-macro;
    container traceoptions {
      uses smid-traceoptions-type;
    }
    container maintain-subscriber {
      uses smid-maintain-subscriber-type;
    }
    leaf gres-route-flush-delay {
      type empty;
    }
    container enforce-strict-scale-limit-license {
      presence "enable enforce-strict-scale-limit-license";
      uses apply-group;
      uses apply-macro;
    }
    container overrides {
      uses apply-group;
      uses apply-macro;
      leaf no-unsolicited-ra {
        type empty;
      }
      container interfaces {
        presence "enable interfaces";
        uses apply-group;
        uses apply-macro;
        container family {
          presence "enable family";
          uses apply-group;
          uses apply-macro;
          container inet6 {
            presence "enable inet6";
            uses apply-group;
            uses apply-macro;
            leaf layer2-liveness-detection {
              type empty;
            }
          }
          container inet {
            presence "enable inet";
            uses apply-group;
            uses apply-macro;
            leaf layer2-liveness-detection {
              type empty;
            }
            leaf receive-gratuitous-arp {
              type empty;
            }
            leaf ipoe-dynamic-arp-enable {
              type empty;
            }
          }
        }
      }
      container shmlog {
        uses apply-group;
        uses apply-macro;
        leaf disable {
          type empty;
        }
        container filtering {
          uses apply-group;
          uses apply-macro;
          leaf enable {
            type empty;
          }
        }
        container file {
          presence "";
          leaf filename {
            mandatory true;
            type string;
          }
          leaf size {
            type string;
          }
          leaf files {
            type uint32;
          }
        }
        list log-name {
          key "name";
          ordered-by user;
          leaf name {
            mandatory true;
            type string;
          }
          uses apply-group;
          uses apply-macro;
          choice choice-none {
            leaf none {
              type empty;
            }
            leaf terse {
              type empty;
            }
            leaf brief {
              type empty;
            }
            leaf detail {
              type empty;
            }
            leaf extensive {
              type empty;
            }
          }
          choice choice-file-logging {
            leaf file-logging {
              type empty;
            }
            leaf no-file-logging {
              type empty;
            }
          }
        }
        list log-type {
          key "name";
          ordered-by user;
          leaf name {
            type string;
          }
          uses apply-group;
          uses apply-macro;
          choice choice-none {
            leaf none {
              type empty;
            }
            leaf terse {
              type empty;
            }
            leaf brief {
              type empty;
            }
            leaf detail {
              type empty;
            }
            leaf extensive {
              type empty;
            }
          }
          choice choice-file-logging {
            leaf file-logging {
              type empty;
            }
            leaf no-file-logging {
              type empty;
            }
          }
        }
      }
    }
    container enable {
      presence "enable enable";
      uses apply-group;
      uses apply-macro;
      container undocumented {
        leaf force {
          type empty;
        }
      }
    }
    container redundancy {
      presence "";
      uses apply-group;
      uses apply-macro;
      list interface {
        key "name";
        leaf name {
          type interface-name;
        }
        uses apply-group;
        uses apply-macro;
        leaf virtual-inet-address {
          type ipaddr;
        }
        leaf virtual-inet6-address {
          type ipaddr;
        }
        leaf local-inet-address {
          type ipaddr;
        }
        leaf shared-key {
          type string;
        }
      }
      container protocol {
        uses apply-group;
        uses apply-macro;
        leaf vrrp {
          type empty;
        }
        leaf pseudo-wire {
          type empty;
        }
      }
      leaf re-authenticate-on-failover {
        type empty;
      }
      leaf no-advertise-routes-on-backup {
        type empty;
      }
    }
  }

  grouping smid-maintain-subscriber-type {
    uses apply-group;
    uses apply-macro;
    leaf interface-delete {
      type empty;
    }
  }

  grouping smid-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    list flag {
      key "name";
      ordered-by user;
      leaf name {
        type string;
      }
    }
    container memory-profiling {
      uses apply-group;
      uses apply-macro;
      leaf enabled {
        type empty;
      }
    }
  }

  grouping softwire-option-type {
    leaf name {
      type key-attribute-string-type;
    }
    uses apply-group;
    uses apply-macro;
    leaf softwire-concentrator {
      type ipv6addr;
    }
    leaf softwire-type {
      type string;
    }
  }

  grouping software-datapath-traceoptions {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping sonet-options-type {
    uses apply-group;
    uses apply-macro;
    leaf vtmapping {
      type string;
    }
    leaf fcs {
      type string;
    }
    leaf path-trace {
      type string;
    }
    leaf loopback {
      type string;
    }
    container trigger {
      uses apply-group;
      uses apply-macro;
      container lol {
        choice choice-3 {
          leaf ignore {
            type empty;
          }
          container hold-time {
            presence "";
            leaf up {
              type uint32;
            }
            leaf down {
              type uint32;
            }
          }
        }
      }
      container pll {
        choice choice-3 {
          leaf ignore {
            type empty;
          }
          container hold-time {
            presence "";
            leaf up {
              type uint32;
            }
            leaf down {
              type uint32;
            }
          }
        }
      }
      container lof {
        choice choice-3 {
          leaf ignore {
            type empty;
          }
          container hold-time {
            presence "";
            leaf up {
              type uint32;
            }
            leaf down {
              type uint32;
            }
          }
        }
      }
      container los {
        choice choice-3 {
          leaf ignore {
            type empty;
          }
          container hold-time {
            presence "";
            leaf up {
              type uint32;
            }
            leaf down {
              type uint32;
            }
          }
        }
      }
      container ais-l {
        choice choice-3 {
          leaf ignore {
            type empty;
          }
          container hold-time {
            presence "";
            leaf up {
              type uint32;
            }
            leaf down {
              type uint32;
            }
          }
        }
      }
      container rfi-l {
        choice choice-3 {
          leaf ignore {
            type empty;
          }
          container hold-time {
            presence "";
            leaf up {
              type uint32;
            }
            leaf down {
              type uint32;
            }
          }
        }
      }
      container ber-sd {
        uses apply-group;
        uses apply-macro;
        choice choice-3 {
          leaf ignore {
            type empty;
          }
          container hold-time {
            presence "";
            leaf up {
              type uint32;
            }
            leaf down {
              type uint32;
            }
          }
        }
      }
      container ber-sf {
        uses apply-group;
        uses apply-macro;
        choice choice-3 {
          leaf ignore {
            type empty;
          }
          container hold-time {
            presence "";
            leaf up {
              type uint32;
            }
            leaf down {
              type uint32;
            }
          }
        }
      }
      container ais-p {
        choice choice-3 {
          leaf ignore {
            type empty;
          }
          container hold-time {
            presence "";
            leaf up {
              type uint32;
            }
            leaf down {
              type uint32;
            }
          }
        }
      }
      container lop-p {
        choice choice-3 {
          leaf ignore {
            type empty;
          }
          container hold-time {
            presence "";
            leaf up {
              type uint32;
            }
            leaf down {
              type uint32;
            }
          }
        }
      }
      container rfi-p {
        choice choice-3 {
          leaf ignore {
            type empty;
          }
          container hold-time {
            presence "";
            leaf up {
              type uint32;
            }
            leaf down {
              type uint32;
            }
          }
        }
      }
      container uneq-p {
        choice choice-3 {
          leaf ignore {
            type empty;
          }
          container hold-time {
            presence "";
            leaf up {
              type uint32;
            }
            leaf down {
              type uint32;
            }
          }
        }
      }
      container plm-p {
        choice choice-3 {
          leaf ignore {
            type empty;
          }
          container hold-time {
            presence "";
            leaf up {
              type uint32;
            }
            leaf down {
              type uint32;
            }
          }
        }
      }
      container locd {
        choice choice-3 {
          leaf ignore {
            type empty;
          }
          container hold-time {
            presence "";
            leaf up {
              type uint32;
            }
            leaf down {
              type uint32;
            }
          }
        }
      }
      container lcdp {
        choice choice-3 {
          leaf ignore {
            type empty;
          }
          container hold-time {
            presence "";
            leaf up {
              type uint32;
            }
            leaf down {
              type uint32;
            }
          }
        }
      }
    }
    container aps {
      uses aps-type;
    }
    choice choice-15 {
      container payload-scrambler {
        presence "enable payload-scrambler";
        choice choice-3;
      }
      leaf no-payload-scrambler {
        type empty;
      }
    }
    leaf z0-increment {
      type empty;
    }
    leaf no-z0-increment {
      type empty;
    }
    leaf loop-timing {
      type empty;
    }
    leaf no-loop-timing {
      type empty;
    }
    container bytes {
      uses apply-group;
      uses apply-macro;
      leaf e1-quiet {
        type uint32;
      }
      leaf f1 {
        type uint32;
      }
      leaf f2 {
        type uint32;
      }
      leaf s1 {
        type uint32;
      }
      leaf z3 {
        type uint32;
      }
      leaf z4 {
        type uint32;
      }
      leaf c2 {
        type uint32;
      }
    }
    leaf rfc-2615 {
      type empty;
    }
    leaf aggregate {
      type interface-device;
    }
    container mpls {
      uses mpls-ifd-options;
    }
  }

  grouping sophos-fallback-settings {
    uses apply-group;
    uses apply-macro;
    leaf default {
      type string;
    }
    leaf content-size {
      type string;
    }
    leaf engine-not-ready {
      type string;
    }
    leaf timeout {
      type string;
    }
    leaf out-of-resources {
      type string;
    }
    leaf too-many-requests {
      type string;
    }
  }

  grouping sophos-scan-options {
    uses apply-group;
    uses apply-macro;
    leaf uri-check {
      type empty;
    }
    leaf no-uri-check {
      type empty;
    }
    leaf content-size-limit {
      type string;
    }
    leaf timeout {
      units "seconds";
      type uint32;
    }
  }

  grouping source-class-name-object {
    leaf name {
      type string;
    }
    uses apply-group;
    uses apply-macro;
  }

  grouping rpm-next-hop {
    leaf name {
      type ipaddr;
    }
    uses apply-advanced;
    list rpm-probe {
      key "name";
      ordered-by user;
      leaf name {
        type string;
      }
      leaf rpm-test {
        type string;
      }
    }
  }

  grouping spring-te-template-map {
    leaf name {
      mandatory true;
      type string;
    }
    uses apply-group;
    uses apply-macro;
    choice choice-color {
      leaf-list color {
        type uint32;
      }
      leaf color-any {
        type empty;
      }
    }
  }

  grouping springte-lsp-nh-obj {
    uses apply-advanced;
    leaf nexthop {
      type string;
    }
    container lsp-source {
      uses apply-advanced;
      choice lsp-src-choice {
        case case_1 {
          leaf pcep {
            type empty;
          }
        }
        case case_2 {
          leaf static {
            type empty;
          }
        }
        case case_3 {
          leaf dtm {
            type empty;
          }
        }
        case case_4 {
          leaf bgp {
            type empty;
          }
        }
      }
    }
  }

  grouping srd-ev-action-object {
    uses apply-group;
    uses apply-macro;
    choice choice-acquire-mastership {
      leaf acquire-mastership {
        type empty;
      }
      leaf release-mastership {
        type empty;
      }
      leaf release-mastership-force {
        type empty;
      }
      leaf release-mastership-if-standby-clear {
        type empty;
      }
      leaf broadcast-warning {
        type empty;
      }
    }
    list add-static-route {
      key "name";
      ordered-by user;
      uses srd-route-add-object;
    }
    list delete-static-route {
      key "name";
      ordered-by user;
      uses srd-route-delete-object;
    }
  }

  grouping srd-route-add-object {
    leaf name {
      type ipv4prefix-mandatory;
    }
    uses apply-group;
    uses apply-macro;
    choice choice-next-hop {
      leaf next-hop {
        type string;
      }
      leaf receive {
        type empty;
      }
    }
    leaf routing-instance {
      type string;
      mandatory true;
    }
  }

  grouping srd-route-delete-object {
    leaf name {
      type ipv4prefix-mandatory;
    }
    uses apply-group;
    uses apply-macro;
    leaf routing-instance {
      type string;
      mandatory true;
    }
  }

  grouping spi-type {
    leaf name {
      type key-attribute-string-type;
    }
    uses apply-group;
    uses apply-macro;
    container entity-type {
      uses peer-entity-type;
    }
    container algorithm {
      uses peer-algorithm-type;
    }
    container key {
      uses peer-key-type;
    }
    container replay-method {
      presence "enable replay-method";
      choice choice-3 {
        container timestamp {
          presence "enable timestamp";
          uses apply-group;
          uses apply-macro;
          leaf seconds {
            type uint32;
          }
        }
        leaf none {
          type empty;
        }
      }
    }
  }

  grouping peer-algorithm-type {
    uses apply-group;
    uses apply-macro;
    choice choice-3 {
      leaf hmac-md5 {
        type empty;
      }
      leaf md5 {
        type empty;
      }
    }
  }

  grouping peer-entity-type {
    uses apply-group;
    uses apply-macro;
    choice choice-3 {
      leaf host {
        type empty;
      }
      leaf mobility-agent {
        type empty;
      }
    }
  }

  grouping peer-key-type {
    uses apply-group;
    uses apply-macro;
    choice choice-3 {
      container hex {
        leaf hex-value {
          type string;
        }
      }
      container ascii {
        leaf ascii-value {
          type string;
        }
      }
    }
  }

  grouping ssd-traceoptions-type {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    leaf level {
      type string;
    }
    list flag {
      key "name";
      ordered-by user;
      leaf name {
        type string;
      }
    }
  }

  grouping ssg-destination-nat-object {
    uses apply-group;
    uses apply-macro;
    list pool {
      key "name";
      ordered-by user;
      leaf name {
        type key-attribute-string-type;
      }
      uses apply-group;
      uses apply-macro;
      leaf description {
        type string;
      }
      container routing-instance {
        uses apply-group;
        uses apply-macro;
        leaf ri-name {
          type string;
        }
      }
      container address {
        presence "";
        leaf ipaddr {
          type ipprefix;
        }
        choice choice-5 {
          container to {
            uses apply-group;
            uses apply-macro;
            leaf ipaddr {
              type ipprefix;
            }
          }
          leaf port {
            type uint16;
          }
        }
      }
    }
    list rule-set {
      key "name";
      ordered-by user;
      leaf name {
        type key-attribute-string-type;
      }
      uses apply-group;
      uses apply-macro;
      leaf description {
        type string;
      }
      container from {
        choice choice-3 {
          leaf-list routing-instance {
            type string;
          }
          leaf-list zone {
            type string;
          }
          leaf-list interface {
            type interface-name;
          }
        }
      }
      list rule {
        key "name";
        ordered-by user;
        uses dest-nat-rule-object;
      }
    }
  }

  grouping dest-nat-rule-object {
    leaf name {
      type key-attribute-string-type;
    }
    uses apply-group;
    uses apply-macro;
    leaf description {
      type string;
    }
    container dest-nat-rule-match {
      presence "";
      uses apply-group;
      uses apply-macro;
      leaf-list source-address {
        type ipprefix;
        ordered-by user;
      }
      container destination-address {
        presence "";
        leaf dst-addr {
          type ipprefix;
        }
      }
      list destination-port {
        key "name";
        ordered-by user;
        leaf name {
          type uint16;
        }
        container to {
          presence "";
          uses apply-group;
          uses apply-macro;
          leaf high {
            type uint16;
            mandatory true;
          }
        }
      }
      leaf-list protocol {
        ordered-by user;
        type string;
      }
      leaf-list application {
        type string;
        ordered-by user;
      }
    }
    container then {
      uses apply-group;
      uses apply-macro;
      container destination-nat {
        choice choice-3 {
          leaf off {
            type empty;
          }
          container pool {
            uses apply-group;
            uses apply-macro;
            leaf pool-name {
              type string;
            }
          }
        }
      }
    }
  }

  grouping ssg-proxy-arp-object {
    uses apply-group;
    uses apply-macro;
    list interface {
      key "name";
      ordered-by user;
      uses ssg-interface-object;
    }
  }

  grouping ssg-interface-object {
    leaf name {
      type interface-name;
    }
    uses apply-group;
    uses apply-macro;
    list address {
      key "name";
      ordered-by user;
      leaf name {
        type ipv4prefix;
      }
      container to {
        uses apply-group;
        uses apply-macro;
        leaf ipaddr {
          type ipv4prefix;
        }
      }
    }
  }

  grouping ssg-source-nat-object {
    uses apply-group;
    uses apply-macro;
    container persistent-nat {
      container log {
        leaf enable-disable {
          type string;
        }
      }
    }
    list pool {
      key "name";
      ordered-by user;
      leaf name {
        type key-attribute-string-type;
      }
      uses apply-group;
      uses apply-macro;
      leaf description {
        type string;
      }
      container routing-instance {
        uses apply-group;
        uses apply-macro;
        leaf ri-name {
          type string;
        }
      }
      list address {
        key "name";
        ordered-by user;
        leaf name {
          type ipprefix;
        }
        container to {
          uses apply-group;
          uses apply-macro;
          leaf ipaddr {
            type ipprefix;
          }
        }
      }
      container host-address-base {
        leaf ipaddr {
          type ipprefix;
        }
      }
      container port {
        choice choice-3 {
          leaf no-translation {
            type empty;
          }
          container range {
            presence "";
            leaf low {
              type string;
            }
            container to {
              presence "";
              uses apply-group;
              uses apply-macro;
              leaf high {
                type string;
              }
            }
          }
        }
        leaf port-overloading-factor {
          type uint16;
        }
        container block-allocation {
          presence "enable block-allocation";
          uses block-allocation-object;
        }
        container deterministic {
          presence "enable deterministic";
          uses deterministic-object;
        }
      }
      container overflow-pool {
        choice choice-3 {
          leaf pool-name {
            type string;
          }
          leaf interface {
            type empty;
          }
        }
      }
      leaf address-shared {
        type empty;
      }
      container address-pooling {
        choice choice-paired {
          leaf paired {
            type empty;
          }
          leaf no-paired {
            type empty;
          }
        }
      }
      container address-persistent {
        container subscriber {
          leaf ipv6-prefix-length {
            type uint16;
          }
        }
      }
      container pool-utilization-alarm {
        presence "";
        uses source-nat-pool-utilization-alarm-object;
      }
      leaf ei-mapping-timeout {
        units "second";
        type uint32;
      }
      leaf mapping-timeout {
        units "second";
        type uint32;
      }
    }
    leaf address-persistent {
      type empty;
    }
    leaf session-persistence-scan {
      type empty;
    }
    leaf session-drop-hold-down {
      type uint16;
    }
    container pool-utilization-alarm {
      presence "";
      uses source-nat-pool-utilization-alarm-object;
    }
    container port-randomization {
      choice choice-3 {
        leaf disable {
          type empty;
        }
      }
    }
    container port-round-robin;
    leaf port-scaling-enlargement {
      type empty;
    }
    leaf pool-distribution {
      type empty;
    }
    container pool-default-port-range {
      presence "";
      leaf low {
        mandatory true;
        type uint16;
      }
      container to {
        presence "";
        uses apply-group;
        uses apply-macro;
        leaf high {
          mandatory true;
          type uint16;
        }
      }
    }
    container pool-default-twin-port-range {
      presence "";
      leaf low {
        mandatory true;
        type uint16;
      }
      container to {
        presence "";
        uses apply-group;
        uses apply-macro;
        leaf high {
          mandatory true;
          type uint16;
        }
      }
    }
    container interface {
      uses apply-group;
      uses apply-macro;
      choice choice-port-overloading {
        container port-overloading {
          leaf off {
            type empty;
          }
        }
        leaf port-overloading-factor {
          type uint16;
        }
      }
    }
    list rule-set {
      key "name";
      ordered-by user;
      leaf name {
        type key-attribute-string-type;
      }
      uses apply-group;
      uses apply-macro;
      container from {
        choice choice-3 {
          leaf-list routing-instance {
            type string;
          }
          leaf-list zone {
            type string;
          }
          leaf-list interface {
            type interface-name;
          }
        }
      }
      container to {
        choice choice-3 {
          leaf-list routing-instance {
            type string;
          }
          leaf-list zone {
            type string;
          }
          leaf-list interface {
            type interface-name;
          }
        }
      }
      list rule {
        key "name";
        ordered-by user;
        uses src-nat-rule-object;
      }
      leaf match-direction {
        type string;
      }
    }
  }

  grouping block-allocation-object {
    uses apply-group;
    uses apply-macro;
    leaf block-size {
      type uint16;
    }
    leaf maximum-blocks-per-host {
      type uint16;
    }
    leaf active-block-timeout {
      type uint16;
    }
    leaf interim-logging-interval {
      type uint32;
    }
    leaf last-block-recycle-timeout {
      type uint32;
    }
    container log {
      leaf enable-disable {
        type string;
      }
    }
  }

  grouping deterministic-object {
    uses apply-group;
    uses apply-macro;
    leaf block-size {
      type uint16;
    }
    container host {
      leaf-list address {
        type ipprefix;
        ordered-by user;
      }
      leaf-list address-name {
        type string;
        ordered-by user;
      }
    }
    leaf include-boundary-addresses {
      type empty;
    }
  }

  grouping source-nat-pool-utilization-alarm-object {
    uses apply-group;
    uses apply-macro;
    leaf raise-threshold {
      type uint16;
    }
    leaf clear-threshold {
      type uint16;
    }
  }

  grouping src-nat-rule-object {
    leaf name {
      type key-attribute-string-type;
    }
    uses apply-group;
    uses apply-macro;
    leaf description {
      type string;
    }
    container src-nat-rule-match {
      uses apply-group;
      uses apply-macro;
      leaf-list source-address {
        type ipprefix;
        ordered-by user;
      }
      leaf-list source-address-name {
        type string;
        ordered-by user;
      }
      list source-port {
        key "name";
        ordered-by user;
        leaf name {
          type uint16;
        }
        container to {
          uses apply-group;
          uses apply-macro;
          leaf high {
            type uint16;
          }
        }
      }
      leaf-list destination-address {
        type ipprefix;
        ordered-by user;
      }
      leaf-list destination-address-name {
        type string;
        ordered-by user;
      }
      list destination-port {
        key "name";
        ordered-by user;
        leaf name {
          type uint16;
        }
        container to {
          uses apply-group;
          uses apply-macro;
          leaf high {
            type uint16;
          }
        }
      }
      leaf-list protocol {
        ordered-by user;
        type string;
      }
      leaf-list application {
        type string;
        ordered-by user;
      }
    }
    container then {
      uses apply-group;
      uses apply-macro;
      container source-nat {
        uses apply-group;
        uses apply-macro;
        choice choice-3 {
          leaf off {
            type empty;
          }
          container pool {
            uses apply-group;
            uses apply-macro;
            leaf pool-name {
              type string;
            }
            container persistent-nat {
              presence "";
              uses persistent-nat-object;
            }
          }
          container interface {
            presence "enable interface";
            uses apply-group;
            uses apply-macro;
            container persistent-nat {
              presence "";
              uses persistent-nat-object;
            }
          }
        }
        container mapping-type {
          leaf endpoint-independent {
            type empty;
          }
          leaf address-pooling-paired {
            type empty;
          }
        }
      }
      leaf syslog {
        type empty;
      }
    }
  }

  grouping persistent-nat-object {
    uses apply-group;
    uses apply-macro;
    container permit {
      choice choice-3 {
        leaf any-remote-host {
          type empty;
        }
        leaf target-host {
          type empty;
        }
        leaf target-host-port {
          type empty;
        }
      }
    }
    leaf address-mapping {
      type empty;
    }
    leaf inactivity-timeout {
      type uint16;
    }
    leaf max-session-number {
      type uint32;
    }
  }

  grouping ssg-static-nat-object {
    uses apply-group;
    uses apply-macro;
    list rule-set {
      key "name";
      ordered-by user;
      leaf name {
        type key-attribute-string-type;
      }
      uses apply-group;
      uses apply-macro;
      leaf description {
        type string;
      }
      container from {
        choice choice-3 {
          leaf-list routing-instance {
            type string;
          }
          leaf-list zone {
            type string;
          }
          leaf-list interface {
            type interface-name;
          }
        }
      }
      list rule {
        key "name";
        ordered-by user;
        uses static-nat-rule-object;
      }
    }
  }

  grouping static-nat-rule-object {
    leaf name {
      type key-attribute-string-type;
    }
    uses apply-group;
    uses apply-macro;
    leaf description {
      type string;
    }
    container static-nat-rule-match {
      uses apply-group;
      uses apply-macro;
      leaf-list source-address {
        type ipprefix;
        ordered-by user;
      }
      leaf-list source-address-name {
        type string;
        ordered-by user;
      }
      list source-port {
        key "name";
        ordered-by user;
        leaf name {
          type uint16;
        }
        container to {
          uses apply-group;
          uses apply-macro;
          container apply-advanced {
            uses apply-group;
            uses apply-macro;
          }
          leaf high {
            type uint16;
          }
        }
      }
      choice choice-destination-address {
        container destination-address {
          presence "";
          leaf dst-addr {
            type ipprefix;
          }
        }
        container destination-address-name {
          presence "";
          leaf dst-addr-name {
            type string;
          }
        }
      }
      container destination-port {
        presence "";
        leaf low {
          type uint16;
        }
        container to {
          presence "";
          uses apply-group;
          uses apply-macro;
          container apply-advanced {
            uses apply-group;
            uses apply-macro;
          }
          leaf high {
            type uint16;
          }
        }
      }
    }
    container then {
      uses apply-group;
      uses apply-macro;
      container static-nat {
        choice choice-3 {
          leaf inet {
            type empty;
          }
          container prefix {
            uses apply-group;
            uses apply-macro;
            leaf addr-prefix {
              type ipprefix;
            }
            container mapped-port {
              presence "";
              uses static-nat-rule-mapped-port-object;
            }
            leaf routing-instance {
              type string;
            }
          }
          container prefix-name {
            uses apply-group;
            uses apply-macro;
            leaf addr-prefix-name {
              type string;
            }
            container mapped-port {
              presence "";
              uses static-nat-rule-mapped-port-object;
            }
            leaf routing-instance {
              type string;
            }
          }
        }
      }
    }
  }

  grouping station-mac-filter {
    uses apply-group;
    uses apply-macro;
    container allow-list {
      uses apply-group;
      uses apply-macro;
      leaf-list mac-address {
        type mac-unicaset;
        ordered-by user;
      }
    }
    container deny-list {
      uses apply-group;
      uses apply-macro;
      leaf-list mac-address {
        type mac-unicaset;
        ordered-by user;
      }
    }
  }

  grouping station-queue-type {
    uses apply-group;
    uses apply-macro;
    leaf arbitration-inter-frame-space {
      type int32;
    }
    container minimum-contention-window {
      uses contention-window;
    }
    container maximum-contention-window {
      uses contention-window;
    }
    leaf transmit-opportunity-limit {
      type int32;
    }
  }

  grouping static-nat-rule-mapped-port-object {
    uses apply-group;
    uses apply-macro;
    container apply-advanced {
      uses apply-group;
      uses apply-macro;
    }
    leaf low {
      type uint16;
      mandatory true;
    }
    container to {
      presence "";
      uses apply-group;
      uses apply-macro;
      container apply-advanced {
        uses apply-group;
        uses apply-macro;
      }
      leaf high {
        type uint16;
        mandatory true;
      }
    }
  }

  grouping stp-interface {
    leaf name {
      type interface-device;
    }
    uses apply-group;
    uses apply-macro;
    leaf priority {
      type uint16;
    }
    leaf cost {
      type uint32;
    }
    leaf disable {
      type empty;
    }
    leaf arp-on-stp {
      type empty;
    }
    leaf mode {
      type string;
    }
    leaf edge {
      type empty;
    }
    container bpdu-timeout-action {
      presence "enable bpdu-timeout-action";
      uses apply-group;
      uses apply-macro;
      leaf block {
        type empty;
      }
      leaf alarm {
        type empty;
      }
      leaf log {
        type empty;
      }
    }
    leaf no-root-port {
      type empty;
    }
  }

  grouping stp-trace-options {
    uses apply-group;
    uses apply-macro;
    container file {
      presence "";
      uses trace-file-type;
    }
    list flag {
      key "name";
      ordered-by user;
      leaf name {
        type string;
      }
      leaf disable {
        type empty;
      }
    }
  }

  grouping subscription-type {
    uses apply-group;
    uses apply-macro;
    leaf link-subscription {
      type string;
    }
    leaf ct0 {
      type string;
    }
    leaf ct1 {
      type string;
    }
    leaf ct2 {
      type string;
    }
    leaf ct3 {
      type string;
    }
  }

  grouping svc-ike-policy {
    leaf name {
      type key-attribute-string-type;
    }
    uses apply-group;
    uses apply-macro;
    leaf description {
      type string;
    }
    leaf mode {
      type string;
    }
    leaf version {
      type string;
    }
    leaf-list proposals {
      type string;
      ordered-by user;
    }
    container local-id {
      choice choice-ipv4_addr {
        leaf ipv4_addr {
          type ipv4addr;
        }
        leaf fqdn {
          type string;
        }
        leaf key-id {
          type string;
        }
        leaf ipv6-addr {
          type ipv6addr;
        }
      }
    }
    leaf local-certificate {
      type string;
    }
    container remote-id {
      uses apply-group;
      uses apply-macro;
      leaf any-remote-id {
        type empty;
      }
      leaf-list ipv4_addr {
        type ipv4addr;
        ordered-by user;
      }
      leaf-list fqdn {
        ordered-by user;
        type string;
      }
      leaf-list key-id {
        ordered-by user;
        type string;
      }
      leaf-list ipv6-addr {
        type ipv6addr;
        ordered-by user;
      }
    }
    container pre-shared-key {
      choice choice-ascii-text {
        leaf ascii-text {
          type string;
        }
        leaf hexadecimal {
          type string;
        }
      }
    }
  }

  grouping sw-rule-object {
    leaf name {
      type key-attribute-string-type;
    }
    uses apply-group;
    uses apply-macro;
    leaf match-direction {
      type string;
    }
    list term {
      key "name";
      ordered-by user;
      leaf name {
        type key-attribute-string-type;
      }
      uses apply-group;
      uses apply-macro;
      container then {
        uses apply-group;
        uses apply-macro;
        choice choice-3 {
          leaf ds-lite {
            type string;
          }
          leaf v6rd {
            type string;
          }
        }
      }
    }
  }

  grouping syslog-object {
    leaf name {
      type string;
    }
    uses apply-group;
    uses apply-macro;
    choice choice-3 {
      leaf any {
        type empty;
      }
      leaf emergency {
        type empty;
      }
      leaf alert {
        type empty;
      }
      leaf critical {
        type empty;
      }
      leaf error {
        type empty;
      }
      leaf warning {
        type empty;
      }
      leaf notice {
        type empty;
      }
      leaf info {
        type empty;
      }
      leaf none {
        type empty;
      }
    }
  }

  grouping system-id-ip-map {
    leaf name {
      type mac-unicaset;
    }
    uses apply-group;
    uses apply-macro;
    leaf ip-address {
      type ipv4prefix;
    }
  }

  grouping tacplus-server-object {
    leaf name {
      type ipv4addr;
    }
    uses apply-group;
    uses apply-macro;
    leaf routing-instance {
      type string;
    }
    leaf port {
      type uint16;
    }
    leaf secret {
      type unreadable;
    }
    leaf timeout {
      type uint32;
    }
    leaf single-connection {
      type empty;
    }
    leaf source-address {
      type ipv4addr;
    }
  }

  grouping te-class-object {
    uses apply-group;
    uses apply-macro;
    leaf traffic-class {
      type string;
    }
    leaf priority {
      type uint32;
    }
  }

  grouping term-object {
    leaf name {
      type key-attribute-string-type;
    }
    uses apply-group;
    uses apply-macro;
    leaf alg {
      type string;
    }
    leaf protocol {
      type string;
    }
    leaf source-port {
      type string;
    }
    leaf destination-port {
      type string;
    }
    leaf icmp-type {
      type string;
    }
    leaf icmp-code {
      type string;
    }
    leaf icmp6-type {
      type string;
    }
    leaf icmp6-code {
      type string;
    }
    leaf rpc-program-number {
      type string;
    }
    leaf uuid {
      type string;
    }
    leaf inactivity-timeout {
      type string;
    }
  }

  grouping three-color-policer-type {
    leaf name {
      type string;
    }
    uses apply-group;
    uses apply-macro;
    leaf logical-interface-policer {
      type empty;
    }
    leaf physical-interface-policer {
      type empty;
    }
    container action {
      uses apply-group;
      uses apply-macro;
      list loss-priority {
        key "name";
        ordered-by user;
        uses three-color-policer-action;
      }
    }
    choice choice-9 {
      container single-rate {
        presence "enable single-rate";
        uses apply-group;
        uses apply-macro;
        choice choice-3 {
          leaf color-blind {
            type empty;
          }
          leaf color-aware {
            type empty;
          }
        }
        leaf committed-information-rate {
          type string;
        }
        leaf committed-burst-size {
          type string;
        }
        leaf excess-burst-size {
          type string;
        }
      }
      container two-rate {
        presence "enable two-rate";
        uses apply-group;
        uses apply-macro;
        choice choice-3 {
          leaf color-blind {
            type empty;
          }
          leaf color-aware {
            type empty;
          }
        }
        leaf committed-information-rate {
          type string;
        }
        leaf committed-burst-size {
          type string;
        }
        leaf peak-information-rate {
          type string;
        }
        leaf peak-burst-size {
          type string;
        }
      }
    }
  }

  grouping three-color-policer-action {
    leaf name {
      type string;
    }
    uses apply-group;
    uses apply-macro;
    container then {
      uses apply-group;
      uses apply-macro;
      leaf discard {
        type empty;
      }
    }
  }

  grouping to-fabric-object {
    uses apply-group;
    uses apply-macro;
    leaf except {
      type empty;
    }
  }

  grouping trace-file-type {
    uses apply-group;
    uses apply-macro;
    leaf filename {
      type string;
    }
    leaf size {
      type string;
    }
    leaf files {
      type uint32;
    }
    leaf world-readable {
      type empty;
    }
    leaf no-world-readable {
      type empty;
    }
  }

  grouping transaction-method-type {
    leaf name {
      type string;
    }
    uses apply-group;
    uses apply-macro;
  }

  grouping transaction-policy-type {
    leaf name {
      type string;
    }
    uses apply-group;
    uses apply-macro;
    list term {
      key "name";
      ordered-by user;
      leaf name {
        type string;
      }
      uses apply-group;
      uses apply-macro;
      container from {
        presence "enable from";
        uses new-transaction-from-type;
      }
      container then {
        presence "enable then";
        uses new-transaction-then-type;
      }
    }
  }

  grouping new-transaction-then-type {
    uses apply-group;
    uses apply-macro;
    leaf accept {
      type empty;
    }
    leaf reject {
      type empty;
    }
    container route {
      uses route-action;
    }
    leaf trace {
      type empty;
    }
    leaf admission-control {
      type string;
    }
    container message-manipulation {
      presence "enable message-manipulation";
      uses apply-group;
      uses apply-macro;
      list forward-manipulation {
        key "name";
        ordered-by user;
        leaf name {
          type string;
        }
        uses apply-group;
        uses apply-macro;
      }
      list reverse-manipulation {
        key "name";
        ordered-by user;
        leaf name {
          type string;
        }
        uses apply-group;
        uses apply-macro;
      }
    }
    leaf signaling-realm {
      type string;
    }
    container on-3xx-response {
      presence "enable on-3xx-response";
      uses apply-group;
      uses apply-macro;
      choice choice-3 {
        leaf recursion-limit {
          type uint32;
        }
      }
    }
  }

  grouping route-action {
    uses apply-group;
    uses apply-macro;
    container next-hop {
      presence "enable next-hop";
      uses apply-group;
      uses apply-macro;
      choice choice-3 {
        container address {
          presence "";
          uses routing-destination-address;
        }
        leaf request-uri {
          type empty;
        }
      }
    }
    leaf egress-service-point {
      type string;
    }
    leaf server-cluster {
      type string;
    }
  }

  grouping transmit-rate-sets {
    uses apply-group;
    uses apply-macro;
    list supported-rates {
      key "name";
      ordered-by user;
      uses rates;
    }
    list supported-basic-rates {
      key "name";
      ordered-by user;
      uses rates;
    }
  }

  grouping rates {
    leaf name {
      type string;
    }
    uses apply-group;
    uses apply-macro;
  }

  grouping transport-protocol {
    uses apply-group;
    uses apply-macro;
    choice choice-3 {
      leaf udp {
        type empty;
      }
      leaf tcp {
        type empty;
      }
    }
  }

  grouping tty-port-object {
    uses apply-group;
    uses apply-macro;
    leaf-list authentication-order {
      ordered-by user;
      type string;
    }
    leaf log-out-on-disconnect {
      type empty;
    }
    leaf port-type {
      type string;
    }
    leaf disable {
      type empty;
    }
    leaf insecure {
      type empty;
    }
    leaf type {
      type string;
    }
    leaf silent-with-modem {
      type empty;
    }
  }

  grouping tunable-object {
    leaf name {
      type string;
    }
    uses apply-group;
    uses apply-macro;
    leaf tunable-value {
      type uint32;
    }
  }

  grouping tunnel-interface-type {
    leaf name {
      type interface-unit;
    }
    uses apply-group;
    uses apply-macro;
  }

  grouping tunnel-end-point {
    leaf name {
      type string;
    }
    uses apply-group;
    uses apply-macro;
    choice choice-ipv6 {
      container ipv6 {
        presence "enable ipv6";
        uses apply-group;
        uses apply-macro;
        leaf source-address {
          type ipv6addr;
        }
        leaf destination-address {
          type ipv6prefix;
        }
      }
      container ipv4 {
        presence "";
        uses apply-group;
        uses apply-macro;
        leaf source-address {
          mandatory true;
          type ipv4addr;
        }
        leaf destination-address {
          mandatory true;
          type ipv4prefix;
        }
      }
    }
    choice choice-gre {
      container gre {
        presence "enable gre";
        uses apply-group;
        uses apply-macro;
        leaf key {
          type uint32;
        }
      }
      container gre-in-udp {
        presence "";
        uses apply-group;
        uses apply-macro;
        leaf source-port {
          mandatory true;
          type uint32;
        }
        leaf destination-port {
          mandatory true;
          type uint32;
        }
        leaf key {
          type uint32;
        }
      }
    }
  }

  grouping tunnel-type {
    uses apply-group;
    uses apply-macro;
    choice choice-3 {
      leaf ipsec-vpn {
        type string;
      }
      leaf ipsec-group-vpn {
        type string;
      }
    }
    leaf pair-policy {
      type string;
    }
  }

  grouping twamp-authentication-key-chain {
    leaf name {
      type string;
    }
    uses apply-group;
    uses apply-macro;
    list key-id {
      key "name";
      leaf name {
        type key-attribute-string-type;
      }
      uses apply-group;
      uses apply-macro;
      leaf secret {
        type string;
      }
    }
  }

  grouping unified-edge-gateway-diameter {
    uses apply-group;
    uses apply-macro;
    list network-element {
      key "name";
      ordered-by user;
      leaf name {
        type key-attribute-string-type;
      }
      uses apply-group;
      uses apply-macro;
      container session-pics {
        uses gateway-diameter-ne-session-pics;
      }
    }
  }

  grouping gateway-diameter-ne-session-pics {
    uses apply-group;
    uses apply-macro;
    list group {
      key "name";
      ordered-by user;
      leaf name {
        type string;
      }
      uses apply-group;
      uses apply-macro;
      list session-pic {
        key "name";
        ordered-by user;
        leaf name {
          type interface-unit;
        }
        uses apply-group;
        uses apply-macro;
      }
    }
  }

  grouping unified-edge-ggsn-pgw-system {
    uses apply-group;
    uses apply-macro;
    container pfes {
      uses apply-group;
      uses apply-macro;
      list interface {
        key "name";
        ordered-by user;
        leaf name {
          type interface-unit;
        }
        uses apply-group;
        uses apply-macro;
        leaf service-mode {
          type string;
        }
      }
    }
    container session-pics {
      uses apply-group;
      uses apply-macro;
      list interface {
        key "name";
        ordered-by user;
        leaf name {
          type interface-unit;
        }
        uses apply-group;
        uses apply-macro;
        leaf service-mode {
          type string;
        }
      }
    }
    container service-pics {
      presence "enable service-pics";
      uses apply-group;
      uses apply-macro;
      list interface {
        key "name";
        ordered-by user;
        leaf name {
          type interface-unit;
        }
        uses apply-group;
        uses apply-macro;
        leaf service-mode {
          type string;
        }
      }
    }
  }

  grouping unified-edge-mobile-options {
    uses apply-group;
    uses apply-macro;
    container traceoptions {
      uses mobiled-traceoptions;
    }
  }

  grouping mobiled-traceoptions {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
      leaf match {
        type regular-expression;
      }
    }
    list flag {
      key "name";
      ordered-by user;
      leaf name {
        type string;
      }
      leaf send {
        type empty;
      }
      leaf receive {
        type empty;
      }
      leaf detail {
        type empty;
      }
      leaf disable {
        type empty;
      }
    }
  }

  grouping unified-edge-pcef {
    uses apply-group;
    uses apply-macro;
    container traceoptions {
      uses pcef-traceoptions;
    }
    container event-trigger-profiles {
      uses apply-group;
      uses apply-macro;
      list profile {
        key "name";
        uses evt-trigger-profile;
      }
    }
    container flow-descriptions {
      uses apply-group;
      uses apply-macro;
      list definition {
        key "name";
        uses pcc-flow;
      }
    }
    container pcc-action-profiles {
      uses apply-group;
      uses apply-macro;
      list definition {
        key "name";
        uses pcc-action-profile;
      }
    }
    container pcc-rules {
      uses apply-group;
      uses apply-macro;
      list definition {
        key "name";
        uses pcc-rule;
      }
    }
    container pcc-rulebases {
      uses apply-group;
      uses apply-macro;
      list definition {
        key "name";
        ordered-by user;
        uses pcc-rulebase;
      }
    }
    container profiles {
      uses apply-group;
      uses apply-macro;
      list definition {
        key "name";
        ordered-by user;
        uses pcef-profiles;
      }
    }
  }

  grouping evt-trigger-profile {
    leaf name {
      type key-attribute-string-type;
    }
    uses apply-group;
    uses apply-macro;
    leaf rat-change {
      type empty;
    }
    leaf sgsn-change {
      type empty;
    }
    leaf plmn-change {
      type empty;
    }
    leaf ip-can-change {
      type empty;
    }
    leaf tft-change {
      type empty;
    }
    leaf rai-change {
      type empty;
    }
    leaf user-location-change {
      type empty;
    }
    leaf ue-timezone-change {
      type empty;
    }
  }

  grouping pcc-action-profile {
    leaf name {
      type key-attribute-string-type;
    }
    uses apply-group;
    uses apply-macro;
    leaf qci {
      type uint8;
    }
    leaf logging-rule {
      type string;
    }
    container allocation-retention-priority {
      presence "";
      uses apply-group;
      uses apply-macro;
      leaf priority-level {
        type uint8;
      }
      leaf preemption-capability {
        type string;
      }
      leaf preemption-vulnerability {
        type string;
      }
    }
    container maximum-bit-rate {
      presence "enable maximum-bit-rate";
      leaf uplink {
        units "kilobits";
        type uint32;
      }
      leaf downlink {
        units "kilobits";
        type uint32;
      }
    }
    container burst-size {
      presence "enable burst-size";
      uses apply-group;
      uses apply-macro;
      leaf uplink {
        units "bytes";
        type uint32;
      }
      leaf downlink {
        units "bytes";
        type uint32;
      }
    }
    container guaranteed-bit-rate {
      presence "enable guaranteed-bit-rate";
      leaf uplink {
        units "kilobits";
        type uint32;
      }
      leaf downlink {
        units "kilobits";
        type uint32;
      }
    }
    leaf gate-status {
      type string;
    }
    container charging {
      uses apply-group;
      uses apply-macro;
      leaf rating-group {
        type uint32;
      }
      leaf service-identifier {
        type uint32;
      }
      leaf charging-method {
        type string;
      }
      leaf measurement-method {
        type string;
      }
      container application-function-record-info {
        presence "enable application-function-record-info";
        uses apply-group;
        uses apply-macro;
        leaf af-charging-identifier {
          type string;
        }
      }
      leaf service-id-level-reporting {
        type empty;
      }
    }
    container redirect {
      uses apply-group;
      uses apply-macro;
      leaf url {
        type string;
      }
    }
    container forwarding-class {
      uses apply-group;
      uses apply-macro;
      leaf class-name {
        type string;
      }
    }
    container steering {
      uses apply-group;
      uses apply-macro;
      container routing-instance {
        leaf uplink {
          type string;
        }
        leaf downlink {
          type string;
        }
      }
      container path {
        choice choice-ipv4-address {
          leaf ipv4-address {
            type ipv4prefix;
          }
          leaf ipv6-address {
            type ipv6prefix;
          }
        }
      }
      leaf keep-existing-steering {
        type empty;
      }
    }
    container hcm-profile {
      uses apply-group;
      uses apply-macro;
      leaf profile-name {
        type string;
      }
    }
    leaf monitoring-key {
      type string;
    }
  }

  grouping pcc-flow {
    leaf name {
      type key-attribute-string-type;
    }
    uses apply-group;
    uses apply-macro;
    leaf direction {
      type string;
    }
    leaf protocol {
      type uint8;
    }
    leaf-list local-ports {
      type uint16;
    }
    list local-port-range {
      key "low high";
      ordered-by user;
      leaf low {
        type key-attribute-ulong-type;
      }
      leaf high {
        type key-attribute-ulong-type;
      }
    }
    leaf-list remote-ports {
      type uint16;
    }
    list remote-port-range {
      key "low high";
      ordered-by user;
      leaf low {
        type key-attribute-ulong-type;
      }
      leaf high {
        type key-attribute-ulong-type;
      }
    }
    container remote-address {
      choice choice-ipv4-address {
        leaf ipv4-address {
          type ipv4prefix;
        }
        leaf ipv6-address {
          type ipv6prefix;
        }
      }
    }
    leaf no-send-to-ue {
      type empty;
    }
  }

  grouping pcc-rule {
    leaf name {
      type string;
    }
    uses apply-group;
    uses apply-macro;
    container from {
      presence "";
      uses apply-group;
      uses apply-macro;
      list flows {
        key "name";
        ordered-by user;
        leaf name {
          type key-attribute-string-type;
        }
        uses apply-group;
        uses apply-macro;
      }
    }
    container then {
      uses apply-group;
      uses apply-macro;
      leaf pcc-action-profile {
        type string;
      }
    }
  }

  grouping pcc-rulebase {
    leaf name {
      type string;
    }
    uses apply-group;
    uses apply-macro;
    list pcc-rule {
      key "name";
      ordered-by user;
      leaf name {
        type key-attribute-string-type;
      }
      leaf precedence {
        type uint16;
      }
    }
  }

  grouping pcef-profiles {
    leaf name {
      type key-attribute-string-type;
    }
    uses apply-group;
    uses apply-macro;
    leaf control-byte-rating-group {
      type uint32;
    }
    leaf unresolved-flow-action {
      type string;
    }
    container maximum-per-pdn-service-flows {
      leaf num {
        type uint32;
      }
    }
    container dynamic-policy-control {
      presence "";
      uses apply-group;
      uses apply-macro;
      container pcc-rules {
        uses apply-group;
        uses apply-macro;
        list rule-assoc {
          key "name";
          ordered-by user;
          uses profile-rule-assoc;
        }
      }
      list pcc-rulebases {
        key "name";
        ordered-by user;
        leaf name {
          type key-attribute-string-type;
        }
        uses apply-group;
        uses apply-macro;
      }
      leaf diameter-profile {
        type string;
      }
      leaf event-trigger-profile {
        type string;
      }
      leaf session-failover-not-supported {
        type empty;
      }
      leaf release {
        type string;
      }
    }
    container static-policy-control {
      uses apply-group;
      uses apply-macro;
      container pcc-rules {
        uses apply-group;
        uses apply-macro;
        list rule-assoc {
          key "name";
          ordered-by user;
          uses profile-rule-assoc;
        }
      }
      list pcc-rulebases {
        key "name";
        ordered-by user;
        leaf name {
          type key-attribute-string-type;
        }
        uses apply-group;
        uses apply-macro;
        leaf time-of-day-profile {
          type string;
        }
      }
      leaf-list activate-dedicated-bearers {
        type uint8;
      }
    }
    container aaa-policy-control {
      presence "";
      uses apply-group;
      uses apply-macro;
      leaf profile {
        type string;
      }
      leaf user-password {
        type string;
      }
      list pcc-rulebases {
        key "name";
        ordered-by user;
        leaf name {
          type key-attribute-string-type;
        }
        uses apply-group;
        uses apply-macro;
      }
    }
  }

  grouping pcef-traceoptions {
    uses apply-group;
    uses apply-macro;
    leaf no-remote-trace {
      type empty;
    }
    container file {
      leaf filename {
        type string;
      }
      leaf size {
        type string;
      }
      leaf files {
        type uint32;
      }
      leaf world-readable {
        type empty;
      }
      leaf no-world-readable {
        type empty;
      }
    }
    leaf level {
      type string;
    }
    list flag {
      key "name";
      ordered-by user;
      leaf name {
        type string;
      }
    }
  }

  grouping profile-rule-assoc {
    leaf name {
      type key-attribute-string-type;
    }
    uses apply-group;
    uses apply-macro;
    leaf precedence {
      type uint16;
    }
  }

  grouping unified-edge-sgw-system {
    uses apply-group;
    uses apply-macro;
    container pfes {
      uses apply-group;
      uses apply-macro;
      list interface {
        key "name";
        ordered-by user;
        leaf name {
          type interface-unit;
        }
        uses apply-group;
        uses apply-macro;
        leaf service-mode {
          type string;
        }
      }
    }
    container session-pics {
      uses apply-group;
      uses apply-macro;
      list interface {
        key "name";
        ordered-by user;
        leaf name {
          type interface-unit;
        }
        uses apply-group;
        uses apply-macro;
        leaf service-mode {
          type string;
        }
      }
    }
  }

  grouping upgrade-group-fpcs {
    leaf name {
      type key-attribute-long-type;
    }
    uses apply-group;
    uses apply-macro;
    leaf-list fpcs {
      type uint32;
    }
  }

  grouping vchassis-trace-file-type {
    uses apply-group;
    uses apply-macro;
    leaf filename {
      type string;
    }
    leaf replace {
      type empty;
    }
    leaf size {
      type string;
    }
    leaf files {
      type uint32;
    }
    leaf no-stamp {
      type empty;
    }
    leaf world-readable {
      type empty;
    }
    leaf no-world-readable {
      type empty;
    }
  }

  grouping url-list-type {
    leaf name {
      type key-attribute-string-type;
    }
    uses apply-group;
    uses apply-macro;
    leaf-list value {
      ordered-by user;
      type string;
    }
  }

  grouping usf-range-address-type {
    leaf name {
      mandatory true;
      type ipprefix;
    }
    uses apply-group;
    uses apply-macro;
    container to {
      presence "";
      uses apply-group;
      uses apply-macro;
      leaf range-high {
        mandatory true;
        type ipprefix;
      }
    }
  }

  grouping utm-apppxy-traceoptions {
    uses apply-group;
    uses apply-macro;
    list flag {
      key "name";
      ordered-by user;
      leaf name {
        type string;
      }
    }
  }

  grouping utm-ipc-traceoptions {
    uses apply-group;
    uses apply-macro;
    list flag {
      key "name";
      ordered-by user;
      leaf name {
        type string;
      }
    }
  }

  grouping utm-traceoptions {
    uses apply-group;
    uses apply-macro;
    list flag {
      key "name";
      ordered-by user;
      leaf name {
        type string;
      }
    }
  }

  grouping v3-user-config {
    leaf name {
      type key-attribute-string-type;
    }
    uses apply-group;
    uses apply-macro;
    choice choice-3 {
      container authentication-md5 {
        uses auth-object;
      }
      container authentication-sha {
        uses auth-object;
      }
      leaf authentication-none {
        type empty;
      }
    }
    choice choice-4 {
      container privacy-des {
        uses priv-object;
      }
      container privacy-3des {
        uses priv-object;
      }
      container privacy-aes128 {
        uses priv-object;
      }
      leaf privacy-none {
        type empty;
      }
    }
  }

  grouping auth-object {
    uses apply-group;
    uses apply-macro;
    choice clear-or-encrypted {
      leaf authentication-password {
        type string;
      }
      leaf authentication-key {
        type unreadable;
      }
    }
  }

  grouping priv-object {
    uses apply-group;
    uses apply-macro;
    choice clear-or-encrypted {
      leaf privacy-password {
        type unreadable;
      }
      leaf privacy-key {
        type unreadable;
      }
    }
  }

  grouping v6-relay-option-interface-id-type {
    uses apply-group;
    uses apply-macro;
    container prefix {
      uses apply-group;
      uses apply-macro;
      leaf host-name {
        type empty;
      }
      leaf logical-system-name {
        type empty;
      }
      leaf routing-instance-name {
        type empty;
      }
    }
    leaf use-interface-description {
      type string;
    }
    leaf use-vlan-id {
      type empty;
    }
    leaf no-vlan-interface-name {
      type empty;
    }
    leaf include-irb-and-l2 {
      type empty;
    }
    leaf use-option-82 {
      type empty;
    }
    container keep-incoming-interface-id {
      presence "enable keep-incoming-interface-id";
      uses v6-relay-option-cid-rid-action;
    }
  }

  grouping v6-server-group-type {
    uses apply-group;
    uses apply-macro;
    list server-group {
      key "name";
      ordered-by user;
      leaf name {
        type key-attribute-string-type;
      }
      uses apply-group;
      uses apply-macro;
      list address {
        key "name";
        ordered-by user;
        leaf name {
          type ipaddr;
        }
        uses apply-group;
        uses apply-macro;
      }
    }
  }

  grouping v6-relay-option-cid-rid-action {
    uses apply-group;
    uses apply-macro;
    leaf strict {
      type empty;
    }
  }

  grouping v6-relay-option-remote-id-type {
    uses apply-group;
    uses apply-macro;
    container prefix {
      uses apply-group;
      uses apply-macro;
      leaf host-name {
        type empty;
      }
      leaf logical-system-name {
        type empty;
      }
      leaf routing-instance-name {
        type empty;
      }
    }
    leaf use-interface-description {
      type string;
    }
    leaf use-vlan-id {
      type empty;
    }
    leaf no-vlan-interface-name {
      type empty;
    }
    leaf include-irb-and-l2 {
      type empty;
    }
    container use-option-82 {
      presence "enable use-option-82";
      uses v6-relay-option-cid-rid-action;
    }
    leaf keep-incoming-remote-id {
      type empty;
    }
  }

  grouping v6rd-object {
    leaf name {
      type key-attribute-string-type;
    }
    uses apply-group;
    uses apply-macro;
    leaf softwire-address {
      type ipv4addr;
    }
    leaf ipv4-prefix {
      type ipv4prefix;
    }
    leaf v6rd-prefix {
      type ipv6prefix;
    }
    leaf mtu-v4 {
      type int32;
    }
  }

  grouping vap-type {
    leaf name {
      type string;
    }
    uses apply-group;
    uses apply-macro;
    leaf description {
      type string;
    }
    leaf ssid {
      type string;
    }
    leaf vlan {
      type int32;
    }
    leaf no-broadcast-ssid {
      type empty;
    }
    container http-redirect {
      presence "enable http-redirect";
      uses http-redirect;
    }
    container security {
      presence "enable security";
      uses security;
    }
  }

  grouping http-redirect {
    uses apply-group;
    uses apply-macro;
    leaf redirect-url {
      type string;
    }
  }

  grouping security {
    uses apply-group;
    uses apply-macro;
    leaf mac-authentication-type {
      type string;
    }
    choice choice-5 {
      container static-wep {
        presence "enable static-wep";
        uses static-wep;
      }
      container dot1x {
        presence "enable dot1x";
        uses dot1x;
      }
      container wpa-personal {
        presence "enable wpa-personal";
        uses wpa-personal;
      }
      container wpa-enterprise {
        presence "enable wpa-enterprise";
        uses wpa-enterprise;
      }
      leaf none {
        type empty;
      }
    }
  }

  grouping dot1x {
    uses apply-group;
    uses apply-macro;
    leaf radius-server {
      type ipaddr;
    }
    leaf radius-key {
      type string;
    }
    leaf broadcast-key-refresh-rate {
      type int32;
    }
    leaf session-key-refresh-rate {
      type int32;
    }
  }

  grouping static-wep {
    uses apply-group;
    uses apply-macro;
    leaf authentication-type {
      type string;
    }
    leaf key-length {
      type string;
    }
    leaf key-type {
      type string;
    }
    leaf transfer-key-index {
      type int32;
    }
    leaf wep-key-1 {
      type unreadable;
    }
    leaf wep-key-2 {
      type unreadable;
    }
    leaf wep-key-3 {
      type unreadable;
    }
    leaf wep-key-4 {
      type unreadable;
    }
  }

  grouping version-ipfix-template {
    leaf name {
      type string;
    }
    uses apply-group;
    uses apply-macro;
    leaf flow-active-timeout {
      type uint32;
    }
    leaf flow-inactive-timeout {
      type uint32;
    }
    leaf template-id {
      type uint32;
    }
    leaf option-template-id {
      type uint32;
    }
    leaf observation-domain-id {
      type uint32;
    }
    container nexthop-learning {
      presence "";
      uses apply-group;
      uses apply-macro;
      leaf enable-disable {
        type string;
      }
      choice enable-disable-choice {
        case case_1 {
          leaf enable {
            type empty;
          }
        }
        case case_2 {
          leaf disable {
            type empty;
          }
        }
      }
    }
    container template-refresh-rate {
      presence "enable template-refresh-rate";
      uses apply-group;
      uses apply-macro;
      leaf packets {
        type uint32;
      }
      leaf seconds {
        type uint32;
      }
    }
    container option-refresh-rate {
      presence "enable option-refresh-rate";
      uses apply-group;
      uses apply-macro;
      leaf packets {
        type uint32;
      }
      leaf seconds {
        type uint32;
      }
    }
    choice choice-11 {
      container ipv4-template {
        presence "enable ipv4-template";
        uses apply-group;
        uses apply-macro;
      }
      container ipv6-template {
        presence "enable ipv6-template";
        uses apply-group;
        uses apply-macro;
      }
      container bridge-template {
        presence "enable bridge-template";
        uses apply-group;
        uses apply-macro;
      }
      container mpls-template {
        presence "enable mpls-template";
        uses apply-group;
        uses apply-macro;
        leaf-list label-position {
          ordered-by user;
          type uint8;
        }
      }
      container mpls-ipv4-template {
        presence "enable mpls-ipv4-template";
        uses apply-group;
        uses apply-macro;
        leaf-list label-position {
          ordered-by user;
          type uint8;
        }
      }
    }
    container tunnel-observation {
      uses apply-group;
      uses apply-macro;
      leaf mpls-over-udp {
        type empty;
      }
      leaf ipv4 {
        type empty;
      }
      leaf ipv6 {
        type empty;
      }
    }
    container flow-key {
      uses apply-group;
      uses apply-macro;
      leaf flow-direction {
        type empty;
      }
      leaf vlan-id {
        type empty;
      }
      leaf output-interface {
        type empty;
      }
    }
  }

  grouping version9-template {
    leaf name {
      type string;
    }
    uses apply-group;
    uses apply-macro;
    leaf flow-active-timeout {
      type uint32;
    }
    leaf flow-inactive-timeout {
      type uint32;
    }
    container flow-key {
      uses apply-group;
      uses apply-macro;
      leaf flow-direction {
        type empty;
      }
      leaf vlan-id {
        type empty;
      }
    }
    leaf template-id {
      type uint32;
    }
    leaf option-template-id {
      type uint32;
    }
    leaf source-id {
      type uint32;
    }
    container nexthop-learning {
      presence "";
      uses apply-group;
      uses apply-macro;
      leaf enable-disable {
        type string;
      }
      leaf enable {
        type empty;
      }
    }
    container template-refresh-rate {
      presence "enable template-refresh-rate";
      uses apply-group;
      uses apply-macro;
      leaf packets {
        type uint32;
      }
      leaf seconds {
        type uint32;
      }
    }
    container option-refresh-rate {
      presence "enable option-refresh-rate";
      uses apply-group;
      uses apply-macro;
      leaf packets {
        type uint32;
      }
      leaf seconds {
        type uint32;
      }
    }
    choice choice-11 {
      container mpls-ipv4-template {
        presence "enable mpls-ipv4-template";
        uses apply-group;
        uses apply-macro;
        leaf-list label-position {
          ordered-by user;
          type uint32;
        }
      }
      container mpls-template {
        presence "enable mpls-template";
        uses apply-group;
        uses apply-macro;
        leaf-list label-position {
          ordered-by user;
          type uint32;
        }
      }
      container ipv6-template {
        presence "enable ipv6-template";
        uses apply-group;
        uses apply-macro;
      }
      container peer-as-billing-template {
        presence "enable peer-as-billing-template";
        uses apply-group;
        uses apply-macro;
      }
      container ipv4-template {
        presence "enable ipv4-template";
        uses apply-group;
        uses apply-macro;
        container nexthop-options {
          presence "enable nexthop-options";
          uses apply-group;
          uses apply-macro;
          choice choice-3 {
            container mpls {
              presence "enable mpls";
              uses apply-group;
              uses apply-macro;
              leaf-list label-position {
                ordered-by user;
                type uint32;
              }
            }
          }
        }
      }
    }
    container tunnel-observation {
      uses apply-group;
      uses apply-macro;
      leaf mpls-over-udp {
        type empty;
      }
      leaf ipv4 {
        type empty;
      }
      leaf ipv6 {
        type empty;
      }
    }
  }

  grouping virtual-interface-indications-object {
    uses apply-group;
    uses apply-macro;
    container virtual-interface-up {
      presence "enable virtual-interface-up";
      uses pgcp-virtual-interface-up-object;
    }
    container virtual-interface-down {
      presence "enable virtual-interface-down";
      uses pgcp-virtual-interface-down-object;
    }
  }

  grouping pgcp-virtual-interface-down-object {
    uses apply-group;
    uses apply-macro;
    leaf graceful {
      type string;
    }
    leaf administrative {
      type string;
    }
  }

  grouping pgcp-virtual-interface-up-object {
    uses apply-group;
    uses apply-macro;
    leaf warm {
      type string;
    }
    leaf cancel-graceful {
      type string;
    }
  }

  grouping vlan-type {
    leaf name {
      type key-attribute-string-type;
    }
    uses apply-group;
    uses apply-macro;
    leaf description {
      type string;
    }
    choice choice-5 {
      leaf vlan-id {
        type string;
      }
      leaf vlan-range {
        type string;
      }
      leaf-list vlan-id-list {
        type string;
      }
      container vlan-tags {
        presence "";
        leaf outer {
          type string;
        }
        leaf inner {
          type string;
        }
      }
    }
    leaf global-layer2-domainid {
      type uint32;
    }
    list global-layer2-domainid-range {
      key "name";
      ordered-by user;
      leaf name {
        type string;
      }
      uses apply-group;
      uses apply-macro;
    }
    list interface {
      key "name";
      ordered-by user;
      leaf name {
        type interface-name;
      }
      uses apply-group;
      uses apply-macro;
      leaf pvlan-trunk {
        type empty;
      }
      choice choice-5 {
        leaf ingress {
          type empty;
        }
        leaf egress {
          type empty;
        }
      }
      container mapping {
        uses apply-group;
        uses apply-macro;
        list mapping-data {
          key "name";
          uses vlan-mapping-type;
        }
        leaf policy {
          type empty;
        }
      }
    }
    container filter {
      uses apply-group;
      uses apply-macro;
      choice choice-3 {
        leaf input {
          type string;
        }
      }
      choice choice-4 {
        leaf output {
          type string;
        }
      }
    }
    leaf l3-interface {
      type interface-name;
    }
    container forwarding-options {
      uses juniper-ethernet-switching-forwarding-options;
    }
    container switch-options {
      uses juniper-protocols-vlan;
    }
    leaf domain-type {
      type string;
    }
    leaf no-irb-layer-2-copy {
      type empty;
    }
    leaf service-id {
      type uint32;
    }
    leaf mcae-mac-synchronize {
      type empty;
    }
    container mac-table-aging-time {
      uses mac-aging-time-config;
    }
    container mac-limit {
      presence "";
      leaf limit {
        mandatory true;
        type uint32;
      }
      leaf action {
        type string;
      }
    }
    container dot1q-tunneling {
      presence "enable dot1q-tunneling";
      uses apply-group;
      uses apply-macro;
      leaf-list customer-vlans {
        type string;
      }
      container layer2-protocol-tunneling {
        uses apply-group;
        uses apply-macro;
        list l2pt-protocol {
          key "name";
          uses l2pt-proto-entry;
        }
      }
    }
    leaf no-local-switching {
      type empty;
    }
    leaf isolation-id {
      type uint32;
    }
    leaf primary-vlan {
      type string;
    }
    leaf no-mac-learning {
      type empty;
    }
    container multicast-snooping-options {
      uses juniper-multicast-snooping-options;
    }
    leaf domain-id {
      type uint32;
    }
    leaf no-arp-suppression {
      type empty;
    }
    leaf mcae-mac-flush {
      type empty;
    }
    leaf private-vlan {
      type string;
    }
    leaf isolated-vlan {
      type string;
    }
    leaf-list community-vlans {
      type string;
      ordered-by user;
    }
    container vxlan {
      presence "";
      uses apply-group;
      uses apply-macro;
      leaf ovsdb-managed {
        type empty;
      }
      leaf vni {
        type uint32;
      }
      leaf multicast-group {
        type ipv4addr;
      }
      leaf encapsulate-inner-vlan {
        type empty;
      }
      leaf decapsulate-accept-inner-vlan {
        type empty;
      }
      leaf unreachable-vtep-aging-timer {
        units "seconds";
        type uint16;
      }
      leaf ingress-node-replication {
        type empty;
      }
    }
  }

  grouping vlan-policy {
    leaf name {
      type string;
    }
    uses apply-group;
    uses apply-macro;
    container policy {
      uses apply-group;
      uses apply-macro;
      leaf policy-name {
        type string;
      }
      choice choice-stateful {
        leaf stateful {
          type empty;
        }
        leaf stateless {
          type empty;
        }
      }
    }
  }

  grouping vlan-types {
    leaf name {
      type key-attribute-string-type;
    }
    uses apply-group;
    uses apply-macro;
    leaf description {
      type string;
    }
    choice choice-vlan-id {
      leaf vlan-id {
        type string;
      }
      leaf-list vlan-id-list {
        type string;
      }
      container vlan-tags {
        presence "";
        leaf outer {
          type string;
          mandatory true;
        }
        leaf inner {
          type string;
        }
      }
    }
    list interface {
      key "name";
      ordered-by user;
      leaf name {
        type string;
      }
      uses apply-group;
      uses apply-macro;
    }
    leaf l3-interface {
      type interface-unit;
    }
    leaf no-local-switching {
      type empty;
    }
    container forwarding-options {
      uses juniper-ethernet-switching-forwarding-options;
    }
    container multicast-snooping-options {
      uses juniper-multicast-snooping-options;
    }
    container switch-options {
      uses juniper-protocols-vlan;
    }
    leaf domain-type {
      type string;
    }
    leaf no-irb-layer-2-copy {
      type empty;
    }
    leaf service-id {
      type uint32;
    }
    leaf domain-id {
      type uint32;
    }
    leaf mcae-mac-synchronize {
      type empty;
    }
    container proxy-mac {
      uses apply-group;
      uses apply-macro;
      leaf irb {
        type empty;
      }
      leaf proxy-mac-address {
        type mac-unicast;
      }
    }
    leaf mcae-mac-flush {
      type empty;
    }
    leaf private-vlan {
      type string;
    }
    leaf isolated-vlan {
      type string;
    }
    leaf-list community-vlans {
      type string;
      ordered-by user;
    }
    container vxlan {
      presence "";
      uses apply-group;
      uses apply-macro;
      leaf ovsdb-managed {
        type empty;
      }
      leaf vni {
        mandatory true;
        type uint32;
      }
      leaf translation-vni {
        type uint32;
      }
      leaf multicast-group {
        type ipv4addr;
      }
      leaf encapsulate-inner-vlan {
        type empty;
      }
      leaf decapsulate-accept-inner-vlan {
        type empty;
      }
      leaf unreachable-vtep-aging-timer {
        units "seconds";
        type uint16;
      }
      leaf ingress-node-replication {
        type empty;
      }
      leaf-list static-remote-vtep-list {
        type ipaddr;
      }
    }
  }

  grouping juniper-ethernet-switching-forwarding-options {
    uses apply-group;
    uses apply-macro;
    container filter {
      uses apply-group;
      uses apply-macro;
      leaf input {
        type string;
      }
      leaf output {
        type string;
      }
    }
    container flood {
      uses apply-group;
      uses apply-macro;
      leaf input {
        type string;
      }
    }
    container dhcp-relay {
      uses jdhcp-relay-type;
    }
    container dhcp-security {
      presence "enable dhcp-security";
      uses jdhcp-security-type;
    }
    container fip-security {
      presence "enable fip-security";
      uses fip-security-type;
    }
  }

  grouping fip-security-type {
    uses apply-group;
    uses apply-macro;
    list interface {
      key "name";
      leaf name {
        type interface-name;
      }
      uses apply-group;
      uses apply-macro;
      leaf fcoe-trusted {
        type empty;
      }
      leaf no-fcoe-trusted {
        type empty;
      }
    }
    leaf fc-map {
      type string;
    }
    container examine-vn2vf {
      presence "enable examine-vn2vf";
      uses apply-group;
      uses apply-macro;
    }
    container examine-vn2vn {
      presence "enable examine-vn2vn";
      uses apply-group;
      uses apply-macro;
      leaf beacon-period {
        units "milliseconds";
        type uint32;
      }
    }
  }

  grouping jdhcp-security-type {
    uses apply-group;
    uses apply-macro;
    leaf no-dhcp-snooping {
      type empty;
    }
    leaf arp-inspection {
      type empty;
    }
    leaf ip-source-guard {
      type empty;
    }
    leaf no-dhcpv6-snooping {
      type empty;
    }
    leaf nd-inspection {
      type empty;
    }
    leaf ipv6-source-guard {
      type empty;
    }
    list group {
      key "name";
      ordered-by user;
      uses ds-group;
    }
    container option-82 {
      presence "enable option-82";
      uses security-option-82-type;
    }
  }

  grouping ds-group {
    leaf name {
      type key-attribute-string-type;
    }
    uses apply-group;
    uses apply-macro;
    container overrides {
      presence "enable overrides";
      uses ds-override-type;
    }
    list interface {
      key "name";
      leaf name {
        type interface-name;
      }
      uses apply-group;
      uses apply-macro;
      list static-ip {
        key "name";
        ordered-by user;
        uses ip-mac-static;
      }
      list static-ipv6 {
        key "name";
        ordered-by user;
        uses ipv6-mac-static;
      }
    }
  }

  grouping ds-override-type {
    uses apply-group;
    uses apply-macro;
    leaf trusted {
      type empty;
    }
    leaf untrusted {
      type empty;
    }
    leaf no-option82 {
      type empty;
    }
    leaf no-option37 {
      type empty;
    }
  }

  grouping ip-mac-static {
    leaf name {
      type ipaddr;
    }
    uses apply-group;
    uses apply-macro;
    leaf mac {
      type mac-addr;
    }
  }

  grouping ipv6-mac-static {
    leaf name {
      type ipv6addr;
    }
    uses apply-group;
    uses apply-macro;
    leaf mac {
      type mac-addr;
    }
  }

  grouping juniper-protocols-vlan {
    uses apply-group;
    uses apply-macro;
    container mac-table-size {
      uses apply-group;
      uses apply-macro;
      leaf limit {
        type uint32;
      }
      leaf packet-action {
        type string;
      }
    }
    container interface-mac-limit {
      uses apply-group;
      uses apply-macro;
      leaf limit {
        type uint32;
      }
      leaf packet-action {
        type string;
      }
    }
    container mac-move-limit {
      presence "";
      leaf limit {
        type uint32;
      }
      leaf packet-action {
        type string;
      }
    }
    leaf mac-table-aging-time {
      units "seconds";
      type uint32;
    }
    leaf no-mac-learning {
      type empty;
    }
    leaf mac-statistics {
      type empty;
    }
    list interface {
      key "name";
      ordered-by user;
      leaf name {
        type interface-name;
      }
      uses apply-group;
      uses apply-macro;
      container interface-mac-limit {
        uses apply-group;
        uses apply-macro;
        leaf limit {
          type uint32;
        }
        leaf packet-action {
          type string;
        }
      }
      leaf remote-site-id {
        type uint32;
      }
      list static-mac {
        key "name";
        ordered-by user;
        leaf name {
          type mac-addr;
        }
        uses apply-group;
        uses apply-macro;
        list vlan-id {
          key "name";
          ordered-by user;
          leaf name {
            type key-attribute-ulong-type;
          }
          uses apply-group;
          uses apply-macro;
        }
      }
      leaf no-mac-learning {
        type empty;
      }
      leaf description {
        type string;
      }
    }
  }

  grouping security-option-82-type {
    uses apply-group;
    uses apply-macro;
    container circuit-id {
      presence "enable circuit-id";
      uses apply-group;
      uses apply-macro;
      container prefix {
        uses apply-group;
        uses apply-macro;
        leaf host-name {
          type empty;
        }
        leaf logical-system-name {
          type empty;
        }
        leaf routing-instance-name {
          type empty;
        }
      }
      leaf use-interface-description {
        type string;
      }
      leaf use-vlan-id {
        type empty;
      }
    }
    container remote-id {
      presence "enable remote-id";
      uses apply-group;
      uses apply-macro;
      leaf host-name {
        type empty;
      }
      leaf use-interface-description {
        type string;
      }
      leaf use-string {
        type string;
      }
    }
    container vendor-id {
      presence "enable vendor-id";
      uses apply-group;
      uses apply-macro;
      leaf use-string {
        type string;
      }
    }
  }

  grouping vlan-map {
    uses apply-group;
    uses apply-macro;
    choice choice-3 {
      leaf push {
        type empty;
      }
      leaf swap {
        type empty;
      }
      leaf pop {
        type empty;
      }
      leaf push-push {
        type empty;
      }
      leaf swap-push {
        type empty;
      }
      leaf swap-swap {
        type empty;
      }
      leaf pop-swap {
        type empty;
      }
      leaf pop-pop {
        type empty;
      }
    }
    leaf tag-protocol-id {
      type string;
    }
    leaf inner-tag-protocol-id {
      type string;
    }
    leaf vlan-id {
      type string;
    }
    leaf inner-vlan-id {
      type uint32;
    }
  }

  grouping l2pt-proto-entry {
    leaf name {
      type string;
    }
    uses apply-group;
    uses apply-macro;
    leaf drop-threshold {
      type uint32;
    }
    leaf shutdown-threshold {
      type uint32;
    }
  }

  grouping vlan-mapping-type {
    leaf name {
      type string;
    }
    uses apply-group;
    uses apply-macro;
    choice choice-3 {
      leaf push {
        type empty;
      }
      leaf swap {
        type empty;
      }
    }
  }

  grouping vpls-filter {
    leaf name {
      type string;
    }
    uses apply-group;
    uses apply-macro;
    leaf-list accounting-profile {
      type string;
      ordered-by user;
    }
    leaf interface-specific {
      type empty;
    }
    leaf physical-interface-filter {
      type empty;
    }
    leaf instance-shared {
      type empty;
    }
    list term {
      key "name";
      ordered-by user;
      leaf name {
        type string;
      }
      uses apply-group;
      uses apply-macro;
      leaf filter {
        type string;
      }
      container from {
        uses apply-group;
        uses apply-macro;
        choice choice-3 {
          leaf-list interface-group {
            type string;
            ordered-by user;
          }
          leaf-list interface-group-except {
            type string;
            ordered-by user;
          }
        }
        choice choice-4 {
          leaf-list ether-type {
            ordered-by user;
            type string;
          }
          leaf-list ether-type-except {
            ordered-by user;
            type string;
          }
        }
        choice choice-5 {
          leaf-list vlan-ether-type {
            ordered-by user;
            type string;
          }
          leaf-list vlan-ether-type-except {
            ordered-by user;
            type string;
          }
        }
        list destination-mac-address {
          key "name";
          ordered-by user;
          uses firewall-mac-addr-object;
        }
        list source-mac-address {
          key "name";
          ordered-by user;
          uses firewall-mac-addr-object;
        }
        choice choice-10 {
          leaf-list forwarding-class {
            type string;
            ordered-by user;
          }
          leaf-list forwarding-class-except {
            type string;
            ordered-by user;
          }
        }
        choice choice-11 {
          leaf-list loss-priority {
            ordered-by user;
            type string;
          }
          leaf-list loss-priority-except {
            ordered-by user;
            type string;
          }
        }
        choice choice-12 {
          leaf-list learn-vlan-id {
            type string;
            ordered-by user;
          }
          leaf-list learn-vlan-id-except {
            type string;
            ordered-by user;
          }
        }
        choice choice-13 {
          leaf-list learn-vlan-1p-priority {
            type uint32;
            ordered-by user;
          }
          leaf-list learn-vlan-1p-priority-except {
            type uint32;
            ordered-by user;
          }
        }
        choice choice-14 {
          leaf-list user-vlan-id {
            type string;
            ordered-by user;
          }
          leaf-list user-vlan-id-except {
            type string;
            ordered-by user;
          }
        }
        choice choice-15 {
          leaf-list user-vlan-1p-priority {
            type uint32;
            ordered-by user;
          }
          leaf-list user-vlan-1p-priority-except {
            type uint32;
            ordered-by user;
          }
        }
        choice choice-16 {
          leaf-list learn-vlan-dei {
            type uint32;
            ordered-by user;
          }
          leaf-list learn-vlan-dei-except {
            type uint32;
            ordered-by user;
          }
        }
        choice choice-17 {
          leaf-list traffic-type {
            ordered-by user;
            type string;
          }
          leaf-list traffic-type-except {
            ordered-by user;
            type string;
          }
        }
        list ip-source-address {
          key "name";
          ordered-by user;
          uses firewall-addr-object;
        }
        list ip-destination-address {
          key "name";
          ordered-by user;
          uses firewall-addr-object;
        }
        list ip-address {
          key "name";
          ordered-by user;
          uses firewall-addr-object;
        }
        choice choice-24 {
          leaf-list ip-protocol {
            ordered-by user;
            type string;
          }
          leaf-list ip-protocol-except {
            ordered-by user;
            type string;
          }
        }
        choice choice-25 {
          leaf-list dscp {
            ordered-by user;
            type string;
          }
          leaf-list dscp-except {
            ordered-by user;
            type string;
          }
        }
        choice choice-26 {
          leaf-list ip-precedence {
            ordered-by user;
            type string;
          }
          leaf-list ip-precedence-except {
            ordered-by user;
            type string;
          }
        }
        choice choice-27 {
          leaf-list source-port {
            ordered-by user;
            type string;
          }
          leaf-list source-port-except {
            ordered-by user;
            type string;
          }
        }
        choice choice-28 {
          leaf-list destination-port {
            ordered-by user;
            type string;
          }
          leaf-list destination-port-except {
            ordered-by user;
            type string;
          }
        }
        choice choice-29 {
          leaf-list port {
            ordered-by user;
            type string;
          }
          leaf-list port-except {
            ordered-by user;
            type string;
          }
        }
        leaf tcp-flags {
          type string;
        }
        choice choice-32 {
          leaf-list icmp-type {
            ordered-by user;
            type string;
          }
          leaf-list icmp-type-except {
            ordered-by user;
            type string;
          }
        }
        choice choice-33 {
          leaf-list icmp-code {
            ordered-by user;
            type string;
          }
          leaf-list icmp-code-except {
            ordered-by user;
            type string;
          }
        }
        list interface {
          key "name";
          ordered-by user;
          uses match-interface-object;
        }
        list interface-set {
          key "name";
          ordered-by user;
          uses match-interface-set-object;
        }
        list source-prefix-list {
          key "name";
          ordered-by user;
          uses firewall-prefix-list;
        }
        list destination-prefix-list {
          key "name";
          ordered-by user;
          uses firewall-prefix-list;
        }
        list prefix-list {
          key "name";
          ordered-by user;
          uses firewall-prefix-list;
        }
        list ipv6-destination-address {
          key "name";
          ordered-by user;
          uses firewall_addr6_object;
        }
        list ipv6-source-address {
          key "name";
          ordered-by user;
          uses firewall_addr6_object;
        }
        list ipv6-address {
          key "name";
          ordered-by user;
          uses firewall_addr6_object;
        }
        choice ipv6-next-header_choice {
          case case_1 {
            leaf-list ipv6-next-header {
              ordered-by user;
              type string;
            }
          }
          case case_2 {
            leaf-list ipv6-next-header-except {
              ordered-by user;
              type string;
            }
          }
        }
        choice ipv6-payload-protocol_choice {
          case case_1 {
            leaf-list ipv6-payload-protocol {
              ordered-by user;
              type string;
            }
          }
          case case_2 {
            leaf-list ipv6-payload-protocol-except {
              ordered-by user;
              type string;
            }
          }
        }
        choice ipv6-traffic-class_choice {
          case case_1 {
            leaf-list ipv6-traffic-class {
              ordered-by user;
              type string;
            }
          }
          case case_2 {
            leaf-list ipv6-traffic-class-except {
              ordered-by user;
              type string;
            }
          }
        }
        list ipv6-source-prefix-list {
          key "name";
          ordered-by user;
          uses firewall-prefix-list;
        }
        list ipv6-destination-prefix-list {
          key "name";
          ordered-by user;
          uses firewall-prefix-list;
        }
        list ipv6-prefix-list {
          key "name";
          ordered-by user;
          uses firewall-prefix-list;
        }
        choice flex-mask_choice {
          case case_1 {
            container flexible-match-mask {
              presence "enable flexible-match-mask";
              uses match_L2_flexible_mask;
            }
          }
        }
        choice flex-range_choice {
          case case_1 {
            container flexible-match-range {
              presence "enable flexible-match-range";
              uses match_L2_flexible_range;
            }
          }
        }
        choice policy-map_choice {
          case case_1 {
            leaf-list policy-map {
              ordered-by user;
              type string;
            }
          }
          case case_2 {
            leaf-list policy-map-except {
              ordered-by user;
              type string;
            }
          }
        }
        choice slice_choice {
          case case_1 {
            leaf-list slice {
              ordered-by user;
              type string;
            }
          }
          case case_2 {
            leaf-list slice-except {
              ordered-by user;
              type string;
            }
          }
        }
      }
      container then {
        uses apply-group;
        uses apply-macro;
        choice choice-3 {
          leaf policer {
            type string;
          }
          container three-color-policer {
            uses apply-group;
            uses apply-macro;
            choice choice-3 {
              leaf single-rate {
                type string;
              }
              leaf two-rate {
                type string;
              }
            }
          }
          leaf hierarchical-policer {
            type string;
          }
        }
        choice choice-clear-policy-map {
          leaf clear-policy-map {
            type empty;
          }
          leaf policy-map {
            type string;
          }
        }
        leaf count {
          type string;
        }
        leaf loss-priority {
          type string;
        }
        leaf forwarding-class {
          type string;
        }
        choice choice-10 {
          leaf accept {
            type empty;
          }
          leaf discard {
            type empty;
          }
          leaf next {
            type string;
          }
        }
        leaf port-mirror-instance {
          type string;
        }
        leaf port-mirror {
          type empty;
        }
        leaf next-hop-group {
          type string;
        }
        leaf sample {
          type empty;
        }
        leaf log {
          type empty;
        }
        leaf syslog {
          type empty;
        }
      }
    }
  }

  grouping vrrp-group {
    leaf name {
      type string;
    }
    uses apply-group;
    uses apply-macro;
    choice choice-3 {
      leaf-list virtual-address {
        type ipv4addr;
        ordered-by user;
      }
      leaf-list virtual-inet6-address {
        type ipv6addr;
        ordered-by user;
      }
    }
    leaf virtual-link-local-address {
      type ipv6addr;
    }
    leaf priority {
      type uint32;
    }
    leaf preferred {
      type empty;
    }
    choice choice-8 {
      leaf advertise-interval {
        type uint32;
      }
      leaf fast-interval {
        type uint32;
      }
      leaf inet6-advertise-interval {
        type uint32;
      }
    }
    choice choice-9 {
      container preempt {
        presence "enable preempt";
        uses apply-group;
        uses apply-macro;
        leaf hold-time {
          type uint32;
        }
      }
      leaf no-preempt {
        type empty;
      }
    }
    choice choice-10 {
      leaf accept-data {
        type empty;
      }
      leaf no-accept-data {
        type empty;
      }
    }
    leaf authentication-type {
      type string;
    }
    leaf authentication-key {
      type unreadable;
    }
    container track {
      uses apply-group;
      uses apply-macro;
      leaf priority-hold-time {
        type uint32;
      }
      list interface {
        key "name";
        ordered-by user;
        leaf name {
          type interface-unit;
        }
        uses apply-group;
        uses apply-macro;
        list bandwidth-threshold {
          key "name";
          leaf name {
            type string;
          }
          leaf priority-cost {
            type uint32;
          }
        }
        leaf priority-cost {
          type uint32;
        }
      }
      list route {
        key "route_address routing-instance";
        ordered-by user;
        leaf route_address {
          type ipprefix-mandatory;
        }
        leaf routing-instance {
          type string;
        }
        leaf priority-cost {
          type uint32;
        }
      }
    }
    container vrrp-inherit-from {
      presence "";
      uses apply-group;
      uses apply-macro;
      leaf active-interface {
        type interface-unit;
      }
      leaf active-group {
        type uint32;
      }
    }
    leaf advertisements-threshold {
      type uint32;
    }
  }

  grouping webfilter-feature {
    uses apply-group;
    uses apply-macro;
    leaf url-whitelist {
      type string;
    }
    leaf url-blacklist {
      type string;
    }
    leaf type {
      type string;
    }
    container traceoptions {
      uses web-filtering-traceoptions;
    }
    container surf-control-integrated {
      uses surf-control-integrated-type;
    }
    container websense-redirect {
      uses websense-type;
    }
    container juniper-local {
      uses juniper-local-type;
    }
    container juniper-enhanced {
      uses juniper-enhanced-type;
    }
  }

  grouping juniper-enhanced-type {
    uses apply-group;
    uses apply-macro;
    container cache {
      presence "enable cache";
      uses apply-group;
      uses apply-macro;
      leaf timeout {
        units "minutes";
        type uint32;
      }
      leaf size {
        type string;
        units "kilobytes";
      }
    }
    container server {
      presence "enable server";
      uses juniper-enhanced-server;
    }
    list profile {
      key "name";
      ordered-by user;
      leaf name {
        type key-attribute-string-type;
      }
      uses apply-group;
      uses apply-macro;
      list category {
        key "name";
        ordered-by user;
        uses juniper-enhanced-category-type;
      }
      container site-reputation-action {
        presence "enable site-reputation-action";
        uses juniper-enhanced-site-reputation-setting;
      }
      leaf default {
        type string;
      }
      leaf custom-block-message {
        type string;
      }
      leaf quarantine-custom-message {
        type string;
      }
      container fallback-settings {
        presence "enable fallback-settings";
        uses web-filtering-fallback-setting;
      }
      leaf timeout {
        units "seconds";
        type uint32;
      }
      leaf no-safe-search {
        type empty;
      }
      container block-message {
        presence "enable block-message";
        uses web-filtering-block-message;
      }
      container quarantine-message {
        presence "enable quarantine-message";
        uses web-filtering-quarantine-message;
      }
    }
  }

  grouping juniper-enhanced-category-type {
    leaf name {
      type key-attribute-string-type;
    }
    uses apply-group;
    uses apply-macro;
    leaf action {
      type string;
    }
    container reputation-action {
      presence "enable reputation-action";
      uses juniper-enhanced-site-reputation-setting;
    }
  }

  grouping juniper-enhanced-server {
    uses apply-group;
    uses apply-macro;
    leaf host {
      type string;
    }
    leaf port {
      type uint32;
    }
  }

  grouping juniper-enhanced-site-reputation-setting {
    uses apply-group;
    uses apply-macro;
    leaf very-safe {
      type string;
    }
    leaf moderately-safe {
      type string;
    }
    leaf fairly-safe {
      type string;
    }
    leaf suspicious {
      type string;
    }
    leaf harmful {
      type string;
    }
  }

  grouping juniper-local-type {
    uses apply-group;
    uses apply-macro;
    list profile {
      key "name";
      ordered-by user;
      leaf name {
        type key-attribute-string-type;
      }
      uses apply-group;
      uses apply-macro;
      leaf default {
        type string;
      }
      leaf custom-block-message {
        type string;
      }
      container fallback-settings {
        presence "enable fallback-settings";
        uses web-filtering-fallback-setting;
      }
      leaf timeout {
        type uint32;
      }
    }
  }

  grouping surf-control-integrated-type {
    uses apply-group;
    uses apply-macro;
    container cache {
      presence "enable cache";
      uses apply-group;
      uses apply-macro;
      leaf timeout {
        type uint32;
      }
      leaf size {
        type string;
      }
    }
    container server {
      presence "enable server";
      uses server;
    }
    list profile {
      key "name";
      ordered-by user;
      leaf name {
        type key-attribute-string-type;
      }
      uses apply-group;
      uses apply-macro;
      list category {
        key "name";
        ordered-by user;
        uses surf-control-integrated-category-type;
      }
      leaf default {
        type string;
      }
      leaf custom-block-message {
        type string;
      }
      container fallback-settings {
        presence "enable fallback-settings";
        uses web-filtering-fallback-setting;
      }
      leaf timeout {
        type uint32;
      }
    }
  }

  grouping server {
    uses apply-group;
    uses apply-macro;
    leaf host {
      type string;
    }
    leaf port {
      type uint32;
    }
  }

  grouping surf-control-integrated-category-type {
    leaf name {
      type key-attribute-string-type;
    }
    uses apply-group;
    uses apply-macro;
    leaf action {
      type string;
    }
  }

  grouping web-filtering-block-message {
    uses apply-group;
    uses apply-macro;
    leaf type {
      type string;
    }
    leaf url {
      type string;
    }
  }

  grouping web-filtering-fallback-setting {
    uses apply-group;
    uses apply-macro;
    leaf default {
      type string;
    }
    leaf server-connectivity {
      type string;
    }
    leaf timeout {
      type string;
    }
    leaf too-many-requests {
      type string;
    }
  }

  grouping web-filtering-quarantine-message {
    uses apply-group;
    uses apply-macro;
    leaf type {
      type string;
    }
    leaf url {
      type string;
    }
  }

  grouping web-filtering-traceoptions {
    uses apply-group;
    uses apply-macro;
    list flag {
      key "name";
      ordered-by user;
      leaf name {
        type string;
      }
    }
  }

  grouping websense-type {
    uses apply-group;
    uses apply-macro;
    list profile {
      key "name";
      ordered-by user;
      leaf name {
        type key-attribute-string-type;
      }
      uses apply-group;
      uses apply-macro;
      container server {
        presence "enable server";
        uses server;
      }
      leaf custom-block-message {
        type string;
      }
      container fallback-settings {
        presence "enable fallback-settings";
        uses web-filtering-fallback-setting;
      }
      leaf timeout {
        type uint32;
      }
      leaf sockets {
        type uint32;
      }
      leaf account {
        type string;
      }
    }
  }

  grouping wildcard-address-type {
    leaf name {
      type key-attribute-string-type;
    }
    uses apply-group;
    uses apply-macro;
  }

  grouping wpa-enterprise {
    uses apply-group;
    uses apply-macro;
    container wpa-version {
      uses wpa-version;
    }
    container cipher-suites {
      uses cipher-suites;
    }
    leaf pre-authenticate {
      type empty;
    }
    leaf radius-server {
      type ipaddr;
    }
    leaf radius-key {
      type string;
    }
    leaf broadcast-key-refresh-rate {
      type int32;
    }
    leaf session-key-refresh-rate {
      type int32;
    }
  }

  grouping cipher-suites {
    uses apply-group;
    uses apply-macro;
    choice choice-3 {
      leaf tkip {
        type empty;
      }
      leaf ccmp {
        type empty;
      }
      leaf both {
        type empty;
      }
    }
  }

  grouping wpa-personal {
    uses apply-group;
    uses apply-macro;
    container wpa-version {
      uses wpa-version;
    }
    container cipher-suites {
      uses cipher-suites;
    }
    leaf key {
      type string;
    }
    leaf broadcast-key-refresh-rate {
      type int32;
    }
  }

  grouping wpa-version {
    uses apply-group;
    uses apply-macro;
    choice choice-3 {
      leaf v1 {
        type empty;
      }
      leaf v2 {
        type empty;
      }
      leaf both {
        type empty;
      }
    }
  }

  grouping zone-interface-list-type {
    leaf name {
      type interface-name;
    }
    uses apply-group;
    uses apply-macro;
    container host-inbound-traffic {
      uses interface-host-inbound-traffic-t;
    }
  }

  grouping interface-host-inbound-traffic-t {
    uses apply-group;
    uses apply-macro;
    list system-services {
      key "name";
      ordered-by user;
      uses interface-system-services-object-type;
    }
    list protocols {
      key "name";
      ordered-by user;
      uses host-inbound-protocols-object-type;
    }
  }

  grouping host-inbound-protocols-object-type {
    leaf name {
      type string;
    }
    uses apply-group;
    uses apply-macro;
    leaf except {
      type empty;
    }
  }

  grouping interface-system-services-object-type {
    leaf name {
      type string;
    }
    uses apply-group;
    uses apply-macro;
    leaf except {
      type empty;
    }
  }

  grouping zone-host-inbound-traffic-t {
    uses apply-group;
    uses apply-macro;
    list system-services {
      key "name";
      ordered-by user;
      uses zone-system-services-object-type;
    }
    list protocols {
      key "name";
      ordered-by user;
      uses host-inbound-protocols-object-type;
    }
  }

  grouping zone-system-services-object-type {
    leaf name {
      type string;
    }
    uses apply-group;
    uses apply-macro;
    leaf except {
      type empty;
    }
  }

  grouping undocumented-redundancy-peer {
    container redundancy-peer {
      leaf ipaddress {
        type ipaddr;
      }
    }
  }

  grouping undocumented-disable-4byte-as {
    leaf minimum-hold-time {
      type uint32;
    }
    leaf disable-4byte-as {
      type empty;
    }
  }

  grouping undocumented-traceoptions {
    container traceoptions {
      container file {
        leaf filename {
          type string;
        }
        leaf size {
          type string;
        }
        leaf files {
          type uint32;
        }
        leaf world-readable {
          type empty;
        }
        leaf no-world-readable {
          type empty;
        }
      }
      leaf level {
        type string;
      }
      list flag {
        key "name";
        ordered-by user;
        leaf name {
          type string;
        }
      }
    }
  }
}
