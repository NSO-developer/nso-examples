module juniper-junos-netsim-nc {
  yang-version 1.1;
  namespace "http://tail-f.com/ns/ned-id/juniper-junos-netsim-nc";
  prefix juniper-junos-netsim-nc;

  import tailf-common {
    prefix tailf;
  }

  import tailf-ncs-ned {
    prefix ned;
  }

  identity juniper-junos-netsim-nc {
    tailf:abstract;
    base ned:netconf-ned-id;
  }
}
