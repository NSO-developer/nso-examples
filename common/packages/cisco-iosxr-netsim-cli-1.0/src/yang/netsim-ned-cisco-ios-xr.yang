module netsim-ned-cisco-ios-xr {
  namespace "http://tail-f.com/ned/cisco-ios-xr";
  prefix cisco-ios-xr;

  import tailf-common {
    prefix tailf;
  }
  import ietf-yang-types {
    prefix yang;
  }
  import ietf-inet-types {
    prefix inet;
  }

  revision 2025-03-11;

  typedef ifname {
    type string;
  }

  typedef month-type {
    type enumeration {
      enum january;
      enum february;
      enum march;
      enum april;
      enum may;
      enum june;
      enum july;
      enum august;
      enum september;
      enum october;
      enum november;
      enum december;
    }
  }

  typedef percentage-type {
    type uint8;
  }

  typedef asn-ip-type {
    type string;
  }

  typedef ipv4-prefix {
    type tailf:ipv4-address-and-prefix-length;
  }

  typedef task-type {
    type string;
  }

  typedef severity-type {
    type enumeration {
      enum alerts;
      enum critical;
      enum debugging;
      enum emergencies;
      enum errors;
      enum info;
      enum informational;
      enum notifications;
      enum warning;
      enum warnings;
      enum disable;
      enum error;
    }
  }

  typedef dscp-type {
    type union {
      type uint8;
      type enumeration {
        enum af11 {
          tailf:code-name "dscp_af11";
        }
        enum af12 {
          tailf:code-name "dscp_af12";
        }
        enum af13 {
          tailf:code-name "dscp_af13";
        }
        enum af21 {
          tailf:code-name "dscp_af21";
        }
        enum af22 {
          tailf:code-name "dscp_af22";
        }
        enum af23 {
          tailf:code-name "dscp_af23";
        }
        enum af31 {
          tailf:code-name "dscp_af31";
        }
        enum af32 {
          tailf:code-name "dscp_af32";
        }
        enum af33 {
          tailf:code-name "dscp_af33";
        }
        enum af41 {
          tailf:code-name "dscp_af41";
        }
        enum af42 {
          tailf:code-name "dscp_af42";
        }
        enum af43 {
          tailf:code-name "dscp_af43";
        }
        enum cs1 {
          tailf:code-name "dscp_cs1";
        }
        enum cs2 {
          tailf:code-name "dscp_cs2";
        }
        enum cs3 {
          tailf:code-name "dscp_cs3";
        }
        enum cs4 {
          tailf:code-name "dscp_cs4";
        }
        enum cs5 {
          tailf:code-name "dscp_cs5";
        }
        enum cs6 {
          tailf:code-name "dscp_cs6";
        }
        enum cs7 {
          tailf:code-name "dscp_cs7";
        }
        enum default {
          tailf:code-name "dscp_default";
        }
        enum ef {
          tailf:code-name "dscp_ef";
        }
      }
    }
  }

  typedef precedence-type {
    type union {
      type uint8;
      type enumeration {
        enum routine {
          value 0;
        }
        enum priority {
          value 1;
        }
        enum immediate {
          value 2;
        }
        enum flash {
          value 3;
        }
        enum flash-override {
          value 4;
        }
        enum critical {
          value 5;
        }
        enum internet {
          value 6;
        }
        enum network {
          value 7;
        }
      }
    }
  }

  typedef police-burst-units-type {
    type enumeration {
      enum bytes;
      enum gbytes;
      enum kbytes;
      enum mbytes;
      enum ms;
      enum packets;
      enum us;
      enum cells;
    }
  }

  typedef police-rate-units-type {
    type enumeration {
      enum bps;
      enum gbps;
      enum kbps;
      enum mbps;
      enum pps;
    }
  }

  typedef ospf-area-type {
    type union {
      type uint32;
      type inet:ipv4-address;
    }
  }

  typedef operator-type {
    type enumeration {
      enum eq;
      enum ge;
      enum gt;
      enum le;
      enum lt;
      enum ne;
      enum rg;
    }
  }

  typedef vrf-type {
    type union {
      type string;
      type enumeration {
        enum default;
      }
    }
  }

  typedef aaa-group-type {
    type union {
      type string;
      type enumeration {
        enum ldap;
        enum radius;
        enum tacacs+;
      }
    }
  }

  typedef if-eth-oam-action-type {
    type enumeration {
      enum disable;
      enum efd;
      enum log;
      enum error-disable-interface;
    }
  }

  typedef iosxr-ipv6-address {
    type string;
  }

  typedef SNMP_TARGET_MIB_SnmpTagValue {
    type string;
  }

  typedef SNMP_FRAMEWORK_MIB_SnmpSecurityModel {
    type int32;
  }

  typedef SNMP_FRAMEWORK_MIB_SnmpEngineID {
    type tailf:hex-list;
  }

  typedef SNMPv2_TC_DisplayString {
    type string;
  }

  typedef SNMPv2_TC_TDomain {
    type yang:object-identifier;
  }

  typedef SNMPv2_TC_TAddress {
    type tailf:octet-list;
  }

  typedef SNMPv2_TC_AutonomousType {
    type yang:object-identifier;
  }

  typedef SNMPv2_TC_RowPointer {
    type yang:object-identifier;
  }

  typedef UDPIPv4TAddress {
    type tailf:octet-list;
  }

  typedef UDPIPv6TAddress {
    type tailf:octet-list;
  }

  typedef UDPXTAddress {
    type tailf:octet-list;
  }

  typedef UDPTAddress {
    type union {
      type UDPIPv4TAddress;
      type UDPIPv6TAddress;
      type UDPXTAddress;
    }
  }

  typedef EmptyOctetList {
    type tailf:octet-list;
  }

  typedef UDPTMask {
    type union {
      type UDPTAddress;
      type EmptyOctetList;
    }
  }

  typedef snmpTargetAddrEngineIDType {
    type tailf:hex-list;
  }

  typedef SnmpTagValue {
    type string;
  }

  typedef SnmpTagList {
    type string;
  }

  typedef snmpTargetAddrNameType {
    type string;
  }

  typedef snmpTargetAddrRetryCountType {
    type int32;
  }

  typedef snmpTargetAddrParamsType {
    type string;
  }

  typedef snmpTargetParamsNameType {
    type string;
  }

  typedef snmpTargetParamsSecurityModelType {
    type int32;
  }

  typedef SNMP_FRAMEWORK_MIB_SnmpAdminString {
    type string;
  }

  typedef SNMP_FRAMEWORK_MIB_SnmpMessageProcessingModel {
    type int32;
  }

  typedef SNMP_FRAMEWORK_MIB_SnmpSecurityLevel {
    type enumeration {
      enum noAuthNoPriv {
        value 1;
      }
      enum authNoPriv {
        value 2;
      }
      enum authPriv {
        value 3;
      }
    }
  }

  typedef SNMPv2_TC_TimeInterval {
    type int32;
  }

  typedef SNMPv2_TC_StorageType {
    type enumeration {
      enum other {
        value 1;
      }
      enum volatile {
        value 2;
      }
      enum nonVolatile {
        value 3;
      }
      enum permanent {
        value 4;
      }
      enum readOnly {
        value 5;
      }
    }
  }

  typedef snmpCommunityIndexType {
    type string;
  }

  typedef snmpCommunityNameType {
    type string;
  }

  typedef snmpCommunitySecurityNameType {
    type string;
  }

  typedef snmpCommunityContextNameType {
    type string;
  }

  typedef snmpTargetAddrTMaskType {
    type tailf:hex-list;
  }

  typedef snmpTargetAddrMMSType {
    type int32;
  }

  typedef snmpNotifyNameType {
    type string;
  }

  typedef snmpNotifyTypeType {
    type enumeration {
      enum trap {
        value 1;
      }
      enum inform {
        value 2;
      }
    }
  }

  typedef KeyChange {
    type tailf:hex-list;
  }

  typedef usmUserNameType {
    type string;
  }

  typedef usmUserPublicType {
    type tailf:hex-list;
  }

  typedef vacmContextNameType {
    type string;
  }

  typedef vacmSecurityModelType {
    type int32;
  }

  typedef vacmSecurityNameType {
    type string;
  }

  typedef vacmGroupNameType {
    type string;
  }

  typedef vacmAccessContextPrefixType {
    type string;
  }

  typedef vacmAccessContextMatchType {
    type enumeration {
      enum exact {
        value 1;
      }
      enum prefix {
        value 2;
      }
    }
  }

  typedef vacmAccessReadViewNameType {
    type string;
  }

  typedef vacmAccessWriteViewNameType {
    type string;
  }

  typedef vacmAccessNotifyViewNameType {
    type string;
  }

  typedef vacmViewTreeFamilyViewNameType {
    type string;
  }

  typedef vacmViewTreeFamilyMaskType {
    type tailf:hex-list;
  }

  typedef vacmViewTreeFamilyTypeType {
    type enumeration {
      enum included {
        value 1;
      }
      enum excluded {
        value 2;
      }
    }
  }

  typedef sysContactType {
    type SNMPv2_TC_DisplayString;
  }

  typedef sysNameType {
    type SNMPv2_TC_DisplayString;
  }

  typedef sysLocationType {
    type SNMPv2_TC_DisplayString;
  }

  typedef snmpEnableAuthenTrapsType {
    type enumeration {
      enum enabled {
        value 1;
      }
      enum disabled {
        value 2;
      }
    }
  }

  typedef facility-type {
    type union {
      type enumeration {
        enum local0;
        enum local1;
        enum local2;
        enum local3;
        enum local4;
        enum local5;
        enum local6;
        enum local7;
      }
      type string;
    }
  }

  grouping description-grouping {
    leaf description {
      tailf:cli-multi-value;
      type string;
    }
  }

  grouping password-grouping {
    leaf type {
      tailf:cli-drop-node-name;
      tailf:cli-optional-in-sequence;
      type enumeration {
        enum clear;
        enum encrypted;
      }
    }
    leaf secret {
      tailf:cli-drop-node-name;
      type string;
    }
  }

  grouping key-grouping {
    leaf encryption {
      tailf:cli-drop-node-name;
      tailf:cli-optional-in-sequence;
      type enumeration {
        enum 0;
        enum 7;
        enum 6;
        enum Encrypt6;
      }
    }
    leaf key {
      tailf:cli-drop-node-name;
      type string;
    }
  }

  grouping banner-grouping {
    leaf start-marker {
      tailf:cli-drop-node-name;
      type string;
    }
    leaf message {
      tailf:cli-drop-node-name;
      type string;
    }
    leaf end-marker {
      tailf:cli-drop-node-name;
      must '../end-marker = ../start-marker';
      type string;
    }
  }

  grouping apply-group-grouping {
    leaf-list apply-group {
      tailf:cli-flat-list-syntax;
      type string;
    }
    leaf exclude-group {
      type string;
    }
  }

  grouping exclude-item-grouping {
    list exclude-item {
      tailf:cli-suppress-mode;
      tailf:cli-delete-when-empty;
      key "name";
      leaf name {
        tailf:cli-multi-word-key;
        type string;
      }
    }
  }

  grouping vrf-af-route-target-grouping {
    list address-list {
      tailf:cli-drop-node-name;
      tailf:cli-suppress-mode;
      tailf:cli-delete-when-empty;
      key "name";
      leaf name {
        type string;
      }
    }
    list stitching-address-list {
      tailf:cli-drop-node-name;
      tailf:cli-suppress-mode;
      tailf:cli-delete-when-empty;
      key "name";
      leaf name {
        type string;
      }
      leaf stitching {
        type empty;
      }
    }
  }

  grouping router-af-redistribute-grouping {
    leaf metric {
      type uint32;
    }
    leaf route-policy {
      type string;
    }
  }

  grouping router-ospf-af-redistribute-grouping {
    leaf metric {
      type union {
        type uint32;
        type enumeration {
          enum use-rib-metric;
        }
      }
    }
    leaf tag {
      type uint32;
    }
    leaf metric-type {
      type enumeration {
        enum 1;
        enum 2;
      }
    }
    leaf route-policy {
      type string;
    }
  }

  grouping router-isis-af-redistribute-grouping {
    leaf level {
      tailf:cli-drop-node-name;
      type enumeration {
        enum level-1;
        enum level-1-2;
        enum level-2;
      }
    }
    uses router-af-redistribute-grouping;
    leaf metric-type {
      type enumeration {
        enum external;
        enum internal;
        enum rib-metric-as-external;
        enum rib-metric-as-internal;
      }
    }
  }

  grouping router-ospf-authentication-grouping {
    container authentication-key {
      tailf:cli-compact-syntax;
      tailf:cli-sequence-commands;
      uses password-grouping {
        refine "secret";
      }
    }
    container authentication {
      tailf:cli-delete-when-empty;
      presence "true";
      choice authentication-choice {
        container message-digest {
          tailf:cli-delete-when-empty;
          presence "true";
          leaf keychain {
            type string;
          }
        }
        container ipsec {
          tailf:cli-compact-syntax;
          tailf:cli-sequence-commands {
            tailf:cli-reset-siblings;
          }
          leaf spi {
            type uint32;
          }
          leaf algorithm {
            tailf:cli-drop-node-name;
            type enumeration {
              enum md5;
              enum sha1;
            }
          }
          leaf type {
            tailf:cli-drop-node-name;
            tailf:cli-optional-in-sequence;
            type enumeration {
              enum clear;
              enum password;
            }
          }
          leaf password {
            tailf:cli-drop-node-name;
            type string;
          }
        }
        leaf disable {
          type empty;
        }
        leaf null {
          type empty;
        }
      }
    }
    list message-digest-key {
      tailf:cli-suppress-mode;
      tailf:cli-delete-when-empty;
      tailf:cli-compact-syntax;
      key "id";
      leaf id {
        tailf:cli-suppress-range;
        type uint8;
      }
      container md5 {
        tailf:cli-compact-syntax;
        tailf:cli-sequence-commands;
        uses password-grouping {
          refine "secret";
        }
      }
    }
  }

  grouping bfd-common-parameters-grouping {
    container bfd {
      leaf minimum-interval {
        type uint16;
      }
      container fast-detect {
        tailf:cli-delete-when-empty;
        presence "true";
        choice fast-detect-choice {
          leaf disable {
            type empty;
          }
          leaf strict-mode {
            type empty;
          }
        }
      }
      leaf multiplier {
        type uint8;
      }
    }
  }

  grouping bgp-common-group-grouping {
    container ao {
      tailf:cli-compact-syntax;
      tailf:cli-sequence-commands {
        tailf:cli-reset-siblings;
      }
      choice ao-choice {
        leaf inheritance-disable {
          type empty;
        }
        case keychain {
          leaf name {
            tailf:cli-drop-node-name;
            type string;
          }
          leaf include-tcp-options {
            type enumeration {
              enum disable;
              enum enable;
            }
          }
          leaf accept-ao-mismatch-connection {
            type empty;
          }
        }
      }
    }
  }

  grouping router-ospf-common-area-grouping {
    leaf cost {
      type uint16;
    }
    container security {
      container ttl {
        tailf:cli-delete-when-empty;
        presence "true";
        leaf hops {
          type uint8;
        }
      }
    }
    container passive {
      tailf:cli-delete-when-empty;
      presence "true";
      leaf mode {
        tailf:cli-drop-node-name;
        type enumeration {
          enum disable;
          enum enable;
        }
      }
    }
    leaf priority {
      type uint8;
    }
    container mtu-ignore {
      presence "true";
      tailf:cli-delete-when-empty;
      leaf mode {
        tailf:cli-drop-node-name;
        type enumeration {
          enum disable;
          enum enable;
        }
      }
    }
    leaf flood-reduction {
      type enumeration {
        enum disable;
        enum enable;
      }
    }
    leaf retransmit-interval {
      type uint16;
    }
    leaf dead-interval {
      type uint16;
    }
    leaf demand-circuit {
      type enumeration {
        enum disable;
        enum enable;
      }
    }
    leaf transmit-delay {
      type uint16;
    }
    container fast-reroute {
      choice per-link-or-prefix {
        leaf disable {
          type empty;
        }
        container per-link {
          tailf:cli-delete-when-empty;
          tailf:cli-compact-syntax;
          presence "true";
          leaf enable {
            type empty;
          }
        }
        leaf per-prefix {
          type empty;
        }
      }
      container per-prefix-conf {
        tailf:cli-drop-node-name;
        container per-prefix {
          leaf ti-lfa {
            type enumeration {
              enum disable;
              enum enable;
            }
          }
          container remote-lfa {
            container tunnel {
              leaf mpls-ldp {
                type empty;
              }
            }
          }
          leaf priority-limit {
            type enumeration {
              enum medium;
              enum high;
              enum critical;
            }
          }
          container tiebreaker {
            container node-protecting {
              choice node-protecting-choice {
                leaf disable {
                  type empty;
                }
                leaf index {
                  type uint8;
                }
              }
            }
            container srlg-disjoint {
              choice node-protecting-choice {
                leaf disable {
                  type empty;
                }
                leaf index {
                  type uint8;
                }
              }
            }
          }
        }
      }
    }
    leaf prefix-suppression {
      type empty;
    }
    container prefix-suppression-sec {
      tailf:cli-drop-node-name;
      container prefix-suppression {
        container secondary-address {
          leaf enable {
            type empty;
          }
        }
      }
    }
    leaf hello-interval {
      type uint16;
    }
    container encryption {
      leaf disable {
        type empty;
      }
    }
  }

  grouping router-ospf-area-grouping {
    uses bfd-common-parameters-grouping;
    uses router-ospf-common-area-grouping;
    uses router-ospf-authentication-grouping;
    leaf external-out {
      type enumeration {
        enum disable;
        enum enable;
      }
    }
    uses route-policy-list-grouping;
    choice network-type-choice {
      container network-p2mp-non-bc {
        tailf:cli-drop-node-name;
        container network {
          tailf:cli-sequence-commands;
          tailf:cli-compact-syntax;
          leaf point-to-multipoint {
            type empty;
          }
          leaf non-broadcast {
            type empty;
          }
        }
      }
      leaf network {
        type enumeration {
          enum broadcast;
          enum non-broadcast;
          enum point-to-multipoint;
          enum point-to-point;
        }
      }
    }
    leaf packet-size {
      type uint32;
    }
    container mpls {
      container ldp {
        container sync {
          presence "true";
          tailf:cli-delete-when-empty;
          leaf disable {
            type empty;
          }
        }
        leaf auto-config {
          type empty;
        }
        container sync-igp-shortcuts {
          presence "true";
          tailf:cli-delete-when-empty;
          leaf disable {
            type empty;
          }
        }
      }
      leaf traffic-eng {
        type empty;
      }
    }
    container segment-routing {
      choice mpls-disable-choice {
        leaf mpls {
          type empty;
        }
        leaf disable {
          type empty;
        }
      }
    }
    container prefix-sid {
      tailf:cli-compact-syntax;
      tailf:cli-sequence-commands {
        tailf:cli-reset-siblings;
      }
      uses router-ospf-prefix-sid-grouping;
    }
    container prefix-sid-conf {
      tailf:cli-drop-node-name;
      container prefix-sid {
        container strict-spf {
          tailf:cli-compact-syntax;
          tailf:cli-sequence-commands {
            tailf:cli-reset-siblings;
          }
          uses router-ospf-prefix-sid-grouping;
        }
        list algorithm {
          tailf:cli-suppress-mode;
          tailf:cli-delete-when-empty;
          tailf:cli-compact-syntax;
          tailf:cli-sequence-commands {
            tailf:cli-reset-siblings;
          }
          key "id";
          leaf id {
            type uint8;
          }
          uses router-ospf-prefix-sid-grouping;
        }
      }
    }
    list distribute-list {
      tailf:cli-suppress-mode;
      tailf:cli-delete-when-empty;
      tailf:cli-compact-syntax;
      tailf:cli-sequence-commands {
        tailf:cli-reset-siblings;
      }
      key "direction";
      leaf direction {
        type enumeration {
          enum in;
        }
      }
      leaf route-policy {
        tailf:cli-prefix-key;
        tailf:cli-optional-in-sequence;
        type empty;
      }
      leaf access-list {
        tailf:cli-drop-node-name;
        tailf:cli-prefix-key;
        type string;
      }
    }
    list neighbor {
      tailf:cli-suppress-mode;
      tailf:cli-delete-when-empty;
      tailf:cli-compact-syntax;
      key "address";
      leaf address {
        type union {
          type inet:ipv6-address-no-zone;
          type inet:ipv4-address;
          type cisco-ios-xr:iosxr-ipv6-address;
        }
      }
      leaf priority {
        type uint8;
      }
    }
    container nssa {
      tailf:cli-compact-syntax;
      tailf:cli-delete-when-empty;
      presence "true";
      leaf no-redistribution {
        type empty;
      }
      leaf default-information-originate {
        type empty;
      }
      leaf metric {
        type uint32;
      }
      leaf metric-type {
        type uint8;
      }
      leaf no-summary {
        type empty;
      }
    }
    container database-filter {
      container all {
        leaf out {
          type enumeration {
            enum disable;
            enum enable;
          }
        }
      }
    }
    container cost-fallback {
      tailf:cli-compact-syntax;
      tailf:cli-sequence-commands;
      leaf cost {
        tailf:cli-drop-node-name;
        type uint16;
      }
      leaf threshold {
        type uint32;
      }
    }
  }

  grouping router-ospf-prefix-sid-grouping {
    choice prefix-sid-choice {
      leaf absolute {
        type uint32;
      }
      leaf index {
        type uint32;
      }
    }
    leaf explicit-null {
      type empty;
    }
  }

  grouping router-ospfvx-common-pre-grouping {
    leaf nsr {
      type empty;
    }
    leaf router-id {
      type inet:ipv4-address;
    }
    leaf summary-in {
      type enumeration {
        enum disable;
        enum enable;
      }
    }
    container trace {
      list size {
        tailf:cli-suppress-mode;
        tailf:cli-delete-when-empty;
        key "name";
        leaf name {
          type string;
        }
        leaf size {
          tailf:cli-drop-node-name;
          type enumeration {
            enum 0;
            enum 256;
            enum 512;
            enum 1024;
            enum 2048;
            enum 4096;
            enum 8192;
            enum 16384;
            enum 32768;
            enum 65536;
          }
        }
      }
    }
    container distribute {
      container link-state {
        tailf:cli-compact-syntax;
        tailf:cli-delete-when-empty;
        presence "true";
        leaf instance-id {
          type uint32;
        }
        leaf throttle {
          type uint16;
        }
      }
    }
    uses router-ospf-common-area-grouping;
    container log {
      container adjacency {
        container changes {
          tailf:cli-delete-when-empty;
          presence "true";
          leaf changes-state {
            tailf:cli-drop-node-name;
            type enumeration {
              enum detail;
              enum disable;
            }
          }
        }
      }
    }
    container timers {
      container throttle {
        container lsa {
          container all {
            tailf:cli-compact-syntax;
            tailf:cli-sequence-commands;
            leaf delay {
              tailf:cli-drop-node-name;
              type uint32;
            }
            leaf min-delay {
              tailf:cli-drop-node-name;
              type uint32;
            }
            leaf max-delay {
              tailf:cli-drop-node-name;
              type uint32;
            }
          }
        }
        container spf {
          tailf:cli-compact-syntax;
          tailf:cli-sequence-commands;
          leaf delay {
            tailf:cli-drop-node-name;
            type uint32;
          }
          leaf min-delay {
            tailf:cli-drop-node-name;
            type uint32;
          }
          leaf max-delay {
            tailf:cli-drop-node-name;
            type uint32;
          }
        }
      }
      container lsa {
        leaf group-pacing {
          type uint16;
        }
        leaf arrival {
          type uint16;
        }
        leaf min-arrival {
          type uint32;
        }
        leaf refresh {
          type uint16;
        }
      }
      container pacing {
        leaf flood {
          type uint8;
        }
      }
    }
    container auto-cost {
      tailf:cli-delete-when-empty;
      presence "true";
      leaf reference-bandwidth {
        type uint32;
      }
    }
    container maximum {
      leaf paths {
        type uint8;
      }
      leaf interfaces {
        type uint32;
      }
      container redistributed-prefixes {
        tailf:cli-compact-syntax;
        tailf:cli-sequence-commands {
          tailf:cli-reset-siblings;
        }
        leaf maximum {
          tailf:cli-drop-node-name;
          type uint32;
        }
        leaf threshold-value {
          tailf:cli-drop-node-name;
          tailf:cli-optional-in-sequence;
          type uint8;
        }
        leaf warning-only {
          type empty;
        }
      }
    }
    container bfd {
      leaf fast-detect {
        type empty;
      }
      leaf minimum-interval {
        type uint16;
      }
      leaf multiplier {
        type uint8;
      }
    }
    container network {
      choice network-choice {
        leaf broadcast {
          type empty;
        }
        leaf non-broadcast {
          type empty;
        }
        container point-to-multipoint {
          tailf:cli-delete-when-empty;
          presence "true";
          leaf non-broadcast {
            type empty;
          }
        }
        leaf point-to-point {
          type empty;
        }
      }
    }
    container domain-id {
      container primary {
        tailf:cli-drop-node-name;
        tailf:cli-compact-syntax;
        tailf:cli-sequence-commands;
        uses router-ospf-domain-id-grouping;
      }
      container secondary {
        tailf:cli-compact-syntax;
        tailf:cli-sequence-commands;
        uses router-ospf-domain-id-grouping;
      }
    }
    container default-information {
      container originate {
        tailf:cli-compact-syntax;
        tailf:cli-delete-when-empty;
        presence "true";
        leaf always {
          type empty;
        }
        uses router-ospf-af-redistribute-grouping;
      }
    }
    container spf {
      container prefix-priority {
        leaf route-policy {
          type string;
        }
      }
    }
    container distance {
      leaf weight {
        tailf:cli-drop-node-name;
        type uint8;
      }
      list distance-list {
        tailf:cli-drop-node-name;
        tailf:cli-suppress-mode;
        tailf:cli-delete-when-empty;
        tailf:cli-compact-syntax;
        tailf:cli-sequence-commands {
          tailf:cli-reset-siblings;
        }
        key "ip-address wildcard-mask";
        leaf weight {
          tailf:cli-prefix-key;
          tailf:cli-drop-node-name;
          type uint8;
        }
        leaf ip-address {
          type inet:ipv4-address;
        }
        leaf wildcard-mask {
          type inet:ipv4-address;
        }
        leaf access-list-name {
          tailf:cli-drop-node-name;
          type string;
        }
      }
      container ospf {
        container external {
          leaf distance {
            tailf:cli-drop-node-name;
            type uint8;
          }
        }
      }
    }
    container redistribute {
      container connected {
        tailf:cli-compact-syntax;
        tailf:cli-delete-when-empty;
        presence "true";
        uses router-ospf-af-redistribute-grouping;
      }
      list ospf {
        tailf:cli-suppress-mode;
        tailf:cli-delete-when-empty;
        tailf:cli-compact-syntax;
        key "id";
        leaf id {
          type string;
        }
        uses router-ospf-af-redistribute-grouping;
      }
      list bgp {
        tailf:cli-suppress-mode;
        tailf:cli-delete-when-empty;
        tailf:cli-compact-syntax;
        key "id";
        leaf id {
          type string;
        }
        leaf preserve-med {
          type empty;
        }
        uses router-ospf-af-redistribute-grouping;
      }
      container rip {
        tailf:cli-compact-syntax;
        tailf:cli-delete-when-empty;
        presence "true";
        uses router-ospf-af-redistribute-grouping;
      }
      container static {
        tailf:cli-compact-syntax;
        tailf:cli-delete-when-empty;
        presence "true";
        uses router-ospf-af-redistribute-grouping;
      }
      list isis {
        tailf:cli-suppress-mode;
        tailf:cli-delete-when-empty;
        tailf:cli-compact-syntax;
        key "id";
        leaf id {
          type string;
        }
        leaf level {
          tailf:cli-drop-node-name;
          type enumeration {
            enum level-1;
            enum level-1-2;
            enum level-2;
          }
        }
        uses router-ospf-af-redistribute-grouping;
      }
      container subscriber {
        tailf:cli-compact-syntax;
        tailf:cli-delete-when-empty;
        presence "true";
        uses router-ospf-af-redistribute-grouping;
      }
    }
  }

  grouping router-ospfvx-common-post-grouping {
    list area {
      key "id";
      leaf id {
        tailf:cli-suppress-range;
        type ospf-area-type;
      }
      uses router-ospf-area-grouping;
      container stub {
        tailf:cli-delete-when-empty;
        presence "true";
        leaf no-summary {
          type empty;
        }
      }
      list range {
        tailf:cli-suppress-mode;
        tailf:cli-delete-when-empty;
        key "prefix";
        leaf prefix {
          type ipv4-prefix;
        }
        leaf mode {
          tailf:cli-drop-node-name;
          type enumeration {
            enum advertise;
            enum not-advertise;
          }
        }
      }
      list multi-area-interface {
        key "name";
        leaf name {
          type string;
        }
        uses router-ospf-area-grouping;
      }
      list interface {
        key "name";
        leaf name {
          type string;
        }
        uses router-ospf-area-grouping;
      }
    }
  }

  grouping router-ospf-grouping {
    uses router-ospfvx-common-pre-grouping;
    list distribute-list {
      tailf:cli-suppress-mode;
      tailf:cli-delete-when-empty;
      tailf:cli-compact-syntax;
      tailf:cli-sequence-commands {
        tailf:cli-reset-siblings;
      }
      key "direction";
      leaf direction {
        type enumeration {
          enum in;
          enum out;
        }
      }
      leaf route-policy {
        tailf:cli-prefix-key;
        tailf:cli-optional-in-sequence;
        type empty;
      }
      leaf access-list {
        tailf:cli-drop-node-name;
        tailf:cli-prefix-key;
        type string;
      }
    }
    container distribute-list-proto {
      tailf:cli-drop-node-name;
      list distribute-list {
        tailf:cli-suppress-mode;
        tailf:cli-delete-when-empty;
        tailf:cli-compact-syntax;
        tailf:cli-sequence-commands;
        key "direction";
        leaf access-list {
          tailf:cli-drop-node-name;
          tailf:cli-prefix-key;
          type string;
        }
        leaf direction {
          type enumeration {
            enum out;
          }
        }
        leaf connected {
          tailf:cli-break-sequence-commands;
          type empty;
        }
        leaf static {
          type empty;
        }
        leaf bgp {
          type union {
            type uint32;
            type string;
          }
        }
        leaf ospf {
          type string;
        }
      }
    }
    uses router-ospfvx-common-post-grouping;
    container capability {
      container type7 {
        leaf prefer {
          type empty;
        }
      }
      container opaque {
        tailf:cli-delete-when-empty;
        presence "true";
        leaf disable {
          type empty;
        }
      }
    }
    container nsf {
      container ietf {
        presence "true";
        container helper {
          leaf disable {
            type empty;
          }
        }
      }
      container cisco {
        tailf:cli-compact-syntax;
        tailf:cli-delete-when-empty;
        presence "true";
        container enforce {
          leaf global {
            type empty;
          }
        }
      }
      leaf interval {
        type uint16;
      }
      leaf lifetime {
        type uint16;
      }
    }
    container max-lsa {
      tailf:cli-compact-syntax;
      tailf:cli-sequence-commands {
        tailf:cli-reset-all-siblings;
      }
      leaf max {
        tailf:cli-drop-node-name;
        type uint32;
      }
      leaf threshold {
        tailf:cli-drop-node-name;
        tailf:cli-break-sequence-commands;
        type uint8;
      }
      leaf warning-only {
        type empty;
      }
      leaf ignore-time {
        type uint32;
      }
      leaf ignore-count {
        type uint32;
      }
      leaf reset-time {
        type uint32;
      }
    }
    container loopback {
      leaf stub-network {
        type enumeration {
          enum disable;
          enum enable;
        }
      }
    }
    container queue {
      container limit {
        leaf low {
          type uint16;
        }
        leaf high {
          type uint16;
        }
        leaf medium {
          type uint16;
        }
      }
    }
    container ignore {
      container lsa {
        leaf mospf {
          type empty;
        }
      }
    }
    container segment-routing {
      container global-block {
        tailf:cli-compact-syntax;
        tailf:cli-sequence-commands {
          tailf:cli-reset-siblings;
        }
        leaf lower-bound {
          tailf:cli-drop-node-name;
          type uint32;
        }
        leaf upper-bound {
          tailf:cli-drop-node-name;
          type uint32;
        }
      }
      choice mpls-disable-choice {
        leaf mpls {
          type empty;
        }
        leaf disable {
          type empty;
        }
      }
      leaf forwarding {
        type enumeration {
          enum disable;
          enum mpls;
        }
      }
      container sr-prefer {
        tailf:cli-delete-when-empty;
        presence "true";
        leaf prefix-list {
          type string;
        }
      }
      container prefix-sid-map {
        container receive {
          presence "true";
          leaf disable {
            type empty;
          }
        }
        leaf advertise-local {
          type empty;
        }
      }
    }
    container microloop {
      container avoidance {
        choice microloop-avoidance-choice {
          leaf segment-routing {
            type empty;
          }
          leaf protected {
            type empty;
          }
        }
        leaf rib-update-delay {
          type uint32;
        }
      }
    }
    list summary-prefix {
      tailf:cli-suppress-mode;
      tailf:cli-delete-when-empty;
      tailf:cli-compact-syntax;
      tailf:cli-sequence-commands {
        tailf:cli-reset-siblings;
      }
      key "prefix";
      leaf prefix {
        type ipv4-prefix;
      }
      choice option-choice {
        leaf not-advertise {
          type empty;
        }
        leaf tag {
          type uint32;
        }
      }
    }
    container address-family {
      container ipv4 {
        tailf:cli-delete-when-empty;
        presence "true";
        leaf unicast {
          type empty;
        }
      }
    }
    container max-metric {
      container router-lsa {
        tailf:cli-compact-syntax;
        tailf:cli-delete-when-empty;
        presence "true";
        uses router-ospf-max-metric-grouping;
      }
      container route-lsa-on-startup {
        tailf:cli-drop-node-name;
        container router-lsa {
          container on-startup {
            tailf:cli-compact-syntax;
            choice on-startup-choice {
              leaf time {
                tailf:cli-drop-node-name;
                type uint32;
              }
              leaf wait-for-bgp {
                type empty;
              }
            }
            uses router-ospf-max-metric-grouping;
          }
        }
      }
      container route-lsa-on-proc-restart {
        tailf:cli-drop-node-name;
        container router-lsa {
          container on-proc-restart {
            tailf:cli-compact-syntax;
            choice on-startup-choice {
              leaf time {
                tailf:cli-drop-node-name;
                type uint32;
              }
              leaf wait-for-bgp {
                type empty;
              }
            }
            uses router-ospf-max-metric-grouping;
          }
        }
      }
    }
    container snmp {
      leaf context {
        type string;
      }
    }
    leaf external-out {
      type enumeration {
        enum disable;
        enum enable;
      }
    }
  }

  grouping router-ospfv3-grouping {
    container graceful-restart {
      presence "true";
    }
    uses router-ospfvx-common-pre-grouping;
    container capability {
      container type7 {
        leaf prefer {
          type empty;
        }
      }
    }
    uses router-ospfvx-common-post-grouping;
    container address-family {
      container ipv6 {
        tailf:cli-delete-when-empty;
        presence "true";
        leaf unicast {
          type empty;
        }
      }
    }
  }

  grouping router-ospf-max-metric-grouping {
    leaf include-stub {
      type empty;
    }
    choice summary-lsa-choice {
      container summary-lsa-container {
        tailf:cli-drop-node-name;
        tailf:cli-flatten-container;
        tailf:cli-compact-syntax;
        leaf summary-lsa {
          type uint32;
        }
      }
      leaf summary-lsa {
        type empty;
      }
    }
    choice external-lsa-choice {
      container external-lsa-container {
        tailf:cli-drop-node-name;
        tailf:cli-flatten-container;
        tailf:cli-compact-syntax;
        leaf external-lsa {
          type uint32;
        }
      }
      leaf external-lsa {
        type empty;
      }
    }
  }

  grouping tiebreaker-config-grouping {
    leaf index {
      type uint8;
    }
    leaf level {
      type uint8;
    }
  }

  grouping router-isis-common-af-grouping {
    uses apply-group-grouping;
    leaf disable {
      type empty;
    }
    leaf metric {
      type union {
        type uint32;
        type enumeration {
          enum maximum;
        }
      }
    }
    container metric-level {
      tailf:cli-drop-node-name;
      list metric {
        tailf:cli-suppress-mode;
        tailf:cli-delete-when-empty;
        tailf:cli-compact-syntax;
        tailf:cli-sequence-commands {
          tailf:cli-reset-siblings;
        }
        key "level";
        leaf level {
          type uint8;
        }
        leaf value {
          tailf:cli-prefix-key;
          tailf:cli-drop-node-name;
          type union {
            type uint32;
            type enumeration {
              enum maximum;
            }
          }
        }
      }
    }
    container metric-fallback {
      tailf:cli-drop-node-name;
      container metric {
        container fallback {
          container anomaly {
            tailf:cli-compact-syntax;
            tailf:cli-sequence-commands {
              tailf:cli-reset-siblings;
            }
            leaf delay {
              tailf:cli-optional-in-sequence;
              type empty;
            }
            choice anomaly-choice {
              leaf multiplier {
                type uint32;
              }
              leaf increment {
                type uint32;
              }
            }
          }
          container bandwidth {
            tailf:cli-compact-syntax;
            tailf:cli-sequence-commands;
            leaf multiplier {
              type uint32;
            }
            leaf threshold {
              type uint8;
            }
          }
        }
      }
    }
    container route {
      container source {
        leaf first-hop {
          type empty;
        }
      }
    }
    container fast-reroute {
      container enable {
        tailf:cli-drop-node-name;
        leaf per-prefix {
          type empty;
        }
      }
      choice fast-reroute-choice {
        leaf disable {
          type empty;
        }
        container per-prefix {
          leaf-list level {
            type uint8;
          }
          container priority-limit {
            leaf value {
              tailf:cli-drop-node-name;
              type enumeration {
                enum critical;
                enum high;
                enum medium;
              }
            }
            list level-value {
              tailf:cli-drop-node-name;
              tailf:cli-suppress-mode;
              tailf:cli-delete-when-empty;
              tailf:cli-compact-syntax;
              tailf:cli-sequence-commands;
              key "level";
              leaf level {
                type uint8;
              }
              leaf value {
                tailf:cli-drop-node-name;
                tailf:cli-prefix-key;
                type enumeration {
                  enum critical;
                  enum high;
                  enum medium;
                }
              }
            }
          }
          container srlg-protection {
            leaf weighted-global {
              type empty;
            }
          }
          container remote-lfa {
            container tunnel {
              container mpls-ldp {
                presence "true";
              }
              container mpls-ldp-level {
                tailf:cli-drop-node-name;
                container mpls-ldp {
                  list level {
                    tailf:cli-suppress-mode;
                    tailf:cli-delete-when-empty;
                    key "level";
                    leaf level {
                      type uint8;
                    }
                  }
                }
              }
            }
            leaf maximum-metric {
              type uint32;
            }
            container maximum-metric-level {
              tailf:cli-drop-node-name;
              list maximum-metric {
                tailf:cli-suppress-mode;
                tailf:cli-delete-when-empty;
                tailf:cli-sequence-commands;
                key "level";
                leaf value {
                  tailf:cli-drop-node-name;
                  tailf:cli-prefix-key;
                  type uint32;
                }
                leaf level {
                  type uint8;
                }
              }
            }
          }
          container ti-lfa {
            presence "true";
          }
          container ti-lfa-level {
            tailf:cli-drop-node-name;
            container ti-lfa {
              list level {
                tailf:cli-suppress-mode;
                tailf:cli-delete-when-empty;
                key "level";
                leaf level {
                  type uint8;
                }
              }
            }
          }
          container tiebreaker {
            container default {
              leaf level {
                type uint8;
              }
            }
            container lc-disjoint {
              tailf:cli-compact-syntax;
              tailf:cli-sequence-commands {
                tailf:cli-reset-siblings;
              }
              uses tiebreaker-config-grouping;
            }
            container lc-disjoint-nolevel {
              tailf:cli-drop-node-name;
              container lc-disjoint {
                leaf index {
                  type uint8;
                }
              }
            }
            container lowest-backup-metric {
              tailf:cli-compact-syntax;
              tailf:cli-sequence-commands {
                tailf:cli-reset-siblings;
              }
              uses tiebreaker-config-grouping;
            }
            container lowest-backup-metric-nolevel {
              tailf:cli-drop-node-name;
              container lowest-backup-metric {
                leaf index {
                  type uint8;
                }
              }
            }
            container node-protecting {
              tailf:cli-compact-syntax;
              tailf:cli-sequence-commands {
                tailf:cli-reset-siblings;
              }
              uses tiebreaker-config-grouping;
            }
            container node-protecting-nolevel {
              tailf:cli-drop-node-name;
              container node-protecting {
                leaf index {
                  type uint8;
                }
              }
            }
            container primary-path {
              tailf:cli-compact-syntax;
              tailf:cli-sequence-commands {
                tailf:cli-reset-siblings;
              }
              uses tiebreaker-config-grouping;
            }
            container primary-path-nolevel {
              tailf:cli-drop-node-name;
              container primary-path {
                leaf index {
                  type uint8;
                }
              }
            }
            container srlg-disjoint {
              tailf:cli-compact-syntax;
              tailf:cli-sequence-commands {
                tailf:cli-reset-siblings;
              }
              uses tiebreaker-config-grouping;
            }
            container srlg-disjoint-nolevel {
              tailf:cli-drop-node-name;
              container srlg-disjoint {
                leaf index {
                  type uint8;
                }
              }
            }
          }
          container exclude {
            list interface {
              tailf:cli-suppress-mode;
              tailf:cli-delete-when-empty;
              key "name";
              leaf name {
                type string;
              }
              leaf level {
                type uint8;
              }
            }
          }
        }
      }
      leaf delay-interval {
        type uint16;
      }
    }
    container mpls {
      container ldp {
        leaf auto-config {
          type empty;
        }
        container sync {
          presence "true";
          leaf level {
            type uint8;
          }
        }
      }
      container traffic-eng {
        leaf level {
          tailf:cli-drop-node-name;
          type enumeration {
            enum level-1;
            enum level-1-2;
            enum level-2-only;
          }
        }
        choice router-id-choice {
          container router-id {
            uses interface-name-grouping;
          }
          container router-id-address {
            tailf:cli-drop-node-name;
            leaf router-id {
              type inet:ipv4-address;
            }
          }
        }
        leaf igp-intact {
          type empty;
        }
        leaf multicast-intact {
          type empty;
        }
        container tunnel {
          leaf restricted {
            type empty;
          }
        }
      }
    }
    choice router-id-choice {
      container router-id {
        uses interface-name-grouping;
      }
      container router-id-address {
        tailf:cli-drop-node-name;
        leaf router-id {
          type inet:ipv4-address;
        }
      }
    }
    container monitor-convergence {
      tailf:cli-add-mode;
      tailf:cli-delete-when-empty;
      presence "true";
      leaf track-ip-frr {
        type empty;
      }
    }
    leaf tag {
      type uint32;
    }
    container tag-level {
      tailf:cli-drop-node-name;
      list tag {
        tailf:cli-suppress-mode;
        tailf:cli-delete-when-empty;
        tailf:cli-sequence-commands;
        key "level";
        leaf value {
          tailf:cli-drop-node-name;
          tailf:cli-prefix-key;
          type uint32;
        }
        leaf level {
          type uint8;
        }
      }
    }
  }

  grouping router-isis-af-grouping {
    container advertise {
      container application {
        container lfa {
          container link-attributes {
            leaf srlg {
              type empty;
            }
          }
        }
      }
      leaf passive-only {
        type empty;
      }
      container link {
        leaf attributes {
          type empty;
        }
      }
    }
    leaf ispf {
      type empty;
    }
    container ispf-conf {
      tailf:cli-drop-node-name;
      container ispf {
        leaf-list level {
          type uint8;
        }
      }
    }
    container spf-interval-level {
      tailf:cli-drop-node-name;
      list spf-interval {
        tailf:cli-suppress-mode;
        tailf:cli-delete-when-empty;
        tailf:cli-compact-syntax;
        tailf:cli-sequence-commands {
          tailf:cli-reset-siblings;
        }
        key "level";
        leaf level {
          type uint8;
        }
        leaf maximum-wait {
          tailf:cli-prefix-key;
          type uint32;
        }
        leaf initial-wait {
          tailf:cli-optional-in-sequence;
          tailf:cli-prefix-key;
          type uint32;
        }
        leaf secondary-wait {
          tailf:cli-optional-in-sequence;
          tailf:cli-prefix-key;
          type uint32;
        }
      }
    }
    container spf-interval {
      tailf:cli-compact-syntax;
      leaf maximum-wait {
        type uint32;
      }
      leaf initial-wait {
        type uint32;
      }
      leaf secondary-wait {
        type uint32;
      }
    }
    container attached-bit {
      leaf receive {
        type enumeration {
          enum ignore;
        }
      }
      leaf send {
        type enumeration {
          enum always-set;
          enum never-set;
        }
      }
    }
    list distribute-list {
      tailf:cli-suppress-mode;
      tailf:cli-delete-when-empty;
      tailf:cli-compact-syntax;
      tailf:cli-sequence-commands {
        tailf:cli-reset-siblings;
      }
      key "direction";
      leaf direction {
        type enumeration {
          enum in;
        }
      }
      choice filter-choice {
        leaf route-policy {
          tailf:cli-prefix-key;
          type string;
        }
        leaf prefix-list {
          tailf:cli-prefix-key;
          type string;
        }
      }
    }
    container distance {
      leaf value {
        tailf:cli-drop-node-name;
        type uint8;
      }
      list prefix-list {
        tailf:cli-drop-node-name;
        tailf:cli-suppress-mode;
        tailf:cli-delete-when-empty;
        tailf:cli-compact-syntax;
        tailf:cli-sequence-commands;
        key "prefix";
        leaf value {
          tailf:cli-drop-node-name;
          tailf:cli-prefix-key;
          type uint8;
        }
        leaf prefix {
          type union {
            type ipv4-prefix;
            type tailf:ipv6-address-and-prefix-length;
          }
        }
        leaf prefix-list-name {
          tailf:cli-drop-node-name;
          type string;
        }
      }
    }
    leaf single-topology {
      type empty;
    }
    container adjacency-check {
      leaf disable {
        type empty;
      }
    }
    container spf {
      container periodic {
        leaf disable {
          type empty;
        }
      }
      list prefix-priority {
        tailf:cli-suppress-mode;
        tailf:cli-delete-when-empty;
        key "priority";
        leaf priority {
          type enumeration {
            enum critical;
            enum high;
            enum medium;
          }
        }
        choice priority-type {
          leaf access-list {
            tailf:cli-drop-node-name;
            type string;
          }
          leaf tag {
            type uint32;
          }
        }
      }
      container prefix-priority-level {
        tailf:cli-drop-node-name;
        list prefix-priority {
          tailf:cli-suppress-mode;
          tailf:cli-delete-when-empty;
          key "level priority";
          leaf level {
            type uint8;
          }
          leaf priority {
            type enumeration {
              enum critical;
              enum high;
              enum medium;
            }
          }
          choice priority-type {
            leaf access-list {
              tailf:cli-drop-node-name;
              type string;
            }
            leaf tag {
              type uint32;
            }
          }
        }
      }
    }
    container default-information {
      container originate {
        tailf:cli-compact-syntax;
        tailf:cli-delete-when-empty;
        presence "true";
        leaf external {
          type empty;
        }
        leaf route-policy {
          type string;
        }
      }
    }
    leaf maximum-paths {
      type uint16;
    }
    leaf maximum-redistributed-prefixes {
      type uint16;
    }
    container maximum-redistributed-prefixes-level {
      tailf:cli-drop-node-name;
      list maximum-redistributed-prefixes {
        tailf:cli-suppress-mode;
        tailf:cli-delete-when-empty;
        tailf:cli-sequence-commands;
        key "level";
        leaf value {
          tailf:cli-drop-node-name;
          tailf:cli-prefix-key;
          type uint16;
        }
        leaf level {
          type uint8;
        }
      }
    }
    container propagate {
      list level {
        tailf:cli-suppress-mode;
        tailf:cli-delete-when-empty;
        tailf:cli-compact-syntax;
        tailf:cli-sequence-commands;
        key "from level";
        leaf from {
          type uint8;
        }
        leaf into {
          tailf:cli-prefix-key {
            tailf:cli-before-key "2";
          }
          type empty;
        }
        leaf level {
          type uint8;
        }
        leaf route-policy {
          type string;
        }
      }
    }
    container microloop {
      container avoidance {
        leaf segment-routing {
          type empty;
        }
        leaf rib-update-delay {
          type uint16;
        }
        leaf protected {
          type empty;
        }
      }
    }
    container redistribute {
      container connected {
        tailf:cli-compact-syntax;
        tailf:cli-delete-when-empty;
        presence "true";
        uses router-isis-af-redistribute-grouping;
      }
      container static {
        tailf:cli-compact-syntax;
        tailf:cli-delete-when-empty;
        presence "true";
        uses router-isis-af-redistribute-grouping;
      }
      list isis {
        tailf:cli-suppress-mode;
        tailf:cli-delete-when-empty;
        tailf:cli-compact-syntax;
        key "name";
        leaf name {
          tailf:cli-suppress-range;
          type string;
        }
        uses router-isis-af-redistribute-grouping;
      }
      list bgp {
        tailf:cli-suppress-mode;
        tailf:cli-delete-when-empty;
        tailf:cli-compact-syntax;
        key "id";
        leaf id {
          tailf:cli-suppress-range;
          type string;
        }
        uses router-isis-af-redistribute-grouping;
      }
      list ospf {
        tailf:cli-suppress-mode;
        tailf:cli-delete-when-empty;
        tailf:cli-compact-syntax;
        key "id";
        leaf id {
          tailf:cli-suppress-range;
          type string;
        }
        leaf match {
          type enumeration {
            enum external;
            enum internal;
            enum nssa-external;
          }
        }
        uses router-isis-af-redistribute-grouping;
      }
      list ospfv3 {
        tailf:cli-suppress-mode;
        tailf:cli-delete-when-empty;
        tailf:cli-compact-syntax;
        key "id";
        leaf id {
          tailf:cli-suppress-range;
          type string;
        }
        leaf match {
          type enumeration {
            enum external;
            enum internal;
            enum nssa-external;
          }
        }
        uses router-isis-af-redistribute-grouping;
      }
    }
    container ucmp {
      presence "true";
    }
    container segment-routing {
      container mpls {
        tailf:cli-delete-when-empty;
        presence "true";
        leaf sr-prefer {
          type empty;
        }
      }
      container prefix-sid-map {
        container receive {
          presence "true";
        }
        leaf advertise-local {
          type empty;
        }
      }
      container srv6 {
        tailf:cli-add-mode;
        presence "true";
        list locator {
          key "name";
          leaf name {
            type string;
          }
        }
      }
    }
    container apply-weight {
      tailf:cli-compact-syntax;
      tailf:cli-sequence-commands {
        tailf:cli-reset-siblings;
      }
      choice paths-choice {
        case case-ecmp {
          leaf ecmp-only {
            type empty;
          }
          leaf bandwidth {
            type empty;
          }
        }
        leaf ucmp-only {
          type empty;
        }
      }
    }
  }

  grouping router-isis-af4-grouping {
    list summary-prefix {
      tailf:cli-suppress-mode;
      tailf:cli-delete-when-empty;
      tailf:cli-compact-syntax;
      tailf:cli-sequence-commands {
        tailf:cli-reset-siblings;
      }
      key "prefix";
      leaf prefix {
        type union {
          type ipv4-prefix;
          type tailf:ipv6-address-and-prefix-length;
        }
      }
      leaf tag {
        tailf:cli-optional-in-sequence;
        type uint32;
      }
      leaf level {
        type uint8;
      }
    }
    uses router-isis-af-grouping;
  }

  grouping router-isis-af6-grouping {
    list summary-prefix {
      tailf:cli-suppress-mode;
      tailf:cli-delete-when-empty;
      tailf:cli-compact-syntax;
      key "prefix";
      leaf prefix {
        type union {
          type ipv4-prefix;
          type tailf:ipv6-address-and-prefix-length;
        }
      }
      leaf tag {
        type uint32;
      }
      leaf level {
        type uint8;
      }
      leaf algorithm {
        type uint8;
      }
      leaf explicit {
        type empty;
      }
    }
    uses router-isis-af-grouping;
  }

  grouping router-isis-common-grouping {
    leaf metric-style {
      type enumeration {
        enum narrow;
        enum transition;
        enum wide;
      }
    }
    container metric-style-list {
      tailf:cli-drop-node-name;
      list metric-style {
        tailf:cli-suppress-mode;
        tailf:cli-delete-when-empty;
        tailf:cli-sequence-commands;
        key "level";
        leaf level {
          type uint8;
        }
        leaf style {
          tailf:cli-drop-node-name;
          tailf:cli-prefix-key;
          type enumeration {
            enum narrow;
            enum transition;
            enum wide;
          }
        }
      }
    }
  }

  grouping router-isis-if-af-grouping {
    container prefix-sid {
      tailf:cli-compact-syntax;
      tailf:cli-sequence-commands {
        tailf:cli-reset-siblings;
      }
      choice value-choice {
        leaf absolute {
          type uint32;
        }
        leaf index {
          type uint32;
        }
      }
      leaf explicit-null {
        tailf:cli-optional-in-sequence;
        type empty;
      }
      leaf n-flag-clear {
        type empty;
      }
    }
    container prefix-sid-algorithm {
      tailf:cli-drop-node-name;
      container prefix-sid {
        list algorithm {
          tailf:cli-suppress-mode;
          tailf:cli-delete-when-empty;
          tailf:cli-compact-syntax;
          tailf:cli-sequence-commands {
            tailf:cli-reset-siblings;
          }
          key "id";
          leaf id {
            type uint8;
          }
          choice value-choice {
            leaf absolute {
              type uint32;
            }
            leaf index {
              type uint32;
            }
          }
          leaf explicit-null {
            tailf:cli-optional-in-sequence;
            type empty;
          }
          leaf n-flag-clear {
            type empty;
          }
        }
      }
    }
    container prefix-sid-strict-spf {
      tailf:cli-drop-node-name;
      container prefix-sid {
        container strict-spf {
          tailf:cli-compact-syntax;
          tailf:cli-sequence-commands {
            tailf:cli-reset-siblings;
          }
          choice value-choice {
            leaf absolute {
              type uint32;
            }
            leaf index {
              type uint32;
            }
          }
          leaf explicit-null {
            tailf:cli-optional-in-sequence;
            type empty;
          }
          leaf n-flag-clear {
            type empty;
          }
        }
      }
    }
    container te-metric {
      leaf flex-algo {
        type uint32;
      }
    }
  }

  grouping vty-pool-grouping {
    leaf first-vty {
      tailf:cli-drop-node-name;
      type uint16;
    }
    leaf last-vty {
      tailf:cli-drop-node-name;
      type uint16;
    }
    leaf line-template {
      tailf:cli-optional-in-sequence;
      type string;
    }
  }

  grouping line-grouping {
    container flowcontrol {
      container hardware {
        leaf direction {
          tailf:cli-drop-node-name;
          type enumeration {
            enum in;
            enum none;
            enum out;
          }
        }
      }
    }
    leaf parity {
      type enumeration {
        enum even;
        enum none;
        enum odd;
      }
    }
    leaf databits {
      type uint8;
    }
    leaf stopbits {
      type enumeration {
        enum 1;
        enum 2;
      }
    }
    container access-class {
      leaf egress {
        type string;
      }
      leaf ingress {
        type string;
      }
    }
    container secret {
      tailf:cli-compact-syntax;
      tailf:cli-sequence-commands;
      leaf type {
        tailf:cli-drop-node-name;
        type enumeration {
          enum 0;
          enum 5;
        }
      }
      leaf secret {
        tailf:cli-drop-node-name;
        type string;
      }
    }
    container password {
      tailf:cli-compact-syntax;
      tailf:cli-sequence-commands;
      leaf encryption {
        tailf:cli-drop-node-name;
        tailf:cli-optional-in-sequence;
        type enumeration {
          enum 0;
          enum 7;
        }
      }
      leaf password {
        tailf:cli-drop-node-name;
        type string;
      }
    }
    container users {
      list group {
        tailf:cli-suppress-mode;
        tailf:cli-delete-when-empty;
        key "name";
        leaf name {
          type string;
        }
      }
    }
    container accounting {
      leaf commands {
        type union {
          type enumeration {
            enum default;
          }
          type string;
        }
      }
      leaf exec {
        type union {
          type enumeration {
            enum default;
          }
          type string;
        }
      }
    }
    container authorization {
      leaf commands {
        type union {
          type enumeration {
            enum default;
          }
          type string;
        }
      }
      leaf exec {
        type union {
          type enumeration {
            enum default;
          }
          type string;
        }
      }
    }
    container timeout {
      container login {
        leaf response {
          type uint16;
        }
      }
    }
    container timestamp {
      tailf:cli-delete-when-empty;
      presence "true";
      leaf disable {
        type empty;
      }
    }
    container transport {
      leaf-list input {
        tailf:cli-flat-list-syntax;
        type enumeration {
          enum all;
          enum none;
          enum ssh;
          enum telnet;
          enum lat;
          enum pad;
          enum udptn;
          enum rlogin;
        }
      }
      leaf-list output {
        tailf:cli-flat-list-syntax;
        type enumeration {
          enum all;
          enum none;
          enum ssh;
          enum telnet;
        }
      }
      leaf pager {
        type enumeration {
          enum none;
          enum more;
          enum less;
        }
      }
      leaf preferred {
        type enumeration {
          enum none;
          enum ssh;
          enum telnet;
        }
      }
    }
    container exec-timeout {
      tailf:cli-compact-syntax;
      tailf:cli-sequence-commands {
        tailf:cli-reset-siblings;
      }
      leaf minutes {
        tailf:cli-drop-node-name;
        type uint32;
      }
      leaf seconds {
        tailf:cli-drop-node-name;
        type uint32;
      }
    }
    leaf length {
      type uint16;
    }
    leaf width {
      type uint16;
    }
    container login {
      leaf authentication {
        type union {
          type enumeration {
            enum default;
          }
          type string;
        }
      }
    }
    leaf session-limit {
      type uint8;
    }
    leaf absolute-timeout {
      type uint16;
    }
    container telnet {
      leaf transparent {
        type empty;
      }
    }
    leaf disconnect-character {
      type string;
    }
    container session-timeout {
      tailf:cli-compact-syntax;
      tailf:cli-sequence-commands {
        tailf:cli-reset-siblings;
      }
      leaf minutes {
        tailf:cli-drop-node-name;
        type uint32;
      }
      leaf output {
        type empty;
      }
    }
    leaf escape-character {
      type string;
    }
    container cli {
      container whitespace {
        leaf completion {
          type empty;
        }
      }
    }
  }

  grouping lpts-flow-grouping {
    list flow {
      tailf:cli-suppress-mode;
      tailf:cli-delete-when-empty;
      key "name";
      leaf name {
        tailf:cli-multi-word-key;
        type string;
      }
      leaf rate {
        type uint32;
      }
      leaf precedence {
        type precedence-type;
      }
    }
  }

  grouping class-random-detect-grouping {
    leaf min-threshold {
      tailf:cli-drop-node-name;
      type uint32;
    }
    leaf min-threshold-unit {
      tailf:cli-drop-node-name;
      type police-burst-units-type;
    }
    leaf max-threshold {
      tailf:cli-drop-node-name;
      type uint32;
    }
    leaf max-threshold-unit {
      tailf:cli-drop-node-name;
      type police-burst-units-type;
    }
  }

  grouping class-map-match-grouping {
    container access-group {
      leaf ipv4 {
        type string;
      }
      leaf ipv6 {
        type string;
      }
      list list {
        tailf:cli-drop-node-name;
        tailf:cli-suppress-mode;
        tailf:cli-delete-when-empty;
        key "af name";
        leaf af {
          type enumeration {
            enum ipv4;
            enum ipv6;
          }
        }
        leaf name {
          type string;
        }
      }
    }
    leaf any {
      type empty;
    }
    container flow-key {
      tailf:cli-compact-syntax;
      tailf:cli-sequence-commands {
        tailf:cli-reset-siblings;
      }
      choice id-choice {
        leaf five-tuple {
          tailf:alt-name "5-tuple";
          tailf:cli-optional-in-sequence;
          type empty;
        }
        case ip {
          leaf src-ip {
            tailf:cli-optional-in-sequence;
            type empty;
          }
          leaf dst-ip {
            tailf:cli-optional-in-sequence;
            type empty;
          }
        }
      }
      container flow-cache {
        tailf:cli-flatten-container;
        tailf:cli-compact-syntax;
        leaf idle-timeout {
          type union {
            type enumeration {
              enum none;
            }
            type uint16;
          }
        }
      }
    }
    container cos {
      leaf-list cos-value {
        tailf:cli-drop-node-name;
        tailf:cli-flat-list-syntax;
        type uint16;
      }
      leaf-list inner {
        tailf:cli-flat-list-syntax;
        type uint16;
      }
    }
    container destination-address {
      list ipv4 {
        tailf:cli-suppress-mode;
        tailf:cli-delete-when-empty;
        key "address mask";
        leaf address {
          tailf:cli-drop-node-name;
          type inet:ipv4-address;
        }
        leaf mask {
          tailf:cli-drop-node-name;
          type inet:ipv4-address;
        }
      }
      leaf mac {
        type string;
      }
    }
    leaf-list destination-port {
      tailf:cli-flat-list-syntax;
      type string;
    }
    leaf-list discard-class {
      tailf:cli-flat-list-syntax;
      type uint16;
    }
    leaf-list traffic-class {
      tailf:cli-flat-list-syntax;
      type uint8;
    }
    container dscp {
      leaf-list dscp-list {
        tailf:cli-drop-node-name;
        tailf:cli-range-list-syntax;
        type dscp-type;
      }
      leaf-list ipv4 {
        tailf:cli-range-list-syntax;
        type dscp-type;
      }
      leaf-list ipv6 {
        tailf:cli-range-list-syntax;
        type dscp-type;
      }
    }
    container fr-de {
      tailf:cli-delete-when-empty;
      presence "true";
      leaf fr-de-value {
        tailf:cli-drop-node-name;
        type enumeration {
          enum 1;
        }
      }
    }
    container frame-relay {
      leaf-list dlci {
        tailf:cli-flat-list-syntax;
        type uint16;
      }
    }
    container mpls {
      container experimental {
        leaf-list topmost {
          tailf:cli-flat-list-syntax;
          type uint8;
        }
      }
    }
    container packet {
      leaf-list length {
        tailf:cli-flat-list-syntax;
        type string;
      }
    }
    container tcp-flag {
      tailf:cli-compact-syntax;
      tailf:cli-sequence-commands {
        tailf:cli-reset-siblings;
      }
      leaf value {
        tailf:cli-drop-node-name;
        type string;
      }
      leaf any {
        type empty;
      }
    }
    container ipv4 {
      leaf-list icmp-type {
        tailf:cli-range-list-syntax;
        type uint8;
      }
      leaf-list icmp-code {
        tailf:cli-range-list-syntax;
        type uint8;
      }
    }
    leaf-list fragment-type {
      tailf:cli-flat-list-syntax;
      type enumeration {
        enum dont-fragment;
        enum first-fragment;
        enum is-fragment;
        enum last-fragment;
      }
    }
    container precedence {
      leaf-list ipv4 {
        tailf:cli-flat-list-syntax;
        type precedence-type;
      }
      leaf-list ipv6 {
        tailf:cli-flat-list-syntax;
        type precedence-type;
      }
      leaf-list list {
        tailf:cli-drop-node-name;
        tailf:cli-flat-list-syntax;
        type precedence-type;
      }
    }
    leaf-list protocol {
      tailf:cli-flat-list-syntax;
      type union {
        type uint8;
        type enumeration {
          enum ahp {
            value 51;
          }
          enum eigrp {
            value 88;
          }
          enum esp {
            value 50;
          }
          enum gre {
            value 47;
          }
          enum icmp {
            value 1;
          }
          enum igmp {
            value 2;
          }
          enum igrp {
            value 9;
          }
          enum ipinip {
            value 1001;
          }
          enum ipv4 {
            value 0;
          }
          enum ipv6 {
            value 41;
          }
          enum ipv6icmp {
            value 58;
          }
          enum mpls {
            value 137;
          }
          enum nos {
            value 94;
          }
          enum ospf {
            value 89;
          }
          enum pcp {
            value 108;
          }
          enum pim {
            value 103;
          }
          enum sctp {
            value 132;
          }
          enum tcp {
            value 6;
          }
          enum udp {
            value 17;
          }
        }
        type string;
      }
    }
    leaf-list qos-group {
      tailf:cli-flat-list-syntax;
      type uint16;
    }
    container source-address {
      list ipv4 {
        tailf:cli-suppress-mode;
        tailf:cli-delete-when-empty;
        key "address mask";
        leaf address {
          type inet:ipv4-address;
        }
        leaf mask {
          type inet:ipv4-address;
        }
      }
      leaf mac {
        type string;
      }
    }
    leaf-list source-port {
      tailf:cli-flat-list-syntax;
      type string;
    }
    container vlan {
      leaf-list vlan-list {
        tailf:cli-drop-node-name;
        tailf:cli-range-list-syntax;
        type uint16;
      }
      leaf-list inner {
        tailf:cli-range-list-syntax;
        type uint16;
      }
    }
    container vpls {
      leaf control {
        type empty;
      }
      leaf broadcast {
        type empty;
      }
      leaf known {
        type empty;
      }
      leaf multicast {
        type empty;
      }
      leaf unknown {
        type empty;
      }
    }
    leaf dei {
      type uint8;
    }
  }

  grouping class-map-filter-control-match-grouping {
    leaf authen-status {
      type enumeration {
        enum authenticated;
        enum unauthenticated;
      }
    }
    leaf-list protocol {
      tailf:cli-flat-list-syntax;
      type enumeration {
        enum ppp;
        enum dhcpv4;
        enum dhcpv6;
      }
    }
    container source-address {
      list ipv4 {
        tailf:cli-suppress-mode;
        tailf:cli-delete-when-empty;
        key "address mask";
        leaf address {
          type inet:ipv4-address;
        }
        leaf mask {
          type inet:ipv4-address;
        }
      }
    }
    container timer {
      leaf value {
        tailf:cli-drop-node-name;
        type string;
      }
    }
    list circuit-id {
      tailf:cli-suppress-mode;
      tailf:cli-delete-when-empty;
      key "name";
      leaf name {
        type string;
      }
      leaf regexp {
        tailf:cli-prefix-key;
        type empty;
      }
    }
  }

  grouping logging-events-lsp-status-grouping {
    container lsp-status {
      leaf reoptimize {
        type empty;
      }
      leaf state {
        type empty;
      }
      leaf reroute {
        type empty;
      }
      leaf record-route {
        type empty;
      }
      leaf insufficient-bandwidth {
        type empty;
      }
      leaf bw-change {
        type empty;
      }
      leaf switchover {
        type empty;
      }
    }
  }

  grouping interface-ipv6-nd-prefix-list-grouping {
    choice prefix-choices {
      container prefix-lifetime {
        tailf:cli-drop-node-name;
        tailf:cli-compact-syntax;
        tailf:cli-sequence-commands;
        leaf valid-lifetime {
          tailf:cli-drop-node-name;
          type union {
            type uint32;
            type enumeration {
              enum infinite;
            }
          }
        }
        leaf preferred-lifetime {
          tailf:cli-drop-node-name;
          type union {
            type uint32;
            type enumeration {
              enum infinite;
            }
          }
        }
      }
      leaf no-adv {
        type empty;
      }
      container options {
        tailf:cli-drop-node-name;
        tailf:cli-compact-syntax;
        leaf no-autoconfig {
          type empty;
        }
        leaf off-link {
          type empty;
        }
      }
    }
  }

  grouping interface-service-policy-grouping {
    container service-policy {
      container input {
        tailf:cli-compact-syntax;
        tailf:cli-sequence-commands {
          tailf:cli-reset-siblings;
        }
        leaf name {
          tailf:cli-drop-node-name;
          type string;
        }
        uses interface-service-policy-content-grouping;
      }
      list input-list {
        tailf:cli-suppress-mode;
        tailf:cli-delete-when-empty;
        tailf:cli-compact-syntax;
        tailf:cli-sequence-commands {
          tailf:cli-reset-siblings;
        }
        key "name";
        leaf name {
          type string;
        }
        uses interface-service-policy-content-grouping;
      }
      container output {
        tailf:cli-compact-syntax;
        tailf:cli-sequence-commands {
          tailf:cli-reset-siblings;
        }
        leaf name {
          tailf:cli-drop-node-name;
          type string;
        }
        uses interface-service-policy-content-grouping;
      }
      list output-list {
        tailf:cli-suppress-mode;
        tailf:cli-delete-when-empty;
        tailf:cli-compact-syntax;
        tailf:cli-sequence-commands {
          tailf:cli-reset-siblings;
        }
        key "name";
        leaf name {
          type string;
        }
        uses interface-service-policy-content-grouping;
      }
      container type {
        container lan-queuing {
          leaf input {
            type string;
          }
          leaf output {
            type string;
          }
        }
        container performance-monitor {
          leaf input {
            type string;
          }
          leaf output {
            type string;
          }
          leaf inline {
            type enumeration {
              enum input;
              enum output;
            }
          }
        }
        container performance-traffic {
          leaf input {
            type string;
          }
        }
        container test {
          leaf input {
            type string;
          }
          leaf output {
            type string;
          }
          leaf inline {
            type enumeration {
              enum input;
              enum output;
            }
          }
        }
        container pbr {
          leaf input {
            type string;
          }
        }
        container control {
          leaf subscriber {
            type string;
          }
        }
      }
    }
  }

  grouping dynamic-template-service-policy-grouping {
    container service-policy {
      container input {
        tailf:cli-compact-syntax;
        tailf:cli-sequence-commands {
          tailf:cli-reset-siblings;
        }
        leaf name {
          tailf:cli-drop-node-name;
          type string;
        }
        uses interface-service-policy-content-grouping;
      }
      container output {
        tailf:cli-compact-syntax;
        tailf:cli-sequence-commands {
          tailf:cli-reset-siblings;
        }
        leaf name {
          tailf:cli-drop-node-name;
          type string;
        }
        uses interface-service-policy-content-grouping;
      }
      container type {
        container pbr {
          leaf input {
            tailf:cli-drop-node-name;
            type string;
          }
        }
      }
    }
  }

  grouping interface-service-policy-content-grouping {
    container account {
      tailf:cli-flatten-container;
      tailf:cli-compact-syntax;
      tailf:cli-optional-in-sequence;
      choice account-choice {
        leaf nolayer2 {
          type empty;
        }
        leaf user-defined {
          type int8;
        }
      }
    }
    leaf subscriber-parent {
      tailf:cli-optional-in-sequence;
      type empty;
    }
    leaf resource-id {
      tailf:cli-optional-in-sequence;
      type uint8;
    }
    leaf shared-policy-instance {
      tailf:cli-optional-in-sequence;
      type string;
    }
    container merge {
      tailf:cli-flatten-container;
      tailf:cli-compact-syntax;
      tailf:cli-sequence-commands {
        tailf:cli-reset-siblings;
      }
      leaf seq {
        tailf:cli-drop-node-name;
        type uint8;
      }
      leaf acct-stats {
        type empty;
      }
    }
  }

  grouping interface-isis-grouping {
    container isis {
      container authentication {
        container mode {
          tailf:cli-compact-syntax;
          tailf:cli-sequence-commands;
          leaf crypt {
            tailf:cli-drop-node-name;
            type enumeration {
              enum md5;
              enum text;
            }
          }
          leaf level {
            tailf:cli-drop-node-name;
            type enumeration {
              enum level-1;
              enum level-2;
            }
          }
        }
        leaf key-chain {
          type string;
        }
        container send-only {
          tailf:cli-delete-when-empty;
          presence "true";
          leaf level {
            tailf:cli-drop-node-name;
            type enumeration {
              enum level-1;
              enum level-2;
            }
          }
        }
      }
      leaf circuit-type {
        type enumeration {
          enum level-1;
          enum level-1-2;
          enum level-2-only;
        }
      }
      container hello {
        leaf padding {
          type empty;
        }
      }
      container metric {
        tailf:cli-compact-syntax;
        tailf:cli-sequence-commands;
        leaf metric {
          tailf:cli-drop-node-name;
          type union {
            type uint32;
            type enumeration {
              enum maximum;
            }
          }
        }
        leaf delay {
          tailf:cli-drop-node-name;
          type union {
            type enumeration {
              enum level-1;
              enum level-2;
            }
            type uint32;
          }
        }
        leaf expense {
          tailf:cli-drop-node-name;
          type union {
            type enumeration {
              enum level-1;
              enum level-2;
            }
            type uint32;
          }
        }
        leaf error {
          tailf:cli-drop-node-name;
          type union {
            type enumeration {
              enum level-1;
              enum level-2;
            }
            type uint32;
          }
        }
        leaf rest {
          tailf:cli-drop-node-name;
          type union {
            type enumeration {
              enum level-1;
              enum level-2;
            }
          }
        }
      }
    }
  }

  grouping interface-switch-grouping {
    container channel-protocol {
      tailf:cli-compact-syntax;
      tailf:cli-sequence-commands {
        tailf:cli-reset-siblings;
      }
      leaf number {
        tailf:cli-drop-node-name;
        type uint16;
      }
      leaf mode {
        type enumeration {
          enum active;
          enum auto;
          enum desirable;
          enum on;
          enum passive;
        }
      }
    }
    container switch {
      container virtual {
        leaf link {
          type uint8;
        }
      }
    }
    container switchport-conf {
      tailf:cli-drop-node-name;
      leaf switchport {
        type boolean;
      }
    }
    container switchport {
      container access {
        leaf vlan {
          type uint16;
        }
      }
      container block {
        leaf multicast {
          type empty;
        }
        leaf unicast {
          type empty;
        }
      }
      container mode {
        choice mode-choice {
          leaf access {
            type empty;
          }
          leaf dot1q-tunnel {
            type empty;
          }
          leaf dynamic {
            type enumeration {
              enum auto;
              enum desirable;
            }
          }
          leaf trunk {
            type empty;
          }
        }
      }
      leaf nonegotiate {
        type empty;
      }
      container trunk {
        container allowed {
          container vlan {
            choice vlan-choice {
              leaf-list vlans {
                tailf:cli-range-list-syntax;
                tailf:cli-drop-node-name;
                type uint16;
              }
              leaf all {
                type empty;
              }
              leaf-list except {
                tailf:cli-range-list-syntax;
                type uint16;
              }
              leaf none {
                type empty;
              }
            }
          }
        }
        container native {
          leaf vlan {
            type union {
              type enumeration {
                enum tag;
              }
              type uint16;
            }
          }
        }
        container pruning {
          container vlan {
            choice vlan-choice {
              leaf-list vlans {
                tailf:cli-range-list-syntax;
                tailf:cli-drop-node-name;
                type uint16;
              }
              leaf-list except {
                tailf:cli-range-list-syntax;
                type uint16;
              }
              leaf none {
                type empty;
              }
            }
          }
        }
      }
    }
    container spanning-tree {
      leaf bpdufilter {
        type enumeration {
          enum disable;
          enum enable;
        }
      }
      leaf bpduguard {
        type enumeration {
          enum disable;
          enum enable;
        }
      }
      leaf guard {
        type enumeration {
          enum loop;
          enum none;
          enum root;
        }
      }
      leaf portfast {
        type enumeration {
          enum disable;
          enum edge;
          enum network;
        }
      }
    }
  }

  grouping interface-bundle-grouping {
    container bundle {
      leaf wait-while {
        type uint16;
      }
      container load-balancing {
        leaf hash {
          type union {
            type uint8;
            type enumeration {
              enum dst-ip;
              enum src-ip;
              enum auto;
            }
          }
        }
        container localize {
          container threshold {
            leaf links {
              type uint8;
            }
          }
        }
      }
      container maximum-active {
        container links {
          tailf:cli-compact-syntax;
          tailf:cli-sequence-commands {
            tailf:cli-reset-siblings;
          }
          leaf number {
            tailf:cli-drop-node-name;
            type uint8;
          }
          leaf hot-standby {
            type empty;
          }
        }
      }
      container minimum-active {
        leaf links {
          type uint8;
        }
        container bandwidth {
          tailf:cli-compact-syntax;
          tailf:cli-sequence-commands {
            tailf:cli-reset-siblings;
          }
          leaf unit {
            tailf:cli-drop-node-name;
            tailf:cli-optional-in-sequence;
            type enumeration {
              enum kbps;
              enum mbps;
              enum gbps;
            }
          }
          leaf value {
            tailf:cli-drop-node-name;
            type uint32;
          }
        }
      }
      container lacp-fallback {
        leaf timeout {
          type uint16;
        }
      }
      container logging {
        leaf oos {
          type empty;
        }
      }
    }
    container lacp {
      leaf mode {
        type enumeration {
          enum active;
          enum on;
          enum passive;
        }
      }
      container churn {
        leaf logging {
          type enumeration {
            enum actor;
            enum both;
            enum partner;
          }
        }
      }
      leaf period {
        type union {
          type uint16;
          type enumeration {
            enum short;
          }
        }
      }
      container system {
        leaf mac {
          type string;
        }
        leaf priority {
          type uint16;
        }
      }
      leaf non-revertive {
        type empty;
      }
      container switchover {
        leaf suppress-flaps {
          type uint16;
        }
      }
      leaf collector-max-delay {
        type uint16;
      }
      container cisco {
        container enable {
          presence "true";
        }
      }
    }
    container mlacp {
      leaf iccp-group {
        type uint32;
      }
      leaf port-priority {
        type uint16;
      }
      container switchover {
        container maximize {
          container links {
            tailf:cli-delete-when-empty;
            presence "true";
            leaf threshold {
              type uint8;
            }
          }
        }
        leaf recovery-delay {
          type uint16;
        }
        leaf type {
          type enumeration {
            enum brute-force;
            enum revertive;
          }
        }
      }
    }
  }

  grouping interface-non-bundle-grouping {
    container bundle {
      container id {
        tailf:cli-compact-syntax;
        tailf:cli-sequence-commands {
          tailf:cli-reset-siblings;
        }
        leaf id-value {
          tailf:cli-drop-node-name;
          type uint16;
        }
        leaf mode {
          type enumeration {
            enum active;
            enum on;
            enum passive;
            enum inherit;
          }
        }
      }
      leaf port-priority {
        type uint16;
      }
    }
    container lacp {
      container period {
        leaf period-value {
          tailf:cli-drop-node-name;
          type uint16;
        }
        container short-enable {
          tailf:cli-drop-node-name;
          leaf short {
            type empty;
          }
        }
        container short {
          leaf receive {
            type uint16;
          }
          leaf transmit {
            type uint16;
          }
        }
      }
    }
    leaf small-frame-padding {
      type empty;
    }
  }

  grouping interface-pointtopoint-grouping {
    container keepalive {
      choice keepalive-choice {
        container values {
          tailf:cli-drop-node-name;
          tailf:cli-compact-syntax;
          tailf:cli-sequence-commands {
            tailf:cli-reset-siblings;
          }
          leaf interval {
            tailf:cli-drop-node-name;
            type uint8;
          }
          leaf retry {
            tailf:cli-drop-node-name;
            type uint8;
          }
        }
        leaf disable {
          type empty;
        }
      }
    }
    list pvc {
      key "dlci";
      leaf dlci {
        type uint16;
      }
      uses interface-service-policy-grouping;
      leaf encap {
        type enumeration {
          enum cisco;
          enum ietf;
        }
      }
      container fragment {
        tailf:cli-compact-syntax;
        leaf end-to-end {
          type uint16;
        }
        leaf fragment-counter {
          type empty;
        }
      }
    }
    container ppp {
      container multilink {
        container minimum-active {
          leaf links {
            type uint16;
          }
        }
      }
    }
  }

  grouping interface-multilink-grouping {
    container multilink {
      tailf:cli-add-mode;
      container fragment-size {
        tailf:cli-add-mode;
        tailf:cli-sequence-commands;
        leaf size {
          tailf:cli-drop-node-name;
          tailf:cli-hide-in-submode;
          type uint16;
        }
        leaf fragment-counter {
          type empty;
        }
      }
      container fragment {
        leaf size {
          type uint16;
        }
      }
    }
  }

  grouping interface-ethernet-grouping {
    leaf fec {
      type enumeration {
        enum none;
        enum base-r;
        enum standard;
      }
    }
    container report {
      leaf sd-ber {
        type empty;
      }
      container sf-ber {
        leaf disable {
          type empty;
        }
      }
    }
    container threshold {
      leaf sd-ber {
        type uint8;
      }
      leaf sf-ber {
        type uint8;
      }
    }
    container signal {
      container sf-ber {
        leaf remote-fault {
          type empty;
        }
      }
    }
    container carrier-delay {
      tailf:cli-compact-syntax;
      leaf up {
        type uint32;
      }
      leaf down {
        type uint32;
      }
    }
    container fat-pw {
      leaf load-balance {
        type enumeration {
          enum forwarding;
          enum terminated;
        }
      }
    }
    leaf duplex {
      type enumeration {
        enum full {
          tailf:code-name "duplex_full";
        }
        enum half {
          tailf:code-name "duplex_half";
        }
      }
    }
    container ethernet {
      container udld {
        tailf:cli-add-mode;
        presence "true";
        leaf mode {
          type enumeration {
            enum aggressive;
            enum normal;
          }
        }
        leaf message-time {
          type uint8;
        }
      }
      container cfm {
        tailf:cli-add-mode;
        container mep {
          list domain {
            key "name";
            leaf name {
              type string;
            }
            leaf service {
              tailf:cli-hide-in-submode;
              type string;
            }
            leaf mep-id {
              tailf:cli-hide-in-submode;
              type uint16;
            }
            leaf cos {
              type uint8;
            }
            container sla {
              container operation {
                list profile {
                  tailf:cli-suppress-mode;
                  tailf:cli-delete-when-empty;
                  tailf:cli-compact-syntax;
                  tailf:cli-sequence-commands;
                  key "name mep-id";
                  leaf name {
                    type string;
                  }
                  leaf target {
                    tailf:cli-prefix-key {
                      tailf:cli-before-key "2";
                    }
                    type empty;
                  }
                  leaf mep-id {
                    type uint16;
                  }
                }
              }
            }
            leaf propagate-remote-status {
              type empty;
            }
          }
        }
        container ais {
          container transmission {
            container up {
              tailf:cli-compact-syntax;
              presence "true";
              leaf cos {
                type uint8;
              }
              leaf interval {
                type enumeration {
                  enum 1s;
                  enum 1m;
                }
              }
            }
          }
        }
        container bandwidth-notifications {
          tailf:cli-add-mode;
          leaf hold-off {
            type uint16;
          }
          leaf wait-to-restore {
            type uint16;
          }
          container log {
            leaf changes {
              type empty;
            }
          }
        }
      }
      container oam {
        tailf:cli-add-mode;
        presence "true";
        leaf mode {
          type enumeration {
            enum active;
            enum passive;
          }
        }
        leaf profile {
          type string;
        }
        container connection {
          leaf timeout {
            type uint8;
          }
        }
        container mib-retrieval {
          tailf:cli-delete-when-empty;
          presence "true";
          leaf disable {
            type empty;
          }
        }
        container link-monitor {
          tailf:cli-add-mode;
          container monitoring {
            tailf:cli-delete-when-empty;
            presence "true";
            leaf disable {
              type empty;
            }
          }
        }
        container require-remote {
          tailf:cli-add-mode;
          leaf link-monitoring {
            type empty;
          }
        }
        container action {
          tailf:cli-add-mode;
          leaf critical-event {
            type if-eth-oam-action-type;
          }
          leaf dying-gasp {
            type if-eth-oam-action-type;
          }
          leaf capabilities-conflict {
            type if-eth-oam-action-type;
          }
          leaf discovery-timeout {
            type if-eth-oam-action-type;
          }
          leaf remote-loopback {
            type if-eth-oam-action-type;
          }
          leaf session-down {
            type if-eth-oam-action-type;
          }
          leaf wiring-conflict {
            type if-eth-oam-action-type;
          }
        }
        container remote-loopback {
          tailf:cli-delete-when-empty;
          presence "true";
          leaf disable {
            type empty;
          }
        }
        leaf hello-interval {
          type enumeration {
            enum 100ms;
            enum 1s;
          }
        }
      }
      leaf egress-filter {
        type enumeration {
          enum disable;
          enum strict;
        }
      }
      container loopback {
        tailf:cli-add-mode;
        container permit {
          leaf external {
            type empty;
          }
          leaf internal {
            type empty;
          }
        }
      }
      container service-activation-test {
        tailf:cli-add-mode;
        leaf permit {
          type enumeration {
            enum all;
            enum external;
            enum internal;
          }
        }
      }
    }
    container eapol {
      leaf destination-address {
        type string;
      }
      leaf eth-type {
        type enumeration {
          enum 876F;
        }
      }
    }
    container ethernet-services {
      list access-group {
        tailf:cli-suppress-mode;
        tailf:cli-delete-when-empty;
        tailf:cli-compact-syntax;
        key "direction";
        leaf direction {
          type enumeration {
            enum egress;
            enum ingress;
          }
        }
        leaf name {
          tailf:cli-drop-node-name;
          tailf:cli-prefix-key;
          type string;
        }
      }
    }
    leaf speed {
      type enumeration {
        enum 10;
        enum 100;
        enum 1000;
      }
    }
    container transceiver {
      container permit {
        container pid {
          leaf all {
            type empty;
          }
        }
      }
    }
    container nv {
      tailf:cli-add-mode;
      container edge {
        tailf:cli-add-mode;
        leaf interface {
          type empty;
        }
      }
      container service-policy {
        list input {
          tailf:cli-suppress-mode;
          tailf:cli-delete-when-empty;
          key "name";
          leaf name {
            type string;
          }
        }
      }
      container satellite-fabric-link {
        tailf:cli-add-mode;
        tailf:cli-compact-syntax;
        tailf:cli-sequence-commands;
        leaf satellite {
          tailf:cli-hide-in-submode;
          type uint16;
        }
        container redundancy {
          tailf:cli-break-sequence-commands;
          tailf:cli-add-mode;
          leaf iccp-group {
            type uint32;
          }
          container minimum {
            container preferred {
              leaf links {
                type uint8;
              }
            }
          }
        }
        container remote-ports {
          choice remote-ports-choice {
            leaf GigabitEthernet {
              type string;
            }
            leaf TenGigE {
              type string;
            }
          }
        }
        container minimum {
          container required {
            leaf links {
              type uint8;
            }
          }
        }
      }
    }
    container attach {
      leaf generic-interface-list {
        type string;
      }
    }
  }

  grouping interface-common-grouping {
    uses apply-group-grouping;
    leaf description {
      tailf:cli-multi-value;
      type string;
    }
    leaf bandwidth {
      type uint64;
    }
    leaf loopback {
      type enumeration {
        enum external;
        enum internal;
        enum line;
      }
    }
    leaf mtu {
      type uint16;
    }
    container negotiation {
      container auto {
        tailf:cli-delete-when-empty;
        presence "true";
        leaf allow-overrides {
          type empty;
        }
      }
    }
    uses interface-monitor-session-grouping;
    container encapsulation {
      choice encapsulation-choice {
        container frame-relay {
          tailf:cli-delete-when-empty;
          presence "true";
          leaf IETF {
            type empty;
          }
        }
        leaf hdlc {
          type empty;
        }
        leaf mfr {
          type empty;
        }
        leaf ppp {
          type empty;
        }
        leaf default {
          type empty;
        }
        container untagged {
          tailf:cli-compact-syntax;
          tailf:cli-delete-when-empty;
          presence "true";
        }
        container ambiguous {
          container dot1q {
            tailf:cli-compact-syntax;
            tailf:cli-sequence-commands {
              tailf:cli-reset-siblings;
            }
            leaf-list vlan-id {
              tailf:cli-drop-node-name;
              tailf:cli-range-list-syntax;
              type union {
                type uint16;
                type enumeration {
                  enum any;
                }
              }
            }
            leaf-list second-dot1q {
              tailf:cli-optional-in-sequence;
              tailf:cli-range-list-syntax;
              type union {
                type uint16;
                type enumeration {
                  enum any;
                }
              }
            }
          }
        }
        container dot1q {
          tailf:cli-compact-syntax;
          tailf:cli-sequence-commands {
            tailf:cli-reset-siblings;
          }
          leaf-list vlan-id {
            tailf:cli-drop-node-name;
            tailf:cli-range-list-syntax;
            type union {
              type uint16;
              type enumeration {
                enum any;
                enum priority-tagged;
                enum untagged;
              }
            }
          }
          leaf-list second-dot1q {
            tailf:cli-optional-in-sequence;
            tailf:cli-range-list-syntax;
            type union {
              type uint16;
              type enumeration {
                enum any;
              }
            }
          }
          leaf exact {
            tailf:cli-optional-in-sequence;
            type empty;
          }
          container ingress {
            tailf:cli-flatten-container;
            tailf:cli-compact-syntax;
            leaf source-mac {
              type string;
            }
          }
        }
        container dot1ad {
          tailf:cli-compact-syntax;
          tailf:cli-sequence-commands {
            tailf:cli-reset-siblings;
          }
          leaf-list vlan-id {
            tailf:cli-drop-node-name;
            tailf:cli-range-list-syntax;
            type union {
              type uint16;
              type enumeration {
                enum any;
                enum priority-tagged;
              }
            }
          }
          leaf-list dot1q {
            tailf:cli-range-list-syntax;
            tailf:cli-optional-in-sequence;
            type union {
              type uint16;
              type enumeration {
                enum any;
              }
            }
          }
          leaf exact {
            type empty;
          }
        }
      }
    }
    container pppoe {
      container enable {
        tailf:cli-delete-when-empty;
        presence "true";
        leaf bba-group {
          type string;
        }
      }
    }
    container frame-relay {
      container lmi {
        leaf disable {
          type empty;
        }
      }
      container lmi-type {
        tailf:cli-delete-when-empty;
        presence "true";
        leaf type {
          tailf:cli-drop-node-name;
          type enumeration {
            enum ansi;
            enum cisco;
            enum q933a;
          }
        }
      }
      container intf-type {
        tailf:cli-delete-when-empty;
        presence "true";
        leaf type {
          tailf:cli-drop-node-name;
          type enumeration {
            enum dce;
          }
        }
      }
      container multilink {
        leaf bandwidth-class {
          type enumeration {
            enum a;
            enum b;
            enum c;
          }
        }
      }
    }
    container frequency {
      container synchronization {
        tailf:cli-add-mode;
        presence "true";
        container selection {
          leaf input {
            type empty;
          }
        }
        leaf priority {
          type uint8;
        }
        leaf wait-to-restore {
          type uint8;
        }
        leaf time-of-day-priority {
          type uint8;
        }
        container quality {
          container receive {
            tailf:cli-compact-syntax;
            tailf:cli-sequence-commands {
              tailf:cli-reset-siblings;
            }
            uses freqsync-quality-grouping;
          }
          container transmit {
            tailf:cli-compact-syntax;
            tailf:cli-sequence-commands {
              tailf:cli-reset-siblings;
            }
            uses freqsync-quality-grouping;
          }
        }
      }
    }
    uses interface-service-policy-grouping;
    leaf vrf {
      type vrf-type;
    }
    container aaa {
      container radius {
        container attribute {
          leaf nas-port-type {
            type union {
              type uint8;
              type string;
            }
          }
        }
      }
    }
    container ptp {
      tailf:cli-add-mode;
      presence "true";
      container cos {
        leaf value {
          tailf:cli-drop-node-name;
          type uint8;
        }
        leaf event {
          type uint8;
        }
        leaf general {
          type uint8;
        }
      }
      leaf profile {
        type string;
      }
      leaf ipv4-ttl {
        type uint8;
      }
      leaf ipv6-hop-limit {
        type uint8;
      }
      container master {
        list ipv4 {
          key "address";
          leaf address {
            type inet:ipv4-address;
          }
          leaf priority {
            type uint8;
          }
        }
      }
      leaf local-priority {
        type uint8;
      }
      container delay-asymmetry {
        tailf:cli-compact-syntax;
        tailf:cli-sequence-commands {
          tailf:cli-reset-siblings;
        }
        leaf value {
          tailf:cli-drop-node-name;
          type int32;
        }
        leaf units {
          tailf:cli-drop-node-name;
          type enumeration {
            enum nanoseconds;
            enum microseconds;
            enum milliseconds;
          }
        }
      }
      container delay-response {
        leaf timeout {
          type uint32;
        }
        leaf grant-duration {
          type uint16;
        }
      }
      uses ptp-profile-grouping;
    }
    container ipv4 {
      leaf point-to-point {
        type empty;
      }
      choice address-choice {
        case yes {
          container address {
            tailf:cli-compact-syntax;
            tailf:cli-sequence-commands;
            leaf ip {
              tailf:cli-drop-node-name;
              type string;
            }
            leaf mask {
              tailf:cli-drop-node-name;
              type string;
            }
            leaf route-tag {
              type uint32;
            }
          }
          container address-secondary-list {
            tailf:cli-drop-node-name;
            list address {
              tailf:cli-suppress-mode;
              tailf:cli-delete-when-empty;
              tailf:cli-compact-syntax;
              tailf:cli-sequence-commands;
              key "ip secondary";
              leaf ip {
                type inet:ipv4-address;
              }
              leaf secondary {
                type enumeration {
                  enum secondary;
                }
              }
              leaf mask {
                tailf:cli-drop-node-name;
                tailf:cli-prefix-key {
                  tailf:cli-before-key "2";
                }
                type string;
              }
              leaf route-tag {
                type uint32;
              }
            }
          }
        }
        container address-dhcp {
          tailf:cli-drop-node-name;
          container address {
            tailf:cli-compact-syntax;
            tailf:cli-sequence-commands {
              tailf:cli-reset-siblings;
            }
            leaf dhcp {
              type empty;
            }
            leaf options {
              type enumeration {
                enum 60;
              }
            }
            leaf ascii {
              type string;
            }
          }
        }
      }
      list access-group {
        tailf:cli-suppress-mode;
        tailf:cli-delete-when-empty;
        tailf:cli-compact-syntax;
        tailf:cli-sequence-commands {
          tailf:cli-reset-all-siblings;
        }
        key "direction";
        leaf direction {
          type enumeration {
            enum egress;
            enum ingress;
          }
        }
        leaf common {
          tailf:cli-optional-in-sequence;
          tailf:cli-prefix-key;
          type string;
        }
        leaf name {
          tailf:cli-drop-node-name;
          tailf:cli-prefix-key;
          type string;
        }
        leaf hardware-count {
          tailf:cli-break-sequence-commands;
          type empty;
        }
        leaf interface-statistics {
          type empty;
        }
        container compress {
          tailf:cli-flatten-container;
          leaf level {
            type uint8;
          }
        }
      }
      container helper-address {
        list vrf {
          tailf:cli-suppress-mode;
          tailf:cli-delete-when-empty;
          key "name address";
          leaf name {
            type string;
          }
          leaf address {
            type inet:ipv4-address;
          }
        }
      }
      leaf mask-reply {
        type empty;
      }
      leaf forwarding-enable {
        type empty;
      }
      leaf redirects {
        type empty;
      }
      leaf directed-broadcast {
        type empty;
      }
      leaf mtu {
        type uint16;
      }
      leaf tcp-mss-adjust {
        type enumeration {
          enum enable;
        }
      }
      container bgp {
        container policy {
          container propagation {
            container input {
              container qos-group {
                choice qos-group-choice {
                  container destination {
                    presence "true";
                  }
                  container source {
                    tailf:cli-delete-when-empty;
                    presence "true";
                    leaf ip-precedence {
                      type enumeration {
                        enum destination;
                        enum source;
                      }
                    }
                  }
                }
              }
            }
          }
        }
      }
      container pim {
        leaf bidir-neighbor-filter {
          type union {
            type uint8;
            type string;
          }
        }
        leaf bsr-border {
          type empty;
        }
        leaf dr-priority {
          type uint32;
        }
        leaf nbma-mode {
          type empty;
        }
        leaf neighbor-filter {
          type union {
            type uint8;
            type string;
          }
        }
        container query-interval {
          tailf:cli-compact-syntax;
          tailf:cli-sequence-commands {
            tailf:cli-reset-siblings;
          }
          choice interval-choice {
            case secs {
              leaf secs {
                tailf:cli-drop-node-name;
                type uint16;
              }
            }
            case msec {
              leaf msecs {
                tailf:cli-drop-node-name;
                type uint16;
                must '../msec';
              }
              leaf msec {
                type empty;
              }
            }
          }
        }
        choice pim-mode {
          leaf sparse-dense-mode {
            type empty;
          }
          container dense-mode {
            presence "true";
            container proxy-register {
              choice proxy-mode {
                leaf list {
                  type union {
                    type uint16;
                    type uint16;
                    type string;
                  }
                }
                leaf route-map {
                  type string;
                }
              }
            }
          }
          leaf sparse-mode {
            type empty;
          }
        }
        container state-refresh {
          container origination-interval {
            tailf:cli-delete-when-empty;
            presence "true";
            leaf secs {
              tailf:cli-drop-node-name;
              type uint8;
            }
          }
        }
      }
      container verify {
        container unicast {
          container notification {
            leaf threshold {
              type uint32;
            }
          }
          container source {
            tailf:cli-compact-syntax;
            tailf:cli-sequence-commands {
              tailf:cli-reset-all-siblings;
            }
            leaf reachable-via {
              type enumeration {
                enum any;
                enum rx;
              }
            }
            leaf allow-self-ping {
              tailf:cli-break-sequence-commands;
              type empty;
            }
            leaf allow-default {
              type empty;
            }
          }
        }
      }
      container router {
        container isis {
          presence "true";
          leaf routing-process {
            tailf:cli-drop-node-name;
            type string;
          }
        }
      }
      container unnumbered {
        uses interface-name-grouping;
      }
      container unreachables {
        leaf disable {
          type empty;
        }
      }
      container flowspec {
        leaf disable {
          type empty;
        }
      }
    }
    container arp {
      leaf timeout {
        type uint32;
      }
      leaf purge-delay {
        type uint16;
      }
      leaf learning {
        type enumeration {
          enum disable;
          enum local;
        }
      }
      container gratuitous {
        leaf ignore {
          type empty;
        }
      }
    }
    leaf proxy-arp {
      type empty;
    }
    leaf local-proxy-arp {
      type empty;
    }
    container ipv6 {
      leaf mtu {
        type uint16;
      }
      leaf tcp-mss-adjust {
        type enumeration {
          enum enable;
        }
      }
      container nd {
        leaf cache-limit {
          type uint32;
        }
        leaf router-preference {
          type enumeration {
            enum low;
            enum high;
            enum medium;
          }
        }
        container dad {
          leaf attempts {
            type uint16;
          }
        }
        leaf managed-config-flag {
          type empty;
        }
        leaf ns-interval {
          type uint32;
        }
        leaf other-config-flag {
          type empty;
        }
        container prefix {
          list prefix-list {
            tailf:cli-drop-node-name;
            tailf:cli-suppress-mode;
            tailf:cli-delete-when-empty;
            tailf:cli-compact-syntax;
            key "prefix";
            leaf prefix {
              type union {
                type inet:ipv6-address-no-zone;
                type tailf:ipv6-address-and-prefix-length;
                type cisco-ios-xr:iosxr-ipv6-address;
              }
            }
            uses interface-ipv6-nd-prefix-list-grouping;
          }
          container default {
            uses interface-ipv6-nd-prefix-list-grouping;
          }
        }
        container ra {
          leaf hoplimit {
            type enumeration {
              enum unspecified;
            }
          }
          leaf mtu {
            type enumeration {
              enum unspecified;
              enum suppress;
            }
          }
        }
        container ra-interval {
          tailf:cli-compact-syntax;
          tailf:cli-sequence-commands {
            tailf:cli-reset-siblings;
          }
          leaf maximum {
            tailf:cli-drop-node-name;
            type uint16;
          }
          leaf minimum {
            tailf:cli-drop-node-name;
            type uint16;
          }
        }
        leaf ra-lifetime {
          type uint16;
        }
        leaf reachable-time {
          type uint32;
        }
        leaf redirects {
          type empty;
        }
        leaf suppress-ra {
          type empty;
        }
        leaf unicast-ra {
          type empty;
        }
      }
      container verify {
        container unicast {
          container source {
            tailf:cli-compact-syntax;
            tailf:cli-sequence-commands;
            leaf reachable-via {
              type enumeration {
                enum any;
                enum rx;
              }
            }
            leaf allow-default {
              tailf:cli-break-sequence-commands;
              type empty;
            }
            leaf allow-self-ping {
              type empty;
            }
          }
        }
      }
      container address {
        list prefix-list {
          tailf:cli-drop-node-name;
          tailf:cli-suppress-mode;
          tailf:cli-delete-when-empty;
          tailf:cli-compact-syntax;
          tailf:cli-sequence-commands {
            tailf:cli-reset-all-siblings;
          }
          key "prefix";
          leaf prefix {
            type union {
              type inet:ipv6-address-no-zone;
              type tailf:ipv6-address-and-prefix-length;
              type string;
            }
          }
          leaf eui-64 {
            tailf:cli-optional-in-sequence;
            type empty;
          }
          leaf link-local {
            tailf:cli-optional-in-sequence;
            type empty;
          }
          leaf route-tag {
            type uint32;
          }
        }
      }
      leaf enable {
        type empty;
      }
      list access-group {
        tailf:cli-suppress-mode;
        tailf:cli-delete-when-empty;
        tailf:cli-compact-syntax;
        key "direction";
        leaf direction {
          type enumeration {
            enum egress;
            enum ingress;
          }
        }
        leaf common {
          tailf:cli-optional-in-sequence;
          tailf:cli-prefix-key;
          type string;
        }
        leaf name {
          tailf:cli-drop-node-name;
          tailf:cli-prefix-key;
          type string;
        }
        leaf interface-statistics {
          type empty;
        }
        container compress {
          tailf:cli-flatten-container;
          leaf level {
            type uint8;
          }
        }
      }
      container unreachables {
        leaf disable {
          type empty;
        }
      }
      container flowspec {
        leaf disable {
          type empty;
        }
      }
      container bgp {
        container policy {
          container propagation {
            container input {
              container qos-group {
                choice qos-group-choice {
                  container destination {
                    tailf:cli-delete-when-empty;
                    presence "true";
                  }
                  container source {
                    tailf:cli-delete-when-empty;
                    presence "true";
                    leaf ip-precedence {
                      type enumeration {
                        enum destination;
                        enum source;
                      }
                    }
                  }
                }
              }
            }
          }
        }
      }
    }
    container lldp {
      tailf:cli-add-mode;
      presence "true";
      leaf enable {
        type empty;
      }
      container receive {
        leaf disable {
          type empty;
        }
      }
      container transmit {
        leaf disable {
          type empty;
        }
      }
    }
    container mpls {
      tailf:cli-add-mode;
      leaf ip {
        type empty;
      }
      container label-security {
        leaf rpf {
          type empty;
        }
        leaf multi-label-packet {
          type enumeration {
            enum drop;
          }
        }
      }
      leaf mtu {
        type uint16;
      }
    }
    container backup-bw {
      tailf:cli-compact-syntax;
      tailf:cli-sequence-commands {
        tailf:cli-reset-siblings;
      }
      choice backup-bw-choice {
        container unlimited {
          tailf:cli-optional-in-sequence;
          choice unlimited-choice {
            leaf any-class-type {
              type empty;
            }
            leaf class-type {
              type uint8;
            }
          }
        }
        case value {
          leaf bandwidth {
            tailf:cli-drop-node-name;
            type uint64;
          }
          leaf any-class-type {
            tailf:cli-optional-in-sequence;
            type empty;
          }
          leaf class-type {
            type uint8;
          }
        }
      }
    }
    uses exclude-item-grouping;
    leaf shutdown {
      type empty;
    }
    uses interface-isis-grouping;
    leaf load-interval {
      type uint16;
    }
    container ipsubscriber {
      leaf interface {
        type empty;
      }
      container ipv4 {
        container routed {
          tailf:cli-add-mode;
          container initiator {
            leaf dhcp {
              type empty;
            }
          }
        }
        container l2-connected {
          tailf:cli-add-mode;
          container initiator {
            leaf dhcp {
              type empty;
            }
            container unclassified-source {
              tailf:cli-delete-when-empty;
              presence "true";
              leaf address-unique {
                type empty;
              }
            }
          }
        }
      }
      container ipv6 {
        container l2-connected {
          tailf:cli-add-mode;
          container initiator {
            leaf dhcp {
              type empty;
            }
          }
        }
      }
    }
    container ipsubscriber-cnbng-nal {
      tailf:cli-drop-node-name;
      container ipsubscriber {
        tailf:cli-add-mode;
        presence "true";
        container ipv4 {
          container l2-connected {
            tailf:cli-add-mode;
            presence "true";
            container initiator {
              leaf dhcp {
                type empty;
              }
            }
          }
        }
        container ipv6 {
          container l2-connected {
            tailf:cli-add-mode;
            presence "true";
            container initiator {
              leaf dhcp {
                type empty;
              }
            }
          }
        }
      }
    }
    container capture {
      container software {
        leaf packets {
          type empty;
        }
      }
    }
    container address-family {
      container ipv4 {
        leaf multicast {
          type empty;
        }
      }
    }
    container transport-mode {
      choice transport-mode-choice {
        leaf wan {
          type empty;
        }
        container otn {
          leaf bit-transparent {
            type enumeration {
              enum opu1e;
              enum opu2e;
            }
          }
        }
        leaf rx-only {
          type empty;
        }
        leaf tx-only {
          type empty;
        }
      }
    }
    leaf flow-control {
      type enumeration {
        enum bidirectional;
        enum egress;
        enum ingress;
      }
    }
    list flow {
      tailf:cli-suppress-mode;
      tailf:cli-delete-when-empty;
      tailf:cli-compact-syntax;
      key "proto monitor direction";
      leaf proto {
        type enumeration {
          enum ipv4;
          enum ipv6;
          enum mpls;
        }
      }
      leaf monitor {
        type string;
      }
      leaf sampler {
        tailf:cli-prefix-key {
          tailf:cli-before-key "3";
        }
        type string;
      }
      leaf direction {
        type enumeration {
          enum egress;
          enum ingress;
        }
      }
    }
    container dampening {
      tailf:cli-compact-syntax;
      tailf:cli-delete-when-empty;
      tailf:cli-sequence-commands {
        tailf:cli-reset-siblings;
      }
      presence "true";
      leaf half-life {
        tailf:cli-drop-node-name;
        type uint8;
      }
      leaf reuse {
        tailf:cli-drop-node-name;
        type uint16;
      }
      leaf suppress {
        tailf:cli-drop-node-name;
        type uint16;
      }
      leaf max-suppress-time {
        tailf:cli-drop-node-name;
        type uint8;
      }
      leaf restart-penalty {
        tailf:cli-drop-node-name;
        type uint16;
      }
    }
    container logging {
      container events {
        leaf all {
          type empty;
        }
        leaf bundle-status {
          type empty;
        }
        leaf link-status {
          type empty;
        }
        leaf nfas-status {
          type empty;
        }
        container spanning-tree {
          leaf status {
            type empty;
          }
        }
        container subif-link-status {
          tailf:cli-delete-when-empty;
          presence "true";
          leaf ignore-bulk {
            type empty;
          }
        }
        leaf trunk-status {
          type empty;
        }
        uses logging-events-lsp-status-grouping;
        container sub-lsp-status {
          leaf state {
            type empty;
          }
        }
        leaf pcalc-failure {
          type empty;
        }
      }
      container ip {
        container access-list {
          container cache {
            leaf in {
              type empty;
            }
            leaf out {
              type empty;
            }
          }
        }
      }
    }
    container storm-control {
      container action {
        leaf level {
          type decimal64 {
            fraction-digits 2;
          }
        }
      }
      container broadcast {
        leaf level {
          type decimal64 {
            fraction-digits 2;
          }
        }
      }
      container multicast {
        leaf level {
          type decimal64 {
            fraction-digits 2;
          }
        }
      }
      container unicast {
        leaf level {
          type decimal64 {
            fraction-digits 2;
          }
        }
      }
    }
    leaf mac-address {
      type string;
    }
    container mac-accounting {
      leaf ingress {
        type empty;
      }
      leaf egress {
        type empty;
      }
    }
    container dot1x {
      leaf profile {
        type string;
      }
    }
    container macsec {
      container psk-keychain {
        tailf:cli-compact-syntax;
        tailf:cli-sequence-commands {
          tailf:cli-reset-siblings;
        }
        leaf name {
          tailf:cli-drop-node-name;
          type string;
        }
        leaf fallback-psk-keychain {
          tailf:cli-optional-in-sequence;
          type string;
        }
        leaf policy {
          type string;
        }
      }
      container eap {
        leaf policy {
          type string;
        }
      }
    }
    container lns {
      leaf enable {
        type empty;
      }
    }
    uses interface-cnbng-nal-grouping;
  }

  grouping subinterface-common-grouping {
    container rewrite {
      container ingress {
        container tag {
          tailf:cli-compact-syntax;
          tailf:cli-sequence-commands {
            tailf:cli-reset-siblings;
          }
          choice tag-choice {
            leaf pop {
              type enumeration {
                enum 1;
                enum 2;
              }
            }
            leaf push {
              type empty;
            }
            leaf translate {
              type enumeration {
                enum 1-to-1;
                enum 1-to-2;
                enum 2-to-1;
                enum 2-to-2;
              }
            }
          }
          leaf dot1ad {
            tailf:cli-optional-in-sequence;
            type uint16;
          }
          leaf dot1q {
            tailf:cli-optional-in-sequence;
            type uint16;
          }
          leaf second-dot1q {
            tailf:cli-optional-in-sequence;
            type uint16;
          }
          leaf mode {
            tailf:cli-drop-node-name;
            type enumeration {
              enum symmetric;
            }
          }
        }
      }
    }
    container dot1q {
      container vlan {
        tailf:cli-compact-syntax;
        tailf:cli-sequence-commands {
          tailf:cli-reset-siblings;
        }
        leaf vlan-id {
          tailf:cli-drop-node-name;
          type uint16;
        }
        leaf second-dot1q {
          tailf:cli-drop-node-name;
          type union {
            type uint16;
            type string;
            type enumeration {
              enum any;
            }
          }
        }
      }
    }
    container dot1ad {
      tailf:cli-compact-syntax;
      tailf:cli-sequence-commands {
        tailf:cli-reset-siblings;
      }
      leaf vlan-id {
        tailf:cli-drop-node-name;
        type uint16;
      }
      leaf second-dot1d {
        tailf:cli-drop-node-name;
        type union {
          type uint16;
          type string;
          type enumeration {
            enum any;
          }
        }
      }
    }
    container l2protocol {
      leaf cpsv {
        type enumeration {
          enum drop;
          enum reverse-tunnel;
          enum tunnel;
        }
      }
    }
  }

  grouping interface-bfd-grouping {
    container bfd {
      container address-family {
        grouping bfd-param-grouping {
          container timers {
            leaf start {
              type uint16;
            }
            leaf nbr-unconfig {
              type uint16;
            }
          }
          leaf multiplier {
            type uint8;
          }
          leaf fast-detect {
            type empty;
          }
          leaf minimum-interval {
            type uint16;
          }
        }

        container ipv4 {
          uses bfd-param-grouping;
          container echo {
            leaf minimum-interval {
              type uint16;
            }
          }
          leaf destination {
            type inet:ipv4-address;
          }
        }
        container ipv6 {
          uses bfd-param-grouping;
          leaf destination {
            type inet:ipv6-address;
          }
        }
      }
      leaf echo {
        type empty;
      }
      container interval {
        tailf:cli-compact-syntax;
        tailf:cli-sequence-commands;
        leaf msecs {
          tailf:cli-drop-node-name;
          type uint16;
        }
        leaf min_rx {
          type uint16;
        }
        leaf multiplier {
          type uint8;
        }
      }
      leaf mode {
        type enumeration {
          enum cisco;
          enum ietf;
        }
      }
    }
  }

  grouping non-subinterface-common-grouping {
    container backup {
      container interface {
        uses interface-name-grouping;
      }
    }
    leaf cdp {
      type empty;
    }
    container dual-active {
      leaf fast-hello {
        type empty;
      }
    }
    container l2transport {
      tailf:cli-add-mode;
      presence "true";
      uses interface-service-policy-grouping;
      container l2protocol {
        leaf cpsv {
          type enumeration {
            enum drop;
            enum reverse-tunnel;
            enum tunnel;
          }
        }
        container cdp {
          tailf:cli-compact-syntax;
          tailf:cli-sequence-commands {
            tailf:cli-reset-siblings;
          }
          uses if-l2transport-l2protocol-grouping;
        }
        container stp {
          tailf:cli-compact-syntax;
          tailf:cli-sequence-commands {
            tailf:cli-reset-siblings;
          }
          uses if-l2transport-l2protocol-grouping;
        }
        container vtp {
          tailf:cli-compact-syntax;
          tailf:cli-sequence-commands {
            tailf:cli-reset-siblings;
          }
          uses if-l2transport-l2protocol-grouping;
        }
        container pvst {
          tailf:cli-compact-syntax;
          tailf:cli-sequence-commands {
            tailf:cli-reset-siblings;
          }
          uses if-l2transport-l2protocol-grouping;
        }
      }
      container propagate {
        leaf remote-status {
          type empty;
        }
      }
      uses interface-monitor-session-grouping;
    }
    container platform {
      container qos {
        leaf channel-consistency {
          type boolean;
        }
      }
    }
    container xconnect {
      leaf vfi {
        type string;
      }
    }
    uses interface-switch-grouping;
  }

  grouping interface-tunnel-te-grouping {
    leaf signalled-name {
      type string;
    }
    container signalled-bandwidth {
      tailf:cli-compact-syntax;
      tailf:cli-sequence-commands {
        tailf:cli-reset-siblings;
      }
      leaf sub-pool {
        tailf:cli-optional-in-sequence;
        type empty;
      }
      leaf bandwidth {
        tailf:cli-drop-node-name;
        type uint32;
      }
      leaf class-type {
        type uint8;
      }
    }
    container priority {
      tailf:cli-compact-syntax;
      tailf:cli-sequence-commands {
        tailf:cli-reset-siblings;
      }
      leaf setup {
        tailf:cli-drop-node-name;
        type uint8;
      }
      leaf hold-value {
        tailf:cli-drop-node-name;
        type uint8;
      }
    }
    container binding-sid {
      container mpls {
        tailf:cli-delete-when-empty;
        presence "true";
        leaf label {
          type uint16;
        }
      }
    }
    choice fast-reroute-choice {
      leaf fast-reroute {
        type empty;
      }
      container fast-reroute-conf {
        tailf:cli-drop-node-name;
        container fast-reroute {
          leaf protect {
            type enumeration {
              enum bandwidth;
              enum node;
            }
          }
        }
      }
    }
    container policy-class {
      choice policy-class-choice {
        leaf-list values {
          tailf:cli-drop-node-name;
          tailf:cli-flat-list-syntax;
          ordered-by user;
          type uint8;
        }
        leaf default {
          type empty;
        }
      }
    }
    leaf record-route {
      type empty;
    }
    uses affinity-grouping;
  }

  grouping mpls-traffic-eng-controller-path-option-grouping {
    list path-option {
      tailf:cli-suppress-mode;
      tailf:cli-delete-when-empty;
      tailf:cli-compact-syntax;
      tailf:cli-sequence-commands {
        tailf:cli-reset-siblings;
      }
      key "id";
      leaf id {
        type uint16;
      }
      choice path-choice {
        case explicit {
          leaf explicit {
            type empty;
          }
          leaf identifier {
            tailf:cli-optional-in-sequence;
            type uint16;
          }
          leaf name {
            type string;
          }
        }
        case no-ero {
          leaf no-ero {
            type empty;
          }
        }
        case dynamic {
          leaf dynamic {
            type empty;
          }
        }
      }
      leaf signaled-label {
        tailf:cli-break-sequence-commands;
        type enumeration {
          enum dwdm;
        }
      }
      leaf wavelength {
        type uint8;
      }
      leaf protected-by {
        type union {
          type uint32;
          type enumeration {
            enum none;
          }
        }
      }
      leaf xro-attribute-set {
        tailf:cli-optional-in-sequence;
        type string;
      }
      leaf lockdown {
        type empty;
      }
      leaf verbatim {
        type empty;
      }
    }
  }

  grouping interface-tunnel-path-option-grouping {
    list path-option {
      tailf:cli-suppress-mode;
      tailf:cli-delete-when-empty;
      tailf:cli-compact-syntax;
      tailf:cli-sequence-commands {
        tailf:cli-reset-all-siblings;
      }
      key "preference-priority";
      leaf preference-priority {
        type uint16;
      }
      choice path-option-choice {
        container dynamic {
          tailf:cli-flatten-container;
          tailf:cli-compact-syntax;
          presence "true";
        }
        container explicit {
          tailf:cli-flatten-container;
          tailf:cli-compact-syntax;
          tailf:cli-sequence-commands {
            tailf:cli-reset-siblings;
          }
          choice path-choice {
            leaf identifier {
              type uint32;
            }
            leaf name {
              type string;
            }
          }
        }
      }
      leaf pce {
        tailf:cli-break-sequence-commands;
        type empty;
      }
      container address {
        tailf:cli-flatten-container;
        tailf:cli-compact-syntax;
        leaf ipv4 {
          type inet:ipv4-address;
        }
      }
      leaf segment-routing {
        type empty;
      }
      leaf verbatim {
        type empty;
      }
      leaf lockdown {
        type empty;
      }
      container ospf {
        tailf:cli-flatten-container;
        tailf:cli-compact-syntax;
        tailf:cli-sequence-commands {
          tailf:cli-reset-siblings;
        }
        leaf instance-name {
          tailf:cli-drop-node-name;
          type string;
        }
        leaf area {
          type union {
            type uint32;
            type inet:ipv4-address;
          }
        }
      }
      leaf attribute-set {
        type string;
      }
      leaf protected-by {
        type union {
          type uint32;
          type enumeration {
            enum none;
          }
        }
      }
      leaf protected-by-secondary {
        tailf:cli-drop-node-name;
        type uint16;
      }
      leaf protected-by-tertiary {
        tailf:cli-drop-node-name;
        type uint16;
      }
      leaf protected-by-fourth {
        tailf:cli-drop-node-name;
        type uint16;
      }
    }
  }

  grouping interface-name-grouping {
    choice interface-choice {
      leaf Bundle-Ether {
        tailf:cli-allow-join-with-value;
        type uint16;
      }
      container Bundle-Ether-subinterface {
        tailf:cli-drop-node-name;
        tailf:cli-flatten-container;
        tailf:cli-compact-syntax;
        leaf Bundle-Ether {
          tailf:cli-allow-join-with-value;
          type string;
        }
      }
      leaf Bundle-POS {
        tailf:cli-allow-join-with-value;
        type uint16;
      }
      leaf BVI {
        tailf:cli-allow-join-with-value;
        type uint32;
      }
      leaf PTP {
        tailf:cli-allow-join-with-value;
        type string;
      }
      leaf FastEthernet {
        tailf:cli-allow-join-with-value;
        type string;
      }
      container FastEthernet-subinterface {
        tailf:cli-drop-node-name;
        tailf:cli-flatten-container;
        tailf:cli-compact-syntax;
        leaf FastEthernet {
          tailf:cli-allow-join-with-value;
          type string;
        }
      }
      leaf GigabitEthernet {
        tailf:cli-allow-join-with-value;
        type string;
      }
      container GigabitEthernet-subinterface {
        tailf:cli-drop-node-name;
        tailf:cli-flatten-container;
        tailf:cli-compact-syntax;
        leaf GigabitEthernet {
          tailf:cli-allow-join-with-value;
          type string;
        }
      }
      leaf TenGigE {
        tailf:cli-allow-join-with-value;
        type string;
      }
      container TenGigE-subinterface {
        tailf:cli-drop-node-name;
        tailf:cli-flatten-container;
        tailf:cli-compact-syntax;
        leaf TenGigE {
          tailf:cli-allow-join-with-value;
          type string;
        }
      }
      leaf TwentyFiveGigE {
        tailf:cli-allow-join-with-value;
        type string;
      }
      container TwentyFiveGigE-subinterface {
        tailf:cli-drop-node-name;
        tailf:cli-flatten-container;
        tailf:cli-compact-syntax;
        leaf TwentyFiveGigE {
          tailf:cli-allow-join-with-value;
          type string;
        }
      }
      leaf FortyGigE {
        tailf:cli-allow-join-with-value;
        type string;
      }
      container FortyGigE-subinterface {
        tailf:cli-drop-node-name;
        tailf:cli-flatten-container;
        tailf:cli-compact-syntax;
        leaf FortyGigE {
          tailf:cli-allow-join-with-value;
          type string;
        }
      }
      leaf FiftyGigE {
        tailf:cli-allow-join-with-value;
        type string;
      }
      container FiftyGigE-subinterface {
        tailf:cli-drop-node-name;
        tailf:cli-flatten-container;
        tailf:cli-compact-syntax;
        leaf FiftyGigE {
          tailf:cli-allow-join-with-value;
          type string;
        }
      }
      leaf HundredGigE {
        tailf:cli-allow-join-with-value;
        type string;
      }
      container HundredGigE-subinterface {
        tailf:cli-drop-node-name;
        tailf:cli-flatten-container;
        tailf:cli-compact-syntax;
        leaf HundredGigE {
          tailf:cli-allow-join-with-value;
          type string;
        }
      }
      leaf TwoHundredGigE {
        tailf:cli-allow-join-with-value;
        type string;
      }
      container TwoHundredGigE-subinterface {
        tailf:cli-drop-node-name;
        tailf:cli-flatten-container;
        tailf:cli-compact-syntax;
        leaf TwoHundredGigE {
          tailf:cli-allow-join-with-value;
          type string;
        }
      }
      leaf FourHundredGigE {
        tailf:cli-allow-join-with-value;
        type string;
      }
      container FourHundredGigE-subinterface {
        tailf:cli-drop-node-name;
        tailf:cli-flatten-container;
        tailf:cli-compact-syntax;
        leaf FourHundredGigE {
          tailf:cli-allow-join-with-value;
          type string;
        }
      }
      leaf PW-Ether {
        tailf:cli-allow-join-with-value;
        type uint16;
      }
      container PW-Ether-subinterface {
        tailf:cli-drop-node-name;
        tailf:cli-flatten-container;
        tailf:cli-compact-syntax;
        leaf PW-Ether {
          tailf:cli-allow-join-with-value;
          type string;
        }
      }
      leaf PW-IW {
        tailf:cli-allow-join-with-value;
        type uint16;
      }
      leaf Null {
        tailf:cli-allow-join-with-value;
        type string;
      }
      leaf Loopback {
        tailf:cli-allow-join-with-value;
        type uint32;
      }
      leaf MgmtEth {
        tailf:cli-allow-join-with-value;
        type string;
      }
      leaf Multilink {
        tailf:cli-allow-join-with-value;
        type string;
      }
      container Multilink-subinterface {
        tailf:cli-drop-node-name;
        tailf:cli-flatten-container;
        tailf:cli-compact-syntax;
        leaf Multilink {
          tailf:cli-allow-join-with-value;
          type string;
        }
      }
      leaf SRP {
        tailf:cli-allow-join-with-value;
        type string;
      }
      leaf Port-channel {
        tailf:cli-allow-join-with-value;
        type uint32;
      }
      leaf POS {
        tailf:cli-allow-join-with-value;
        type string;
      }
      container POS-subinterface {
        tailf:cli-drop-node-name;
        tailf:cli-flatten-container;
        tailf:cli-compact-syntax;
        leaf POS {
          tailf:cli-allow-join-with-value;
          type string;
        }
      }
      leaf Serial {
        tailf:cli-allow-join-with-value;
        type string;
      }
      container Serial-subinterface {
        tailf:cli-drop-node-name;
        tailf:cli-flatten-container;
        tailf:cli-compact-syntax;
        leaf Serial {
          tailf:cli-allow-join-with-value;
          type string;
        }
      }
      leaf tunnel-ip {
        tailf:cli-allow-join-with-value;
        type uint16;
      }
      leaf tunnel-te {
        tailf:cli-allow-join-with-value;
        type uint16;
      }
      leaf tunnel-tp {
        tailf:cli-allow-join-with-value;
        type uint16;
      }
      leaf tunnel-mte {
        tailf:cli-allow-join-with-value;
        type uint16;
      }
      leaf tunnel-ipsec {
        type uint32;
      }
      leaf ATM {
        tailf:cli-allow-join-with-value;
        type string;
      }
      container ATM-subinterface {
        tailf:cli-drop-node-name;
        tailf:cli-flatten-container;
        tailf:cli-compact-syntax;
        leaf ATM {
          tailf:cli-allow-join-with-value;
          type string;
        }
      }
      leaf Vlan {
        tailf:cli-allow-join-with-value;
        type uint16;
      }
      leaf CEM {
        tailf:cli-allow-join-with-value;
        type string;
      }
      leaf GCC0 {
        tailf:cli-allow-join-with-value;
        type string;
      }
      leaf CSI {
        tailf:cli-allow-join-with-value;
        type uint8;
      }
    }
  }

  grouping interface-grouping {
    list Null {
      tailf:cli-allow-join-with-key;
      key "id";
      leaf id {
        type string;
      }
      container ipv4 {
        container icmp {
          container unreachables {
            leaf disable {
              type empty;
            }
          }
        }
      }
      container ipv6 {
        container icmp {
          container unreachables {
            leaf disable {
              type empty;
            }
          }
        }
      }
    }
    list Loopback {
      tailf:cli-allow-join-with-key;
      key "id";
      leaf id {
        type uint32;
      }
      uses interface-common-grouping;
      uses interface-bfd-grouping;
      uses non-subinterface-common-grouping;
    }
    list Bundle-Ether {
      tailf:cli-allow-join-with-key;
      key "id";
      leaf id {
        type uint16;
      }
      uses interface-common-grouping;
      uses interface-ethernet-grouping;
      uses interface-bfd-grouping;
      uses non-subinterface-common-grouping;
      uses interface-bundle-grouping;
    }
    container Bundle-Ether-subinterface {
      tailf:cli-drop-node-name;
      list Bundle-Ether {
        tailf:cli-allow-join-with-key;
        key "id";
        leaf id {
          type string;
        }
        leaf mode {
          tailf:cli-drop-node-name;
          tailf:cli-hide-in-submode;
          type enumeration {
            enum l2transport;
            enum symmetric;
          }
        }
        uses interface-common-grouping;
        uses interface-ethernet-grouping;
        uses subinterface-common-grouping;
        uses interface-bundle-grouping;
      }
    }
    list Bundle-POS {
      tailf:cli-allow-join-with-key;
      key "id";
      leaf id {
        type uint16;
      }
      uses interface-common-grouping;
      uses interface-ethernet-grouping;
      uses interface-bfd-grouping;
      uses non-subinterface-common-grouping;
      uses interface-bundle-grouping;
    }
    list MgmtEth {
      tailf:cli-allow-join-with-key;
      key "id";
      leaf id {
        type string;
      }
      uses interface-common-grouping;
      uses interface-ethernet-grouping;
      uses interface-bfd-grouping;
      uses non-subinterface-common-grouping;
      uses interface-non-bundle-grouping;
    }
    list TenGigE {
      tailf:cli-allow-join-with-key;
      key "id";
      leaf id {
        type string;
      }
      uses interface-common-grouping;
      uses interface-ethernet-grouping;
      uses interface-bfd-grouping;
      uses non-subinterface-common-grouping;
      uses interface-non-bundle-grouping;
    }
    container TenGigE-subinterface {
      tailf:cli-drop-node-name;
      list TenGigE {
        tailf:cli-allow-join-with-key;
        key "id";
        leaf id {
          type string;
        }
        leaf mode {
          tailf:cli-drop-node-name;
          tailf:cli-hide-in-submode;
          type enumeration {
            enum l2transport;
            enum symmetric;
          }
        }
        uses interface-common-grouping;
        uses interface-ethernet-grouping;
        uses subinterface-common-grouping;
      }
    }
    list TwentyFiveGigE {
      tailf:cli-allow-join-with-key;
      key "id";
      leaf id {
        type string;
      }
      uses interface-common-grouping;
      uses interface-ethernet-grouping;
      uses interface-bfd-grouping;
      uses non-subinterface-common-grouping;
      uses interface-non-bundle-grouping;
    }
    container TwentyFiveGigE-subinterface {
      tailf:cli-drop-node-name;
      list TwentyFiveGigE {
        tailf:cli-allow-join-with-key;
        key "id";
        leaf id {
          type string;
        }
        leaf mode {
          tailf:cli-drop-node-name;
          tailf:cli-hide-in-submode;
          type enumeration {
            enum l2transport;
            enum symmetric;
          }
        }
        uses interface-common-grouping;
        uses interface-ethernet-grouping;
        uses subinterface-common-grouping;
      }
    }
    list FortyGigE {
      tailf:cli-allow-join-with-key;
      key "id";
      leaf id {
        type string;
      }
      uses interface-common-grouping;
      uses interface-ethernet-grouping;
      uses interface-bfd-grouping;
      uses non-subinterface-common-grouping;
      uses interface-non-bundle-grouping;
    }
    container FortyGigE-subinterface {
      tailf:cli-drop-node-name;
      list FortyGigE {
        tailf:cli-allow-join-with-key;
        key "id";
        leaf id {
          type string;
        }
        leaf mode {
          tailf:cli-drop-node-name;
          tailf:cli-hide-in-submode;
          type enumeration {
            enum l2transport;
            enum symmetric;
          }
        }
        uses interface-common-grouping;
        uses interface-ethernet-grouping;
        uses subinterface-common-grouping;
      }
    }
    list FiftyGigE {
      tailf:cli-allow-join-with-key;
      key "id";
      leaf id {
        type string;
      }
      uses interface-common-grouping;
      uses interface-ethernet-grouping;
      uses interface-bfd-grouping;
      uses non-subinterface-common-grouping;
      uses interface-non-bundle-grouping;
    }
    container FiftyGigE-subinterface {
      tailf:cli-drop-node-name;
      list FiftyGigE {
        tailf:cli-allow-join-with-key;
        key "id";
        leaf id {
          type string;
        }
        leaf mode {
          tailf:cli-drop-node-name;
          tailf:cli-hide-in-submode;
          type enumeration {
            enum l2transport;
            enum symmetric;
          }
        }
        uses interface-common-grouping;
        uses interface-ethernet-grouping;
        uses subinterface-common-grouping;
      }
    }
    list HundredGigE {
      tailf:cli-allow-join-with-key;
      key "id";
      leaf id {
        type string;
      }
      uses interface-common-grouping;
      uses interface-ethernet-grouping;
      uses interface-bfd-grouping;
      uses non-subinterface-common-grouping;
      uses interface-non-bundle-grouping;
    }
    container HundredGigE-subinterface {
      tailf:cli-drop-node-name;
      list HundredGigE {
        tailf:cli-allow-join-with-key;
        key "id";
        leaf id {
          type string;
        }
        leaf mode {
          tailf:cli-drop-node-name;
          tailf:cli-hide-in-submode;
          type enumeration {
            enum l2transport;
            enum symmetric;
          }
        }
        uses interface-common-grouping;
        uses interface-ethernet-grouping;
        uses subinterface-common-grouping;
      }
    }
    list TwoHundredGigE {
      tailf:cli-allow-join-with-key;
      key "id";
      leaf id {
        type string;
      }
      uses interface-common-grouping;
      uses interface-ethernet-grouping;
      uses interface-bfd-grouping;
      uses non-subinterface-common-grouping;
      uses interface-non-bundle-grouping;
    }
    container TwoHundredGigE-subinterface {
      tailf:cli-drop-node-name;
      list TwoHundredGigE {
        tailf:cli-allow-join-with-key;
        key "id";
        leaf id {
          type string;
        }
        leaf mode {
          tailf:cli-drop-node-name;
          tailf:cli-hide-in-submode;
          type enumeration {
            enum l2transport;
            enum symmetric;
          }
        }
        uses interface-common-grouping;
        uses interface-ethernet-grouping;
        uses subinterface-common-grouping;
      }
    }
    list FourHundredGigE {
      tailf:cli-allow-join-with-key;
      key "id";
      leaf id {
        type string;
      }
      uses interface-common-grouping;
      uses interface-ethernet-grouping;
      uses interface-bfd-grouping;
      uses non-subinterface-common-grouping;
      uses interface-non-bundle-grouping;
    }
    container FourHundredGigE-subinterface {
      tailf:cli-drop-node-name;
      list FourHundredGigE {
        tailf:cli-allow-join-with-key;
        key "id";
        leaf id {
          type string;
        }
        leaf mode {
          tailf:cli-drop-node-name;
          tailf:cli-hide-in-submode;
          type enumeration {
            enum l2transport;
            enum symmetric;
          }
        }
        uses interface-common-grouping;
        uses interface-ethernet-grouping;
        uses subinterface-common-grouping;
      }
    }
    list FastEthernet {
      tailf:cli-allow-join-with-key;
      key "id";
      leaf id {
        type string;
      }
      uses interface-common-grouping;
      uses interface-ethernet-grouping;
      uses interface-bfd-grouping;
      uses non-subinterface-common-grouping;
      uses interface-non-bundle-grouping;
    }
    container FastEthernet-subinterface {
      tailf:cli-drop-node-name;
      list FastEthernet {
        tailf:cli-allow-join-with-key;
        key "id";
        leaf id {
          type string;
        }
        leaf mode {
          tailf:cli-drop-node-name;
          tailf:cli-hide-in-submode;
          type enumeration {
            enum l2transport;
          }
        }
        uses interface-common-grouping;
        uses interface-ethernet-grouping;
        uses subinterface-common-grouping;
      }
    }
    list GigabitEthernet {
      tailf:cli-allow-join-with-key;
      key "id";
      leaf id {
        type string;
      }
      uses interface-common-grouping;
      uses interface-ethernet-grouping;
      uses interface-bfd-grouping;
      uses non-subinterface-common-grouping;
      uses interface-non-bundle-grouping;
    }
    container GigabitEthernet-subinterface {
      tailf:cli-drop-node-name;
      list GigabitEthernet {
        tailf:cli-allow-join-with-key;
        key "id";
        leaf id {
          type string;
        }
        leaf mode {
          tailf:cli-drop-node-name;
          tailf:cli-hide-in-submode;
          type enumeration {
            enum l2transport;
            enum symmetric;
          }
        }
        uses interface-common-grouping;
        uses interface-ethernet-grouping;
        uses subinterface-common-grouping;
      }
    }
    list nve {
      tailf:cli-allow-join-with-key;
      key "name";
      leaf name {
        type uint16;
      }
      uses interface-common-grouping;
      container redundancy {
        tailf:cli-add-mode;
        presence "true";
        container backbone {
          container mpls {
            tailf:cli-add-mode;
            presence "true";
            container iccp {
              leaf group {
                type uint32;
              }
            }
          }
          container vxlan {
            tailf:cli-add-mode;
            presence "true";
            container iccp {
              leaf group {
                type uint32;
              }
            }
          }
        }
      }
      container member {
        list vni {
          tailf:cli-range-list-syntax;
          key "id";
          leaf id {
            type union {
              type uint32;
              type string;
            }
          }
          leaf vrf {
            type string;
          }
          leaf suppress-unknown-unicast-flooding {
            type empty;
          }
          container host-reachability {
            leaf protocol {
              type enumeration {
                enum bgp;
              }
            }
          }
          container host-reachabilty {
            leaf protocol {
              type enumeration {
                enum bgp;
              }
            }
          }
          container load-balance {
            leaf per-evi {
              type empty;
            }
          }
          container mcast-group {
            tailf:cli-compact-syntax;
            tailf:cli-sequence-commands {
              tailf:cli-reset-siblings;
            }
            leaf ip-address {
              tailf:cli-drop-node-name;
              type inet:ipv4-address;
            }
            leaf end-ip-address {
              tailf:cli-drop-node-name;
              type inet:ipv4-address;
            }
          }
        }
      }
      leaf remap-replication-servers {
        type empty;
      }
      leaf overlay-encapsulation {
        type enumeration {
          enum soft-gre;
          enum vxlan;
        }
      }
      leaf replication-server {
        type inet:ipv4-address;
      }
      container source-interface {
        leaf Loopback {
          tailf:cli-allow-join-with-value;
          type uint32;
        }
      }
      container anycast {
        container source-interface {
          leaf Loopback {
            tailf:cli-allow-join-with-value;
            type uint32;
          }
        }
      }
      container ingress-replication {
        leaf protocol {
          type enumeration {
            enum bgp;
          }
        }
      }
    }
    list PW-Ether {
      tailf:cli-allow-join-with-key;
      key "id";
      leaf id {
        type uint16;
      }
      uses interface-common-grouping;
      uses interface-ethernet-grouping;
      uses interface-bfd-grouping;
      uses non-subinterface-common-grouping;
      uses interface-non-bundle-grouping;
      leaf l2overhead {
        type uint8;
      }
    }
    container PW-Ether-subinterface {
      tailf:cli-drop-node-name;
      list PW-Ether {
        tailf:cli-allow-join-with-key;
        key "id";
        leaf id {
          type string;
        }
        leaf l2transport {
          tailf:cli-hide-in-submode;
          type empty;
        }
        uses interface-common-grouping;
        uses interface-ethernet-grouping;
        uses subinterface-common-grouping;
      }
    }
    list PW-IW {
      tailf:cli-allow-join-with-key;
      key "id";
      leaf id {
        type uint16;
      }
      uses interface-common-grouping;
      uses interface-ethernet-grouping;
      uses interface-bfd-grouping;
      uses non-subinterface-common-grouping;
      uses interface-non-bundle-grouping;
    }
    list Port-channel {
      tailf:cli-allow-join-with-key;
      key "id";
      leaf id {
        type uint32;
      }
      uses interface-common-grouping;
      uses interface-ethernet-grouping;
      uses interface-bfd-grouping;
      uses non-subinterface-common-grouping;
    }
    list POS {
      tailf:cli-allow-join-with-key;
      key "id";
      leaf id {
        type string;
      }
      uses interface-common-grouping;
      uses interface-bfd-grouping;
      uses non-subinterface-common-grouping;
      uses interface-pointtopoint-grouping;
      container pos {
        tailf:cli-add-mode;
        leaf crc {
          type enumeration {
            enum 16;
            enum 32;
          }
        }
      }
    }
    container POS-subinterface {
      tailf:cli-drop-node-name;
      list POS {
        tailf:cli-allow-join-with-key;
        key "id";
        leaf id {
          type string;
        }
        leaf mode {
          tailf:cli-drop-node-name;
          tailf:cli-hide-in-submode;
          type enumeration {
            enum point-to-point;
          }
        }
        uses interface-common-grouping;
        uses subinterface-common-grouping;
        uses interface-pointtopoint-grouping;
      }
    }
    list PTP {
      tailf:cli-allow-join-with-key;
      key "id";
      leaf id {
        type string;
      }
      uses interface-common-grouping;
      uses interface-ethernet-grouping;
      uses interface-bfd-grouping;
      uses non-subinterface-common-grouping;
      uses interface-non-bundle-grouping;
    }
    list BVI {
      tailf:cli-allow-join-with-key;
      key "id";
      leaf id {
        type uint32;
      }
      leaf host-routing {
        type empty;
      }
      uses interface-common-grouping;
      uses interface-bfd-grouping;
      uses non-subinterface-common-grouping;
    }
    list Vlan {
      tailf:cli-allow-join-with-key;
      key "id";
      leaf id {
        type uint16;
      }
      uses interface-common-grouping;
      uses interface-bfd-grouping;
      uses non-subinterface-common-grouping;
    }
    list tunnel-ip {
      tailf:cli-allow-join-with-key;
      key "id";
      leaf id {
        type uint16;
      }
      uses interface-common-grouping;
      uses interface-bfd-grouping;
      uses non-subinterface-common-grouping;
      uses interface-pointtopoint-grouping;
      container tunnel {
        container protection {
          container ipsec {
            tailf:cli-compact-syntax;
            tailf:cli-sequence-commands {
              tailf:cli-reset-siblings;
            }
            leaf profile {
              type string;
            }
            leaf ipsec-node {
              type string;
            }
          }
        }
        container mode {
          choice mode-choice {
            leaf gre {
              type enumeration {
                enum ipv4;
                enum ipv6;
              }
            }
            leaf ipv4 {
              type empty;
            }
            leaf ipv6 {
              type empty;
            }
          }
        }
        leaf source {
          type string;
        }
        leaf vrf {
          type string;
        }
        leaf destination {
          type union {
            type inet:ipv4-address;
            type inet:ipv6-address;
          }
        }
        container dfbit {
          leaf disable {
            type empty;
          }
        }
      }
    }
    list tunnel-te {
      tailf:cli-allow-join-with-key;
      key "id";
      leaf id {
        type uint16;
      }
      uses interface-common-grouping;
      uses non-subinterface-common-grouping;
      uses interface-tunnel-te-grouping;
      container bfd {
        tailf:cli-add-mode;
        presence "true";
        leaf multiplier {
          type uint8;
        }
        container fast-detect {
          tailf:cli-delete-when-empty;
          presence "true";
          leaf sbfd {
            type empty;
          }
        }
        leaf minimum-interval {
          type uint16;
        }
        container dampening {
          leaf maximum-wait {
            type uint32;
          }
          leaf secondary-wait {
            type uint32;
          }
          leaf initial-wait {
            type uint32;
          }
        }
        leaf bringup-timeout {
          type uint16;
        }
        container lsp-ping {
          choice lsp-ping-choice {
            leaf disable {
              type empty;
            }
            leaf interval {
              type uint16;
            }
          }
        }
      }
      leaf load-share {
        type uint32;
      }
      container auto-bw {
        tailf:cli-add-mode;
        presence "true";
        container bw-limit {
          tailf:cli-compact-syntax;
          tailf:cli-sequence-commands {
            tailf:cli-reset-siblings;
          }
          leaf min {
            type uint32;
          }
          leaf max {
            type uint32;
          }
        }
        container overflow {
          uses interface-tunnel-te-auto-bw-threshold-grouping;
        }
        container underflow {
          uses interface-tunnel-te-auto-bw-threshold-grouping;
        }
        container adjustment-threshold {
          tailf:cli-compact-syntax;
          tailf:cli-sequence-commands {
            tailf:cli-reset-siblings;
          }
          leaf percentage {
            tailf:cli-drop-node-name;
            type uint8;
          }
          leaf min {
            type uint32;
          }
        }
        leaf application {
          type uint16;
        }
      }
      container autoroute {
        container metric {
          choice metric-choice {
            leaf absolute {
              type uint32;
            }
            leaf relative {
              type int8;
            }
          }
        }
        container announce {
          tailf:cli-add-mode;
          presence "true";
          container metric {
            choice metric-choice {
              leaf constant {
                tailf:cli-drop-node-name;
                type uint32;
              }
              leaf absolute {
                type uint32;
              }
              leaf relative {
                type int8;
              }
            }
          }
          container exclude-traffic {
            leaf segment-routing {
              type empty;
            }
          }
          leaf include-ipv6 {
            type empty;
          }
        }
        list destination {
          tailf:cli-suppress-mode;
          tailf:cli-delete-when-empty;
          key "addr";
          leaf addr {
            type inet:ipv4-address;
          }
        }
      }
      container forwarding-adjacency {
        tailf:cli-add-mode;
        presence "true";
        leaf holdtime {
          type uint16;
        }
        leaf include-ipv6 {
          type empty;
        }
      }
      leaf destination {
        type inet:ipv4-address;
      }
      container bidirectional {
        tailf:cli-add-mode;
        presence "true";
        container association {
          container id {
            tailf:cli-compact-syntax;
            tailf:cli-sequence-commands {
              tailf:cli-reset-siblings;
            }
            leaf value {
              tailf:cli-drop-node-name;
              type uint16;
            }
            leaf source-address {
              type inet:ipv4-address;
            }
            leaf global-id {
              type uint32;
            }
          }
          container type {
            container co-routed {
              tailf:cli-add-mode;
              presence "true";
              leaf wrap-protection {
                type empty;
              }
            }
          }
        }
      }
      leaf forward-class {
        type uint8;
      }
      leaf soft-preemption {
        type empty;
      }
      container path-protection {
        tailf:cli-add-mode;
        presence "true";
        container protection-mode {
          leaf non-revertive {
            type empty;
          }
        }
        leaf srlg-diverse {
          type empty;
        }
      }
      container path-selection {
        tailf:cli-add-mode;
        container metric {
          leaf metric-type {
            tailf:cli-drop-node-name;
            type enumeration {
              enum igp;
              enum te;
              enum delay;
            }
          }
        }
        leaf delay-limit {
          type uint32;
        }
        leaf hop-limit {
          type uint8;
        }
        leaf cost-limit {
          type uint32;
        }
        container segment-routing {
          leaf adjacency {
            type enumeration {
              enum protected;
              enum unprotected;
            }
          }
        }
      }
      uses interface-tunnel-path-option-grouping;
      container pce {
        tailf:cli-add-mode;
        presence "true";
        container delegation {
          tailf:cli-add-mode;
          presence "true";
          leaf reopt {
            type empty;
          }
        }
      }
      leaf delay-measurement {
        type empty;
      }
    }
    list tunnel-tp {
      tailf:cli-allow-join-with-key;
      key "id";
      leaf id {
        type uint16;
      }
      uses interface-common-grouping;
      uses non-subinterface-common-grouping;
    }
    list tunnel-mte {
      tailf:cli-allow-join-with-key;
      key "id";
      leaf id {
        type uint16;
      }
      uses interface-common-grouping;
      uses non-subinterface-common-grouping;
      uses interface-tunnel-te-grouping;
      list destination {
        key "addr";
        leaf addr {
          type inet:ipv4-address;
        }
        uses interface-tunnel-path-option-grouping;
      }
    }
    list tunnel-ipsec {
      key "id";
      leaf id {
        type uint32;
      }
      uses interface-common-grouping;
      uses non-subinterface-common-grouping;
    }
    list ATM {
      tailf:cli-allow-join-with-key;
      key "id";
      leaf id {
        type string;
      }
      uses interface-common-grouping;
      uses interface-bfd-grouping;
      uses non-subinterface-common-grouping;
      uses interface-atm-grouping;
    }
    container ATM-subinterface {
      tailf:cli-drop-node-name;
      list ATM {
        tailf:cli-allow-join-with-key;
        key "id";
        leaf id {
          type string;
        }
        choice mode-choice {
          leaf l2transport {
            tailf:cli-hide-in-submode;
            type empty;
          }
          leaf point-to-point {
            tailf:cli-hide-in-submode;
            type empty;
          }
        }
        uses interface-common-grouping;
        uses subinterface-common-grouping;
        uses interface-atm-grouping;
      }
    }
    list Multilink {
      tailf:cli-allow-join-with-key;
      key "id";
      leaf id {
        type string;
      }
      uses interface-common-grouping;
      uses interface-bfd-grouping;
      uses non-subinterface-common-grouping;
      uses interface-pointtopoint-grouping;
      uses interface-multilink-grouping;
    }
    container Multilink-subinterface {
      tailf:cli-drop-node-name;
      list Multilink {
        tailf:cli-allow-join-with-key;
        key "id";
        leaf id {
          type string;
        }
        leaf mode {
          tailf:cli-drop-node-name;
          tailf:cli-hide-in-submode;
          type enumeration {
            enum point-to-point;
          }
        }
        uses interface-common-grouping;
        uses subinterface-common-grouping;
        uses interface-pointtopoint-grouping;
        uses interface-multilink-grouping;
      }
    }
    list SRP {
      tailf:cli-allow-join-with-key;
      key "id";
      leaf id {
        type string;
      }
      uses interface-common-grouping;
      uses non-subinterface-common-grouping;
      container threshold {
        leaf b2-tca {
          type uint8;
        }
      }
    }
    list Serial {
      tailf:cli-allow-join-with-key;
      key "id";
      leaf id {
        type string;
      }
      uses interface-common-grouping;
      uses interface-bfd-grouping;
      uses non-subinterface-common-grouping;
      uses interface-pointtopoint-grouping;
      container multilink {
        tailf:cli-add-mode;
        leaf group {
          type uint32;
        }
      }
      container serial {
        tailf:cli-add-mode;
        leaf crc {
          type enumeration {
            enum 16;
            enum 32;
          }
        }
        leaf scramble {
          type empty;
        }
      }
    }
    container Serial-subinterface {
      tailf:cli-drop-node-name;
      list Serial {
        tailf:cli-allow-join-with-key;
        key "id";
        leaf id {
          type string;
        }
        leaf mode {
          tailf:cli-drop-node-name;
          tailf:cli-hide-in-submode;
          type enumeration {
            enum point-to-point;
            enum l2transport;
          }
        }
        uses interface-common-grouping;
        uses interface-bfd-grouping;
        uses subinterface-common-grouping;
        uses interface-pointtopoint-grouping;
        leaf subinterface {
          type empty;
        }
      }
    }
    list CEM {
      tailf:cli-allow-join-with-key;
      key "id";
      leaf id {
        type string;
      }
      uses interface-common-grouping;
      uses interface-bfd-grouping;
      uses non-subinterface-common-grouping;
      container cem {
        leaf class-attach {
          type string;
        }
        leaf dejitter {
          type uint16;
        }
      }
    }
    list GCC0 {
      tailf:cli-allow-join-with-key;
      key "id";
      leaf id {
        type string;
      }
      uses interface-common-grouping;
      uses interface-bfd-grouping;
      uses non-subinterface-common-grouping;
    }
    list CSI {
      tailf:cli-allow-join-with-key;
      key "id";
      leaf id {
        type uint8;
      }
      uses interface-common-grouping;
      uses non-subinterface-common-grouping;
    }
  }

  grouping bgp-address-family-pre-grouping {
    uses apply-group-grouping;
    container mvpn {
      leaf single-forwarder-selection {
        type enumeration {
          enum all;
          enum highest-ip-address;
        }
      }
    }
    container label {
      container mode {
        choice mode-choice {
          leaf per-ce {
            type empty;
          }
          leaf per-prefix {
            type empty;
          }
          leaf per-vrf {
            type empty;
          }
          leaf route-policy {
            type string;
          }
        }
      }
    }
    leaf table-policy {
      type string;
    }
    container retain {
      leaf local-label {
        type uint8;
      }
      container route-target {
        choice route-target-choice {
          leaf all {
            type empty;
          }
          leaf route-policy {
            type string;
          }
        }
      }
    }
    container update {
      container limit {
        leaf address-family {
          type uint16;
        }
        container sub-group {
          leaf ebgp {
            type uint16;
          }
          leaf ibgp {
            type uint16;
          }
        }
      }
      leaf wait-install {
        type empty;
      }
    }
    container additional-paths {
      leaf receive {
        type empty;
      }
      leaf send {
        type empty;
      }
      container selection {
        choice selection-choice {
          leaf disable {
            type empty;
          }
          list route-policy {
            tailf:cli-suppress-mode;
            tailf:cli-delete-when-empty;
            key "name";
            leaf name {
              type string;
            }
          }
        }
      }
    }
    leaf weight {
      type union {
        type enumeration {
          enum reset-on-import;
        }
        type uint32;
      }
    }
    container advertise {
      leaf best-external {
        type empty;
      }
      container local-labeled-route {
        tailf:cli-compact-syntax;
        tailf:cli-sequence-commands {
          tailf:cli-reset-siblings;
        }
        tailf:cli-delete-when-empty;
        presence "true";
        leaf safi-unicast {
          tailf:cli-optional-in-sequence;
          type empty;
        }
        leaf disable {
          type empty;
        }
      }
      leaf permanent-network {
        type empty;
      }
      container vpnv4 {
        container unicast {
          tailf:cli-delete-when-empty;
          presence "true";
          uses router-bgp-af-advertise-grouping;
        }
      }
      container vpnv6 {
        container unicast {
          tailf:cli-delete-when-empty;
          presence "true";
          uses router-bgp-af-advertise-grouping;
        }
      }
      container l2vpn {
        container evpn {
          tailf:cli-delete-when-empty;
          presence "true";
          uses router-bgp-af-advertise-grouping;
        }
      }
    }
    container bgp {
      leaf attribute-download {
        type empty;
      }
      container dampening {
        tailf:cli-compact-syntax;
        tailf:cli-sequence-commands {
          tailf:cli-reset-siblings;
        }
        tailf:cli-delete-when-empty;
        presence "true";
        choice dampening-choice {
          case a {
            leaf half-life {
              tailf:cli-drop-node-name;
              type uint8;
            }
            leaf reuse {
              tailf:cli-drop-node-name;
              type uint16;
            }
            leaf suppress {
              tailf:cli-drop-node-name;
              type uint16;
            }
            leaf max-suppress-time {
              tailf:cli-drop-node-name;
              type uint8;
            }
          }
          case b {
            leaf route-policy {
              type string;
            }
          }
        }
      }
      leaf scan-time {
        type uint16;
      }
      container label-delay {
        tailf:cli-compact-syntax;
        tailf:cli-sequence-commands;
        leaf seconds {
          tailf:cli-drop-node-name;
          type uint8;
        }
        leaf milliseconds {
          tailf:cli-drop-node-name;
          type uint16;
        }
      }
      container import-delay {
        tailf:cli-compact-syntax;
        tailf:cli-sequence-commands;
        leaf seconds {
          tailf:cli-drop-node-name;
          type uint8;
        }
        leaf milliseconds {
          tailf:cli-drop-node-name;
          type uint16;
        }
      }
      container client-to-client {
        container reflection {
          leaf disable {
            type empty;
          }
        }
      }
      container origin-as {
        container validation {
          leaf enable {
            type empty;
          }
          container signal {
            leaf ibgp {
              type empty;
            }
          }
        }
      }
      container bestpath {
        uses bgp-bestpath-origin-as-grouping;
      }
    }
    container maximum-paths {
      container eibgp {
        tailf:cli-compact-syntax;
        tailf:cli-sequence-commands {
          tailf:cli-reset-siblings;
        }
        leaf maximum {
          tailf:cli-drop-node-name;
          type uint8;
        }
        leaf selective {
          type empty;
        }
      }
      container ebgp {
        tailf:cli-compact-syntax;
        tailf:cli-sequence-commands {
          tailf:cli-reset-siblings;
        }
        leaf maximum {
          tailf:cli-drop-node-name;
          type uint8;
        }
        leaf selective {
          type empty;
        }
      }
      container ibgp {
        tailf:cli-compact-syntax;
        tailf:cli-sequence-commands {
          tailf:cli-reset-siblings;
        }
        leaf maximum {
          tailf:cli-drop-node-name;
          type uint8;
        }
        leaf unequal-cost {
          tailf:cli-optional-in-sequence;
          type empty;
        }
        leaf deterministic {
          tailf:cli-optional-in-sequence;
          type empty;
        }
        leaf selective {
          type empty;
        }
      }
    }
    container distance {
      container bgp {
        tailf:cli-compact-syntax;
        tailf:cli-sequence-commands;
        leaf external {
          tailf:cli-drop-node-name;
          type uint8;
        }
        leaf internal {
          tailf:cli-drop-node-name;
          type uint8;
        }
        leaf local {
          tailf:cli-drop-node-name;
          type uint8;
        }
      }
    }
    container nexthop {
      container resolution {
        container prefix-length {
          leaf minimum {
            type uint16;
          }
        }
      }
      leaf route-policy {
        type string;
      }
      container trigger-delay {
        leaf critical {
          type uint32;
        }
        leaf non-critical {
          type uint32;
        }
      }
    }
    leaf domain-distinguisher {
      type string;
    }
  }

  grouping router-bgp-af-segment-routing-grouping {
    container segment-routing {
      leaf prefix-sid-map {
        type empty;
      }
      container srv6 {
        tailf:cli-add-mode;
        presence "true";
        leaf locator {
          type string;
        }
        container alloc {
          leaf mode {
            type enumeration {
              enum per-ce;
              enum per-vrf;
            }
          }
        }
      }
    }
  }

  grouping bgp-address-family-post-grouping {
    container allow {
      container vpn {
        leaf default-originate {
          type empty;
        }
      }
    }
    list aggregate-address {
      tailf:cli-suppress-mode;
      tailf:cli-delete-when-empty;
      tailf:cli-compact-syntax;
      key "prefix";
      leaf prefix {
        type union {
          type ipv4-prefix;
          type tailf:ipv6-address-and-prefix-length;
        }
      }
      leaf as-set {
        type empty;
      }
      leaf as-confed-set {
        type empty;
      }
      leaf summary-only {
        type empty;
      }
      container route-policy {
        tailf:cli-flatten-container;
        tailf:cli-compact-syntax;
        tailf:cli-sequence-commands {
          tailf:cli-reset-siblings;
        }
        leaf name {
          tailf:cli-drop-node-name;
          type string;
        }
      }
    }
    container redistribute {
      container connected {
        tailf:cli-compact-syntax;
        tailf:cli-delete-when-empty;
        presence "true";
        uses router-af-redistribute-grouping;
      }
      container static {
        tailf:cli-compact-syntax;
        tailf:cli-delete-when-empty;
        presence "true";
        uses router-af-redistribute-grouping;
      }
      container rip {
        tailf:cli-compact-syntax;
        tailf:cli-delete-when-empty;
        presence "true";
        uses router-af-redistribute-grouping;
      }
      container mobile {
        tailf:cli-compact-syntax;
        tailf:cli-delete-when-empty;
        presence "true";
        uses router-af-redistribute-grouping;
      }
      container subscriber {
        tailf:cli-compact-syntax;
        tailf:cli-delete-when-empty;
        presence "true";
        uses router-af-redistribute-grouping;
      }
      list ospf {
        tailf:cli-suppress-mode;
        tailf:cli-delete-when-empty;
        tailf:cli-compact-syntax;
        key "id";
        leaf id {
          type string;
        }
        leaf match {
          type empty;
        }
        leaf internal {
          type empty;
        }
        leaf external {
          type empty;
        }
        leaf external-type {
          tailf:cli-drop-node-name;
          type enumeration {
            enum 1;
            enum 2;
          }
        }
        leaf nssa-external {
          type empty;
        }
        leaf nssa-external-type {
          tailf:cli-drop-node-name;
          type enumeration {
            enum 1;
            enum 2;
          }
        }
        uses router-af-redistribute-grouping;
      }
      list ospfv3 {
        tailf:cli-suppress-mode;
        tailf:cli-delete-when-empty;
        tailf:cli-compact-syntax;
        key "id";
        leaf id {
          type string;
        }
        leaf match {
          type empty;
        }
        leaf internal {
          type empty;
        }
        leaf external {
          type empty;
        }
        leaf external-type {
          tailf:cli-drop-node-name;
          type enumeration {
            enum 1;
            enum 2;
          }
        }
        leaf nssa-external {
          type empty;
        }
        leaf nssa-external-type {
          tailf:cli-drop-node-name;
          type enumeration {
            enum 1;
            enum 2;
          }
        }
        uses router-af-redistribute-grouping;
      }
      list isis {
        tailf:cli-suppress-mode;
        tailf:cli-delete-when-empty;
        tailf:cli-compact-syntax;
        tailf:cli-sequence-commands {
          tailf:cli-reset-siblings;
        }
        key "id";
        leaf id {
          type string;
        }
        leaf level {
          tailf:cli-optional-in-sequence;
          type enumeration {
            enum 1;
            enum 1-inter-area;
            enum 2;
          }
        }
        container second-level {
          tailf:cli-drop-node-name;
          tailf:cli-flatten-container;
          tailf:cli-optional-in-sequence;
          leaf level {
            type enumeration {
              enum 1;
              enum 1-inter-area;
              enum 2;
            }
          }
        }
        container third-level {
          tailf:cli-drop-node-name;
          tailf:cli-flatten-container;
          tailf:cli-optional-in-sequence;
          leaf level {
            type enumeration {
              enum 1;
              enum 1-inter-area;
              enum 2;
            }
          }
        }
        uses router-af-redistribute-grouping {
          refine "metric" {
            tailf:cli-optional-in-sequence;
          }
        }
      }
      list eigrp {
        tailf:cli-suppress-mode;
        tailf:cli-delete-when-empty;
        tailf:cli-compact-syntax;
        key "id";
        leaf id {
          type string;
        }
        leaf match {
          type empty;
        }
        leaf internal {
          type empty;
        }
        leaf external {
          type empty;
        }
        uses router-af-redistribute-grouping;
      }
    }
    container allocate-label {
      choice allocate-label-choice {
        leaf all {
          type empty;
        }
        leaf route-policy {
          type string;
        }
        container all-unlabeled-path {
          tailf:cli-drop-node-name;
          tailf:cli-compact-syntax;
          tailf:cli-sequence-commands {
            tailf:cli-reset-siblings;
          }
          leaf all {
            type empty;
          }
          leaf unlabeled-path {
            type empty;
          }
        }
      }
    }
    container as-path-loopcheck {
      leaf out {
        type enumeration {
          enum disable;
        }
      }
    }
    container dynamic-med {
      leaf interval {
        type uint8;
      }
    }
    leaf global-table-multicast {
      type empty;
    }
    container vrf {
      container all {
        tailf:cli-add-mode;
        presence "true";
        container label {
          container mode {
            choice mode-choice {
              leaf per-ce {
                type empty;
              }
              leaf per-prefix {
                type empty;
              }
              leaf per-vrf {
                type empty;
              }
              leaf route-policy {
                type string;
              }
            }
          }
        }
        container source {
          container rt {
            leaf import-policy {
              type empty;
            }
          }
        }
        uses router-bgp-af-segment-routing-grouping;
      }
    }
    uses router-bgp-af-segment-routing-grouping;
  }

  grouping bgp-address-family-ipv4-grouping {
    uses bgp-address-family-pre-grouping;
    list network {
      tailf:cli-suppress-mode;
      tailf:cli-delete-when-empty;
      tailf:cli-compact-syntax;
      key "net";
      leaf net {
        type ipv4-prefix;
      }
      leaf backdoor {
        type empty;
      }
      leaf route-policy {
        type string;
      }
    }
    uses bgp-address-family-post-grouping;
  }

  grouping bgp-address-family-ipv6-grouping {
    uses bgp-address-family-pre-grouping;
    list network {
      tailf:cli-suppress-mode;
      tailf:cli-delete-when-empty;
      tailf:cli-compact-syntax;
      key "net";
      leaf net {
        type tailf:ipv6-address-and-prefix-length;
      }
      leaf backdoor {
        type empty;
      }
      leaf route-policy {
        type string;
      }
    }
    uses bgp-address-family-post-grouping;
  }

  grouping bgp-address-family-grouping {
    list optimal-route-reflection {
      tailf:cli-suppress-mode;
      tailf:cli-delete-when-empty;
      tailf:cli-compact-syntax;
      tailf:cli-sequence-commands {
        tailf:cli-reset-siblings;
      }
      key "name";
      leaf name {
        type string;
      }
      leaf primary {
        tailf:cli-drop-node-name;
        type union {
          type inet:ipv4-address;
          type inet:ipv6-address;
        }
      }
      leaf secondary {
        tailf:cli-drop-node-name;
        type union {
          type inet:ipv4-address;
          type inet:ipv6-address;
        }
      }
      leaf tertiary {
        tailf:cli-drop-node-name;
        type union {
          type inet:ipv4-address;
          type inet:ipv6-address;
        }
      }
    }
  }

  grouping router-bgp-neighbor-af-grouping {
    leaf multipath {
      type empty;
    }
    uses route-policy-list-grouping;
    leaf encapsulation-type {
      type enumeration {
        enum mpls;
        enum vxlan;
        enum srv6;
      }
    }
    container remove-private-AS {
      tailf:cli-delete-when-empty;
      presence "true";
      choice remove-choice {
        leaf entire-aspath {
          type empty;
        }
        leaf inheritance-disable {
          type empty;
        }
      }
    }
    container remove-private-AS-inbound {
      tailf:cli-drop-node-name;
      container remove-private-AS {
        container inbound {
          tailf:cli-delete-when-empty;
          presence "true";
          choice remove-choice {
            leaf entire-aspath {
              type empty;
            }
            leaf inheritance-disable {
              type empty;
            }
          }
        }
      }
    }
    container soft-reconfiguration {
      container inbound {
        tailf:cli-compact-syntax;
        presence "true";
        leaf type {
          tailf:cli-drop-node-name;
          type enumeration {
            enum always;
            enum inheritance-disable;
          }
        }
      }
    }
    container allowas-in {
      leaf as-occurrence-number {
        tailf:cli-drop-node-name;
        type uint8;
      }
    }
    leaf site-of-origin {
      type string;
    }
    container import {
      choice import-choice {
        container stitching-rt {
          tailf:cli-compact-syntax;
          tailf:cli-sequence-commands {
            tailf:cli-reset-siblings;
          }
          tailf:cli-delete-when-empty;
          presence "true";
          choice re-originate-choice {
            leaf re-originate {
              type empty;
            }
            leaf reoriginate {
              type empty;
            }
          }
          leaf stitching-rt {
            type empty;
          }
        }
        container reoriginate {
          tailf:cli-delete-when-empty;
          presence "true";
          leaf stitching-rt {
            type empty;
          }
        }
        container re-originate {
          tailf:cli-delete-when-empty;
          presence "true";
          leaf stitching-rt {
            type empty;
          }
        }
      }
    }
    container accept-own {
      tailf:cli-delete-when-empty;
      presence "true";
      leaf inheritance-disable {
        type empty;
      }
    }
    container as-override {
      tailf:cli-compact-syntax;
      tailf:cli-delete-when-empty;
      presence "true";
      leaf inheritance-disable {
        type empty;
      }
    }
    container maximum-prefix {
      tailf:cli-compact-syntax;
      tailf:cli-sequence-commands;
      leaf max-prefix-limit {
        tailf:cli-drop-node-name;
        type uint32;
      }
      leaf threshold {
        tailf:cli-drop-node-name;
        tailf:cli-break-sequence-commands;
        type uint8;
      }
      leaf restart {
        type uint16;
      }
      leaf warning-only {
        type empty;
      }
      leaf discard-extra-paths {
        type empty;
      }
    }
    container next-hop-self {
      tailf:cli-delete-when-empty;
      presence "true";
      leaf inheritance-disable {
        type empty;
      }
    }
    container next-hop-unchanged {
      tailf:cli-delete-when-empty;
      presence "true";
      leaf inheritance-disable {
        type empty;
      }
    }
    container next-hop-unchanged-multipath {
      tailf:cli-drop-node-name;
      container next-hop-unchanged {
        leaf multipath {
          type empty;
        }
      }
    }
    leaf route-reflector-client {
      type empty;
    }
    container default-originate {
      tailf:cli-delete-when-empty;
      presence "true";
      choice default-originate-choice {
        leaf route-policy {
          type string;
        }
        leaf inheritance-disable {
          type empty;
        }
      }
    }
    container send-community-ebgp {
      tailf:cli-delete-when-empty;
      presence "true";
      leaf inheritance-disable {
        type empty;
      }
    }
    container send-extended-community-ebgp {
      tailf:cli-delete-when-empty;
      presence "true";
      leaf inheritance-disable {
        type empty;
      }
    }
    container send-community-gshut-ebgp {
      tailf:cli-delete-when-empty;
      presence "true";
      leaf inheritance-disable {
        type empty;
      }
    }
    container orf {
      leaf route-policy {
        type string;
      }
    }
    container use {
      leaf af-group {
        type string;
      }
    }
    container capability {
      container orf {
        leaf prefix {
          type enumeration {
            enum both;
            enum none;
            enum receive;
            enum send;
          }
        }
      }
    }
    container Signalling {
      choice signalling-choice {
        container bgp {
          leaf disable {
            type empty;
          }
        }
        container ldp {
          leaf disable {
            type empty;
          }
        }
      }
    }
    choice agp-choice {
      container aigp-enable {
        tailf:cli-drop-node-name;
        leaf aigp {
          type empty;
        }
      }
      container aigp-disable {
        tailf:cli-drop-node-name;
        container aigp {
          leaf disable {
            type empty;
          }
        }
      }
    }
    container aigp {
      container send {
        container cost-community {
          tailf:cli-compact-syntax;
          tailf:cli-sequence-commands {
            tailf:cli-reset-siblings;
          }
          choice cc-choice {
            leaf disable {
              type empty;
            }
            case id-case {
              leaf id {
                tailf:cli-drop-node-name;
                type uint8;
              }
              leaf poi {
                type enumeration {
                  enum igp-cost;
                  enum pre-bestpath;
                }
              }
              leaf transitive {
                type empty;
              }
            }
          }
        }
        container med {
          tailf:cli-delete-when-empty;
          presence "true";
          leaf disable {
            type empty;
          }
        }
      }
    }
    leaf optimal-route-reflection {
      type string;
    }
    container long-lived-graceful-restart {
      leaf capable {
        type empty;
      }
      container stale-time {
        tailf:cli-compact-syntax;
        tailf:cli-sequence-commands {
          tailf:cli-reset-siblings;
        }
        leaf send {
          type uint32;
        }
        leaf accept {
          type uint32;
        }
      }
    }
    container slow-peer {
      choice slow-peer-choice {
        container dynamic {
          tailf:cli-delete-when-empty;
          presence "true";
          choice dynamic-choice {
            leaf disable {
              type empty;
            }
            leaf threshold {
              type uint16;
            }
          }
        }
        leaf static {
          type empty;
        }
      }
    }
  }

  grouping bgp-neighbor-grouping {
    leaf remote-as {
      type union {
        type uint32;
        type string;
      }
    }
    container local {
      container address {
        leaf ip {
          tailf:cli-drop-node-name;
          type inet:host;
        }
      }
    }
    container local-as {
      tailf:cli-compact-syntax;
      tailf:cli-sequence-commands {
        tailf:cli-reset-siblings;
      }
      choice local-as-choice {
        leaf inheritance-disable {
          type empty;
        }
        case as-number-case {
          leaf as-number {
            tailf:cli-drop-node-name;
            type string;
          }
          leaf no-prepend {
            type empty;
          }
          leaf replace-as {
            type empty;
          }
          leaf dual-as {
            type empty;
          }
        }
      }
    }
    uses bfd-common-parameters-grouping;
    uses bgp-common-group-grouping;
    container ebgp-multihop {
      tailf:cli-compact-syntax;
      leaf ttl-value {
        tailf:cli-drop-node-name;
        type uint8;
      }
      leaf mpls {
        type empty;
      }
    }
    container egress-engineering {
      tailf:cli-delete-when-empty;
      presence "true";
      leaf inheritance-disable {
        type empty;
      }
    }
    container enforce-first-as {
      tailf:cli-delete-when-empty;
      presence "true";
      leaf disable {
        type empty;
      }
    }
    choice precedence-choice {
      leaf precedence {
        type precedence-type;
      }
      leaf dscp {
        type dscp-type;
      }
    }
    container advertisement-interval {
      tailf:cli-compact-syntax;
      tailf:cli-sequence-commands {
        tailf:cli-reset-siblings;
      }
      leaf seconds {
        tailf:cli-drop-node-name;
        type uint16;
      }
      leaf milliseconds {
        tailf:cli-drop-node-name;
        type uint16;
      }
    }
    container bmp-activate {
      list server {
        tailf:cli-suppress-mode;
        tailf:cli-delete-when-empty;
        key "id";
        leaf id {
          type uint8;
        }
      }
    }
    container timers {
      tailf:cli-compact-syntax;
      tailf:cli-sequence-commands {
        tailf:cli-reset-siblings;
      }
      leaf keepalive {
        tailf:cli-drop-node-name;
        type uint16;
      }
      leaf holdtime {
        tailf:cli-drop-node-name;
        type uint16;
      }
      leaf min-holdtime {
        tailf:cli-drop-node-name;
        type uint16;
      }
    }
    container tcp {
      leaf mss {
        type union {
          type uint16;
          type enumeration {
            enum inheritance-disable;
          }
        }
      }
    }
    leaf description {
      tailf:cli-multi-value;
      type string;
    }
    container dmz-link-bandwidth {
      tailf:cli-delete-when-empty;
      presence "true";
      leaf inheritance-disable {
        type empty;
      }
    }
    container password {
      tailf:cli-compact-syntax;
      tailf:cli-sequence-commands {
        tailf:cli-reset-siblings;
      }
      leaf enc-type {
        tailf:cli-drop-node-name;
        type enumeration {
          enum clear;
          enum encrypted;
          enum inheritance-disable;
        }
      }
      leaf password {
        tailf:cli-drop-node-name;
        tailf:cli-multi-value;
        type string;
      }
    }
    container ttl-security {
      tailf:cli-delete-when-empty;
      presence "true";
      leaf inheritance-disable {
        type empty;
      }
    }
    container update {
      container in {
        container filtering {
          tailf:cli-add-mode;
          presence "true";
          container attribute-filter {
            leaf group {
              type string;
            }
          }
          container message {
            leaf buffers {
              type uint8;
            }
          }
        }
      }
    }
    container update-source {
      uses interface-name-grouping;
    }
    container ignore-connected-check {
      presence "true";
    }
    leaf cluster-id {
      type union {
        type uint32;
        type inet:host;
      }
    }
    container graceful-maintenance {
      tailf:cli-add-mode;
      presence "true";
      leaf local-preference {
        type union {
          type uint32;
          type enumeration {
            enum inheritance-disable;
          }
        }
      }
      leaf as-prepends {
        type union {
          type uint8;
          type enumeration {
            enum inheritance-disable;
          }
        }
      }
      container activate {
        tailf:cli-delete-when-empty;
        presence "true";
        leaf inheritance-disable {
          type empty;
        }
      }
    }
    container graceful-restart {
      presence "true";
      leaf suppress {
        type empty;
      }
      leaf disable {
        type empty;
      }
      leaf restart-time {
        type uint16;
      }
      leaf stalepath-time {
        type uint16;
      }
    }
    container capability {
      container additional-paths {
        container receive {
          tailf:cli-delete-when-empty;
          presence "true";
          leaf disable {
            type empty;
          }
        }
        container send {
          tailf:cli-delete-when-empty;
          presence "true";
          leaf disable {
            type empty;
          }
        }
      }
      container suppress {
        container all {
          tailf:cli-delete-when-empty;
          presence "true";
          leaf inheritance-disable {
            type empty;
          }
        }
        container four-byte-as {
          tailf:alt-name "4-byte-as";
          tailf:cli-delete-when-empty;
          presence "true";
          leaf inheritance-disable {
            type empty;
          }
        }
      }
    }
    container log {
      list message {
        tailf:cli-suppress-mode;
        tailf:cli-delete-when-empty;
        key "direction";
        leaf direction {
          type enumeration {
            enum in;
            enum out;
          }
        }
        choice logging-choice {
          leaf range {
            tailf:cli-drop-node-name;
            type uint8;
          }
          leaf disable {
            type empty;
          }
          leaf inheritance-diable {
            type empty;
          }
        }
      }
    }
    leaf internal-vpn-client {
      type empty;
    }
    leaf local-address-subnet {
      type union {
        type ipv4-prefix;
        type tailf:ipv6-address-and-prefix-length;
      }
    }
    leaf maximum-peers {
      type uint16;
    }
    container send-buffer-size {
      tailf:cli-compact-syntax;
      tailf:cli-sequence-commands {
        tailf:cli-reset-siblings;
      }
      leaf socket-size {
        tailf:cli-drop-node-name;
        type uint32;
      }
      leaf bgp-size {
        tailf:cli-drop-node-name;
        type uint32;
      }
    }
    container receive-buffer-size {
      tailf:cli-compact-syntax;
      tailf:cli-sequence-commands {
        tailf:cli-reset-siblings;
      }
      leaf socket-size {
        tailf:cli-drop-node-name;
        type uint32;
      }
      leaf bgp-size {
        tailf:cli-drop-node-name;
        type uint32;
      }
    }
    container address-family {
      container ipv4 {
        container unicast {
          tailf:cli-add-mode;
          presence "true";
          uses bgp-address-family-ipv4-grouping;
          uses router-bgp-neighbor-af-grouping;
        }
        container multicast {
          tailf:cli-add-mode;
          presence "true";
          uses bgp-address-family-ipv4-grouping;
          uses router-bgp-neighbor-af-grouping;
        }
        container labeled-unicast {
          tailf:cli-add-mode;
          presence "true";
          uses bgp-address-family-ipv4-grouping;
          uses router-bgp-neighbor-af-grouping;
        }
        container mdt {
          tailf:cli-add-mode;
          presence "true";
          uses bgp-address-family-ipv4-grouping;
          uses router-bgp-neighbor-af-grouping;
        }
        container rt-filter {
          tailf:cli-add-mode;
          presence "true";
          uses bgp-address-family-ipv4-grouping;
          uses router-bgp-neighbor-af-grouping;
        }
        container flowspec {
          tailf:cli-add-mode;
          presence "true";
          container validation {
            tailf:cli-delete-when-empty;
            presence "true";
            choice validation-choice {
              leaf disable {
                type empty;
              }
              container redirect {
                leaf disable {
                  type empty;
                }
              }
            }
          }
          uses bgp-address-family-ipv4-grouping;
          uses router-bgp-neighbor-af-grouping;
        }
        container mvpn {
          tailf:cli-add-mode;
          presence "true";
          uses bgp-address-family-ipv4-grouping;
          uses router-bgp-neighbor-af-grouping;
        }
        container sr-policy {
          tailf:cli-add-mode;
          presence "true";
          uses bgp-address-family-ipv4-grouping;
          uses router-bgp-neighbor-af-grouping;
        }
      }
      container l2vpn {
        container vpls-vpws {
          tailf:cli-add-mode;
          presence "true";
          uses bgp-address-family-ipv4-grouping;
          uses router-bgp-neighbor-af-grouping;
        }
        container evpn {
          tailf:cli-add-mode;
          presence "true";
          uses bgp-address-family-ipv4-grouping;
          uses router-bgp-neighbor-af-grouping;
        }
        container mspw {
          tailf:cli-add-mode;
          presence "true";
          uses bgp-address-family-ipv4-grouping;
          uses router-bgp-neighbor-af-grouping;
        }
      }
      container vpnv4 {
        container unicast {
          tailf:cli-add-mode;
          presence "true";
          uses bgp-address-family-ipv4-grouping;
          uses router-bgp-neighbor-af-grouping;
        }
        container multicast {
          tailf:cli-add-mode;
          presence "true";
          uses bgp-address-family-ipv4-grouping;
          uses router-bgp-neighbor-af-grouping;
        }
        container flowspec {
          tailf:cli-add-mode;
          presence "true";
          uses bgp-address-family-ipv4-grouping;
          uses router-bgp-neighbor-af-grouping;
        }
      }
      container ipv6 {
        container unicast {
          tailf:cli-add-mode;
          presence "true";
          uses bgp-address-family-ipv6-grouping;
          uses router-bgp-neighbor-af-grouping;
        }
        container multicast {
          tailf:cli-add-mode;
          presence "true";
          uses bgp-address-family-ipv6-grouping;
          uses router-bgp-neighbor-af-grouping;
        }
        container labeled-unicast {
          tailf:cli-add-mode;
          presence "true";
          uses bgp-address-family-ipv6-grouping;
          uses router-bgp-neighbor-af-grouping;
        }
        container mvpn {
          tailf:cli-add-mode;
          presence "true";
          uses bgp-address-family-ipv6-grouping;
          uses router-bgp-neighbor-af-grouping;
        }
        container sr-policy {
          tailf:cli-add-mode;
          presence "true";
          uses bgp-address-family-ipv6-grouping;
          uses router-bgp-neighbor-af-grouping;
        }
        container flowspec {
          tailf:cli-add-mode;
          presence "true";
          container validation {
            tailf:cli-delete-when-empty;
            presence "true";
            choice validation-choice {
              leaf disable {
                type empty;
              }
              container redirect {
                leaf disable {
                  type empty;
                }
              }
            }
          }
          uses bgp-address-family-ipv6-grouping;
          uses router-bgp-neighbor-af-grouping;
        }
      }
      container vpnv6 {
        container unicast {
          tailf:cli-add-mode;
          presence "true";
          uses bgp-address-family-ipv6-grouping;
          uses router-bgp-neighbor-af-grouping;
        }
        container multicast {
          tailf:cli-add-mode;
          presence "true";
          uses bgp-address-family-ipv6-grouping;
          uses router-bgp-neighbor-af-grouping;
        }
        container flowspec {
          tailf:cli-add-mode;
          presence "true";
          uses bgp-address-family-ipv6-grouping;
          uses router-bgp-neighbor-af-grouping;
        }
      }
      container link-state {
        container link-state {
          tailf:cli-add-mode;
          presence "true";
          uses bgp-address-family-ipv6-grouping;
          uses router-bgp-neighbor-af-grouping;
        }
      }
    }
    leaf keychain {
      type string;
    }
    container peer-group {
      tailf:cli-compact-syntax;
      tailf:cli-delete-when-empty;
      presence "true";
      leaf group-name {
        tailf:cli-drop-node-name;
        type string;
      }
    }
    container use {
      leaf af-group {
        type string;
      }
      leaf neighbor-group {
        type string;
      }
      leaf session-group {
        type string;
      }
    }
    leaf session-open-mode {
      type enumeration {
        enum active-only;
        enum both;
        enum passive-only;
      }
    }
    container shutdown {
      presence "true";
    }
  }

  grouping router-bgp-vrf-grouping {
    container bfd {
      leaf multiplier {
        type uint8;
      }
      leaf minimum-interval {
        type uint16;
      }
    }
    container timers {
      container bgp {
        tailf:cli-compact-syntax;
        tailf:cli-sequence-commands {
          tailf:cli-reset-siblings;
        }
        leaf keepalive {
          tailf:cli-drop-node-name;
          type uint16;
        }
        leaf holdtime {
          tailf:cli-drop-node-name;
          type uint16;
        }
        leaf min-neighbor-holdtime {
          tailf:cli-drop-node-name;
          type uint16;
        }
      }
    }
    leaf mvpn {
      type empty;
    }
    container bgp {
      leaf router-id {
        type inet:ipv4-address;
      }
      container confederation {
        leaf identifier {
          type string;
        }
        container peers {
          tailf:cli-add-mode;
          list as-number {
            tailf:cli-drop-node-name;
            tailf:cli-suppress-mode;
            tailf:cli-delete-when-empty;
            key "id";
            leaf id {
              type string;
            }
          }
        }
      }
      leaf cluster-id {
        type union {
          type uint32;
          type inet:host;
        }
      }
      leaf scan-time {
        type uint16;
      }
      container update-delay {
        tailf:cli-compact-syntax;
        tailf:cli-sequence-commands {
          tailf:cli-reset-siblings;
        }
        leaf update-delay-value {
          tailf:cli-drop-node-name;
          type uint16;
        }
        leaf always {
          type empty;
        }
      }
      leaf redistribute-internal {
        type empty;
      }
      container graceful-restart {
        presence "true";
        leaf extended {
          type empty;
        }
        leaf restart-time {
          type uint16;
        }
        leaf stalepath-time {
          type uint16;
        }
        leaf purge-time {
          type uint16;
        }
        leaf graceful-reset {
          type empty;
        }
      }
      container bestpath {
        leaf compare-routerid {
          type empty;
        }
        container cost-community {
          leaf ignore {
            type empty;
          }
        }
        container aigp {
          leaf ignore {
            type empty;
          }
        }
        container med {
          leaf always {
            type empty;
          }
          leaf confed {
            type empty;
          }
          leaf missing-as-worst {
            type empty;
          }
        }
        container as-path {
          leaf ignore {
            type empty;
          }
          leaf multipath-relax {
            type empty;
          }
        }
        uses bgp-bestpath-origin-as-grouping;
        container igp-metric {
          leaf ignore {
            type empty;
          }
          leaf sr-policy {
            type empty;
          }
        }
      }
      container log {
        container neighbor {
          leaf changes {
            type enumeration {
              enum detail;
              enum disable;
            }
          }
        }
      }
      container default {
        leaf local-preference {
          type uint32;
        }
      }
      container auto-policy-soft-reset {
        leaf disable {
          type empty;
        }
      }
      container label-delay {
        tailf:cli-compact-syntax;
        tailf:cli-sequence-commands;
        leaf seconds {
          tailf:cli-drop-node-name;
          type uint8;
        }
        leaf milliseconds {
          tailf:cli-drop-node-name;
          type uint16;
        }
      }
      container import-delay {
        tailf:cli-compact-syntax;
        tailf:cli-sequence-commands;
        leaf seconds {
          tailf:cli-drop-node-name;
          type uint8;
        }
        leaf milliseconds {
          tailf:cli-drop-node-name;
          type uint16;
        }
      }
      container fast-external-fallover {
        leaf disable {
          type empty;
        }
      }
      leaf unsafe-ebgp-policy {
        type empty;
      }
      container origin-as {
        container validation {
          leaf time {
            type union {
              type uint8;
              type enumeration {
                enum off;
              }
            }
          }
          container signal {
            leaf ibgp {
              type empty;
            }
          }
          leaf disable {
            type empty;
          }
        }
      }
      container enforce-first-as {
        leaf disable {
          type empty;
        }
      }
    }
    container rpki {
      list server {
        key "name";
        leaf name {
          type inet:host;
        }
        leaf shutdown {
          type empty;
        }
        leaf username {
          type string;
        }
        container bind-source {
          container interface {
            uses interface-name-grouping;
          }
        }
        container transport {
          tailf:cli-compact-syntax;
          tailf:cli-sequence-commands;
          leaf protocol {
            tailf:cli-drop-node-name;
            type enumeration {
              enum ssh;
              enum tcp;
            }
          }
          leaf port {
            type uint16;
          }
        }
        leaf purge-time {
          type uint16;
        }
        leaf refresh-time {
          type union {
            type uint16;
            type enumeration {
              enum off;
            }
          }
        }
        leaf response-time {
          type union {
            type uint16;
            type enumeration {
              enum off;
            }
          }
        }
      }
    }
    container default-information {
      leaf originate {
        type empty;
      }
    }
    container mpls {
      container activate {
        tailf:cli-add-mode;
        list interface {
          tailf:cli-suppress-mode;
          tailf:cli-delete-when-empty;
          key "name";
          leaf name {
            type string;
          }
        }
      }
    }
    container update {
      leaf limit {
        type uint16;
      }
      container in {
        container error-handling {
          container extended {
            leaf ebgp {
              type empty;
            }
            leaf ibgp {
              type empty;
            }
          }
          container basic {
            container ebgp {
              leaf disable {
                type empty;
              }
            }
            container ibgp {
              leaf disable {
                type empty;
              }
            }
          }
        }
      }
    }
    container ibgp {
      container policy {
        container out {
          leaf enforce-modifications {
            type empty;
          }
        }
      }
    }
    container segment-routing {
      container srv6 {
        tailf:cli-add-mode;
        presence "true";
        leaf locator {
          type string;
        }
      }
    }
    container address-family {
      grouping orr-config-grouping {
        container orr-config {
          tailf:cli-drop-node-name;
          container optimal-route-reflection {
            list apply {
              tailf:cli-suppress-mode;
              tailf:cli-delete-when-empty;
              key "group";
              leaf group {
                type string;
              }
            }
            leaf fallback-default-bestpath {
              type empty;
            }
          }
        }
      }

      container ipv4 {
        container unicast {
          tailf:cli-add-mode;
          presence "true";
          uses bgp-address-family-grouping;
          uses orr-config-grouping;
          uses bgp-address-family-ipv4-grouping;
        }
        container multicast {
          tailf:cli-add-mode;
          presence "true";
          uses bgp-address-family-grouping;
          uses orr-config-grouping;
          uses bgp-address-family-ipv4-grouping;
        }
        container labeled-unicast {
          tailf:cli-add-mode;
          presence "true";
          uses bgp-address-family-grouping;
          uses bgp-address-family-ipv4-grouping;
        }
        container mdt {
          tailf:cli-add-mode;
          presence "true";
          uses bgp-address-family-grouping;
          uses bgp-address-family-ipv4-grouping;
        }
        container rt-filter {
          tailf:cli-add-mode;
          presence "true";
          uses bgp-address-family-grouping;
          uses bgp-address-family-ipv4-grouping;
        }
        container flowspec {
          tailf:cli-add-mode;
          presence "true";
          uses bgp-address-family-grouping;
          uses bgp-address-family-ipv4-grouping;
        }
        container mvpn {
          tailf:cli-add-mode;
          presence "true";
          uses bgp-address-family-grouping;
          uses bgp-address-family-ipv4-grouping;
        }
        container sr-policy {
          tailf:cli-add-mode;
          presence "true";
          uses bgp-address-family-grouping;
          uses bgp-address-family-ipv4-grouping;
        }
      }
      container ipv6 {
        container unicast {
          tailf:cli-add-mode;
          presence "true";
          uses bgp-address-family-grouping;
          uses orr-config-grouping;
          uses bgp-address-family-ipv6-grouping;
        }
        container multicast {
          tailf:cli-add-mode;
          presence "true";
          uses bgp-address-family-grouping;
          uses orr-config-grouping;
          uses bgp-address-family-ipv6-grouping;
        }
        container mvpn {
          tailf:cli-add-mode;
          presence "true";
          uses bgp-address-family-grouping;
          uses bgp-address-family-ipv6-grouping;
        }
        container sr-policy {
          tailf:cli-add-mode;
          presence "true";
          uses bgp-address-family-grouping;
          uses bgp-address-family-ipv6-grouping;
        }
        container flowspec {
          tailf:cli-add-mode;
          presence "true";
          uses bgp-address-family-grouping;
          uses bgp-address-family-ipv6-grouping;
        }
      }
      container vpnv4 {
        container unicast {
          tailf:cli-add-mode;
          presence "true";
          uses bgp-address-family-grouping;
          uses bgp-address-family-ipv4-grouping;
        }
        container multicast {
          tailf:cli-add-mode;
          presence "true";
          uses bgp-address-family-grouping;
          uses bgp-address-family-ipv4-grouping;
        }
        container flowspec {
          tailf:cli-add-mode;
          presence "true";
          uses bgp-address-family-grouping;
          uses bgp-address-family-ipv4-grouping;
        }
      }
      container vpnv6 {
        container unicast {
          tailf:cli-add-mode;
          presence "true";
          uses bgp-address-family-grouping;
          uses bgp-address-family-ipv6-grouping;
        }
        container multicast {
          tailf:cli-add-mode;
          presence "true";
          uses bgp-address-family-grouping;
          uses bgp-address-family-ipv6-grouping;
        }
        container flowspec {
          tailf:cli-add-mode;
          presence "true";
          uses bgp-address-family-grouping;
          uses bgp-address-family-ipv6-grouping;
        }
      }
      container l2vpn {
        container vpls-vpws {
          tailf:cli-add-mode;
          presence "true";
          uses bgp-address-family-grouping;
          uses bgp-address-family-ipv4-grouping;
        }
        container evpn {
          tailf:cli-add-mode;
          presence "true";
          uses bgp-address-family-grouping;
          uses bgp-address-family-ipv4-grouping;
        }
        container mspw {
          tailf:cli-add-mode;
          presence "true";
          uses bgp-address-family-grouping;
          uses bgp-address-family-ipv4-grouping;
        }
      }
      container link-state {
        container link-state {
          tailf:cli-add-mode;
          presence "true";
          uses bgp-address-family-grouping;
          uses bgp-address-family-pre-grouping;
        }
      }
    }
    list af-group {
      key "name address-family af-modifier";
      leaf name {
        type string;
      }
      leaf address-family {
        type enumeration {
          enum ipv4;
          enum ipv6;
          enum l2vpn;
          enum vpnv4;
          enum vpnv6;
        }
      }
      leaf af-modifier {
        type enumeration {
          enum labeled-unicast;
          enum mdt;
          enum multicast;
          enum mvpn;
          enum rt-filter;
          enum tunnel;
          enum unicast;
          enum vpls-vpws;
          enum evpn;
          enum mspw;
        }
      }
      uses router-bgp-neighbor-af-grouping;
    }
    list neighbor-group {
      key "name";
      leaf name {
        type string;
      }
      uses bgp-neighbor-grouping;
    }
    list neighbor {
      key "id";
      leaf id {
        tailf:cli-suppress-range;
        type union {
          type inet:ipv4-address;
          type inet:ipv6-address;
          type ipv4-prefix;
          type tailf:ipv6-address-and-prefix-length;
        }
      }
      leaf activate {
        tailf:cli-hide-in-submode;
        type empty;
      }
      uses bgp-neighbor-grouping;
      container peer-node-sid {
        leaf index {
          type uint32;
        }
      }
    }
    container socket {
      container receive-buffer-size {
        tailf:cli-compact-syntax;
        tailf:cli-sequence-commands {
          tailf:cli-reset-siblings;
        }
        leaf socket-size {
          tailf:cli-drop-node-name;
          type uint32;
        }
        leaf bgp-size {
          tailf:cli-drop-node-name;
          type uint32;
        }
      }
      container send-buffer-size {
        tailf:cli-compact-syntax;
        tailf:cli-sequence-commands {
          tailf:cli-reset-siblings;
        }
        leaf socket-size {
          tailf:cli-drop-node-name;
          type uint32;
        }
        leaf bgp-size {
          tailf:cli-drop-node-name;
          type uint32;
        }
      }
    }
  }

  grouping bgp-bestpath-origin-as-grouping {
    container origin-as {
      container use {
        leaf validity {
          type empty;
        }
      }
      container allow {
        leaf invalid {
          type empty;
        }
      }
    }
  }

  grouping router-bgp-grouping {
    uses apply-group-grouping;
    container as-league {
      tailf:cli-add-mode;
      presence "true";
      container peers {
        tailf:cli-add-mode;
        list as-number {
          tailf:cli-drop-node-name;
          tailf:cli-suppress-mode;
          tailf:cli-delete-when-empty;
          key "id";
          leaf id {
            type string;
          }
        }
      }
    }
    container nsr {
      tailf:cli-delete-when-empty;
      presence "true";
      leaf disable {
        type empty;
      }
    }
    uses router-bgp-vrf-grouping {
      augment "rpki/server" {
        container password {
          tailf:cli-compact-syntax;
          tailf:cli-sequence-commands {
            tailf:cli-reset-siblings;
          }
          leaf enc-type {
            tailf:cli-drop-node-name;
            type enumeration {
              enum clear;
              enum encrypted;
            }
          }
          leaf password {
            tailf:cli-drop-node-name;
            tailf:cli-multi-value;
            type string;
          }
        }
      }
    }
    list session-group {
      key "name";
      leaf name {
        type string;
      }
      leaf remote-as {
        type string;
      }
      container use {
        leaf session-group {
          type string;
        }
      }
      container ebgp-multihop {
        tailf:cli-compact-syntax;
        tailf:cli-sequence-commands {
          tailf:cli-reset-siblings;
        }
        leaf ttl-value {
          tailf:cli-drop-node-name;
          type uint8;
        }
        leaf mpls {
          type empty;
        }
      }
      container advertisement-interval {
        tailf:cli-sequence-commands {
          tailf:cli-reset-siblings;
        }
        tailf:cli-compact-syntax;
        leaf seconds {
          tailf:cli-drop-node-name;
          type uint16;
        }
        leaf milliseconds {
          tailf:cli-drop-node-name;
          type uint16;
        }
      }
      leaf maximum-peers {
        type uint16;
      }
      uses bgp-common-group-grouping;
      container tcp {
        leaf mss {
          type uint16;
        }
      }
      container local {
        leaf address {
          type union {
            type inet:ipv4-address;
            type inet:ipv6-address;
            type enumeration {
              enum inheritance-disable;
            }
          }
        }
      }
      container local-as {
        tailf:cli-compact-syntax;
        tailf:cli-sequence-commands {
          tailf:cli-reset-siblings;
        }
        choice local-as-choice {
          case a {
            leaf inheritance-disable {
              type empty;
            }
          }
          case b {
            leaf as-number {
              tailf:cli-drop-node-name;
              type string;
            }
            leaf no-prepend {
              type empty;
            }
            leaf replace-as {
              type empty;
            }
            leaf dual-as {
              type empty;
            }
          }
        }
      }
      container egress-engineering {
        tailf:cli-delete-when-empty;
        presence "true";
        leaf inheritance-disable {
          type empty;
        }
      }
      container password {
        choice password-choice {
          leaf clear {
            type string;
          }
          leaf encrypted {
            type string;
          }
          leaf inheritance-disable {
            type empty;
          }
        }
      }
      leaf shutdown {
        type empty;
      }
      container dmz-link-bandwidth {
        tailf:cli-delete-when-empty;
        presence "true";
        leaf inheritance-disable {
          type empty;
        }
      }
      leaf description {
        tailf:cli-multi-value;
        type string;
      }
      container ttl-security {
        tailf:cli-delete-when-empty;
        presence "true";
        leaf inheritance-disable {
          type empty;
        }
      }
      container bmp-activate {
        list server {
          tailf:cli-suppress-mode;
          tailf:cli-delete-when-empty;
          key "id";
          leaf id {
            type uint8;
          }
        }
      }
      container update-source {
        uses interface-name-grouping;
      }
      container ignore-connected-check {
        tailf:cli-delete-when-empty;
        presence "true";
        leaf inheritance-disable {
          type empty;
        }
      }
      leaf session-open-mode {
        type enumeration {
          enum active-only;
          enum both;
          enum passive-only;
        }
      }
      leaf send-buffer-size {
        type uint32;
      }
      leaf receive-buffer-size {
        type uint32;
      }
      container timers {
        tailf:cli-compact-syntax;
        tailf:cli-sequence-commands {
          tailf:cli-reset-siblings;
        }
        leaf keepalive {
          tailf:cli-drop-node-name;
          type uint16;
        }
        leaf holdtime {
          tailf:cli-drop-node-name;
          type uint16;
        }
        leaf min-holdtime {
          tailf:cli-drop-node-name;
          type uint16;
        }
      }
      uses bfd-common-parameters-grouping;
    }
    list vrf {
      key "name";
      leaf name {
        type string;
      }
      leaf rd {
        type string;
      }
      leaf label-allocation-mode {
        type enumeration {
          enum per-ce;
          enum per-vrf;
        }
      }
      container label {
        leaf mode {
          type enumeration {
            enum per-ce;
            enum per-vrf;
          }
        }
      }
      grouping mpls-alloc-grouping {
        container mpls {
          container alloc {
            leaf enable {
              type empty;
            }
          }
        }
      }

      uses router-bgp-vrf-grouping {
        augment "address-family/ipv4/unicast" {
          uses mpls-alloc-grouping;
        }
        augment "address-family/ipv6/unicast" {
          uses mpls-alloc-grouping;
        }
      }
    }
    container attribute-filter {
      list group {
        key "name";
        leaf name {
          type string;
        }
        container attribute {
          list explicit {
            tailf:cli-drop-node-name;
            tailf:cli-suppress-mode;
            tailf:cli-delete-when-empty;
            tailf:cli-compact-syntax;
            tailf:cli-sequence-commands;
            key "code";
            leaf code {
              type union {
                type enumeration {
                  enum AGGREGATOR {
                    value 7;
                  }
                  enum AIGP {
                    value 26;
                  }
                  enum AS4-AGGREGATOR {
                    value 18;
                  }
                  enum AS4-PATH {
                    value 17;
                  }
                  enum ATOMIC-AGGREGATE {
                    value 6;
                  }
                  enum CLUSTER-LIST {
                    value 10;
                  }
                  enum COMMUNITY {
                    value 8;
                  }
                  enum CONNECTOR {
                    value 20;
                  }
                  enum EXTENDED-COMMUNITIES {
                    value 16;
                  }
                  enum LOCAL-PREF {
                    value 5;
                  }
                  enum LSATTR {
                    value 29;
                  }
                  enum MULTI-EXIT-DISC {
                    value 4;
                  }
                  enum ORIGINATOR-ID {
                    value 9;
                  }
                  enum PMSI-TUNNEL {
                    value 22;
                  }
                  enum PPMP {
                    value 70;
                  }
                  enum SSA {
                    value 19;
                  }
                  enum unrecognized {
                    value 255;
                  }
                  enum ATTRSET {
                    value 128;
                  }
                  enum LARGE-COMMUNITY {
                    value 32;
                  }
                  enum TUNNEL-ENCAP {
                    value 23;
                  }
                }
                type uint8;
              }
            }
            choice config-choice {
              leaf discard {
                type empty;
              }
              leaf treat-as-withdraw {
                type empty;
              }
            }
          }
          list range {
            tailf:cli-suppress-mode;
            tailf:cli-delete-when-empty;
            key "code-range";
            leaf code-range {
              type string;
            }
            choice config-choice {
              leaf discard {
                type empty;
              }
              leaf treat-as-withdraw {
                type empty;
              }
            }
          }
        }
      }
    }
    list optimal-route-reflection {
      tailf:cli-suppress-mode;
      tailf:cli-delete-when-empty;
      tailf:cli-compact-syntax;
      tailf:cli-sequence-commands {
        tailf:cli-reset-siblings;
      }
      key "proto name";
      leaf proto {
        type enumeration {
          enum ipv4;
          enum ipv6;
        }
      }
      leaf name {
        type string;
      }
      leaf primary {
        tailf:cli-drop-node-name;
        mandatory true;
        type union {
          type inet:ipv4-address;
          type inet:ipv6-address;
        }
      }
      leaf secondary {
        tailf:cli-drop-node-name;
        tailf:cli-optional-in-sequence;
        type union {
          type inet:ipv4-address;
          type inet:ipv6-address;
        }
      }
      leaf tertiary {
        tailf:cli-drop-node-name;
        tailf:cli-optional-in-sequence;
        type union {
          type inet:ipv4-address;
          type inet:ipv6-address;
        }
      }
      leaf flex-algo {
        type uint8;
      }
    }
  }

  grouping police-set-grouping {
    leaf atm-clp {
      type empty;
    }
    container cos {
      leaf cos-value {
        tailf:cli-drop-node-name;
        type uint8;
      }
      leaf inner {
        type uint8;
      }
    }
    leaf dei {
      type uint8;
    }
    leaf discard-class {
      type uint8;
    }
    leaf traffic-class {
      type uint8;
    }
    container dscp {
      leaf outer {
        tailf:cli-drop-node-name;
        type dscp-type;
      }
      leaf tunnel {
        type dscp-type;
      }
    }
    leaf fr-de {
      type enumeration {
        enum 1;
      }
    }
    container mpls {
      container experimental {
        leaf imposition {
          type uint8;
        }
        leaf topmost {
          type uint8;
        }
      }
    }
    container precedence {
      leaf outer {
        tailf:cli-drop-node-name;
        type precedence-type;
      }
      leaf tunnel {
        type precedence-type;
      }
    }
    leaf qos-group {
      type uint8;
    }
    leaf forward-class {
      type uint8;
    }
    leaf srp-priority {
      type uint8;
    }
    leaf df {
      type uint8;
    }
  }

  grouping police-action-grouping {
    leaf child-conform-aware {
      tailf:cli-break-sequence-commands;
      type empty;
    }
    container conform-action {
      leaf drop {
        type empty;
      }
      container set {
        uses police-set-grouping;
      }
      leaf transmit {
        type empty;
      }
    }
    container exceed-action {
      leaf drop {
        type empty;
      }
      container set {
        uses police-set-grouping;
      }
      leaf transmit {
        type empty;
      }
    }
    container violate-action {
      leaf drop {
        type empty;
      }
      container set {
        uses police-set-grouping;
      }
      leaf transmit {
        type empty;
      }
    }
  }

  grouping policy-map-class-grouping {
    leaf type {
      tailf:cli-prefix-key;
      type enumeration {
        enum traffic;
      }
    }
    leaf drop {
      type empty;
    }
    leaf transmit {
      type empty;
    }
    container redirect {
      tailf:cli-compact-syntax;
      tailf:cli-sequence-commands {
        tailf:cli-reset-siblings;
      }
      leaf af {
        tailf:cli-drop-node-name;
        tailf:cli-optional-in-sequence;
        type enumeration {
          enum ipv4;
          enum ipv6;
        }
      }
      uses policy-map-class-redirect-nexthop-grouping;
      container nexthop2 {
        tailf:cli-drop-node-name;
        tailf:cli-flatten-container;
        uses policy-map-class-redirect-nexthop-grouping;
      }
    }
    leaf http-redirect {
      type string;
    }
    container shape {
      container average {
        tailf:cli-compact-syntax;
        tailf:cli-sequence-commands {
          tailf:cli-reset-siblings;
        }
        choice average-choice {
          case percent-case {
            leaf percent {
              type uint8;
            }
          }
          case unit-case {
            leaf rate {
              tailf:cli-drop-node-name;
              tailf:cli-optional-in-sequence;
              type uint32;
            }
            leaf rate-unit {
              tailf:cli-drop-node-name;
              type enumeration {
                enum bps;
                enum cellsps;
                enum gbps;
                enum kbps;
                enum mbps;
              }
            }
          }
          case variable-case {
            leaf variable {
              tailf:cli-drop-node-name;
              tailf:cli-multi-value;
              type string;
            }
          }
          case per-thousand {
            leaf per-thousand {
              type uint16;
            }
          }
          case per-million {
            leaf per-million {
              type uint32;
            }
          }
        }
        leaf burst {
          tailf:cli-drop-node-name;
          type uint32;
        }
        leaf burst-unit {
          tailf:cli-drop-node-name;
          type police-burst-units-type;
        }
      }
    }
    container bandwidth {
      container bandwidth-units {
        tailf:cli-drop-node-name;
        tailf:cli-compact-syntax;
        tailf:cli-sequence-commands {
          tailf:cli-reset-siblings;
        }
        leaf rate {
          tailf:cli-drop-node-name;
          type uint32;
        }
        leaf units {
          tailf:cli-drop-node-name;
          type police-rate-units-type;
        }
      }
      leaf percent {
        type percentage-type;
      }
      container remaining {
        leaf percent {
          type percentage-type;
        }
        leaf ratio {
          type uint16;
        }
      }
    }
    choice police-choice {
      case police-rate-unit-case {
        container police-rate-unit {
          tailf:cli-no-keyword;
          tailf:cli-drop-node-name;
          container police {
            container rate {
              tailf:cli-add-mode;
              tailf:cli-sequence-commands {
                tailf:cli-reset-siblings;
              }
              choice rate-choice {
                case units-case {
                  leaf cir {
                    tailf:cli-drop-node-name;
                    tailf:cli-hide-in-submode;
                    type uint64;
                  }
                  leaf cir-unit {
                    tailf:cli-drop-node-name;
                    tailf:cli-hide-in-submode;
                    type police-rate-units-type;
                  }
                }
                case percent-case {
                  leaf percent {
                    tailf:cli-hide-in-submode;
                    type uint8;
                  }
                }
                leaf per-million {
                  tailf:cli-hide-in-submode;
                  type uint32;
                }
                leaf per-thousand {
                  tailf:cli-hide-in-submode;
                  type uint16;
                }
              }
              leaf burst {
                tailf:cli-optional-in-sequence;
                tailf:cli-hide-in-submode;
                type uint32;
              }
              leaf burst-units {
                tailf:cli-drop-node-name;
                tailf:cli-optional-in-sequence;
                tailf:cli-hide-in-submode;
                type police-burst-units-type;
              }
              leaf peak-rate {
                tailf:cli-optional-in-sequence;
                tailf:cli-hide-in-submode;
                type uint64;
              }
              leaf peak-rate-units {
                tailf:cli-drop-node-name;
                tailf:cli-optional-in-sequence;
                tailf:cli-hide-in-submode;
                type police-rate-units-type;
              }
              container peak-rate-percent {
                tailf:cli-drop-node-name;
                tailf:cli-optional-in-sequence;
                tailf:cli-hide-in-submode;
                tailf:cli-flatten-container;
                container peak-rate {
                  tailf:cli-flatten-container;
                  tailf:cli-hide-in-submode;
                  leaf percent {
                    type percentage-type;
                  }
                }
              }
              leaf peak-burst {
                tailf:cli-hide-in-submode;
                tailf:cli-optional-in-sequence;
                type uint32;
              }
              leaf peak-burst-units {
                tailf:cli-drop-node-name;
                tailf:cli-optional-in-sequence;
                tailf:cli-hide-in-submode;
                type police-burst-units-type;
              }
              uses police-action-grouping;
            }
          }
        }
      }
      case police-unit-case {
        container police-unit {
          tailf:cli-no-keyword;
          tailf:cli-drop-node-name;
          container police {
            tailf:cli-add-mode;
            tailf:cli-flatten-container;
            tailf:cli-sequence-commands {
              tailf:cli-reset-siblings;
            }
            leaf cir {
              tailf:cli-hide-in-submode;
              type uint32;
            }
            leaf bc {
              tailf:cli-hide-in-submode;
              tailf:cli-optional-in-sequence;
              type uint32;
            }
            leaf be {
              tailf:cli-hide-in-submode;
              tailf:cli-optional-in-sequence;
              type uint32;
            }
            uses police-action-grouping;
          }
        }
      }
    }
    container set {
      uses police-set-grouping;
    }
    container priority {
      leaf level {
        type uint8;
      }
    }
    container queue-limit {
      tailf:cli-compact-syntax;
      tailf:cli-sequence-commands;
      choice queue-limit-choice {
        case percent {
          leaf percent {
            type uint8;
          }
        }
        case value {
          leaf queue-limit-value {
            tailf:cli-drop-node-name;
            type uint32;
          }
          leaf queue-limit-unit {
            tailf:cli-drop-node-name;
            type enumeration {
              enum bytes;
              enum kbytes;
              enum mbytes;
              enum ms;
              enum packets;
              enum us;
            }
          }
        }
        list discard-class {
          tailf:cli-suppress-mode;
          tailf:cli-delete-when-empty;
          tailf:cli-compact-syntax;
          tailf:cli-sequence-commands {
            tailf:cli-reset-siblings;
          }
          key "id";
          leaf id {
            type uint8;
          }
          choice limit-choice {
            case value {
              leaf queue-limit-value {
                tailf:cli-drop-node-name;
                type uint32;
              }
              leaf queue-limit-unit {
                tailf:cli-drop-node-name;
                type enumeration {
                  enum bytes;
                  enum kbytes;
                  enum mbytes;
                  enum ms;
                  enum packets;
                  enum us;
                }
              }
            }
            leaf percent {
              type uint8;
            }
          }
        }
      }
    }
    container service-function-path {
      tailf:cli-compact-syntax;
      tailf:cli-sequence-commands {
        tailf:cli-reset-siblings;
      }
      leaf id {
        tailf:cli-drop-node-name;
        type uint32;
      }
      leaf index {
        type uint8;
      }
      leaf metadata {
        type string;
      }
    }
    container service-policy {
      tailf:cli-compact-syntax;
      tailf:cli-sequence-commands {
        tailf:cli-reset-all-siblings;
      }
      leaf type {
        tailf:cli-optional-in-sequence;
        type enumeration {
          enum accounting;
          enum control;
          enum none;
          enum pbr;
          enum performance-traffic;
          enum qos;
          enum redirect;
          enum traffic;
        }
      }
      leaf name {
        tailf:cli-drop-node-name;
        type string;
      }
    }
    container random-detect {
      leaf default {
        type empty;
      }
      list cos {
        tailf:cli-suppress-mode;
        tailf:cli-delete-when-empty;
        tailf:cli-compact-syntax;
        tailf:cli-sequence-commands {
          tailf:cli-reset-all-siblings;
        }
        key "name";
        leaf name {
          type string;
        }
        uses class-random-detect-grouping;
      }
      list dei {
        tailf:cli-suppress-mode;
        tailf:cli-delete-when-empty;
        tailf:cli-compact-syntax;
        tailf:cli-sequence-commands {
          tailf:cli-reset-all-siblings;
        }
        key "name";
        leaf name {
          type string;
        }
        uses class-random-detect-grouping;
      }
      list dscp {
        tailf:cli-suppress-mode;
        tailf:cli-delete-when-empty;
        tailf:cli-compact-syntax;
        tailf:cli-sequence-commands {
          tailf:cli-reset-all-siblings;
        }
        key "name";
        leaf name {
          type string;
        }
        uses class-random-detect-grouping;
      }
      list exp {
        tailf:cli-suppress-mode;
        tailf:cli-delete-when-empty;
        tailf:cli-compact-syntax;
        tailf:cli-sequence-commands {
          tailf:cli-reset-all-siblings;
        }
        key "name";
        leaf name {
          type string;
        }
        uses class-random-detect-grouping;
      }
      list precedence {
        tailf:cli-suppress-mode;
        tailf:cli-delete-when-empty;
        tailf:cli-compact-syntax;
        tailf:cli-sequence-commands {
          tailf:cli-reset-all-siblings;
        }
        key "name";
        leaf name {
          type string;
        }
        uses class-random-detect-grouping;
      }
      list discard-class {
        tailf:cli-suppress-mode;
        tailf:cli-delete-when-empty;
        tailf:cli-compact-syntax;
        tailf:cli-sequence-commands {
          tailf:cli-reset-all-siblings;
        }
        key "name";
        leaf name {
          type uint8;
        }
        uses class-random-detect-grouping;
      }
      container default-values {
        tailf:cli-drop-node-name;
        tailf:cli-compact-syntax;
        tailf:cli-sequence-commands {
          tailf:cli-reset-all-siblings;
        }
        uses class-random-detect-grouping;
      }
    }
    container monitor {
      container parameters {
        tailf:cli-add-mode;
        leaf flows {
          type uint16;
        }
        container interval {
          leaf duration {
            type uint16;
          }
        }
        leaf history {
          type uint8;
        }
        leaf timeout {
          type uint8;
        }
      }
      container metric {
        container ip-cbr {
          tailf:cli-add-mode;
          container rate {
            container layer3 {
              tailf:cli-compact-syntax;
              tailf:cli-sequence-commands {
                tailf:cli-reset-siblings;
              }
              leaf packet {
                type uint32;
              }
              leaf pps {
                type empty;
              }
            }
            container media {
              tailf:cli-compact-syntax;
              tailf:cli-sequence-commands {
                tailf:cli-reset-siblings;
              }
              leaf value {
                tailf:cli-drop-node-name;
                type uint32;
              }
              leaf units {
                tailf:cli-drop-node-name;
                type police-rate-units-type;
              }
            }
          }
        }
        container mdi {
          container mpeg {
            tailf:cli-add-mode;
            presence "true";
            container filter {
              tailf:cli-compact-syntax;
              tailf:cli-sequence-commands {
                tailf:cli-reset-siblings;
              }
              leaf packet-rate {
                type uint32;
              }
              leaf pps {
                type empty;
              }
            }
            container rate {
              container layer3 {
                tailf:cli-compact-syntax;
                tailf:cli-sequence-commands {
                  tailf:cli-reset-siblings;
                }
                leaf packet {
                  type uint32;
                }
                leaf pps {
                  type empty;
                }
              }
            }
          }
        }
      }
    }
    list react {
      key "id type";
      leaf id {
        type uint32;
      }
      leaf type {
        type enumeration {
          enum delay-factor;
          enum flow-count;
          enum mdi-error-seconds;
          enum mdi-jitter;
          enum mdi-mdc;
          enum mdi-mlr;
          enum mdi-transport-availability;
          enum media-stop;
          enum mpeg-loss-pkts;
          enum mrv;
          enum packet-rate;
          enum rtp-error-seconds;
          enum rtp-jitter;
          enum rtp-loss-fraction;
          enum rtp-loss-pkts;
          enum rtp-max-jitter;
          enum rtp-out-of-order;
          enum rtp-transport-availability;
        }
      }
      container threshold {
        container type {
          leaf immediate {
            type empty;
          }
        }
        container value {
          tailf:cli-compact-syntax;
          tailf:cli-sequence-commands {
            tailf:cli-reset-siblings;
          }
          leaf operator {
            tailf:cli-drop-node-name;
            type enumeration {
              enum ge;
              enum gt;
              enum le;
              enum lt;
              enum range;
            }
          }
          leaf value {
            tailf:cli-drop-node-name;
            type string;
          }
        }
      }
      container action {
        leaf syslog {
          type empty;
        }
        leaf snmp {
          type empty;
        }
      }
      container alarm {
        leaf severity {
          type enumeration {
            enum error;
            enum critical;
            enum alert;
            enum emergency;
          }
        }
        container type {
          leaf discrete {
            type empty;
          }
        }
      }
    }
  }

  grouping policy-map-class-redirect-nexthop-grouping {
    container nexthop {
      tailf:cli-flatten-container;
      tailf:cli-compact-syntax;
      tailf:cli-sequence-commands {
        tailf:cli-reset-siblings;
      }
      leaf vrf {
        tailf:cli-optional-in-sequence;
        type vrf-type;
      }
      choice nexthop-choice {
        leaf IPv4-address {
          tailf:cli-drop-node-name;
          type inet:ipv4-address;
        }
        leaf IPv6-address {
          tailf:cli-drop-node-name;
          type string;
        }
        leaf route-target {
          type string;
        }
      }
    }
  }

  grouping performance-mgmt-grouping {
    choice case-choice {
      container AverageCpuUsed {
        tailf:cli-compact-syntax;
        tailf:cli-sequence-commands {
          tailf:cli-reset-all-siblings;
        }
        uses average-cpu-used-grouping;
      }
      container AverageCPUUsed {
        tailf:cli-compact-syntax;
        tailf:cli-sequence-commands {
          tailf:cli-reset-all-siblings;
        }
        uses average-cpu-used-grouping;
      }
    }
    leaf sample-size {
      type uint8;
    }
    leaf sample-interval {
      type uint8;
    }
  }

  grouping performance-mgmt-template-grouping {
    list template {
      key "name";
      leaf name {
        type string;
      }
      uses performance-mgmt-grouping;
    }
  }

  grouping ipv4-ipv6-common-grouping {
    leaf conflict-policy {
      type enumeration {
        enum highest-ip;
        enum longest-prefix;
        enum static;
      }
    }
    list prefix-list {
      key "name";
      leaf name {
        type string;
      }
      list rule {
        tailf:cli-drop-node-name;
        tailf:cli-suppress-mode;
        tailf:cli-delete-when-empty;
        key "id";
        leaf id {
          type uint32;
        }
        leaf line {
          tailf:cli-drop-node-name;
          tailf:cli-multi-value;
          type string;
        }
      }
    }
  }

  grouping arp-grouping {
    list arp-list {
      tailf:cli-drop-node-name;
      tailf:cli-suppress-mode;
      tailf:cli-delete-when-empty;
      tailf:cli-compact-syntax;
      tailf:cli-sequence-commands {
        tailf:cli-reset-all-siblings;
      }
      key "address";
      leaf address {
        type inet:ipv4-address;
      }
      leaf mac {
        tailf:cli-drop-node-name;
        type string;
      }
      leaf type {
        tailf:cli-drop-node-name;
        type enumeration {
          enum ARPA;
          enum SRP;
          enum SRPA;
          enum SRPB;
        }
      }
      leaf alias {
        tailf:cli-optional-in-sequence;
        type empty;
      }
      leaf interface {
        type string;
      }
    }
  }

  grouping tftp-server-grouping {
    list tftp-server-list {
      tailf:cli-drop-node-name;
      tailf:cli-suppress-mode;
      tailf:cli-delete-when-empty;
      tailf:cli-compact-syntax;
      tailf:cli-sequence-commands {
        tailf:cli-reset-all-siblings;
      }
      key "af";
      leaf af {
        type enumeration {
          enum ipv4;
          enum ipv6;
        }
      }
      leaf server {
        type empty;
      }
      leaf homedir {
        type string;
      }
      leaf max-servers {
        tailf:cli-break-sequence-commands;
        type union {
          type uint32;
          type enumeration {
            enum no-limit;
          }
        }
      }
      leaf access-list {
        type string;
      }
    }
  }

  grouping telnet-server-grouping {
    list telnet-server-list {
      tailf:cli-drop-node-name;
      tailf:cli-suppress-mode;
      tailf:cli-delete-when-empty;
      tailf:cli-compact-syntax;
      key "af";
      leaf af {
        type enumeration {
          enum ipv4;
          enum ipv6;
        }
      }
      leaf dscp {
        type uint8;
      }
      container server {
        tailf:cli-compact-syntax;
        tailf:cli-sequence-commands {
          tailf:cli-reset-siblings;
        }
        leaf max-servers {
          type uint8;
        }
        leaf access-list {
          type string;
        }
      }
    }
  }

  grouping ntp-server-grouping {
    list server-list {
      tailf:cli-drop-node-name;
      tailf:cli-suppress-mode;
      tailf:cli-delete-when-empty;
      tailf:cli-compact-syntax;
      key "name";
      leaf name {
        type inet:host;
      }
      leaf ip-version {
        tailf:cli-drop-node-name;
        tailf:cli-prefix-key;
        type enumeration {
          enum ipv4;
          enum ipv6;
        }
      }
      leaf version {
        type uint8;
      }
      leaf minpoll {
        type uint8;
      }
      leaf maxpoll {
        type uint8;
      }
      leaf prefer {
        type empty;
      }
      leaf burst {
        type empty;
      }
      leaf iburst {
        type empty;
      }
      container source {
        tailf:cli-flatten-container;
        tailf:cli-compact-syntax;
        uses interface-name-grouping;
      }
      leaf key {
        type uint16;
      }
    }
  }

  grouping router-static-ipv6-grouping {
    list routes {
      tailf:cli-drop-node-name;
      tailf:cli-suppress-mode;
      tailf:cli-delete-when-empty;
      tailf:cli-compact-syntax;
      key "net interface address";
      leaf net {
        type tailf:ipv6-address-and-prefix-length;
      }
      leaf interface {
        type string;
      }
      leaf address {
        type inet:ipv6-address;
      }
      uses router-static-options-grouping;
    }
    list routes-ip {
      tailf:cli-drop-node-name;
      tailf:cli-suppress-mode;
      tailf:cli-delete-when-empty;
      tailf:cli-compact-syntax;
      key "net address";
      leaf net {
        type tailf:ipv6-address-and-prefix-length;
      }
      leaf address {
        type inet:ipv6-address;
      }
      uses router-static-options-grouping;
    }
    list routes-if {
      tailf:cli-drop-node-name;
      tailf:cli-suppress-mode;
      tailf:cli-delete-when-empty;
      tailf:cli-compact-syntax;
      key "net interface";
      leaf net {
        type tailf:ipv6-address-and-prefix-length;
      }
      leaf interface {
        type string;
      }
      uses router-static-options-grouping;
    }
    list routes-vrf {
      tailf:cli-drop-node-name;
      tailf:cli-suppress-mode;
      tailf:cli-delete-when-empty;
      tailf:cli-compact-syntax;
      key "net vrf interface address";
      leaf net {
        type tailf:ipv6-address-and-prefix-length;
      }
      leaf vrf {
        type string;
      }
      leaf interface {
        type string;
      }
      leaf address {
        type inet:ipv6-address;
      }
      uses router-static-options-grouping;
    }
    list routes-base-vrf {
      tailf:cli-drop-node-name;
      tailf:cli-suppress-mode;
      tailf:cli-delete-when-empty;
      tailf:cli-compact-syntax;
      key "net vrf";
      leaf net {
        type tailf:ipv6-address-and-prefix-length;
      }
      leaf vrf {
        type string;
      }
      uses router-static-options-grouping;
    }
    list routes-ip-vrf {
      tailf:cli-drop-node-name;
      tailf:cli-suppress-mode;
      tailf:cli-delete-when-empty;
      tailf:cli-compact-syntax;
      key "net vrf address";
      leaf net {
        type tailf:ipv6-address-and-prefix-length;
      }
      leaf vrf {
        type string;
      }
      leaf address {
        type inet:ipv6-address;
      }
      uses router-static-options-grouping;
    }
    list routes-if-vrf {
      tailf:cli-drop-node-name;
      tailf:cli-suppress-mode;
      tailf:cli-delete-when-empty;
      tailf:cli-compact-syntax;
      key "net vrf interface";
      leaf net {
        type tailf:ipv6-address-and-prefix-length;
      }
      leaf vrf {
        type string;
      }
      leaf interface {
        type string;
      }
      uses router-static-options-grouping;
    }
  }

  grouping router-static-options-grouping {
    leaf bfd {
      type enumeration {
        enum fast-detect;
      }
    }
    leaf minimum-interval {
      type uint16;
    }
    leaf multiplier {
      type uint8;
    }
    leaf metric {
      tailf:cli-drop-node-name;
      type uint8;
    }
    leaf tag {
      type uint32;
    }
    leaf permanent {
      type empty;
    }
    leaf vrflabel {
      type uint32;
    }
    leaf tunnel-id {
      type uint32;
    }
    leaf track {
      type string;
    }
    container metric2 {
      tailf:cli-drop-node-name;
      tailf:cli-flatten-container;
      tailf:cli-compact-syntax;
      leaf metric {
        type uint32;
      }
    }
    leaf description {
      type string;
    }
  }

  grouping router-static-grouping {
    container maximum {
      container path {
        leaf ipv4 {
          type uint32;
        }
        leaf ipv6 {
          type uint32;
        }
      }
    }
    container address-family {
      container ipv4 {
        container unicast {
          tailf:cli-add-mode;
          uses router-static-ipv4-grouping;
        }
        container multicast {
          tailf:cli-add-mode;
          uses router-static-ipv4-grouping;
        }
      }
      container ipv6 {
        container unicast {
          tailf:cli-add-mode;
          uses router-static-ipv6-grouping;
        }
        container multicast {
          tailf:cli-add-mode;
          uses router-static-ipv6-grouping;
        }
      }
    }
  }

  grouping router-static-ipv4-grouping {
    list routes {
      tailf:cli-drop-node-name;
      tailf:cli-suppress-mode;
      tailf:cli-delete-when-empty;
      tailf:cli-compact-syntax;
      key "net interface address";
      leaf net {
        type ipv4-prefix;
      }
      leaf interface {
        type string;
      }
      leaf address {
        type inet:ipv4-address;
      }
      uses router-static-options-grouping;
    }
    list routes-ip {
      tailf:cli-drop-node-name;
      tailf:cli-suppress-mode;
      tailf:cli-delete-when-empty;
      tailf:cli-compact-syntax;
      key "net address";
      leaf net {
        type ipv4-prefix;
      }
      leaf address {
        type inet:ipv4-address;
      }
      uses router-static-options-grouping;
    }
    list routes-if {
      tailf:cli-drop-node-name;
      tailf:cli-suppress-mode;
      tailf:cli-delete-when-empty;
      tailf:cli-compact-syntax;
      key "net interface";
      leaf net {
        type ipv4-prefix;
      }
      leaf interface {
        type string;
      }
      uses router-static-options-grouping;
    }
    list routes-vrf {
      tailf:cli-drop-node-name;
      tailf:cli-suppress-mode;
      tailf:cli-delete-when-empty;
      tailf:cli-compact-syntax;
      key "net vrf interface address";
      leaf net {
        type ipv4-prefix;
      }
      leaf vrf {
        type string;
      }
      leaf interface {
        type string;
      }
      leaf address {
        type inet:ipv4-address;
      }
      uses router-static-options-grouping;
    }
    list routes-ip-vrf {
      tailf:cli-drop-node-name;
      tailf:cli-suppress-mode;
      tailf:cli-delete-when-empty;
      tailf:cli-compact-syntax;
      key "net vrf address";
      leaf net {
        type ipv4-prefix;
      }
      leaf vrf {
        type string;
      }
      leaf address {
        type inet:ipv4-address;
      }
      uses router-static-options-grouping;
    }
    list routes-if-vrf {
      tailf:cli-drop-node-name;
      tailf:cli-suppress-mode;
      tailf:cli-delete-when-empty;
      tailf:cli-compact-syntax;
      key "net vrf interface";
      leaf net {
        type ipv4-prefix;
      }
      leaf vrf {
        type string;
      }
      leaf interface {
        type string;
      }
      uses router-static-options-grouping;
    }
    list routes-net-vrf {
      tailf:cli-drop-node-name;
      tailf:cli-suppress-mode;
      tailf:cli-delete-when-empty;
      tailf:cli-compact-syntax;
      key "net vrf";
      leaf net {
        type ipv4-prefix;
      }
      leaf vrf {
        type string;
      }
      uses router-static-options-grouping;
    }
    list routes-net-sr-policy {
      tailf:cli-drop-node-name;
      tailf:cli-suppress-mode;
      tailf:cli-delete-when-empty;
      tailf:cli-compact-syntax;
      key "net sr-policy";
      leaf net {
        type ipv4-prefix;
      }
      leaf sr-policy {
        type string;
      }
      uses router-static-options-grouping;
    }
  }

  grouping router-igmp-grouping {
    list interface {
      key "name";
      leaf name {
        type string;
      }
      uses apply-group-grouping;
      leaf access-group {
        type string;
      }
      container explicit-tracking {
        tailf:cli-delete-when-empty;
        presence "true";
        leaf disable {
          type empty;
        }
      }
      leaf version {
        type uint8;
      }
      leaf router {
        type enumeration {
          enum disable;
          enum enable;
        }
      }
      list join-group {
        tailf:cli-suppress-mode;
        tailf:cli-delete-when-empty;
        tailf:cli-compact-syntax;
        key "address";
        leaf address {
          type inet:ipv4-address;
        }
        choice source-choice {
          leaf source-address {
            tailf:cli-drop-node-name;
            type inet:ipv4-address;
          }
          leaf exclude {
            type inet:ipv4-address;
          }
        }
      }
      container static-group-address {
        tailf:cli-drop-node-name;
        list static-group {
          tailf:cli-suppress-mode;
          tailf:cli-delete-when-empty;
          key "address";
          leaf address {
            type inet:ipv4-address;
          }
          leaf suppress-reports {
            type empty;
          }
        }
      }
      list static-group {
        tailf:cli-suppress-mode;
        tailf:cli-delete-when-empty;
        key "address source-address";
        leaf address {
          type inet:ipv4-address;
        }
        leaf source-address {
          type inet:ipv4-address;
        }
      }
      container static-group-inc-mask {
        tailf:cli-drop-node-name;
        list static-group {
          tailf:cli-suppress-mode;
          tailf:cli-delete-when-empty;
          tailf:cli-compact-syntax;
          tailf:cli-sequence-commands {
            tailf:cli-reset-siblings;
          }
          key "address inc-mask source-address";
          leaf address {
            type inet:ipv4-address;
          }
          leaf inc-mask {
            type inet:ipv4-address;
          }
          leaf count {
            tailf:cli-prefix-key {
              tailf:cli-before-key "3";
            }
            type uint16;
          }
          leaf source-address {
            type inet:ipv4-address;
          }
        }
      }
      container static-group-inc-mask-source {
        tailf:cli-drop-node-name;
        list static-group {
          tailf:cli-suppress-mode;
          tailf:cli-delete-when-empty;
          tailf:cli-compact-syntax;
          tailf:cli-sequence-commands {
            tailf:cli-reset-siblings;
          }
          key "address inc-mask source-address source-inc-mask";
          leaf address {
            type inet:ipv4-address;
          }
          leaf inc-mask {
            type inet:ipv4-address;
          }
          leaf count {
            tailf:cli-prefix-key {
              tailf:cli-before-key "3";
            }
            type uint16;
          }
          leaf source-address {
            type inet:ipv4-address;
          }
          leaf source-inc-mask {
            type inet:ipv4-address;
          }
          leaf source-count {
            type uint16;
          }
          leaf suppress-reports {
            type empty;
          }
        }
      }
    }
    container interface-all {
      tailf:cli-drop-node-name;
      container interface {
        container all {
          container router {
            leaf disable {
              type empty;
            }
          }
        }
      }
    }
    container ssm {
      container map {
        list static {
          tailf:cli-suppress-mode;
          tailf:cli-delete-when-empty;
          key "address";
          leaf address {
            type inet:ipv4-address;
          }
          leaf acl {
            tailf:cli-drop-node-name;
            type string;
          }
        }
      }
    }
    container explicit-tracking {
      presence "true";
    }
    leaf version {
      type uint8;
    }
    leaf access-group {
      type string;
    }
    leaf query-interval {
      type uint16;
    }
    leaf query-max-response-time {
      type uint8;
    }
    leaf robustness-count {
      type uint8;
    }
    container traffic {
      leaf profile {
        type string;
      }
    }
    container maximum {
      leaf groups {
        type uint32;
      }
      leaf groups-per-interface {
        type uint32;
      }
    }
  }

  grouping l2vpn-bridge-domain-mac-grouping {
    container aging {
      tailf:cli-add-mode;
      leaf time {
        type uint16;
      }
      leaf type {
        type enumeration {
          enum absolute;
          enum inactivity;
        }
      }
    }
    container learning {
      tailf:cli-delete-when-empty;
      presence "true";
      leaf disable {
        type empty;
      }
    }
    container limit {
      tailf:cli-add-mode;
      leaf maximum {
        type uint32;
      }
      leaf action {
        type enumeration {
          enum flood;
          enum no-flood;
          enum none;
          enum shutdown;
        }
      }
      leaf notification {
        type enumeration {
          enum both;
          enum none;
          enum syslog;
          enum trap;
        }
      }
    }
    container port-down {
      container flush {
        tailf:cli-delete-when-empty;
        presence "true";
        leaf disable {
          type empty;
        }
      }
    }
    container secure {
      tailf:cli-add-mode;
      tailf:cli-delete-when-empty;
      presence "true";
      leaf shutdown-recovery-timeout {
        type uint16;
      }
      leaf action {
        type enumeration {
          enum none;
          enum shutdown;
          enum restrict;
        }
      }
      leaf logging {
        type empty;
      }
    }
  }

  grouping l2vpn-bridge-domain-grouping {
    container transport-mode {
      container vlan {
        leaf passthrough {
          type empty;
        }
      }
    }
    uses storm-control-grouping;
    leaf coupled-mode {
      type empty;
    }
    container igmp {
      container snooping {
        leaf profile {
          type string;
        }
      }
    }
    container mac {
      tailf:cli-add-mode;
      uses l2vpn-bridge-domain-mac-grouping;
      container withdraw {
        choice withdraw-choice {
          leaf state-down {
            type empty;
          }
          leaf optimize {
            type empty;
          }
          leaf disable {
            type empty;
          }
        }
      }
    }
    container flooding {
      leaf disable {
        type empty;
      }
      container unknown-unicast {
        leaf disable {
          type empty;
        }
      }
    }
  }

  typedef itu-t-1-type {
    type enumeration {
      enum PRC;
      enum SSU-A;
      enum SSU-B;
      enum SEC;
      enum DNU;
      enum EEC1;
      enum PRTC;
      enum eEEC;
      enum ePRC;
      enum ePRTC;
    }
  }

  typedef itu-t-2-type {
    type enumeration {
      enum DUS;
      enum PRS;
      enum SMC;
      enum ST2;
      enum ST3;
      enum ST3E;
      enum STU;
      enum TNC;
      enum ST4;
      enum PROV;
      enum EEC2;
      enum PRTC;
      enum eEEC;
      enum ePRC;
      enum ePRTC;
    }
  }

  grouping freqsync-quality-grouping {
    choice quality-type {
      leaf exact {
        type empty;
      }
      leaf highest {
        type empty;
      }
      leaf lowest {
        type empty;
      }
    }
    container itu-t {
      tailf:cli-flatten-container;
      tailf:cli-compact-syntax;
      tailf:cli-sequence-commands {
        tailf:cli-reset-siblings;
      }
      leaf option {
        type enumeration {
          enum 1;
          enum 2;
        }
      }
      leaf generation {
        type enumeration {
          enum 1;
          enum 2;
        }
      }
      leaf ql1 {
        tailf:cli-drop-node-name;
        type itu-t-1-type;
      }
      leaf ql2 {
        tailf:cli-drop-node-name;
        type itu-t-2-type;
      }
      container highest {
        tailf:cli-flatten-container;
        tailf:cli-compact-syntax;
        leaf ql1 {
          tailf:cli-drop-node-name;
          type itu-t-1-type;
        }
        leaf ql2 {
          tailf:cli-drop-node-name;
          type itu-t-2-type;
        }
      }
    }
  }

  grouping router-hsrp-group-grouping {
    leaf name {
      type string;
    }
    leaf authentication {
      type string;
    }
    container timers {
      tailf:cli-compact-syntax;
      tailf:cli-sequence-commands;
      choice hello-timer-choice {
        leaf hello-seconds {
          tailf:cli-drop-node-name;
          type uint8;
        }
        leaf msec {
          type uint16;
        }
      }
      choice hold-timer-choice {
        leaf hold-seconds {
          tailf:cli-drop-node-name;
          type uint8;
        }
        container hold {
          tailf:cli-drop-node-name;
          tailf:cli-flatten-container;
          leaf msec {
            type uint16;
          }
        }
      }
    }
    leaf mac-address {
      type string;
    }
    container preempt {
      tailf:cli-delete-when-empty;
      presence "true";
      leaf delay {
        type uint16;
      }
    }
    leaf priority {
      type uint8;
    }
    list track {
      tailf:cli-suppress-mode;
      tailf:cli-delete-when-empty;
      tailf:cli-compact-syntax;
      key "name";
      leaf object {
        tailf:cli-prefix-key;
        type empty;
      }
      leaf name {
        type string;
      }
      leaf priority-decrement {
        tailf:cli-drop-node-name;
        type uint8;
      }
    }
    container bfd {
      container fast-detect {
        tailf:cli-delete-when-empty;
        presence "true";
        container peer {
          container ipv4 {
            tailf:cli-flatten-container;
            tailf:cli-compact-syntax;
            tailf:cli-sequence-commands {
              tailf:cli-reset-siblings;
            }
            leaf ipv4-address {
              tailf:cli-drop-node-name;
              type inet:ipv4-address;
            }
            container interface {
              tailf:cli-drop-node-name;
              tailf:cli-flatten-container;
              tailf:cli-compact-syntax;
              uses interface-name-grouping;
            }
          }
          container ipv6 {
            tailf:cli-flatten-container;
            tailf:cli-compact-syntax;
            tailf:cli-sequence-commands {
              tailf:cli-reset-siblings;
            }
            leaf ipv6-address {
              tailf:cli-drop-node-name;
              type inet:ipv6-address;
            }
            container interface {
              tailf:cli-drop-node-name;
              tailf:cli-flatten-container;
              tailf:cli-compact-syntax;
              uses interface-name-grouping;
            }
          }
        }
      }
      leaf minimum-interval {
        type uint16;
      }
      leaf multiplier {
        type uint8;
      }
    }
  }

  grouping router-hsrp-old-group-grouping {
    uses router-hsrp-group-grouping;
    container ipv4 {
      leaf address {
        tailf:cli-drop-node-name;
        type inet:ipv4-address;
      }
      list secondary {
        tailf:cli-drop-node-name;
        tailf:cli-suppress-mode;
        tailf:cli-delete-when-empty;
        tailf:cli-compact-syntax;
        tailf:cli-sequence-commands;
        key "address";
        leaf address {
          type inet:ipv4-address;
        }
        leaf secondary {
          type empty;
        }
      }
    }
  }

  grouping router-hsrp-ipv4-address-grouping {
    leaf address {
      type union {
        type inet:ipv4-address;
        type enumeration {
          enum learn;
        }
      }
    }
    container address-secondary-list {
      tailf:cli-drop-node-name;
      list address {
        tailf:cli-suppress-mode;
        tailf:cli-compact-syntax;
        tailf:cli-sequence-commands;
        tailf:cli-delete-when-empty;
        key "address";
        leaf address {
          type inet:ipv4-address;
        }
        leaf secondary {
          type empty;
        }
      }
    }
  }

  grouping router-hsrp-ipv4-group-grouping {
    uses router-hsrp-ipv4-address-grouping;
    uses router-hsrp-group-grouping;
  }

  grouping router-hsrp-ipv4-slave-group-grouping {
    leaf follow {
      type string;
    }
    leaf mac-address {
      type string;
    }
    uses router-hsrp-ipv4-address-grouping;
  }

  grouping router-hsrp-ipv6-address-grouping {
    container address {
      leaf-list global {
        type inet:ipv6-address;
      }
      container linklocal {
        choice linklocal-choice {
          leaf address {
            tailf:cli-drop-node-name;
            type inet:ipv6-address;
          }
          container autoconfig {
            tailf:cli-delete-when-empty;
            presence "true";
            leaf legacy-compatible {
              type empty;
            }
          }
        }
      }
    }
  }

  grouping router-hsrp-ipv6-group-grouping {
    uses router-hsrp-group-grouping;
    uses router-hsrp-ipv6-address-grouping;
  }

  grouping router-hsrp-ipv6-slave-group-grouping {
    leaf follow {
      type string;
    }
    leaf mac-address {
      type string;
    }
    uses router-hsrp-ipv6-address-grouping;
  }

  grouping interface-atm-grouping {
    container atm {
      container mcpt-timers {
        tailf:cli-compact-syntax;
        tailf:cli-sequence-commands {
          tailf:cli-reset-siblings;
        }
        leaf timer-1 {
          tailf:cli-drop-node-name;
          type uint16;
        }
        leaf timer-2 {
          tailf:cli-drop-node-name;
          type uint16;
        }
        leaf timer-3 {
          tailf:cli-drop-node-name;
          type uint16;
        }
      }
      container ilmi-keepalive {
        presence "true";
      }
    }
    list pvc {
      key "vpi-vci";
      leaf vpi-vci {
        type string;
      }
      uses interface-service-policy-grouping;
      container shape {
        choice shape-choice {
          container vbr-nrt {
            tailf:cli-compact-syntax;
            tailf:cli-sequence-commands {
              tailf:cli-reset-siblings;
            }
            leaf peak-output-rate {
              tailf:cli-drop-node-name;
              type uint32;
            }
            leaf sustained-output-rate {
              tailf:cli-drop-node-name;
              type uint32;
            }
            leaf burst-size {
              tailf:cli-drop-node-name;
              type uint16;
            }
          }
          leaf cbr {
            type uint32;
          }
        }
      }
      leaf encapsulation {
        type enumeration {
          enum aal0;
          enum aal5;
          enum aal5mux;
          enum aal5nlpid;
          enum aal5snap;
        }
      }
      container oam {
        container retry {
          tailf:cli-compact-syntax;
          tailf:cli-sequence-commands;
          tailf:cli-delete-when-empty;
          presence "true";
          leaf up-count {
            tailf:cli-drop-node-name;
            type uint16;
          }
          leaf down-count {
            tailf:cli-drop-node-name;
            type uint16;
          }
          leaf retry-frequency {
            tailf:cli-drop-node-name;
            type uint16;
          }
        }
      }
      container oam-pvc {
        container manage {
          tailf:cli-delete-when-empty;
          presence "true";
          leaf disable {
            type empty;
          }
          leaf frequency {
            tailf:cli-drop-node-name;
            type uint16;
          }
        }
      }
      container cell-packing {
        tailf:cli-compact-syntax;
        tailf:cli-sequence-commands {
          tailf:cli-reset-siblings;
        }
        leaf cells {
          tailf:cli-drop-node-name;
          type uint8;
        }
        leaf timer {
          tailf:cli-drop-node-name;
          type uint8;
        }
      }
    }
  }

  grouping ipsla-operation-type-grouping {
    leaf tag {
      type string;
    }
    leaf timeout {
      type uint32;
    }
    leaf vrf {
      type string;
    }
    container history {
      tailf:cli-add-mode;
      leaf lives {
        type uint8;
      }
      leaf filter {
        type enumeration {
          enum all;
          enum failures;
        }
      }
      leaf buckets {
        type uint8;
      }
    }
    container source {
      leaf address {
        type union {
          type inet:ipv4-address;
          type inet:ipv6-address;
        }
      }
      leaf port {
        type uint16;
      }
    }
    container destination {
      leaf address {
        type union {
          type inet:ipv4-address;
          type inet:ipv6-address;
        }
      }
      leaf port {
        type uint16;
      }
    }
    container statistics {
      tailf:cli-add-mode;
      leaf hourly {
        tailf:cli-hide-in-submode;
        type empty;
      }
      leaf buckets {
        type uint8;
      }
      container distribution {
        leaf count {
          type uint8;
        }
        leaf interval {
          type uint8;
        }
      }
    }
    container packet {
      leaf count {
        type uint16;
      }
      leaf interval {
        type uint16;
      }
    }
    leaf tos {
      type uint8;
    }
    container datasize {
      leaf request {
        type uint16;
      }
    }
    container target {
      container traffic-eng {
        leaf tunnel {
          type uint16;
        }
      }
      container pseudowire {
        tailf:cli-compact-syntax;
        tailf:cli-sequence-commands;
        leaf address {
          tailf:cli-drop-node-name;
          type inet:ipv4-address;
        }
        leaf pw-id {
          tailf:cli-drop-node-name;
          type uint32;
        }
      }
      leaf ipv4 {
        type ipv4-prefix;
      }
    }
    leaf frequency {
      type uint32;
    }
    container statistics-interval {
      tailf:cli-drop-node-name;
      container statistics {
        list interval {
          key "seconds";
          leaf seconds {
            type uint16;
          }
          leaf buckets {
            type uint8;
          }
        }
      }
    }
  }

  grouping storm-control-grouping {
    container storm-control {
      container broadcast {
        leaf kbps {
          type uint32;
        }
        leaf pps {
          type uint32;
        }
      }
      container multicast {
        leaf kbps {
          type uint32;
        }
        leaf pps {
          type uint32;
        }
      }
      container unknown-unicast {
        leaf kbps {
          type uint32;
        }
        leaf pps {
          type uint32;
        }
      }
    }
  }

  grouping vrf-af-import-from-grouping {
    container from {
      container vrf {
        leaf advertise-as-vpn {
          type empty;
        }
      }
      container bridge-domain {
        leaf advertise-as-vpn {
          type empty;
        }
      }
      container default-vrf {
        tailf:cli-compact-syntax;
        tailf:cli-sequence-commands {
          tailf:cli-reset-siblings;
        }
        leaf route-policy {
          type string;
        }
        leaf advertise-as-vpn {
          type empty;
        }
      }
    }
  }

  grouping vrf-af-ipv4-grouping {
    container import {
      leaf route-policy {
        type string;
      }
      container route-target {
        tailf:cli-add-mode;
        uses vrf-af-route-target-grouping;
      }
      uses vrf-af-import-from-grouping;
    }
    container export {
      leaf route-policy {
        type string;
      }
      container route-target {
        tailf:cli-add-mode;
        uses vrf-af-route-target-grouping;
      }
      container to {
        container vrf {
          leaf allow-imported-vpn {
            type empty;
          }
        }
        container default-vrf {
          tailf:cli-compact-syntax;
          tailf:cli-sequence-commands {
            tailf:cli-reset-siblings;
          }
          leaf route-policy {
            type string;
          }
          leaf allow-imported-vpn {
            type empty;
          }
        }
      }
    }
    container maximum {
      container prefix {
        tailf:cli-compact-syntax;
        tailf:cli-sequence-commands {
          tailf:cli-reset-all-siblings;
        }
        leaf limit {
          tailf:cli-drop-node-name;
          type uint32;
        }
        leaf mid-thresh {
          tailf:cli-drop-node-name;
          type uint8;
        }
      }
    }
  }

  grouping vrf-af-ipv6-grouping {
    container import {
      leaf route-policy {
        type string;
      }
      container route-target {
        tailf:cli-add-mode;
        uses vrf-af-route-target-grouping;
      }
      uses vrf-af-import-from-grouping;
    }
    container export {
      leaf route-policy {
        type string;
      }
      container route-target {
        tailf:cli-add-mode;
        uses vrf-af-route-target-grouping;
      }
      container to {
        container vrf {
          leaf allow-imported-vpn {
            type empty;
          }
        }
        container default-vrf {
          tailf:cli-compact-syntax;
          tailf:cli-sequence-commands {
            tailf:cli-reset-siblings;
          }
          leaf route-policy {
            type string;
          }
          leaf allow-imported-vpn {
            type empty;
          }
        }
      }
    }
    container maximum {
      container prefix {
        tailf:cli-compact-syntax;
        tailf:cli-sequence-commands {
          tailf:cli-reset-all-siblings;
        }
        leaf limit {
          tailf:cli-drop-node-name;
          type uint32;
        }
        leaf mid-thresh {
          tailf:cli-drop-node-name;
          type uint8;
        }
      }
    }
  }

  grouping snmp-server-host-grouping {
    list host {
      tailf:cli-suppress-mode;
      tailf:cli-delete-when-empty;
      tailf:cli-compact-syntax;
      tailf:cli-sequence-commands;
      key "address type community-string";
      leaf address {
        type string;
      }
      leaf type {
        type enumeration {
          enum traps;
          enum informs;
        }
      }
      leaf version {
        tailf:cli-optional-in-sequence;
        tailf:cli-prefix-key {
          tailf:cli-before-key "3";
        }
        type enumeration {
          enum 1;
          enum 2c;
          enum 3;
        }
      }
      leaf security-level {
        tailf:cli-drop-node-name;
        tailf:cli-optional-in-sequence;
        tailf:cli-prefix-key {
          tailf:cli-before-key "3";
        }
        type enumeration {
          enum auth;
          enum noauth;
          enum priv;
        }
      }
      leaf enc {
        tailf:cli-drop-node-name;
        tailf:cli-optional-in-sequence;
        tailf:cli-prefix-key {
          tailf:cli-before-key "3";
        }
        type enumeration {
          enum clear;
          enum encrypted;
        }
      }
      leaf encryption-aes {
        tailf:cli-optional-in-sequence;
        tailf:cli-prefix-key {
          tailf:cli-before-key "3";
        }
        type empty;
      }
      leaf community-string {
        type string;
      }
      leaf udp-port {
        tailf:cli-optional-in-sequence;
        type uint16;
      }
      leaf dying-gasp {
        type empty;
      }
    }
  }

  grouping multicast-routing-af-grouping {
    list interface {
      key "name";
      leaf name {
        type string;
      }
      uses apply-group-grouping;
      choice status-choice {
        leaf enable {
          type empty;
        }
        leaf disable {
          type empty;
        }
      }
      leaf boundary {
        type string;
      }
    }
    container interface-inheritance {
      leaf disable {
        type empty;
      }
    }
    leaf nsf {
      type empty;
    }
    container static {
      list sr-policy {
        tailf:cli-suppress-mode;
        tailf:cli-delete-when-empty;
        key "name";
        leaf name {
          type string;
        }
        leaf ingress {
          type inet:ipv4-address;
        }
      }
    }
    container mdt {
      leaf mtu {
        type uint16;
      }
      container source {
        uses interface-name-grouping;
      }
      container partitioned {
        container mldp {
          leaf ipv4 {
            type enumeration {
              enum mp2mp;
              enum p2mp;
            }
          }
        }
        container segment-routing {
          container mpls {
            tailf:cli-compact-syntax;
            tailf:cli-delete-when-empty;
            presence "true";
            leaf color {
              type uint32;
            }
            leaf fast-reroute {
              type enumeration {
                enum lfa;
              }
            }
          }
        }
      }
      container static {
        container p2mp-te {
          list tunnel-mte {
            tailf:cli-suppress-mode;
            tailf:cli-delete-when-empty;
            tailf:cli-allow-join-with-key;
            key "id";
            leaf id {
              type uint16;
            }
          }
        }
        container segment-routing {
          tailf:cli-delete-when-empty;
          presence "true";
          leaf strict-rpf {
            type empty;
          }
        }
      }
      container mldp {
        container in-band-signaling {
          leaf ipv4 {
            type empty;
          }
        }
      }
      container data {
        container value {
          tailf:cli-drop-node-name;
          tailf:cli-compact-syntax;
          tailf:cli-sequence-commands {
            tailf:cli-reset-all-siblings;
          }
          leaf max-data-mdts {
            tailf:cli-drop-node-name;
            type uint32;
          }
          uses multicast-routing-af-mdt-data-grouping;
        }
        container address {
          tailf:cli-drop-node-name;
          tailf:cli-compact-syntax;
          tailf:cli-sequence-commands {
            tailf:cli-reset-all-siblings;
          }
          leaf mdt-group-address {
            tailf:cli-drop-node-name;
            type ipv4-prefix;
          }
          uses multicast-routing-af-mdt-data-grouping;
        }
        container p2mp-te {
          tailf:cli-compact-syntax;
          tailf:cli-sequence-commands {
            tailf:cli-reset-all-siblings;
          }
          leaf max-data-mdts {
            tailf:cli-drop-node-name;
            type uint32;
          }
          uses multicast-routing-af-mdt-data-grouping;
        }
        container mldp {
          tailf:cli-compact-syntax;
          tailf:cli-sequence-commands {
            tailf:cli-reset-all-siblings;
          }
          leaf max-data-mdts {
            tailf:cli-drop-node-name;
            type uint32;
          }
          uses multicast-routing-af-mdt-data-grouping;
        }
        container segment-routing {
          container mpls {
            tailf:cli-compact-syntax;
            tailf:cli-sequence-commands {
              tailf:cli-reset-all-siblings;
            }
            leaf max-data-mdts {
              tailf:cli-drop-node-name;
              type uint32;
            }
            leaf color {
              tailf:cli-optional-in-sequence;
              type uint32;
            }
            leaf fast-reroute {
              tailf:cli-optional-in-sequence;
              type enumeration {
                enum lfa;
              }
            }
            uses multicast-routing-af-mdt-data-grouping;
          }
        }
      }
      container default {
        leaf ipv4 {
          type inet:ipv4-address;
        }
        container mldp {
          list ipv4 {
            tailf:cli-suppress-mode;
            tailf:cli-delete-when-empty;
            tailf:cli-compact-syntax;
            key "address";
            leaf address {
              type inet:ipv4-address;
            }
            container partitioned {
              leaf bidir {
                type empty;
              }
            }
          }
          container p2mp {
            tailf:cli-compact-syntax;
            tailf:cli-sequence-commands {
              tailf:cli-reset-siblings;
            }
            tailf:cli-delete-when-empty;
            presence "true";
            leaf flex-algo {
              tailf:cli-optional-in-sequence;
              type uint8;
            }
            container partitioned {
              leaf bidir {
                type empty;
              }
            }
          }
        }
        container p2mp-te {
          tailf:cli-delete-when-empty;
          presence "true";
          leaf attribute-set {
            type string;
          }
          container static {
            leaf tunnel-mte {
              tailf:cli-allow-join-with-value;
              type uint16;
            }
          }
        }
        container segment-routing {
          container mpls {
            tailf:cli-compact-syntax;
            tailf:cli-delete-when-empty;
            presence "true";
            leaf color {
              type uint32;
            }
            leaf fast-reroute {
              type enumeration {
                enum lfa;
              }
            }
          }
        }
      }
    }
    leaf export-rt {
      type string;
    }
    leaf import-rt {
      type string;
    }
    leaf log-traps {
      type empty;
    }
    container maximum {
      leaf disable {
        type empty;
      }
    }
    container bgp {
      container auto-discovery {
        tailf:cli-add-mode;
        tailf:cli-sequence-commands;
        tailf:cli-delete-when-empty;
        presence "true";
        leaf ad-tree {
          tailf:cli-drop-node-name;
          tailf:cli-hide-in-submode;
          type enumeration {
            enum ingress-replication;
            enum mldp;
            enum p2mp-te;
            enum pim;
            enum segment-routing;
          }
        }
        leaf inter-as {
          tailf:cli-break-sequence-commands;
          type empty;
        }
        leaf receiver-site {
          type empty;
        }
        leaf leaf-info-required {
          type empty;
        }
        container anycast-rp {
          tailf:cli-delete-when-empty;
          presence "true";
          leaf route-policy {
            type string;
          }
        }
      }
    }
    container multipath {
      tailf:cli-delete-when-empty;
      presence "true";
      leaf hash {
        type enumeration {
          enum source;
          enum source-group;
          enum source-nexthop;
        }
      }
    }
    container core-tree-protocol {
      container rsvp-te {
        tailf:cli-delete-when-empty;
        presence "true";
        leaf group-list {
          type string;
        }
      }
    }
    container ssm {
      leaf range {
        type string;
      }
      leaf allow-override {
        type empty;
      }
    }
    container oom-handling {
      presence "true";
    }
    leaf rate-per-route {
      type empty;
    }
    container interface-all {
      tailf:cli-drop-node-name;
      container interface {
        container all {
          leaf enable {
            type empty;
          }
        }
      }
    }
    container accounting {
      container per-prefix {
        tailf:cli-delete-when-empty;
        presence "true";
        leaf forward-only {
          type empty;
        }
      }
    }
  }

  grouping multicast-routing-grouping {
    container address-family {
      container ipv4 {
        tailf:cli-add-mode;
        presence "true";
        uses multicast-routing-af-grouping;
      }
      container ipv6 {
        tailf:cli-add-mode;
        presence "true";
        uses multicast-routing-af-grouping;
      }
    }
  }

  grouping router-mld-grouping {
    leaf version {
      type uint8;
    }
    list interface {
      key "name";
      leaf name {
        type ifname;
      }
      uses apply-group-grouping;
      leaf version {
        type uint8;
      }
      leaf router {
        type enumeration {
          enum enable;
          enum disable;
        }
      }
      list static-group {
        tailf:cli-suppress-mode;
        tailf:cli-delete-when-empty;
        tailf:cli-compact-syntax;
        tailf:cli-sequence-commands {
          tailf:cli-reset-siblings;
        }
        key "group-address source-address";
        leaf group-address {
          type inet:ipv6-address;
        }
        leaf inc-mask {
          tailf:cli-optional-in-sequence;
          tailf:cli-prefix-key {
            tailf:cli-before-key "2";
          }
          type inet:ipv6-address;
        }
        leaf count {
          type uint16;
        }
        leaf source-address {
          type inet:ipv6-address;
        }
      }
    }
  }

  grouping router-pim-if-grouping {
    leaf hello-interval {
      type uint16;
    }
    leaf dr-priority {
      type uint32;
    }
    leaf neighbor-filter {
      type string;
    }
    leaf join-prune-mtu {
      type uint16;
    }
  }

  grouping router-pim-af-grouping {
    container allow-rp {
      tailf:cli-compact-syntax;
      tailf:cli-delete-when-empty;
      presence "true";
      leaf rp-list {
        type string;
      }
      leaf group-list {
        type string;
      }
    }
    container register-source {
      uses interface-name-grouping;
    }
    container rpf {
      container topology {
        leaf route-policy {
          type string;
        }
      }
    }
    container rpf-vector {
      tailf:cli-compact-syntax;
      tailf:cli-delete-when-empty;
      presence "true";
      leaf allow-ebgp {
        type empty;
      }
      leaf disable-ibgp {
        type empty;
      }
      leaf use-standard-encoding {
        type empty;
      }
    }
    container mdt {
      container c-multicast-routing {
        tailf:cli-add-mode;
        tailf:cli-compact-syntax;
        tailf:cli-sequence-commands;
        choice protocol-choice {
          leaf bgp {
            tailf:cli-hide-in-submode;
            type empty;
          }
          leaf pim {
            tailf:cli-hide-in-submode;
            type empty;
          }
        }
        container migration {
          tailf:cli-break-sequence-commands;
          tailf:cli-delete-when-empty;
          presence "true";
          leaf route-policy {
            type string;
          }
        }
        container unicast-reachability {
          tailf:cli-compact-syntax;
          leaf connector {
            type enumeration {
              enum disable;
              enum enable;
            }
          }
        }
        leaf announce-pim-join-tlv {
          type empty;
        }
      }
      container data {
        leaf max-aggregation {
          type uint32;
        }
        leaf announce-interval {
          type uint8;
        }
        leaf switchover-interval {
          type uint8;
        }
      }
    }
    leaf accept-register {
      type string;
    }
    container spt-threshold {
      container infinity {
        tailf:cli-delete-when-empty;
        presence "true";
        leaf group-list {
          type string;
        }
      }
    }
    uses router-pim-af-maximum-grouping;
    container global {
      uses router-pim-af-maximum-grouping;
    }
    container neighbor-check-on-recv {
      leaf enable {
        type empty;
      }
    }
    container neighbor-check-on-send {
      leaf enable {
        type empty;
      }
    }
    container log {
      container neighbor {
        leaf changes {
          type empty;
        }
      }
    }
    leaf old-register-checksum {
      type empty;
    }
    container multipath {
      tailf:cli-delete-when-empty;
      presence "true";
      leaf hash {
        type enumeration {
          enum source;
          enum source-group;
          enum source-nexthop;
        }
      }
    }
    container ssm {
      leaf range {
        type string;
      }
    }
    uses router-pim-if-grouping;
    list interface {
      key "name";
      leaf name {
        type string;
      }
      uses apply-group-grouping;
      uses bfd-common-parameters-grouping;
      leaf bsr-border {
        type empty;
      }
      choice status-choice {
        leaf enable {
          type empty;
        }
        leaf disable {
          type empty;
        }
      }
      uses router-pim-if-grouping;
    }
  }

  grouping router-pim-af-maximum-grouping {
    container maximum {
      container route-interfaces {
        tailf:cli-compact-syntax;
        tailf:cli-sequence-commands {
          tailf:cli-reset-siblings;
        }
        leaf value {
          tailf:cli-drop-node-name;
          type uint32;
        }
        leaf threshold {
          type uint32;
        }
      }
      container routes {
        tailf:cli-compact-syntax;
        tailf:cli-sequence-commands {
          tailf:cli-reset-siblings;
        }
        leaf value {
          tailf:cli-drop-node-name;
          type uint32;
        }
        leaf threshold {
          type uint32;
        }
      }
      container group-mappings {
        container bsr {
          tailf:cli-compact-syntax;
          tailf:cli-sequence-commands {
            tailf:cli-reset-siblings;
          }
          leaf value {
            tailf:cli-drop-node-name;
            type uint16;
          }
          leaf threshold {
            type uint16;
          }
        }
      }
      container bsr {
        tailf:cli-compact-syntax;
        tailf:cli-sequence-commands {
          tailf:cli-reset-siblings;
        }
        leaf crp-cache {
          type uint16;
        }
        leaf threshold {
          type uint16;
        }
      }
      container register-states {
        tailf:cli-compact-syntax;
        tailf:cli-sequence-commands {
          tailf:cli-reset-siblings;
        }
        leaf source {
          tailf:cli-drop-node-name;
          type uint32;
        }
        leaf threshold {
          type uint8;
        }
      }
    }
  }

  grouping router-pim-af4-grouping {
    uses router-pim-af-grouping;
    list rp-address {
      tailf:cli-suppress-mode;
      tailf:cli-delete-when-empty;
      tailf:cli-compact-syntax;
      tailf:cli-sequence-commands {
        tailf:cli-reset-siblings;
      }
      key "name";
      leaf name {
        type inet:ipv4-address;
      }
      leaf group-access-list {
        tailf:cli-drop-node-name;
        tailf:cli-optional-in-sequence;
        type string;
      }
      leaf override {
        tailf:cli-optional-in-sequence;
        type empty;
      }
      leaf bidir {
        type empty;
      }
    }
    container bsr {
      container candidate-bsr {
        tailf:cli-compact-syntax;
        tailf:cli-sequence-commands {
          tailf:cli-reset-siblings;
        }
        leaf address {
          tailf:cli-drop-node-name;
          type string;
        }
        leaf hash-mask-len {
          tailf:cli-optional-in-sequence;
          type uint8;
        }
        leaf priority {
          type uint8;
        }
      }
      list candidate-rp {
        tailf:cli-suppress-mode;
        tailf:cli-delete-when-empty;
        tailf:cli-compact-syntax;
        tailf:cli-sequence-commands {
          tailf:cli-reset-siblings;
        }
        key "address";
        leaf address {
          type inet:ipv4-address;
        }
        leaf group-list {
          tailf:cli-optional-in-sequence;
          type string;
        }
        leaf priority {
          tailf:cli-optional-in-sequence;
          type uint8;
        }
        leaf interval {
          tailf:cli-optional-in-sequence;
          type uint16;
        }
        leaf bidir {
          type empty;
        }
      }
    }
    list sr-p2mp-policy {
      tailf:cli-delete-when-empty;
      key "name";
      leaf name {
        type string;
      }
      list static-group {
        tailf:cli-suppress-mode;
        tailf:cli-delete-when-empty;
        key "address source-address";
        leaf address {
          type inet:ipv4-address;
        }
        leaf source-address {
          type inet:ipv4-address;
        }
      }
      container static-group-inc-mask {
        tailf:cli-drop-node-name;
        list static-group {
          tailf:cli-suppress-mode;
          tailf:cli-delete-when-empty;
          tailf:cli-compact-syntax;
          tailf:cli-sequence-commands {
            tailf:cli-reset-siblings;
          }
          key "address inc-mask";
          leaf address {
            type inet:ipv4-address;
          }
          leaf inc-mask {
            type inet:ipv4-address;
          }
          leaf count {
            type uint16;
          }
          leaf source-address {
            tailf:cli-drop-node-name;
            type inet:ipv4-address;
          }
          container source {
            tailf:cli-drop-node-name;
            tailf:cli-flatten-container;
            tailf:cli-compact-syntax;
            tailf:cli-sequence-commands {
              tailf:cli-reset-siblings;
            }
            leaf inc-mask {
              type inet:ipv4-address;
            }
            leaf count {
              type uint16;
            }
          }
        }
      }
      container static-group-src-inc-mask {
        tailf:cli-drop-node-name;
        list static-group {
          tailf:cli-suppress-mode;
          tailf:cli-delete-when-empty;
          key "address source-address inc-mask";
          leaf address {
            type inet:ipv4-address;
          }
          leaf source-address {
            type inet:ipv4-address;
          }
          leaf inc-mask {
            type inet:ipv4-address;
          }
          leaf count {
            type uint16;
          }
        }
      }
      container static-group-address {
        tailf:cli-drop-node-name;
        list static-group {
          tailf:cli-suppress-mode;
          tailf:cli-delete-when-empty;
          key "address";
          leaf address {
            type inet:ipv4-address;
          }
        }
      }
    }
  }

  grouping router-pim-af6-grouping {
    uses router-pim-af-grouping;
    list rp-address {
      tailf:cli-suppress-mode;
      tailf:cli-delete-when-empty;
      tailf:cli-compact-syntax;
      tailf:cli-sequence-commands {
        tailf:cli-reset-siblings;
      }
      key "name";
      leaf name {
        type inet:ipv6-address;
      }
      leaf group-access-list {
        tailf:cli-drop-node-name;
        tailf:cli-optional-in-sequence;
        type string;
      }
      leaf override {
        tailf:cli-optional-in-sequence;
        type empty;
      }
      leaf bidir {
        type empty;
      }
    }
  }

  grouping router-pim-grouping {
    container address-family {
      container ipv4 {
        tailf:cli-add-mode;
        container auto-rp {
          list candidate-rp {
            tailf:cli-suppress-mode;
            tailf:cli-delete-when-empty;
            tailf:cli-compact-syntax;
            tailf:cli-sequence-commands {
              tailf:cli-reset-siblings;
            }
            key "name";
            leaf name {
              type string;
            }
            leaf scope {
              type uint8;
            }
            leaf group-list {
              type string;
            }
            leaf interval {
              type uint16;
            }
            leaf bidir {
              type empty;
            }
          }
          container listen {
            leaf disable {
              type empty;
            }
          }
        }
        container nsf {
          leaf lifetime {
            type uint16;
          }
        }
        uses router-pim-af4-grouping;
      }
      container ipv6 {
        tailf:cli-add-mode;
        uses router-pim-af6-grouping;
      }
    }
  }

  grouping router-rip-redistribute-grouping {
    leaf route-policy {
      type string;
    }
  }

  grouping router-rip-if-grouping {
    leaf broadcast-for-v2 {
      type empty;
    }
    uses route-policy-list-grouping;
  }

  grouping router-rip-grouping {
    list interface {
      key "name";
      leaf name {
        type ifname;
      }
      uses apply-group-grouping;
      container authentication {
        container keychain {
          tailf:cli-compact-syntax;
          tailf:cli-sequence-commands {
            tailf:cli-reset-siblings;
          }
          leaf name {
            tailf:cli-drop-node-name;
            type string;
          }
          leaf mode {
            type enumeration {
              enum md5;
              enum text;
            }
          }
        }
      }
      leaf passive-interface {
        type empty;
      }
      container send {
        leaf version {
          type enumeration {
            enum 1;
            enum 2;
          }
        }
      }
      uses router-rip-if-grouping;
    }
    container timers {
      container basic {
        tailf:cli-compact-syntax;
        tailf:cli-sequence-commands {
          tailf:cli-reset-siblings;
        }
        leaf update {
          tailf:cli-drop-node-name;
          type uint16;
        }
        leaf invalid {
          tailf:cli-drop-node-name;
          type uint32;
        }
        leaf holddown {
          tailf:cli-drop-node-name;
          type uint32;
        }
        leaf flush {
          tailf:cli-drop-node-name;
          type uint32;
        }
      }
    }
    container redistribute {
      container connected {
        tailf:cli-compact-syntax;
        tailf:cli-delete-when-empty;
        presence "true";
        uses router-rip-redistribute-grouping;
      }
      container static {
        tailf:cli-compact-syntax;
        tailf:cli-delete-when-empty;
        presence "true";
        uses router-rip-redistribute-grouping;
      }
      list bgp {
        tailf:cli-suppress-mode;
        tailf:cli-delete-when-empty;
        tailf:cli-compact-syntax;
        key "id";
        leaf id {
          type string;
        }
        uses router-rip-redistribute-grouping;
      }
    }
    leaf auto-summary {
      type empty;
    }
    leaf maximum-paths {
      type uint8;
    }
    leaf default-metric {
      type uint8;
    }
    container default-information {
      container originate {
        tailf:cli-compact-syntax;
        tailf:cli-delete-when-empty;
        presence "true";
        leaf route-policy {
          type string;
        }
      }
    }
    uses router-rip-if-grouping;
  }

  grouping router-vrrp-if-af-vrrp-grouping {
    leaf name {
      type string;
    }
    leaf priority {
      type uint8;
    }
    container preempt {
      choice preempt-choice {
        leaf delay {
          tailf:cli-optional-in-sequence;
          type uint16;
        }
        leaf disable {
          type empty;
        }
      }
    }
    container timer {
      tailf:cli-compact-syntax;
      tailf:cli-sequence-commands {
        tailf:cli-reset-siblings;
      }
      choice timer-choice {
        leaf time-value {
          tailf:cli-drop-node-name;
          type uint8;
        }
        leaf msec {
          type uint16;
        }
      }
      leaf force {
        type empty;
      }
    }
    container track {
      list interface {
        tailf:cli-suppress-mode;
        tailf:cli-delete-when-empty;
        tailf:cli-compact-syntax;
        key "name";
        leaf name {
          type string;
        }
        leaf priority {
          tailf:cli-drop-node-name;
          type uint8;
        }
      }
      list object {
        tailf:cli-suppress-mode;
        tailf:cli-delete-when-empty;
        tailf:cli-compact-syntax;
        key "name";
        leaf name {
          type string;
        }
        leaf priority {
          tailf:cli-drop-node-name;
          type uint8;
        }
      }
    }
  }

  grouping router-vrrp-if-af4-vrrp-grouping {
    uses router-vrrp-if-af-vrrp-grouping;
    list address {
      tailf:cli-suppress-mode;
      tailf:cli-delete-when-empty;
      tailf:cli-compact-syntax;
      key "ip";
      leaf ip {
        type inet:ipv4-address;
      }
      leaf secondary {
        type empty;
      }
    }
    container bfd {
      container fast-detect {
        container peer {
          leaf ipv4 {
            type inet:ipv4-address;
          }
        }
      }
    }
    leaf text-authentication {
      type string;
    }
  }

  grouping router-bgp-af-advertise-grouping {
    container re-originated {
      tailf:cli-delete-when-empty;
      presence "true";
      leaf route-target {
        tailf:cli-drop-node-name;
        type enumeration {
          enum regular-rt;
          enum stitching-rt;
        }
      }
    }
    container local {
      tailf:cli-delete-when-empty;
      presence "true";
      leaf route-target {
        tailf:cli-drop-node-name;
        type enumeration {
          enum regular-rt;
          enum stitching-rt;
        }
      }
    }
    leaf disable {
      type empty;
    }
    container imported-from-vrf {
      leaf disable {
        type empty;
      }
    }
    container imported-from-default-vrf {
      leaf disable {
        type empty;
      }
    }
  }

  grouping controller-dwdm-grouping {
    list dwdm {
      tailf:cli-allow-join-with-key;
      key "id";
      leaf id {
        type string;
      }
      uses description-grouping;
      leaf proactive {
        type empty;
      }
      container proactive-conf {
        tailf:cli-drop-node-name;
        container proactive {
          container revert {
            container threshold {
              tailf:cli-compact-syntax;
              tailf:cli-sequence-commands;
              leaf x-coefficient {
                tailf:cli-drop-node-name;
                type uint8;
              }
              leaf y-power {
                tailf:cli-drop-node-name;
                type uint8;
              }
            }
            leaf window {
              type uint32;
            }
          }
          container trigger {
            container threshold {
              tailf:cli-compact-syntax;
              tailf:cli-sequence-commands;
              leaf x-coefficient {
                tailf:cli-drop-node-name;
                type uint8;
              }
              leaf y-power {
                tailf:cli-drop-node-name;
                type uint8;
              }
            }
            leaf window {
              type uint32;
            }
          }
        }
      }
      container g709 {
        leaf enable {
          type empty;
        }
        container fec {
          choice fec-choice {
            leaf ci-bch {
              type empty;
            }
            leaf disable {
              type empty;
            }
            leaf enhanced {
              type enumeration {
                enum i.4;
                enum i.7;
              }
            }
            leaf high-gain-hd-fec {
              type empty;
            }
            leaf high-gain-multivendor-hd-fec {
              type empty;
            }
            leaf high-gain-sd-fec {
              type empty;
            }
            leaf long-haul-hd-fec {
              type empty;
            }
            leaf long-haul-sd-fec {
              type empty;
            }
            leaf standard {
              type empty;
            }
          }
        }
        leaf framing {
          type enumeration {
            enum opu1e;
            enum opu2e;
          }
        }
        container odu {
          container overhead {
            container tti {
              container expected {
                leaf ascii {
                  tailf:cli-multi-value;
                  type string;
                }
              }
              container sent {
                leaf ascii {
                  tailf:cli-multi-value;
                  type string;
                }
              }
            }
          }
          container threshold {
            leaf sd-ber {
              type uint8;
            }
            leaf sf-ber {
              type uint8;
            }
          }
        }
        container otu {
          container overhead {
            container tti {
              container expected {
                leaf ascii {
                  tailf:cli-multi-value;
                  type string;
                }
              }
              container sent {
                leaf ascii {
                  tailf:cli-multi-value;
                  type string;
                }
              }
            }
          }
          container threshold {
            leaf prefec-sd-ber {
              type uint8;
            }
            leaf prefec-sf-ber {
              type uint8;
            }
            leaf sd-ber {
              type uint8;
            }
            leaf sf-ber {
              type uint8;
            }
          }
        }
        leaf tti-processing {
          type empty;
        }
      }
      leaf loopback {
        type enumeration {
          enum internal;
          enum line;
        }
      }
      container wavelength {
        choice wave-length-choice {
          leaf channel-number {
            tailf:cli-drop-node-name;
            type uint8;
          }
          leaf frequency {
            type uint16;
          }
          leaf update {
            type uint32;
          }
          container hundred-Grid {
            tailf:alt-name "100MHz-Grid";
            leaf frequency {
              type string;
            }
          }
          container fifty-Grid {
            tailf:alt-name "50GHz-Grid";
            choice config-choice {
              leaf itu-ch {
                tailf:cli-drop-node-name;
                type uint8;
              }
              leaf frequency {
                type uint16;
              }
              leaf update {
                type uint32;
              }
            }
          }
        }
      }
      container network {
        container port {
          leaf id {
            tailf:cli-multi-value;
            type string;
          }
        }
      }
      leaf admin-state {
        type enumeration {
          enum in-service;
          enum maintenance;
          enum out-of-service;
          enum in-service-config-allowed;
        }
      }
      leaf transmit-power {
        type int16;
      }
      leaf shutdown {
        type empty;
      }
    }
  }

  grouping controller-grouping {
    uses controller-dwdm-grouping;
    list MgmtMultilink {
      tailf:cli-allow-join-with-key;
      key "id";
      leaf id {
        type string;
      }
      list bundle {
        tailf:cli-suppress-mode;
        tailf:cli-delete-when-empty;
        key "id";
        leaf id {
          type uint32;
        }
      }
    }
    list T1 {
      tailf:cli-allow-join-with-key;
      key "id";
      leaf id {
        type string;
      }
      uses description-grouping;
      leaf mode {
        type enumeration {
          enum atm;
        }
      }
      leaf framing {
        type enumeration {
          enum esf;
          enum sf;
        }
      }
      leaf linecode {
        type enumeration {
          enum ami;
          enum b8zs;
        }
      }
      container carrier-delay {
        choice carrier-delay-choice {
          leaf seconds {
            tailf:cli-drop-node-name;
            type uint8;
          }
          leaf msec {
            type uint16;
          }
        }
      }
      list channel-group {
        key "id";
        leaf id {
          type uint8;
        }
        leaf speed {
          type enumeration {
            enum 56;
            enum 64;
          }
        }
        leaf timeslots {
          type string;
        }
      }
      container clock {
        container source {
          choice source-choice {
            leaf internal {
              type empty;
            }
            leaf line {
              type empty;
            }
          }
        }
      }
      container bert {
        leaf error {
          type uint8;
        }
        leaf interval {
          type uint16;
        }
        leaf pattern {
          type enumeration {
            enum 0s;
            enum 1in8;
            enum 1s;
            enum 2e11;
            enum 2e15;
            enum 2e20;
            enum 2e20-QRSS;
            enum 2e23;
            enum 2e9;
            enum 3in24;
            enum 55Daly;
            enum 55Octet;
            enum alt-0-1;
          }
        }
      }
      leaf shutdown {
        type empty;
      }
      container loopback {
        leaf local {
          type empty;
        }
        leaf network {
          type enumeration {
            enum line;
            enum payload;
          }
        }
        container remote {
          tailf:cli-compact-syntax;
          choice line-payload {
            container line {
              leaf fdl {
                type enumeration {
                  enum ansi;
                  enum bellcore;
                }
              }
              leaf inband {
                type empty;
              }
            }
            container payload {
              leaf fdl {
                type enumeration {
                  enum ansi;
                }
              }
            }
          }
        }
      }
    }
    list T3 {
      tailf:cli-allow-join-with-key;
      key "id";
      leaf id {
        type string;
      }
      uses description-grouping;
      leaf mode {
        type enumeration {
          enum atm;
          enum e1;
          enum serial;
          enum t1;
        }
      }
      container dsu {
        tailf:cli-add-mode;
        leaf bandwidth {
          type uint16;
        }
        leaf mode {
          type enumeration {
            enum adtran;
            enum digital-link;
            enum kentrox;
            enum larscom;
            enum verilink;
          }
        }
        leaf remote {
          type enumeration {
            enum disable;
            enum fullrate;
          }
        }
      }
      leaf framing {
        type enumeration {
          enum auto-detect;
          enum c-bit;
          enum m23;
        }
      }
      container delay {
        leaf trigger {
          type uint16;
        }
      }
      leaf cablelength {
        type uint16;
      }
      container clock {
        container source {
          choice source-choice {
            leaf internal {
              type empty;
            }
            leaf line {
              type empty;
            }
          }
        }
      }
      container bert {
        leaf error {
          type uint8;
        }
        leaf interval {
          type uint16;
        }
        leaf pattern {
          type enumeration {
            enum 0s;
            enum 1in8;
            enum 1s;
            enum 2e11;
            enum 2e15;
            enum 2e20;
            enum 2e20-QRSS;
            enum 2e23;
            enum 2e9;
            enum 3in24;
            enum 55Daly;
            enum 55Octet;
            enum alt-0-1;
          }
        }
      }
      leaf shutdown {
        type empty;
      }
      container loopback {
        leaf local {
          type empty;
        }
        leaf network {
          type enumeration {
            enum line;
            enum payload;
          }
        }
        leaf remote {
          type enumeration {
            enum line;
            enum payload;
          }
        }
      }
    }
    list E1 {
      key "name";
      leaf name {
        type string;
      }
      uses description-grouping;
      container loopback {
        choice loopback-choice {
          leaf local {
            type empty;
          }
          leaf network {
            type enumeration {
              enum line;
            }
          }
        }
      }
      container prbs {
        tailf:cli-compact-syntax;
        tailf:cli-sequence-commands {
          tailf:cli-reset-siblings;
        }
        leaf mode {
          type enumeration {
            enum sink;
            enum source;
            enum source-sink;
          }
        }
        leaf pattern {
          type enumeration {
            enum PN15;
          }
        }
        leaf direction {
          type enumeration {
            enum line;
            enum system;
          }
        }
      }
      leaf sec-admin-state {
        type enumeration {
          enum normal;
          enum maintenance;
        }
      }
      container cem-group {
        leaf unframed {
          type empty;
        }
        list framed {
          tailf:cli-suppress-mode;
          tailf:cli-delete-when-empty;
          key "id";
          leaf id {
            type uint8;
          }
          leaf timeslots {
            type string;
          }
        }
      }
      leaf framing {
        type enumeration {
          enum crc4;
          enum no-crc4;
          enum unframed;
        }
      }
      leaf linecode {
        type enumeration {
          enum ami;
          enum hdb3;
        }
      }
      list channel-group {
        key "id";
        leaf id {
          type uint8;
        }
        leaf timeslots {
          type string;
        }
      }
      leaf down-when-looped {
        type empty;
      }
      container clock {
        container source {
          choice source-choice {
            leaf internal {
              type empty;
            }
            leaf line {
              type empty;
            }
            leaf recovered {
              type union {
                type uint8;
                type enumeration {
                  enum acr;
                  enum dcr;
                }
              }
            }
          }
        }
      }
      leaf shutdown {
        type empty;
      }
      container vlan {
        tailf:cli-compact-syntax;
        tailf:cli-sequence-commands {
          tailf:cli-reset-siblings;
        }
        leaf id {
          tailf:cli-drop-node-name;
          type uint16;
        }
        leaf ecid {
          type uint16;
        }
      }
    }
    list E3 {
      key "name";
      leaf name {
        type string;
      }
      uses description-grouping;
      leaf mode {
        type enumeration {
          enum atm;
          enum e1;
          enum serial;
          enum t1;
        }
      }
      leaf framing {
        type enumeration {
          enum g751;
          enum g832;
        }
      }
      container dsu {
        tailf:cli-add-mode;
        leaf mode {
          type enumeration {
            enum cisco;
            enum digital-link;
            enum kentrox;
          }
        }
        leaf bandwidth {
          type uint16;
        }
      }
      leaf down-when-looped {
        type empty;
      }
      container clock {
        container source {
          choice source-choice {
            leaf internal {
              type empty;
            }
            leaf line {
              type empty;
            }
            leaf recovered {
              type uint8;
            }
          }
        }
      }
      leaf shutdown {
        type empty;
      }
    }
    list SONET {
      tailf:cli-allow-join-with-key;
      key "id";
      leaf id {
        tailf:cli-case-insensitive;
        type string;
      }
      uses description-grouping;
      leaf ais-shut {
        type empty;
      }
      container line {
        tailf:cli-add-mode;
        container delay {
          leaf clear {
            type uint32;
          }
          leaf trigger {
            type uint16;
          }
        }
      }
      container path {
        tailf:cli-add-mode;
        container report {
          leaf pais {
            type empty;
          }
          leaf prdi {
            type empty;
          }
        }
        leaf ais-shut {
          type empty;
        }
        container delay {
          leaf clear {
            type uint32;
          }
          leaf trigger {
            type uint16;
          }
        }
        container overhead {
          leaf c2 {
            type string;
          }
        }
        leaf scrambling {
          type enumeration {
            enum disable;
            enum enable;
          }
        }
        container threshold {
          leaf b3-tca {
            type uint8;
          }
        }
      }
      leaf framing {
        type enumeration {
          enum sdh;
          enum sonet;
        }
      }
      container report {
        leaf lais {
          type empty;
        }
        leaf lrdi {
          type empty;
        }
        leaf sd-ber {
          type empty;
        }
      }
      container overhead {
        leaf j0 {
          type uint8;
        }
        leaf s1s0 {
          type uint8;
        }
      }
      list sts {
        key "id";
        leaf id {
          type uint32;
        }
        leaf width {
          type uint16;
        }
        container mode {
          tailf:cli-compact-syntax;
          tailf:cli-sequence-commands {
            tailf:cli-reset-siblings;
          }
          leaf carrying {
            tailf:cli-drop-node-name;
            type enumeration {
              enum atm;
              enum pos;
              enum t3;
              enum vt15;
              enum vt15-t1;
              enum vt2;
            }
          }
          leaf pos-option {
            tailf:cli-drop-node-name;
            type enumeration {
              enum scramble;
              enum unscramble;
            }
          }
        }
        container delay {
          leaf trigger {
            type uint16;
          }
        }
        container report {
          leaf pais {
            type empty;
          }
          leaf puneq {
            type empty;
          }
        }
      }
      container threshold {
        leaf sf-ber {
          type uint8;
        }
        leaf b1-tca {
          type uint8;
        }
        leaf b2-tca {
          type uint8;
        }
      }
      leaf down-when-looped {
        type empty;
      }
      list au {
        key "id";
        leaf id {
          type uint8;
        }
        leaf width {
          type uint16;
        }
        container mode {
          tailf:cli-compact-syntax;
          tailf:cli-sequence-commands {
            tailf:cli-reset-siblings;
          }
          leaf carrying {
            tailf:cli-drop-node-name;
            type enumeration {
              enum atm;
              enum c11;
              enum c11-t1;
              enum c12;
              enum c12-e1;
              enum e3;
              enum pos;
              enum t3;
              enum tug3;
            }
          }
          leaf pos-option {
            tailf:cli-drop-node-name;
            type enumeration {
              enum scramble;
              enum unscramble;
            }
          }
        }
        list tug3 {
          key "id";
          leaf id {
            type uint8;
          }
          container mode {
            tailf:cli-compact-syntax;
            tailf:cli-sequence-commands {
              tailf:cli-reset-siblings;
            }
            leaf carrying {
              tailf:cli-drop-node-name;
              type enumeration {
                enum c11;
                enum c11-t1;
                enum c12;
                enum c12-e1;
                enum e3;
                enum t3;
              }
            }
          }
        }
      }
      container clock {
        leaf source {
          type enumeration {
            enum internal;
            enum line;
          }
        }
      }
      container s1byte {
        leaf ignore {
          type empty;
        }
      }
      leaf shutdown {
        type empty;
      }
    }
    list wanphy {
      tailf:cli-allow-join-with-key;
      key "id";
      leaf id {
        type string;
      }
      container lanmode {
        leaf on {
          type empty;
        }
      }
      container wanmode {
        leaf on {
          type empty;
        }
      }
    }
    list Optics {
      tailf:cli-allow-join-with-key;
      key "id";
      leaf id {
        type string;
      }
      uses description-grouping;
      leaf shutdown {
        type empty;
      }
      leaf transmit-power {
        type int16;
      }
      leaf fec {
        type enumeration {
          enum CFEC;
          enum EnhancedHG15;
          enum EnhancedHG15DE;
          enum EnhancedHG20;
          enum EnhancedHG25;
          enum EnhancedHG25DE;
          enum EnhancedHG7;
          enum EnhancedI4;
          enum EnhancedI7;
          enum EnhancedSD15;
          enum EnhancedSD15DE;
          enum EnhancedSD20;
          enum EnhancedSD27;
          enum EnhancedSD7;
          enum EnhancedStaircaseDE;
          enum EnhancedSwizzle;
          enum None;
          enum OFEC;
          enum Standard;
        }
      }
      container mode {
        leaf etm {
          type empty;
        }
      }
      leaf modulation {
        type enumeration {
          enum 16Qam;
          enum 16Qam-32Qam;
          enum 32Qam;
          enum 32Qam-64Qam;
          enum 64Qam;
          enum 8Qam;
          enum 8Qam-16Qam;
          enum Bpsk;
          enum Bpsk-Qpsk;
          enum Qpsk;
          enum Qpsk-8Qam;
        }
      }
      container dwdm-carrier {
        tailf:cli-compact-syntax;
        tailf:cli-sequence-commands {
          tailf:cli-reset-siblings;
        }
        leaf grid {
          tailf:cli-drop-node-name;
          type enumeration {
            enum 50GHz-grid;
            enum 100MHz-grid;
          }
        }
        choice config-choice {
          leaf frequency {
            tailf:cli-break-sequence-commands;
            type uint32;
          }
          leaf itu-ch {
            type uint8;
          }
          leaf wavelength {
            type uint32;
          }
        }
      }
      leaf breakout {
        type string;
      }
      list breakout-mode {
        tailf:cli-suppress-mode;
        tailf:cli-delete-when-empty;
        tailf:cli-compact-syntax;
        tailf:cli-sequence-commands {
          tailf:cli-reset-siblings;
        }
        key "id";
        leaf id {
          type uint8;
        }
        leaf type {
          tailf:cli-drop-node-name;
          type enumeration {
            enum Ethernet;
            enum FC;
            enum Otn;
            enum SDH;
            enum Sonet;
          }
        }
        leaf framing {
          type string;
        }
        leaf mapping {
          type enumeration {
            enum GfpF;
            enum GfpF-Ext;
            enum wis;
          }
        }
        leaf rate {
          type enumeration {
            enum OC192;
            enum STM64;
          }
        }
      }
      container port-mode {
        tailf:cli-compact-syntax;
        tailf:cli-sequence-commands {
          tailf:cli-reset-siblings;
        }
        choice port-mode-choice {
          case type-case {
            leaf type {
              tailf:cli-drop-node-name;
              type enumeration {
                enum Ethernet;
                enum FC;
                enum Otn;
                enum SDH;
                enum Sonet;
              }
            }
            leaf framing {
              type string;
            }
            leaf rate {
              tailf:cli-optional-in-sequence;
              type string;
            }
            leaf mapping {
              type string;
            }
          }
          case speed-case {
            container speed {
              tailf:cli-compact-syntax;
              tailf:cli-sequence-commands {
                tailf:cli-reset-siblings;
              }
              leaf speed {
                tailf:cli-drop-node-name;
                type enumeration {
                  enum 100G;
                  enum 150G;
                  enum 200G;
                }
              }
              leaf mod {
                type enumeration {
                  enum 16qam;
                  enum 8qam;
                  enum qpsk;
                }
              }
              leaf fec {
                type enumeration {
                  enum 15sdfec;
                  enum 15sdfecde;
                  enum 25sdfec;
                  enum otu7staircase;
                }
              }
              leaf diff {
                type enumeration {
                  enum disable;
                  enum enable;
                }
              }
            }
          }
        }
      }
      leaf speed {
        type enumeration {
          enum none;
          enum 1g;
          enum 10g;
          enum 25g;
          enum 40g;
          enum 50g;
          enum 100g;
          enum 200g;
          enum 300g;
          enum 400g;
        }
      }
      container speed-n-mode {
        tailf:cli-drop-node-name;
        leaf speed {
          type enumeration {
            enum 1x40;
            enum 1x100;
            enum 2x50;
            enum 2x100;
            enum 3x100;
            enum 4x10;
            enum 4x25;
            enum 4x100;
            enum 8x50;
          }
        }
      }
      leaf DAC-Rate {
        type enumeration {
          enum 1x1;
          enum 1x1.25;
          enum 1x1.50;
          enum 1x1.75;
          enum 1x2;
        }
      }
      leaf cd-max {
        type int32;
      }
      leaf cd-min {
        type int32;
      }
      leaf rx-low-threshold {
        type int16;
      }
      leaf perf-mon {
        type enumeration {
          enum disable;
          enum enable;
        }
      }
      list app-sel-code {
        tailf:cli-sequence-commands {
          tailf:cli-reset-siblings;
        }
        leaf mode-type {
          tailf:cli-drop-node-name;
          tailf:cli-prefix-key;
          type enumeration {
            enum mixed;
            enum simple;
          }
        }
        key "instance";
        leaf instance {
          type uint8;
        }
        leaf app-sel-code-id {
          tailf:cli-break-sequence-commands;
          type uint32;
        }
        leaf host-lane-count {
          type uint32;
        }
        leaf host-start-lane {
          type uint32;
        }
        leaf media-lane-count {
          type uint32;
        }
        leaf media-start-lane {
          type uint32;
        }
      }
    }
    list CoherentDSP {
      tailf:cli-allow-join-with-key;
      key "id";
      leaf id {
        type string;
      }
      uses description-grouping;
      leaf shutdown {
        type empty;
      }
      leaf perf-mon {
        type enumeration {
          enum disable;
          enum enable;
        }
      }
    }
    container pse {
      container tcam {
        list location {
          key "name";
          leaf name {
            type string;
          }
          container compression {
            container ipv6 {
              leaf anchor-prefix {
                tailf:cli-multi-value;
                type string;
              }
            }
          }
        }
      }
    }
    list OTU {
      tailf:cli-allow-join-with-key;
      key "id";
      leaf id {
        tailf:cli-suppress-range;
        type string;
      }
      uses controller-oxu-grouping;
    }
    list ODU {
      tailf:cli-allow-join-with-key;
      key "id";
      leaf id {
        tailf:cli-suppress-range;
        type string;
      }
      uses controller-oxu-grouping;
    }
    list STM {
      tailf:cli-allow-join-with-key;
      key "id";
      leaf id {
        tailf:cli-suppress-range;
        type string;
      }
      uses controller-stm-grouping;
    }
  }

  grouping controller-oxu-grouping {
    uses description-grouping;
    leaf secondary-admin-state {
      type enumeration {
        enum maintenance;
        enum normal;
      }
    }
    leaf gcc0 {
      type empty;
    }
    leaf perf-mon {
      type enumeration {
        enum disable;
        enum enable;
      }
    }
    container terminate {
      container ether {
        leaf mapping {
          type enumeration {
            enum GfpF;
            enum gmp;
          }
        }
      }
    }
  }

  grouping controller-stm-grouping {
    container overhead {
      container j0 {
        container send {
          uses ctrl-stm-overhead-j0-id-grouping;
        }
        container expected {
          uses ctrl-stm-overhead-j0-id-grouping;
        }
      }
    }
    container aug-mapping {
      container au4 {
        list au-4 {
          key "id";
          leaf id {
            type uint8;
          }
          container mode {
            container tug3 {
              tailf:cli-add-mode;
              presence "true";
              list tug-3 {
                key "id";
                leaf id {
                  type uint8;
                }
                container mode {
                  container tug2 {
                    tailf:cli-add-mode;
                    presence "true";
                    list tug-2 {
                      key "id";
                      leaf id {
                        type uint8;
                      }
                      leaf payload {
                        tailf:cli-hide-in-submode;
                        type enumeration {
                          enum vc12;
                        }
                      }
                      list vc12 {
                        tailf:cli-suppress-mode;
                        tailf:cli-delete-when-empty;
                        key "id";
                        leaf id {
                          type uint8;
                        }
                        leaf mapping {
                          tailf:cli-hide-in-submode;
                          type enumeration {
                            enum e1;
                          }
                        }
                      }
                    }
                  }
                }
              }
            }
          }
        }
      }
    }
    leaf propagate-tdm-alarm {
      type empty;
    }
    leaf loopback {
      type enumeration {
        enum internal;
        enum line;
      }
    }
    container clock {
      leaf source {
        type enumeration {
          enum internal;
          enum line;
        }
      }
    }
    container sec-admin-state {
      leaf maintenance {
        type empty;
      }
    }
  }

  grouping ctrl-stm-overhead-j0-id-grouping {
    choice id-choice {
      leaf oneByte {
        tailf:alt-name "1Byte";
        type uint8;
      }
      leaf sixteenBytes {
        tailf:alt-name "16Bytes";
        type string;
      }
      leaf sixtyfourBytes {
        tailf:alt-name "64Bytes";
        type string;
      }
    }
  }

  grouping set-list-grouping {
    list set {
      tailf:cli-drop-node-name;
      tailf:cli-suppress-mode;
      tailf:cli-delete-when-empty;
      ordered-by user;
      key "value";
      leaf value {
        tailf:cli-multi-word-key;
        type string;
      }
    }
  }

  grouping ipsla-reaction-operation-react-grouping {
    container action {
      leaf logging {
        type empty;
      }
      leaf trigger {
        type empty;
      }
    }
    container threshold {
      container type {
        choice type-choice {
          leaf immediate {
            type empty;
          }
          leaf consecutive {
            type uint8;
          }
          leaf average {
            type uint8;
          }
        }
      }
      container limit {
        tailf:cli-drop-node-name;
        tailf:cli-compact-syntax;
        tailf:cli-sequence-commands {
          tailf:cli-reset-siblings;
        }
        leaf lower-limit {
          type uint32;
        }
        leaf upper-limit {
          type uint32;
        }
      }
    }
  }

  grouping interface-tunnel-te-auto-bw-threshold-grouping {
    container threshold {
      tailf:cli-compact-syntax;
      tailf:cli-sequence-commands {
        tailf:cli-reset-siblings;
      }
      leaf percentage {
        tailf:cli-drop-node-name;
        type uint8;
      }
      leaf min {
        tailf:cli-optional-in-sequence;
        type uint32;
      }
      leaf limit {
        type uint8;
      }
    }
  }

  grouping interface-monitor-session-grouping {
    list monitor-session {
      key "name";
      leaf name {
        type string;
      }
      leaf ethernet {
        tailf:cli-hide-in-submode;
        type empty;
      }
      leaf ipv4 {
        tailf:cli-hide-in-submode;
        type empty;
      }
      leaf direction {
        tailf:cli-hide-in-submode;
        type enumeration {
          enum rx-only;
          enum tx-only;
        }
      }
      leaf port-level {
        tailf:cli-hide-in-submode;
        type empty;
      }
      leaf acl {
        type empty;
      }
      container mirror {
        leaf first {
          type uint16;
        }
      }
    }
  }

  grouping router-ospf-domain-id-grouping {
    leaf type {
      type enumeration {
        enum 0005;
        enum 0105;
        enum 0205;
        enum 8005;
      }
    }
    leaf value {
      type string;
    }
  }

  grouping explicit-path-index-list-grouping {
    list index {
      tailf:cli-suppress-mode;
      tailf:cli-delete-when-empty;
      tailf:cli-compact-syntax;
      tailf:cli-sequence-commands {
        tailf:cli-reset-all-siblings;
      }
      key "index-id";
      leaf index-id {
        type uint16;
      }
      leaf keyword {
        tailf:cli-drop-node-name;
        type enumeration {
          enum exclude-address;
          enum exclude-srlg;
          enum next-address;
          enum next-label;
        }
      }
      leaf hop-type {
        tailf:cli-optional-in-sequence;
        tailf:cli-drop-node-name;
        type enumeration {
          enum loose;
          enum strict;
        }
      }
      leaf label {
        tailf:cli-optional-in-sequence;
        tailf:cli-drop-node-name;
        type uint32;
      }
      container ipv4 {
        tailf:cli-flatten-container;
        tailf:cli-compact-syntax;
        tailf:cli-sequence-commands {
          tailf:cli-reset-siblings;
        }
        leaf unicast {
          type union {
            type inet:ipv4-address;
            type enumeration {
              enum unnumbered;
            }
          }
        }
        leaf router-id {
          tailf:cli-drop-node-name;
          type inet:ipv4-address;
        }
        leaf ifindex {
          tailf:cli-drop-node-name;
          type uint32;
        }
      }
    }
  }

  grouping route-target-import-export-grouping {
    container route-target {
      list route-target-list {
        tailf:cli-drop-node-name;
        tailf:cli-suppress-mode;
        tailf:cli-delete-when-empty;
        key "name";
        leaf name {
          type string;
        }
      }
      leaf-list import {
        type string;
      }
      leaf-list export {
        type string;
      }
    }
  }

  grouping username-grouping {
    list username {
      key "name";
      leaf name {
        type string;
      }
      list group {
        tailf:cli-suppress-mode;
        tailf:cli-delete-when-empty;
        key "name";
        leaf name {
          type string;
        }
      }
      leaf policy {
        type string;
      }
      container secret {
        tailf:cli-compact-syntax;
        tailf:cli-sequence-commands;
        leaf encryption {
          tailf:cli-drop-node-name;
          type enumeration {
            enum 0;
            enum 5;
            enum 8;
            enum 9;
            enum 10;
          }
        }
        leaf password {
          tailf:cli-drop-node-name;
          type string;
        }
      }
      container password {
        tailf:cli-compact-syntax;
        tailf:cli-sequence-commands;
        leaf encryption {
          tailf:cli-drop-node-name;
          type enumeration {
            enum 0;
            enum 7;
          }
        }
        leaf password {
          tailf:cli-drop-node-name;
          type string;
        }
      }
      container password-policy {
        tailf:cli-compact-syntax;
        tailf:cli-sequence-commands;
        leaf policy-name {
          tailf:cli-drop-node-name;
          type string;
        }
        container password {
          tailf:cli-compact-syntax;
          tailf:cli-sequence-commands;
          tailf:cli-flatten-container;
          leaf encryption {
            tailf:cli-drop-node-name;
            type enumeration {
              enum 0;
              enum 7;
            }
          }
          leaf password {
            tailf:cli-drop-node-name;
            type string;
          }
        }
      }
      leaf login-history {
        type enumeration {
          enum disable;
          enum enable;
        }
      }
    }
  }

  grouping clock-grouping {
    container clock {
      leaf calendar-valid {
        type empty;
      }
      container summer-time {
        tailf:cli-compact-syntax;
        tailf:cli-sequence-commands {
          tailf:cli-reset-siblings;
        }
        leaf zone {
          tailf:cli-drop-node-name;
          type string;
        }
        choice summer {
          case a {
            container date;
          }
          case b {
            leaf recurring {
              type empty;
            }
            leaf start {
              tailf:cli-drop-node-name;
              type union {
                type uint8;
                type enumeration {
                  enum first;
                  enum last;
                }
              }
            }
            leaf start-day {
              tailf:cli-drop-node-name;
              type enumeration {
                enum monday;
                enum tuesday;
                enum wednesday;
                enum thursday;
                enum friday;
                enum saturday;
                enum sunday;
              }
            }
            leaf start-month {
              tailf:cli-drop-node-name;
              type month-type;
            }
            leaf start-time {
              tailf:cli-drop-node-name;
              type string;
            }
            leaf end {
              tailf:cli-drop-node-name;
              type union {
                type uint8;
                type enumeration {
                  enum first;
                  enum last;
                }
              }
            }
            leaf end-day {
              tailf:cli-drop-node-name;
              type enumeration {
                enum monday;
                enum tuesday;
                enum wednesday;
                enum thursday;
                enum friday;
                enum saturday;
                enum sunday;
              }
            }
            leaf end-month {
              tailf:cli-drop-node-name;
              type month-type;
            }
            leaf end-time {
              tailf:cli-drop-node-name;
              type string;
            }
            leaf end-offset {
              tailf:cli-drop-node-name;
              type uint16;
            }
          }
        }
      }
      container timezone {
        tailf:cli-compact-syntax;
        tailf:cli-sequence-commands {
          tailf:cli-reset-siblings;
        }
        leaf zone {
          tailf:cli-drop-node-name;
          type string;
        }
        choice timezone-choice {
          leaf region {
            tailf:cli-drop-node-name;
            type string;
          }
          case offset {
            leaf hours-offset {
              tailf:cli-drop-node-name;
              type int8;
            }
            leaf minutes-offset {
              tailf:cli-drop-node-name;
              type int8;
            }
          }
        }
      }
    }
  }

  grouping exception-grouping {
    container exception {
      list choice {
        tailf:cli-suppress-mode;
        tailf:cli-delete-when-empty;
        tailf:cli-compact-syntax;
        key "order";
        leaf order {
          type uint8;
        }
        leaf compress {
          type enumeration {
            enum off;
            enum on;
          }
        }
        container filename {
          tailf:cli-flatten-container;
          tailf:cli-compact-syntax;
          leaf name {
            tailf:cli-drop-node-name;
            type string;
          }
          leaf limit {
            tailf:cli-drop-node-name;
            type string;
          }
        }
        leaf filepath {
          type string;
        }
      }
      leaf sparse {
        type enumeration {
          enum off;
          enum on;
        }
      }
      leaf sprsize {
        type uint16;
      }
      leaf coresize {
        type uint32;
      }
      leaf pakmem {
        type enumeration {
          enum off;
          enum on;
        }
      }
    }
  }

  grouping average-cpu-used-grouping {
    leaf op {
      tailf:cli-drop-node-name;
      type operator-type;
    }
    leaf threshold {
      tailf:cli-drop-node-name;
      type uint8;
    }
    leaf percent {
      tailf:cli-optional-in-sequence;
      type empty;
    }
    container rearm {
      tailf:cli-flatten-container;
      tailf:cli-compact-syntax;
      choice rearm-choice {
        leaf toggle {
          type empty;
        }
        leaf window {
          type uint8;
        }
      }
    }
  }

  grouping evpn-timers-grouping {
    container timers {
      tailf:cli-add-mode;
      tailf:cli-delete-when-empty;
      presence "true";
      leaf peering {
        type uint16;
      }
      leaf recovery {
        type uint16;
      }
    }
  }

  grouping evpn-virtual-grouping {
    container ethernet-segment {
      tailf:cli-add-mode;
      container identifier {
        tailf:cli-compact-syntax;
        tailf:cli-sequence-commands {
          tailf:cli-reset-siblings;
        }
        leaf type {
          type uint8;
        }
        leaf esi-value {
          tailf:cli-drop-node-name;
          type string;
        }
      }
      container bgp {
        leaf route-target {
          type string;
        }
      }
    }
    uses evpn-timers-grouping;
  }

  grouping evpn-bgp-grouping {
    leaf rd {
      type string;
    }
    container route-target {
      list route-target-list {
        tailf:cli-drop-node-name;
        tailf:cli-suppress-mode;
        tailf:cli-delete-when-empty;
        key "name";
        leaf name {
          type string;
        }
      }
      list import {
        tailf:cli-suppress-mode;
        tailf:cli-delete-when-empty;
        key "name";
        leaf name {
          type string;
        }
        leaf stitching {
          type empty;
        }
      }
      list export {
        tailf:cli-suppress-mode;
        tailf:cli-delete-when-empty;
        key "name";
        leaf name {
          type string;
        }
        leaf stitching {
          type empty;
        }
      }
    }
  }

  grouping pppoe-bba-group-grouping {
    leaf mtu {
      type uint16;
    }
    container ac {
      leaf name {
        type string;
      }
    }
    container tag {
      container ppp-max-payload {
        container minimum {
          tailf:cli-compact-syntax;
          tailf:cli-sequence-commands;
          leaf value {
            tailf:cli-drop-node-name;
            type uint16;
          }
          leaf maximum {
            type uint16;
          }
        }
      }
    }
    container pado {
      container delay {
        leaf delay {
          tailf:cli-drop-node-name;
          type uint16;
        }
        container service-name {
          list string {
            tailf:cli-suppress-mode;
            tailf:cli-delete-when-empty;
            key "name";
            leaf name {
              type string;
            }
            leaf delay {
              tailf:cli-drop-node-name;
              type uint16;
            }
          }
        }
      }
    }
    container service {
      container selection {
        leaf disable {
          type empty;
        }
      }
    }
    container sessions {
      container mac {
        uses pppoe-bba-group-sessions-grouping;
      }
      container vlan {
        uses pppoe-bba-group-sessions-grouping;
      }
      container inner-vlan {
        uses pppoe-bba-group-sessions-grouping;
      }
      container outer-vlan {
        uses pppoe-bba-group-sessions-grouping;
      }
      container max {
        container limit {
          tailf:cli-compact-syntax;
          tailf:cli-sequence-commands {
            tailf:cli-reset-siblings;
          }
          leaf value {
            tailf:cli-drop-node-name;
            type uint16;
          }
          leaf threshold {
            type uint16;
          }
        }
      }
      container circuit-id {
        uses pppoe-bba-group-sessions-grouping;
      }
      container circuit-id-and-remote-id {
        uses pppoe-bba-group-sessions-grouping;
      }
    }
    container control-packets {
      leaf priority {
        type uint8;
      }
    }
    leaf invalid-session-id {
      type enumeration {
        enum drop;
        enum log;
      }
    }
  }

  grouping pppoe-bba-group-sessions-grouping {
    container limit {
      tailf:cli-compact-syntax;
      tailf:cli-sequence-commands {
        tailf:cli-reset-siblings;
      }
      leaf value {
        tailf:cli-drop-node-name;
        type uint16;
      }
      leaf threshold {
        type uint16;
      }
    }
    container throttle {
      tailf:cli-compact-syntax;
      tailf:cli-sequence-commands {
        tailf:cli-reset-siblings;
      }
      leaf limit {
        tailf:cli-drop-node-name;
        type uint16;
      }
      leaf request-period {
        tailf:cli-drop-node-name;
        type uint8;
      }
      leaf block-period {
        tailf:cli-drop-node-name;
        type uint8;
      }
    }
  }

  grouping router-eigrp-if-grouping;

  grouping router-eigrp-af-grouping {
    container passive-interface {
      leaf default {
        type empty;
      }
    }
    container stub {
      tailf:cli-compact-syntax;
      tailf:cli-delete-when-empty;
      presence "true";
      leaf connected {
        type empty;
      }
      leaf redistributed {
        type empty;
      }
      leaf static {
        type empty;
      }
      leaf summary {
        type empty;
      }
    }
    container timers {
      container nsf {
        leaf route-hold {
          type uint16;
        }
      }
    }
    container distance {
      tailf:cli-compact-syntax;
      tailf:cli-sequence-commands;
      leaf internal {
        tailf:cli-drop-node-name;
        type uint8;
      }
      leaf external {
        tailf:cli-drop-node-name;
        type uint8;
      }
    }
    leaf maximum-paths {
      type uint8;
    }
    leaf router-id {
      type inet:ipv4-address;
    }
    uses route-policy-list-grouping;
    container metric {
      leaf maximum-hops {
        type uint8;
      }
      container weights {
        tailf:cli-compact-syntax;
        tailf:cli-sequence-commands {
          tailf:cli-reset-siblings;
        }
        leaf tos {
          tailf:cli-drop-node-name;
          type uint8;
        }
        leaf k1 {
          tailf:cli-drop-node-name;
          type uint8;
        }
        leaf k2 {
          tailf:cli-drop-node-name;
          type uint8;
        }
        leaf k3 {
          tailf:cli-drop-node-name;
          type uint8;
        }
        leaf k4 {
          tailf:cli-drop-node-name;
          type uint8;
        }
        leaf k5 {
          tailf:cli-drop-node-name;
          type uint8;
        }
      }
      leaf version {
        type enumeration {
          enum 32bit;
        }
      }
    }
    container default-metric {
      tailf:cli-compact-syntax;
      tailf:cli-sequence-commands;
      leaf bandwidth {
        tailf:cli-drop-node-name;
        type uint32;
      }
      leaf delay {
        tailf:cli-drop-node-name;
        type uint32;
      }
      leaf reliability {
        tailf:cli-drop-node-name;
        type uint8;
      }
      leaf loading {
        tailf:cli-drop-node-name;
        type uint8;
      }
      leaf mtu {
        tailf:cli-drop-node-name;
        type uint16;
      }
    }
    leaf log-neighbor-changes {
      type empty;
    }
    leaf log-neighbor-warnings {
      type empty;
    }
    leaf autonomous-system {
      type uint16;
    }
    container redistribute {
      list protocol-list {
        tailf:cli-drop-node-name;
        tailf:cli-suppress-mode;
        tailf:cli-delete-when-empty;
        key "protocol id";
        leaf protocol {
          type enumeration {
            enum bgp;
            enum isis;
            enum ospf;
            enum eigrp;
          }
        }
        leaf id {
          type string;
        }
        leaf route-policy {
          type string;
        }
      }
      list name-list {
        tailf:cli-drop-node-name;
        tailf:cli-suppress-mode;
        tailf:cli-delete-when-empty;
        key "name";
        leaf name {
          type enumeration {
            enum connected;
            enum rip;
            enum static;
            enum subscriber;
          }
        }
        leaf route-policy {
          type string;
        }
      }
    }
    list interface {
      key "name";
      leaf name {
        type ifname;
      }
      container authentication {
        leaf keychain {
          type string;
        }
      }
      container metric {
        tailf:cli-compact-syntax;
        leaf bandwidth {
          type uint32;
        }
        leaf delay {
          type uint32;
        }
        leaf picoseconds {
          type empty;
        }
        leaf reliability {
          type uint8;
        }
        leaf load {
          type uint8;
        }
      }
      leaf hello-interval {
        type uint16;
      }
      leaf hold-time {
        type uint16;
      }
      list neighbor {
        tailf:cli-suppress-mode;
        tailf:cli-delete-when-empty;
        key "address";
        leaf address {
          type inet:ipv4-address;
        }
        leaf remote {
          type uint8;
        }
      }
      list summary-address {
        tailf:cli-suppress-mode;
        tailf:cli-delete-when-empty;
        key "prefix";
        leaf prefix {
          type union {
            type ipv4-prefix;
            type tailf:ipv6-address-and-prefix-length;
          }
        }
        leaf admin-distance {
          tailf:cli-drop-node-name;
          type uint8;
        }
      }
      leaf bandwidth-percent {
        type uint32;
      }
      container passive-interface {
        tailf:cli-delete-when-empty;
        presence "true";
        leaf disable {
          type empty;
        }
      }
      uses route-policy-list-grouping;
      leaf site-of-origin {
        type asn-ip-type;
      }
    }
  }

  grouping router-eigrp-grouping {
    container address-family {
      container ipv4 {
        tailf:cli-add-mode;
        presence "true";
        uses router-eigrp-af-grouping;
      }
      container ipv6 {
        tailf:cli-add-mode;
        presence "true";
        uses router-eigrp-af-grouping;
      }
    }
  }

  grouping router-msdp-grouping {
    container connect-source {
      uses interface-name-grouping;
    }
    leaf originator-id {
      type ifname;
    }
    container cache-sa-state {
      leaf rp-list {
        type string;
      }
      leaf list {
        type string;
      }
    }
    leaf cache-sa-holdtime {
      type uint16;
    }
    list peer {
      key "address";
      leaf address {
        type inet:host;
      }
      leaf connect-source {
        type ifname;
      }
      uses description-grouping;
      leaf mesh-group {
        type string;
      }
      list sa-filter {
        tailf:cli-suppress-mode;
        tailf:cli-delete-when-empty;
        key "direction";
        leaf direction {
          type enumeration {
            enum in;
            enum out;
          }
        }
        leaf list {
          type string;
        }
        leaf rp-list {
          type string;
        }
      }
      container maximum {
        leaf external-sa {
          type uint32;
        }
      }
      container keepalive {
        tailf:cli-compact-syntax;
        tailf:cli-sequence-commands {
          tailf:cli-reset-siblings;
        }
        leaf keepalive-period {
          tailf:cli-drop-node-name;
          type uint8;
        }
        leaf peer-timeout {
          tailf:cli-drop-node-name;
          type uint8;
        }
      }
      container password {
        tailf:cli-compact-syntax;
        tailf:cli-sequence-commands {
          tailf:cli-reset-siblings;
        }
        leaf enc-type {
          tailf:cli-drop-node-name;
          type enumeration {
            enum clear;
            enum encrypted;
          }
        }
        leaf password {
          tailf:cli-drop-node-name;
          tailf:cli-multi-value;
          type string;
        }
      }
      leaf remote-as {
        type union {
          type uint32;
          type string;
        }
      }
    }
    container sa-filter {
      container in {
        uses sa-filter-access-list-grouping;
      }
      container out {
        uses sa-filter-access-list-grouping;
      }
    }
  }

  grouping sa-filter-access-list-grouping {
    leaf list {
      type string;
    }
    leaf rp-list {
      type string;
    }
  }

  grouping route-policy-list-grouping {
    list route-policy {
      tailf:cli-suppress-mode;
      tailf:cli-delete-when-empty;
      tailf:cli-compact-syntax;
      tailf:cli-sequence-commands;
      key "direction";
      leaf direction {
        type enumeration {
          enum in;
          enum out;
        }
      }
      leaf name {
        tailf:cli-drop-node-name;
        tailf:cli-prefix-key;
        type string;
      }
    }
  }

  grouping telemetry-policy-driven-encoder-grouping {
    container policy {
      list group {
        key "name";
        leaf name {
          type string;
        }
        list policy {
          tailf:cli-suppress-mode;
          tailf:cli-delete-when-empty;
          key "name";
          leaf name {
            type string;
          }
        }
        container source {
          container interface {
            uses interface-name-grouping;
          }
        }
        container transport {
          container tcp {
            tailf:cli-add-mode;
            presence "true";
            container encoding-format {
              leaf gpb-compact {
                type empty;
              }
            }
          }
        }
        container destination {
          list ipv4 {
            tailf:cli-suppress-mode;
            tailf:cli-delete-when-empty;
            key "address port";
            leaf address {
              type inet:ipv4-address;
            }
            leaf port {
              type uint16;
            }
          }
          list ipv6 {
            tailf:cli-suppress-mode;
            tailf:cli-delete-when-empty;
            key "address port";
            leaf address {
              type inet:ipv6-address;
            }
            leaf port {
              type uint16;
            }
          }
        }
      }
    }
  }

  grouping telemetry-model-driven-dest-addr-grouping {
    leaf encoding {
      type enumeration {
        enum gpb;
        enum self-describing-gpb;
        enum json;
      }
    }
    container protocol {
      choice protocol-choice {
        container udp {
          tailf:cli-delete-when-empty;
          presence "true";
          leaf packetsize {
            type uint16;
          }
        }
        container tcp {
          presence "true";
        }
        container grpc {
          tailf:cli-compact-syntax;
          tailf:cli-delete-when-empty;
          presence "true";
          leaf no-tls {
            type empty;
          }
          leaf tls-hostname {
            type string;
          }
        }
      }
    }
  }

  grouping affinity-grouping {
    container affinity {
      container affinity-value {
        tailf:cli-drop-node-name;
        tailf:cli-compact-syntax;
        tailf:cli-sequence-commands;
        leaf value {
          tailf:cli-drop-node-name;
          type string;
        }
        leaf mask {
          type string;
        }
      }
      list include {
        tailf:cli-suppress-mode;
        tailf:cli-delete-when-empty;
        key "name";
        leaf name {
          tailf:cli-multi-word-key;
          type string;
        }
      }
      list include-strict {
        tailf:cli-suppress-mode;
        tailf:cli-delete-when-empty;
        key "name";
        leaf name {
          tailf:cli-multi-word-key;
          type string;
        }
      }
      list exclude {
        tailf:cli-suppress-mode;
        tailf:cli-delete-when-empty;
        key "name";
        leaf name {
          tailf:cli-multi-word-key;
          type string;
        }
      }
      leaf ignore {
        type empty;
      }
    }
  }

  grouping hw-module-location-list-grouping {
    list location-list {
      tailf:cli-drop-node-name;
      tailf:cli-suppress-mode;
      tailf:cli-delete-when-empty;
      key "id";
      leaf id {
        type string;
      }
      leaf port-mode {
        type string;
      }
      container qos-mode {
        leaf lowburst-enabled {
          type empty;
        }
      }
      list tcp-mss-adjust {
        tailf:cli-suppress-mode;
        tailf:cli-delete-when-empty;
        key "np";
        leaf np {
          type uint8;
        }
        leaf value {
          type uint16;
        }
      }
      container early-fast-discard {
        tailf:cli-add-mode;
        presence "true";
        container high-priority-list {
          leaf-list mpls-exp {
            tailf:cli-flat-list-syntax;
            type uint8;
          }
        }
      }
    }
    list location-bay-breakout-list {
      tailf:cli-drop-node-name;
      tailf:cli-suppress-mode;
      tailf:cli-delete-when-empty;
      key "id bay port";
      leaf id {
        type string;
      }
      leaf bay {
        type uint8;
      }
      leaf port {
        type uint8;
      }
      leaf breakout {
        type string;
      }
    }
    list location-breakout-list {
      tailf:cli-drop-node-name;
      tailf:cli-suppress-mode;
      tailf:cli-delete-when-empty;
      key "id port";
      leaf id {
        type string;
      }
      leaf port {
        type uint8;
      }
      leaf breakout {
        type string;
      }
    }
    list location-slice-breakout {
      tailf:cli-drop-node-name;
      tailf:cli-suppress-mode;
      tailf:cli-compact-syntax;
      tailf:cli-delete-when-empty;
      key "name slice";
      leaf name {
        type string;
      }
      leaf slice {
        type uint8;
      }
      leaf breakout {
        type string;
      }
      leaf power-savings {
        type empty;
      }
      leaf config-mode {
        type string;
      }
    }
    list location-slice-list {
      tailf:cli-drop-node-name;
      tailf:cli-suppress-mode;
      tailf:cli-delete-when-empty;
      tailf:cli-compact-syntax;
      tailf:cli-sequence-commands {
        tailf:cli-reset-siblings;
      }
      key "name slice";
      leaf name {
        type string;
      }
      leaf slice {
        type uint8;
      }
      container client {
        tailf:cli-flatten-container;
        leaf bitrate {
          type enumeration {
            enum 100G;
            enum 10G;
            enum 40G;
          }
        }
      }
      container trunk {
        tailf:cli-flatten-container;
        leaf bitrate {
          type enumeration {
            enum 100G;
            enum 200G;
            enum 250G;
          }
        }
      }
      leaf fec {
        type enumeration {
          enum SoftDecision7;
          enum SoftDecision20;
        }
      }
      leaf encrypted {
        type empty;
      }
    }
  }

  grouping ipv6-mobile-heartbeat-grouping {
    container heartbeat {
      tailf:cli-compact-syntax;
      tailf:cli-sequence-commands {
        tailf:cli-reset-siblings;
      }
      leaf interval {
        type uint16;
      }
      leaf retries {
        type uint8;
      }
      leaf timeout {
        type uint16;
      }
    }
  }

  grouping ipv6-mobile-mnp-maximum-grouping {
    container logical-mn {
      leaf maximum {
        type uint8;
      }
    }
    container customer {
      leaf maximum {
        type uint32;
      }
    }
  }

  grouping ipv6-mobile-mnp-grouping {
    container mnp {
      container afi-all {
        uses ipv6-mobile-mnp-maximum-grouping;
      }
      container ipv4 {
        uses ipv6-mobile-mnp-maximum-grouping;
      }
      container ipv6 {
        uses ipv6-mobile-mnp-maximum-grouping;
      }
    }
  }

  grouping ssh-server-vrf-grouping {
    list vrf {
      tailf:cli-suppress-mode;
      tailf:cli-delete-when-empty;
      tailf:cli-compact-syntax;
      key "name";
      leaf name {
        type string;
      }
      container ipv4 {
        tailf:cli-flatten-container;
        tailf:cli-compact-syntax;
        leaf access-list {
          type string;
        }
      }
      container ipv6 {
        tailf:cli-flatten-container;
        tailf:cli-compact-syntax;
        leaf access-list {
          type string;
        }
      }
    }
  }

  grouping aaa-radius-attribute-grouping {
    leaf format {
      type string;
    }
    list nas-port-type-list {
      tailf:cli-drop-node-name;
      tailf:cli-suppress-mode;
      tailf:cli-delete-when-empty;
      tailf:cli-compact-syntax;
      tailf:cli-sequence-commands {
        tailf:cli-reset-siblings;
      }
      key "type";
      leaf type {
        type uint8;
      }
      leaf format {
        tailf:cli-prefix-key;
        type string;
      }
    }
  }

  grouping aaa-accounting-grouping {
    leaf notice {
      tailf:cli-drop-node-name;
      type enumeration {
        enum start-stop;
        enum stop-only;
      }
    }
    leaf group {
      tailf:cli-optional-in-sequence;
      type union {
        type string;
        type enumeration {
          enum radius;
          enum tacacs+;
        }
      }
    }
    container group2 {
      tailf:cli-drop-node-name;
      tailf:cli-flatten-container;
      tailf:cli-compact-syntax;
      tailf:cli-optional-in-sequence;
      leaf group {
        type string;
      }
    }
    container group3 {
      tailf:cli-drop-node-name;
      tailf:cli-flatten-container;
      tailf:cli-compact-syntax;
      tailf:cli-optional-in-sequence;
      leaf group {
        type string;
      }
    }
    leaf local {
      tailf:cli-optional-in-sequence;
      type empty;
    }
    leaf none {
      type empty;
    }
  }

  grouping if-l2transport-l2protocol-grouping {
    leaf policy {
      tailf:cli-drop-node-name;
      type enumeration {
        enum drop;
        enum forward;
        enum tunnel;
      }
    }
    leaf experimental {
      type uint8;
    }
  }

  grouping multicast-routing-af-mdt-data-grouping {
    leaf route-policy {
      tailf:cli-break-sequence-commands;
      type string;
    }
    leaf attribute-set {
      type string;
    }
    leaf threshold {
      type uint32;
    }
    leaf acl-name {
      tailf:cli-drop-node-name;
      type string;
    }
    leaf immediate-switch {
      type empty;
    }
    leaf flex-algo {
      type uint8;
    }
  }

  grouping key-duration-grouping {
    leaf start-time {
      tailf:cli-drop-node-name;
      type string;
    }
    leaf start-month {
      tailf:cli-drop-node-name;
      type month-type;
    }
    leaf start-day {
      tailf:cli-drop-node-name;
      type uint8;
    }
    leaf start-year {
      tailf:cli-drop-node-name;
      type uint16;
    }
    choice stop-choice {
      case duration {
        leaf duration {
          type uint32;
        }
      }
      case infinite {
        leaf infinite {
          type empty;
        }
      }
      case stop-time {
        leaf stop-time {
          tailf:cli-drop-node-name;
          type string;
        }
        leaf stop-month {
          tailf:cli-drop-node-name;
          type month-type;
        }
        leaf stop-day {
          tailf:cli-drop-node-name;
          type uint8;
        }
        leaf stop-year {
          tailf:cli-drop-node-name;
          type uint16;
        }
      }
    }
  }

  grouping tpa-af-grouping {
    container default-route {
      leaf mgmt {
        type empty;
      }
    }
    container update-source {
      tailf:cli-compact-syntax;
      tailf:cli-sequence-commands {
        tailf:cli-reset-siblings;
      }
      leaf dataports {
        tailf:cli-optional-in-sequence;
        type empty;
      }
      leaf active-management {
        tailf:cli-optional-in-sequence;
        type empty;
      }
      uses interface-name-grouping;
    }
    container protection {
      tailf:cli-add-mode;
      list allow {
        tailf:cli-suppress-mode;
        tailf:cli-delete-when-empty;
        key "protocol local-port interface local-address remote-address";
        leaf protocol {
          type enumeration {
            enum tcp;
            enum udp;
          }
        }
        leaf local-port {
          type uint16;
        }
        leaf interface {
          type string;
        }
        leaf local-address {
          type union {
            type tailf:ipv4-address-and-prefix-length;
            type tailf:ipv6-address-and-prefix-length;
            type string;
          }
        }
        leaf remote-address {
          type union {
            type tailf:ipv4-address-and-prefix-length;
            type tailf:ipv6-address-and-prefix-length;
            type string;
          }
        }
      }
    }
  }

  grouping call-home-profile-subscribe-to-alert-group-grouping {
    leaf periodic {
      type empty;
    }
    choice frequency-choice {
      leaf daily {
        type empty;
      }
      leaf monthly {
        type uint8;
      }
      leaf weekly {
        type enumeration {
          enum monday;
          enum tuesday;
          enum wednesday;
          enum thursday;
          enum friday;
          enum saturday;
          enum sunday;
        }
      }
    }
    leaf time {
      tailf:cli-drop-node-name;
      type string;
    }
  }

  grouping router-isis-lsp-gen-interval-level-grouping {
    leaf maximum-wait {
      tailf:cli-optional-in-sequence;
      type uint32;
    }
    leaf initial-wait {
      tailf:cli-optional-in-sequence;
      type uint32;
    }
    leaf secondary-wait {
      tailf:cli-optional-in-sequence;
      type uint32;
    }
  }

  grouping rsvp-authentication-grouping {
    container authentication {
      tailf:cli-add-mode;
      container key-source {
        leaf key-chain {
          type string;
        }
      }
      leaf window-size {
        type uint8;
      }
    }
  }

  grouping ethernet-oam-profile-link-monitor-frame-grouping {
    leaf window {
      type uint32;
    }
    container threshold {
      tailf:cli-compact-syntax;
      tailf:cli-sequence-commands {
        tailf:cli-reset-siblings;
      }
      leaf unit {
        tailf:cli-drop-node-name;
        tailf:cli-optional-in-sequence;
        type enumeration {
          enum frames;
          enum ppm;
          enum symbols;
        }
      }
      leaf low {
        tailf:cli-optional-in-sequence;
        type uint32;
      }
      leaf low-unit {
        tailf:cli-drop-node-name;
        tailf:cli-optional-in-sequence;
        type enumeration {
          enum thousand;
          enum million;
          enum billion;
        }
      }
      leaf high {
        type uint32;
      }
      leaf high-unit {
        tailf:cli-drop-node-name;
        type enumeration {
          enum thousand;
          enum million;
          enum billion;
        }
      }
    }
  }

  grouping ptp-profile-grouping {
    container multicast {
      tailf:cli-delete-when-empty;
      presence "true";
      container target-address {
        leaf ethernet {
          type enumeration {
            enum 01-1B-19-00-00-00;
            enum 01-80-C2-00-00-0E;
          }
        }
      }
    }
    leaf transport {
      type enumeration {
        enum ethernet;
        enum ipv4;
        enum ipv6;
      }
    }
    container port {
      leaf state {
        type enumeration {
          enum any;
          enum master-only;
          enum slave-only;
        }
      }
    }
    container sync {
      leaf frequency {
        type enumeration {
          enum 1;
          enum 2;
          enum 4;
          enum 8;
          enum 16;
          enum 32;
          enum 64;
          enum 128;
        }
      }
    }
    container clock {
      leaf operation {
        type enumeration {
          enum one-step;
          enum two-step;
        }
      }
    }
    container announce {
      leaf timeout {
        type uint8;
      }
      leaf frequency {
        type enumeration {
          enum 1;
          enum 2;
          enum 4;
          enum 8;
          enum 16;
          enum 32;
          enum 64;
        }
      }
      leaf grant-duration {
        type uint16;
      }
      leaf interval {
        type enumeration {
          enum 1;
          enum 2;
          enum 4;
          enum 8;
          enum 16;
        }
      }
    }
    container delay-request {
      leaf frequency {
        type enumeration {
          enum 1;
          enum 2;
          enum 4;
          enum 8;
          enum 16;
          enum 32;
          enum 64;
          enum 128;
        }
      }
    }
  }

  grouping max-servers-grouping {
    leaf max-servers {
      type union {
        type uint32;
        type enumeration {
          enum no-limit;
        }
      }
    }
    leaf access-list {
      tailf:cli-drop-node-name;
      type string;
    }
  }

  grouping tcp-small-servers-grouping {
    container tcp-small-servers {
      tailf:cli-sequence-commands {
        tailf:cli-reset-siblings;
      }
      tailf:cli-compact-syntax;
      uses max-servers-grouping;
    }
  }

  grouping udp-small-servers-grouping {
    container udp-small-servers {
      tailf:cli-sequence-commands {
        tailf:cli-reset-siblings;
      }
      tailf:cli-compact-syntax;
      uses max-servers-grouping;
    }
  }

  grouping pce-disjoint-path-group-id-grouping {
    leaf strict {
      type empty;
    }
    list lsp {
      tailf:cli-suppress-mode;
      tailf:cli-delete-when-empty;
      tailf:cli-compact-syntax;
      tailf:cli-sequence-commands {
        tailf:cli-reset-siblings;
      }
      key "id";
      leaf id {
        type enumeration {
          enum 1;
          enum 2;
        }
      }
      container pcc {
        tailf:cli-flatten-container;
        leaf ipv4 {
          type inet:ipv4-address;
        }
      }
      leaf lsp-name {
        type string;
      }
      leaf shortest-path {
        type empty;
      }
    }
  }

  container admin {
    tailf:cli-add-mode;
    uses username-grouping;
    container control-ethernet {
      container crc {
        container threshold {
          leaf sf {
            type uint8;
          }
          leaf sd {
            type uint8;
          }
        }
        leaf switchover {
          type enumeration {
            enum disable;
            enum enable;
          }
        }
      }
    }
    container fpd {
      container auto-upgrade {
        tailf:cli-delete-when-empty;
        presence "true";
        leaf status {
          tailf:cli-drop-node-name;
          type enumeration {
            enum disable {
              tailf:code-name "admin_fpd_disable";
            }
            enum enable {
              tailf:code-name "admin_fpd_enable";
            }
          }
        }
      }
    }
    container logging {
      leaf console {
        type enumeration {
          enum disable {
            value -1;
          }
          enum emergency {
            value 0;
          }
          enum alert {
            value 1;
          }
          enum critical {
            value 2;
          }
          enum error {
            value 3;
          }
          enum warning {
            value 4;
          }
          enum notice {
            value 5;
          }
          enum informational {
            value 6;
          }
          enum debug {
            value 7;
          }
        }
      }
    }
    container fault-manager {
      container datapath {
        container port {
          leaf shutdown {
            type empty;
          }
        }
      }
    }
    container fabric {
      container enable {
        leaf mode {
          type enumeration {
            enum A99-highbandwidth;
            enum highbandwidth;
          }
        }
      }
    }
    container power {
      container budget {
        container reservation {
          container standby-rsp {
            leaf disable {
              type empty;
            }
          }
        }
      }
    }
    container power-mgmt {
      container single-feed-mode {
        leaf enable {
          type empty;
        }
      }
      container redundancy-num-pms {
        leaf value {
          tailf:cli-drop-node-name;
          type uint8;
        }
        list location {
          tailf:cli-suppress-mode;
          tailf:cli-delete-when-empty;
          key "id";
          leaf id {
            type string;
          }
          leaf value {
            tailf:cli-drop-node-name;
            type uint8;
          }
        }
      }
      container progressive {
        list location {
          key "name";
          leaf name {
            type string;
          }
          container priority {
            list location {
              tailf:cli-suppress-mode;
              tailf:cli-delete-when-empty;
              key "name";
              leaf name {
                type string;
              }
              leaf value {
                tailf:cli-drop-node-name;
                type uint16;
              }
            }
          }
        }
      }
    }
    container environment {
      container graceful-shutdown {
        leaf disable {
          type empty;
        }
      }
      list altitude {
        tailf:cli-suppress-mode;
        tailf:cli-delete-when-empty;
        key "rack";
        leaf rack {
          type uint8;
        }
        leaf value {
          tailf:cli-drop-node-name;
          tailf:cli-prefix-key;
          type uint16;
        }
      }
    }
    container hw-module {
      container profile {
        container feature {
          choice feature-choice {
            leaf default {
              type empty;
            }
            leaf l2 {
              type empty;
            }
          }
        }
        leaf scale {
          type enumeration {
            enum bng-max;
            enum default;
            enum l2;
            enum l3;
            enum l3xl;
            enum lsr;
            enum sat;
          }
        }
      }
      container power {
        container disable {
          list location {
            tailf:cli-suppress-mode;
            tailf:cli-delete-when-empty;
            key "name";
            leaf name {
              type string;
            }
          }
        }
        container saving {
          list location {
            tailf:cli-suppress-mode;
            tailf:cli-delete-when-empty;
            key "id";
            leaf id {
              type string;
            }
            leaf slice {
              type uint8;
            }
          }
        }
      }
      container bfd-hw-offload {
        container enable {
          leaf location {
            type string;
          }
        }
      }
      container location {
        uses hw-module-location-list-grouping;
      }
      container shutdown {
        list location {
          tailf:cli-suppress-mode;
          tailf:cli-delete-when-empty;
          key "id";
          leaf id {
            type string;
          }
        }
      }
      container reset {
        container auto {
          container disable {
            list location {
              tailf:cli-suppress-mode;
              tailf:cli-delete-when-empty;
              key "name";
              leaf name {
                type string;
              }
            }
          }
        }
      }
    }
    container license {
      container smart {
        leaf enable {
          type empty;
        }
      }
      list feature {
        tailf:cli-drop-node-name;
        key "name";
        leaf name {
          type string;
        }
        list location {
          tailf:cli-suppress-mode;
          tailf:cli-delete-when-empty;
          key "name";
          leaf name {
            type string;
          }
        }
      }
    }
    container nv {
      tailf:cli-add-mode;
      container edge {
        tailf:cli-add-mode;
        container control {
          tailf:cli-add-mode;
          list serial {
            tailf:cli-suppress-mode;
            tailf:cli-delete-when-empty;
            tailf:cli-compact-syntax;
            tailf:cli-sequence-commands;
            key "rack";
            unique "id";
            leaf id {
              tailf:cli-drop-node-name;
              tailf:cli-prefix-key;
              type string;
            }
            leaf rack {
              type uint8;
            }
          }
          container control-link {
            list disable {
              tailf:cli-suppress-mode;
              tailf:cli-delete-when-empty;
              key "port location";
              leaf port {
                type uint8;
              }
              leaf location {
                type string;
              }
            }
          }
        }
      }
    }
    uses clock-grouping;
    uses exception-grouping;
    container diagnostic {
      container bootup {
        tailf:cli-compact-syntax;
        tailf:cli-sequence-commands;
        leaf level {
          type enumeration {
            enum complete;
            enum minimal;
            enum bypass;
          }
        }
        leaf location {
          type string;
        }
      }
      container monitor {
        leaf syslog {
          type empty;
        }
        container threshold {
          list location {
            key "location";
            leaf location {
              type string;
            }
            list test {
              key "name";
              leaf name {
                type string;
              }
              leaf failure-count {
                type uint8;
              }
            }
          }
        }
      }
      container test-parameters {
        tailf:cli-add-mode;
        container FabricUcastMcastTest {
          tailf:cli-add-mode;
          grouping node-failure-config-grouping {
            container reload {
              leaf threshold {
                type uint8;
              }
            }
            container shutdown {
              leaf threshold {
                type uint8;
              }
            }
          }

          container single-DRP-node-failure {
            tailf:cli-add-mode;
            uses node-failure-config-grouping;
          }
          container single-LC-node-failure {
            tailf:cli-add-mode;
            uses node-failure-config-grouping;
          }
          container single-RP-node-failure {
            tailf:cli-add-mode;
            uses node-failure-config-grouping;
          }
        }
      }
      container schedule {
        list location {
          tailf:cli-suppress-mode;
          tailf:cli-delete-when-empty;
          tailf:cli-compact-syntax;
          key "name";
          leaf name {
            type string;
          }
          leaf test {
            type string;
          }
          leaf daily {
            type string;
          }
          leaf card-type {
            type string;
          }
        }
      }
    }
    container disk_status_config {
      leaf minor {
        type uint8;
      }
      leaf severe {
        type uint8;
      }
      leaf critical {
        type uint8;
      }
    }
    container memory_status_config {
      leaf minor {
        type uint8;
      }
      leaf severe {
        type uint8;
      }
      leaf critical {
        type uint8;
      }
      leaf recovery_enabled {
        type enumeration {
          enum false;
          enum true;
        }
      }
    }
    container aaa {
      container admin-accounting {
        leaf enable {
          type boolean;
        }
      }
      container authentication {
        container users {
          list user {
            key "name";
            leaf name {
              type string;
            }
            leaf uid {
              type uint32;
            }
            leaf gid {
              type int32;
            }
            leaf password {
              type string;
            }
            leaf ssh_keydir {
              type string;
            }
            leaf homedir {
              type string;
            }
          }
        }
        container groups {
          list group {
            key "name";
            leaf name {
              type string;
            }
            leaf gid {
              type int32;
            }
            leaf-list users {
              type string;
            }
          }
        }
        list login {
          tailf:cli-suppress-mode;
          tailf:cli-delete-when-empty;
          key "name";
          leaf name {
            type string;
          }
          leaf methods {
            tailf:cli-drop-node-name;
            tailf:cli-multi-value;
            type string;
          }
        }
      }
      container authorization {
        list cmdrules {
          key "cmdrule";
          leaf cmdrule {
            type uint32;
          }
          leaf context {
            type string;
          }
          leaf command {
            type string;
          }
          leaf group {
            type string;
          }
          leaf ops {
            type string;
          }
          leaf action {
            type enumeration {
              enum reject;
              enum accept;
              enum accept_log;
            }
          }
        }
        list datarules {
          key "datarule";
          leaf datarule {
            type uint32;
          }
          leaf namespace {
            type string;
          }
          leaf context {
            type string;
          }
          leaf keypath {
            type string;
          }
          leaf group {
            type string;
          }
          leaf ops {
            type string;
          }
          leaf action {
            type enumeration {
              enum reject;
              enum accept;
              enum accept_log;
            }
          }
        }
      }
      container disaster-recovery {
        tailf:cli-compact-syntax;
        tailf:cli-sequence-commands;
        leaf username {
          type string;
        }
        leaf password {
          type string;
        }
      }
    }
    container confdConfig {
      container cli {
        leaf maxLineLength {
          type uint32;
        }
        leaf timezone {
          type string;
        }
        leaf utcOffset {
          type int32;
        }
        leaf idleTimeout {
          type string;
        }
        container timestamp {
          choice enabled-choice {
            leaf enabled {
              type empty;
            }
            leaf disabled {
              type empty;
            }
          }
          leaf clock24 {
            type boolean;
          }
          leaf format {
            type string;
          }
        }
        container suppressCommitMessages {
          presence "true";
        }
        leaf historySave {
          type boolean;
        }
        leaf allOrNothingLoad {
          type boolean;
        }
        leaf enableLoadMergeLeafList {
          type boolean;
        }
      }
    }
    container console {
      container attach-sdr {
        list location {
          key "name";
          leaf name {
            type string;
          }
          list tty-name {
            key "name";
            leaf name {
              type string;
            }
            leaf sdr-name {
              type string;
            }
          }
        }
      }
    }
    container connect {
      list sdr {
        tailf:cli-suppress-mode;
        tailf:cli-delete-when-empty;
        key "name remote-name csi-id";
        leaf name {
          type string;
        }
        leaf remote-name {
          type string;
        }
        leaf csi-id {
          type uint8;
        }
      }
    }
    list sdr {
      key "name";
      leaf name {
        type string;
      }
      leaf-list initial-image {
        tailf:cli-flat-list-syntax;
        type string;
      }
      leaf pairing-mode {
        type enumeration {
          enum inter-rack;
          enum intra-rack;
        }
      }
      container resources {
        leaf mgmt_ext_vlan {
          type uint16;
        }
        list card-type {
          key "name";
          leaf name {
            type enumeration {
              enum CC;
              enum LC;
              enum RP;
            }
          }
          leaf vm-cpu {
            type uint8;
          }
          leaf vm-memory {
            type uint8;
          }
        }
      }
      list location {
        key "name";
        leaf name {
          type string;
        }
      }
    }
    container service {
      container cli {
        leaf interactive {
          type enumeration {
            enum disabled;
            enum enabled;
          }
        }
      }
    }
    container vm {
      container memory {
        leaf admin {
          type uint32;
        }
        leaf rp {
          type uint32;
        }
        leaf lc {
          type uint32;
        }
      }
      container cpu {
        leaf assign {
          type string;
        }
      }
    }
    container chassis {
      list serial {
        key "name";
        leaf name {
          type string;
        }
        leaf rack {
          type string;
        }
      }
    }
    container interface {
      list MgmtEth {
        tailf:cli-allow-join-with-key;
        key "id";
        leaf id {
          type string;
        }
        container ipv4 {
          container address {
            tailf:cli-compact-syntax;
            tailf:cli-sequence-commands;
            leaf ip {
              tailf:cli-drop-node-name;
              type string;
            }
            leaf mask {
              tailf:cli-drop-node-name;
              type string;
            }
          }
        }
        leaf default-gw {
          type inet:ipv4-address;
        }
      }
    }
    container alias {
      list alias-list {
        tailf:cli-drop-node-name;
        tailf:cli-suppress-mode;
        tailf:cli-delete-when-empty;
        key "name";
        leaf name {
          type string;
        }
        leaf line {
          tailf:cli-drop-node-name;
          tailf:cli-multi-value;
          type string;
        }
      }
    }
    container SNMP-COMMUNITY-MIB {
      container snmpCommunityTable {
        list snmpCommunityEntry {
          key "snmpCommunityIndex";
          leaf snmpCommunityIndex {
            type snmpCommunityIndexType;
          }
          leaf snmpCommunityName {
            type snmpCommunityNameType;
            mandatory true;
          }
          leaf snmpCommunitySecurityName {
            type snmpCommunitySecurityNameType;
            mandatory true;
          }
          leaf snmpCommunityContextEngineID {
            type SNMP_FRAMEWORK_MIB_SnmpEngineID;
            mandatory true;
          }
          leaf snmpCommunityContextName {
            type snmpCommunityContextNameType;
          }
          leaf snmpCommunityTransportTag {
            type SNMP_TARGET_MIB_SnmpTagValue;
          }
          leaf snmpCommunityStorageType {
            type SNMPv2_TC_StorageType;
          }
        }
      }
    }
    container SNMP-NOTIFICATION-MIB {
      container snmpNotifyTable {
        list snmpNotifyEntry {
          key "snmpNotifyName";
          leaf snmpNotifyName {
            type snmpNotifyNameType;
          }
          leaf snmpNotifyTag {
            type SNMP_TARGET_MIB_SnmpTagValue;
          }
          leaf snmpNotifyType {
            type snmpNotifyTypeType;
          }
          leaf snmpNotifyStorageType {
            type SNMPv2_TC_StorageType;
          }
        }
      }
    }
    container SNMP-TARGET-MIB {
      container snmpTargetObjects {
        config false;
        leaf snmpUnavailableContexts {
          type yang:counter32;
          config false;
        }
        leaf snmpUnknownContexts {
          type yang:counter32;
          config false;
        }
      }
      container snmpTargetAddrTable {
        list snmpTargetAddrEntry {
          key "snmpTargetAddrName";
          leaf snmpTargetAddrName {
            type snmpTargetAddrNameType;
          }
          leaf snmpTargetAddrTDomain {
            type SNMPv2_TC_TDomain;
            mandatory true;
          }
          leaf snmpTargetAddrTAddress {
            type UDPTAddress;
            mandatory true;
          }
          leaf snmpTargetAddrTimeout {
            type SNMPv2_TC_TimeInterval;
          }
          leaf snmpTargetAddrRetryCount {
            type snmpTargetAddrRetryCountType;
          }
          leaf snmpTargetAddrTagList {
            type SnmpTagList;
          }
          leaf snmpTargetAddrParams {
            type snmpTargetAddrParamsType;
            mandatory true;
          }
          leaf snmpTargetAddrStorageType {
            type SNMPv2_TC_StorageType;
          }
          leaf snmpTargetAddrEngineID {
            type snmpTargetAddrEngineIDType;
          }
          leaf snmpTargetAddrTMask {
            type UDPTMask;
          }
          leaf snmpTargetAddrMMS {
            type snmpTargetAddrMMSType;
          }
          leaf enabled {
            type empty;
          }
        }
      }
      container snmpTargetParamsTable {
        list snmpTargetParamsEntry {
          key "snmpTargetParamsName";
          leaf snmpTargetParamsName {
            type snmpTargetParamsNameType;
          }
          leaf snmpTargetParamsMPModel {
            type SNMP_FRAMEWORK_MIB_SnmpMessageProcessingModel;
            mandatory true;
          }
          leaf snmpTargetParamsSecurityModel {
            type snmpTargetParamsSecurityModelType;
            mandatory true;
          }
          leaf snmpTargetParamsSecurityName {
            type SNMP_FRAMEWORK_MIB_SnmpAdminString;
            mandatory true;
          }
          leaf snmpTargetParamsSecurityLevel {
            type SNMP_FRAMEWORK_MIB_SnmpSecurityLevel;
            mandatory true;
          }
          leaf snmpTargetParamsStorageType {
            type SNMPv2_TC_StorageType;
          }
        }
      }
    }
    container SNMP-USER-BASED-SM-MIB {
      container usmStats {
        config false;
        leaf usmStatsUnsupportedSecLevels {
          type yang:counter32;
          config false;
        }
        leaf usmStatsNotInTimeWindows {
          type yang:counter32;
          config false;
        }
        leaf usmStatsUnknownUserNames {
          type yang:counter32;
          config false;
        }
        leaf usmStatsUnknownEngineIDs {
          type yang:counter32;
          config false;
        }
        leaf usmStatsWrongDigests {
          type yang:counter32;
          config false;
        }
        leaf usmStatsDecryptionErrors {
          type yang:counter32;
          config false;
        }
      }
      container usmUserTable {
        list usmUserEntry {
          key "usmUserEngineID usmUserName";
          unique "usmUserEngineID usmUserSecurityName";
          leaf usmUserEngineID {
            type SNMP_FRAMEWORK_MIB_SnmpEngineID;
          }
          leaf usmUserName {
            type usmUserNameType;
          }
          leaf usmUserSecurityName {
            type SNMP_FRAMEWORK_MIB_SnmpAdminString;
            mandatory true;
          }
          leaf usmUserCloneFrom {
            type SNMPv2_TC_RowPointer;
          }
          leaf usmUserAuthProtocol {
            type SNMPv2_TC_AutonomousType;
          }
          leaf usmUserAuthKeyChange {
            type KeyChange;
          }
          leaf usmUserOwnAuthKeyChange {
            type KeyChange;
          }
          leaf usmUserPrivProtocol {
            type SNMPv2_TC_AutonomousType;
          }
          leaf usmUserPrivKeyChange {
            type KeyChange;
          }
          leaf usmUserOwnPrivKeyChange {
            type KeyChange;
          }
          leaf usmUserPublic {
            type usmUserPublicType;
          }
          leaf usmUserStorageType {
            type SNMPv2_TC_StorageType;
          }
          leaf usmUserAuthKey {
            type KeyChange;
          }
          leaf usmUserPrivKey {
            type KeyChange;
          }
        }
      }
    }
    container SNMP-VIEW-BASED-ACM-MIB {
      container vacmSecurityToGroupTable {
        list vacmSecurityToGroupEntry {
          key "vacmSecurityModel vacmSecurityName";
          leaf vacmSecurityModel {
            type vacmSecurityModelType;
          }
          leaf vacmSecurityName {
            type vacmSecurityNameType;
          }
          leaf vacmGroupName {
            type vacmGroupNameType;
            mandatory true;
          }
          leaf vacmSecurityToGroupStorageType {
            type SNMPv2_TC_StorageType;
          }
        }
      }
      container vacmAccessTable {
        list vacmAccessEntry {
          key "vacmGroupName vacmAccessContextPrefix vacmAccessSecurityModel vacmAccessSecurityLevel";
          leaf vacmGroupName {
            type vacmGroupNameType;
          }
          leaf vacmAccessContextPrefix {
            type vacmAccessContextPrefixType;
          }
          leaf vacmAccessSecurityModel {
            type SNMP_FRAMEWORK_MIB_SnmpSecurityModel;
          }
          leaf vacmAccessSecurityLevel {
            type SNMP_FRAMEWORK_MIB_SnmpSecurityLevel;
          }
          leaf vacmAccessContextMatch {
            type vacmAccessContextMatchType;
          }
          leaf vacmAccessReadViewName {
            type vacmAccessReadViewNameType;
          }
          leaf vacmAccessWriteViewName {
            type vacmAccessWriteViewNameType;
          }
          leaf vacmAccessNotifyViewName {
            type vacmAccessNotifyViewNameType;
          }
          leaf vacmAccessStorageType {
            type SNMPv2_TC_StorageType;
          }
        }
      }
      container vacmViewTreeFamilyTable {
        list vacmViewTreeFamilyEntry {
          key "vacmViewTreeFamilyViewName vacmViewTreeFamilySubtree";
          leaf vacmViewTreeFamilyViewName {
            type vacmViewTreeFamilyViewNameType;
          }
          leaf vacmViewTreeFamilySubtree {
            type yang:object-identifier;
          }
          leaf vacmViewTreeFamilyMask {
            type vacmViewTreeFamilyMaskType;
          }
          leaf vacmViewTreeFamilyType {
            type vacmViewTreeFamilyTypeType;
          }
          leaf vacmViewTreeFamilyStorageType {
            type SNMPv2_TC_StorageType;
          }
        }
      }
    }
    container SNMPv2-MIB {
      container system {
        leaf sysContact {
          type sysContactType;
        }
        leaf sysName {
          type sysNameType;
        }
        leaf sysLocation {
          type sysLocationType;
        }
      }
      container snmp {
        leaf snmpEnableAuthenTraps {
          type snmpEnableAuthenTrapsType;
        }
      }
    }
    container controllers {
      container fabric {
        list link {
          tailf:cli-suppress-mode;
          tailf:cli-delete-when-empty;
          tailf:cli-compact-syntax;
          tailf:cli-sequence-commands {
            tailf:cli-reset-siblings;
          }
          key "location";
          leaf location {
            type string;
          }
          leaf port {
            tailf:cli-prefix-key;
            type enumeration {
              enum fabricqrx;
              enum ingressqtx;
              enum s1rx;
              enum s1tx;
              enum s2rx;
              enum s2tx;
              enum s3rx;
              enum s3tx;
            }
          }
          leaf shutdown {
            type empty;
          }
        }
        list plane {
          key "id";
          leaf id {
            type uint8;
          }
          container oim {
            leaf count {
              type enumeration {
                enum 1;
                enum 3;
              }
            }
            leaf width {
              type enumeration {
                enum 1;
                enum 2;
              }
            }
            list instance {
              tailf:cli-suppress-mode;
              tailf:cli-delete-when-empty;
              key "id";
              leaf id {
                type uint8;
              }
              leaf location {
                type string;
              }
            }
          }
        }
      }
    }
    container dsc {
      list serial {
        tailf:cli-suppress-mode;
        tailf:cli-delete-when-empty;
        key "serial";
        leaf serial {
          type string;
        }
        leaf rack {
          type uint8;
        }
      }
    }
    grouping admin-session-grouping {
      container session {
        tailf:cli-delete-when-empty;
        presence "true";
        leaf complete-on-space {
          type boolean;
        }
      }
    }

    uses admin-session-grouping;
    container crs16 {
      container set {
        list min-power-modules {
          tailf:cli-suppress-mode;
          tailf:cli-delete-when-empty;
          tailf:cli-compact-syntax;
          tailf:cli-sequence-commands;
          key "location";
          leaf location {
            type string;
          }
          leaf value {
            tailf:cli-drop-node-name;
            tailf:cli-prefix-key;
            type uint8;
          }
        }
      }
    }
    list user {
      key "name";
      leaf name {
        type string;
      }
      uses admin-session-grouping;
    }
    leaf bad-config {
      type empty;
    }
    container lcd {
      leaf name {
        type string;
      }
    }
    list external_alarms {
      tailf:cli-suppress-mode;
      tailf:cli-delete-when-empty;
      key "name";
      leaf name {
        type string;
      }
      leaf status {
        tailf:cli-drop-node-name;
        type enumeration {
          enum disable;
          enum enable;
        }
      }
    }
    leaf xyzroot {
      type uint16;
    }
  }
  list group {
    key "name";
    leaf name {
      type string;
    }
    leaf line {
      tailf:cli-drop-node-name;
      type string;
    }
    container config {
      tailf:cli-drop-node-name;
      uses control-plane-grouping;
      uses segment-routing-grouping;
      uses evpn-config-grouping;
      container crypto {
        uses crypto-ca-grouping;
      }
      container filesystem-inventory {
        tailf:cli-add-mode;
        presence "true";
        leaf snapshot-interval {
          type uint16;
        }
      }
      container l2vpn {
        tailf:cli-add-mode;
        presence "true";
        container bridge {
          list group {
            key "group-name";
            leaf group-name {
              type string;
            }
            list bridge-domain {
              key "bridge-domain-name";
              leaf bridge-domain-name {
                type string;
              }
              container flood {
                leaf mode {
                  type enumeration {
                    enum convergence-optimized;
                    enum resilience-optimized;
                    enum ac-ingress-replication;
                  }
                }
              }
            }
          }
        }
      }
    }
  }
  container configuration {
    container commit {
      container auto-save {
        leaf filename {
          type string;
        }
      }
    }
    container display {
      container interface {
        leaf slot-order {
          type empty;
        }
      }
    }
  }
  leaf hostname {
    type string;
  }
  container license {
    container smart {
      leaf transport {
        type enumeration {
          enum off;
          enum callhome;
          enum cslu;
          enum smart;
        }
      }
      container flexible-consumption {
        leaf enable {
          type empty;
        }
      }
      container software-upgrade {
        leaf enable {
          type empty;
        }
      }
      container url {
        leaf cslu {
          type string;
        }
        leaf smart {
          tailf:cli-drop-node-name;
          type string;
        }
      }
      leaf reservation {
        type empty;
      }
      container proxy {
        leaf hostname {
          type inet:host;
        }
        leaf port {
          type uint16;
        }
      }
    }
  }
  container locale {
    leaf language {
      type string;
    }
    leaf country {
      type string;
    }
  }
  uses apply-group-grouping;
  uses clock-grouping;
  container banner {
    container exec {
      tailf:cli-compact-syntax;
      tailf:cli-sequence-commands {
        tailf:cli-reset-siblings;
      }
      uses banner-grouping;
    }
    container incoming {
      tailf:cli-compact-syntax;
      tailf:cli-sequence-commands {
        tailf:cli-reset-siblings;
      }
      uses banner-grouping;
    }
    container motd {
      tailf:cli-compact-syntax;
      tailf:cli-sequence-commands {
        tailf:cli-reset-siblings;
      }
      uses banner-grouping;
    }
    container login {
      tailf:cli-compact-syntax;
      tailf:cli-sequence-commands {
        tailf:cli-reset-siblings;
      }
      uses banner-grouping;
    }
    container slip-ppp {
      tailf:cli-compact-syntax;
      tailf:cli-sequence-commands {
        tailf:cli-reset-siblings;
      }
      uses banner-grouping;
    }
    container prompt-timeout {
      tailf:cli-compact-syntax;
      tailf:cli-sequence-commands {
        tailf:cli-reset-siblings;
      }
      uses banner-grouping;
    }
  }
  container banner-edit {
    tailf:cli-drop-node-name;
    list banner {
      key "name";
      leaf name {
        tailf:cli-suppress-range;
        type enumeration {
          enum exec;
          enum incoming;
          enum motd;
          enum login;
          enum slip-ppp;
          enum prompt-timeout;
        }
      }
      list line {
        tailf:cli-drop-node-name;
        tailf:cli-suppress-mode;
        tailf:cli-delete-when-empty;
        key "id";
        leaf id {
          tailf:cli-suppress-range;
          type uint32;
        }
        leaf value {
          tailf:cli-drop-node-name;
          tailf:cli-multi-value;
          type string;
        }
      }
    }
  }
  uses exception-grouping;
  container address-family {
    container ipv4 {
      container unicast {
        tailf:cli-add-mode;
        presence "true";
      }
      container multicast {
        list topology {
          key "name";
          leaf name {
            type string;
          }
        }
      }
    }
    container ipv6 {
      container unicast {
        tailf:cli-add-mode;
        presence "true";
      }
      container multicast {
        list topology {
          key "name";
          leaf name {
            type string;
          }
        }
      }
    }
  }
  container cef {
    container adjacency {
      container route {
        leaf override {
          type enumeration {
            enum rib;
          }
        }
      }
    }
    container load-balancing {
      tailf:cli-add-mode;
      container algorithm {
        leaf adjust {
          type uint8;
        }
      }
      container fields {
        container l3 {
          tailf:cli-delete-when-empty;
          presence "true";
          leaf global {
            type empty;
          }
        }
        container l4 {
          tailf:cli-delete-when-empty;
          presence "true";
          leaf gtp {
            type empty;
          }
        }
      }
    }
    container load-balancing-non-mode {
      tailf:cli-drop-node-name;
      container load-balancing {
        leaf fields {
          type enumeration {
            enum L3;
            enum L4;
          }
        }
        leaf payload {
          type enumeration {
            enum L2;
          }
        }
      }
    }
    container fast-reroute {
      container follow {
        leaf bgp-pic {
          type empty;
        }
      }
    }
    container encap-sharing {
      leaf disable {
        type empty;
      }
    }
    container proactive-arp-nd {
      leaf enable {
        type empty;
      }
    }
    container platform {
      container load-balancing-mode {
        tailf:cli-drop-node-name;
        container load-balancing {
          tailf:cli-add-mode;
          container fields-level {
            tailf:cli-drop-node-name;
            container fields {
              tailf:cli-compact-syntax;
              tailf:cli-sequence-commands;
              leaf level {
                tailf:cli-drop-node-name;
                tailf:cli-case-insensitive;
                type enumeration {
                  enum L3;
                  enum L4;
                }
              }
              leaf global {
                type empty;
              }
            }
          }
        }
      }
      container load-balancing {
        container mpls-hashing {
          container inner-non-ip {
            leaf use-labels-only {
              type empty;
            }
          }
        }
      }
    }
  }
  container explicit-path {
    list name {
      key "pathname";
      leaf pathname {
        type string;
      }
      uses explicit-path-index-list-grouping;
    }
    list identifier {
      key "identifier";
      leaf identifier {
        type uint16;
      }
      uses explicit-path-index-list-grouping;
    }
  }
  container selective-vrf-download {
    tailf:cli-add-mode;
    leaf disable {
      type empty;
    }
  }
  container lcc {
    container ipv4 {
      container unicast {
        leaf enable {
          type empty;
        }
        leaf period {
          type uint32;
        }
      }
    }
    container ipv6 {
      container unicast {
        leaf enable {
          type empty;
        }
        leaf period {
          type uint32;
        }
      }
    }
  }
  container vrf {
    list vrf-list {
      tailf:cli-drop-node-name;
      key "name";
      leaf name {
        type string;
      }
      leaf description {
        tailf:cli-multi-value;
        type string;
      }
      leaf fallback-vrf {
        type string;
      }
      leaf rd {
        type union {
          type inet:ipv4-address;
          type string;
        }
      }
      container vpn {
        leaf id {
          type string;
        }
      }
      container mode {
        leaf big {
          type empty;
        }
      }
      container address-family {
        container ipv4 {
          container unicast {
            tailf:cli-add-mode;
            presence "true";
            uses vrf-af-ipv4-grouping;
          }
          container multicast {
            tailf:cli-add-mode;
            presence "true";
            uses vrf-af-ipv4-grouping;
          }
          container flowspec {
            tailf:cli-add-mode;
            presence "true";
            uses vrf-af-ipv4-grouping;
          }
        }
        container ipv6 {
          container unicast {
            tailf:cli-add-mode;
            presence "true";
            uses vrf-af-ipv6-grouping;
          }
          container multicast {
            tailf:cli-add-mode;
            presence "true";
            uses vrf-af-ipv6-grouping;
          }
          container flowspec {
            tailf:cli-add-mode;
            presence "true";
            uses vrf-af-ipv6-grouping;
          }
        }
      }
    }
  }
  container ethernet {
    container egress-filter {
      leaf strict {
        type empty;
      }
    }
    container sla {
      tailf:cli-add-mode;
      list profile {
        key "name";
        leaf name {
          type string;
        }
        leaf type {
          tailf:cli-hide-in-submode;
          type enumeration {
            enum cfm-delay-measurement;
            enum cfm-delay-measurement-version-0;
            enum cfm-loopback;
            enum cfm-loss-measurement;
            enum cfm-synthetic-loss-measurement;
          }
        }
        container probe {
          tailf:cli-add-mode;
          container send {
            tailf:cli-compact-syntax;
            tailf:cli-sequence-commands {
              tailf:cli-reset-siblings;
            }
            leaf type {
              tailf:cli-drop-node-name;
              type enumeration {
                enum burst;
                enum packet;
              }
            }
            choice once-or-interval {
              leaf once {
                type empty;
              }
              case interval {
                leaf every {
                  type uint16;
                }
                leaf every-time {
                  tailf:cli-drop-node-name;
                  type enumeration {
                    enum seconds;
                    enum minutes;
                    enum hours;
                  }
                }
              }
            }
            container packet {
              tailf:cli-flatten-container;
              tailf:cli-compact-syntax;
              tailf:cli-sequence-commands {
                tailf:cli-reset-siblings;
              }
              leaf count {
                type uint16;
              }
              leaf interval {
                type uint16;
              }
              choice time-choice {
                leaf seconds {
                  tailf:cli-optional-in-sequence;
                  type empty;
                }
                leaf milliseconds {
                  type empty;
                }
              }
            }
          }
          leaf priority {
            type uint8;
          }
          container packet {
            leaf size {
              type uint16;
            }
          }
          container synthetic {
            container loss {
              container calculation {
                leaf packets {
                  type uint32;
                }
              }
            }
          }
        }
        container schedule {
          tailf:cli-add-mode;
          container every {
            tailf:cli-compact-syntax;
            tailf:cli-sequence-commands {
              tailf:cli-reset-siblings;
            }
            leaf number {
              tailf:cli-drop-node-name;
              type uint8;
            }
            leaf every-time {
              tailf:cli-drop-node-name;
              type enumeration {
                enum minutes;
                enum hours;
              }
            }
            leaf for {
              type uint16;
            }
            leaf for-time {
              tailf:cli-drop-node-name;
              type enumeration {
                enum seconds;
                enum minutes;
              }
            }
          }
        }
        container statistics {
          tailf:cli-add-mode;
          list measure {
            key "id";
            leaf id {
              type enumeration {
                enum one-way-delay-ds;
                enum one-way-delay-sd;
                enum one-way-jitter-ds;
                enum one-way-jitter-sd;
                enum round-trip-delay;
                enum round-trip-jitter;
                enum one-way-loss-ds;
                enum one-way-loss-sd;
              }
            }
            container aggregate {
              tailf:cli-compact-syntax;
              tailf:cli-sequence-commands {
                tailf:cli-reset-siblings;
              }
              choice aggregate-choice {
                case none {
                  leaf none {
                    type empty;
                  }
                }
                case bins-width {
                  leaf bins {
                    type uint8;
                  }
                  leaf width {
                    type uint16;
                  }
                }
              }
            }
            container buckets {
              container size {
                tailf:cli-compact-syntax;
                tailf:cli-sequence-commands {
                  tailf:cli-reset-siblings;
                }
                leaf number {
                  tailf:cli-drop-node-name;
                  type uint8;
                }
                leaf probes {
                  type empty;
                }
              }
              leaf archive {
                type uint8;
              }
            }
          }
        }
      }
    }
    container cfm {
      tailf:cli-add-mode;
      container traceroute {
        container cache {
          tailf:cli-compact-syntax;
          leaf hold-time {
            type uint32;
          }
          leaf size {
            type uint32;
          }
        }
      }
      list domain {
        key "name";
        leaf name {
          type string;
        }
        leaf level {
          tailf:cli-hide-in-submode;
          type uint8;
        }
        container id {
          tailf:cli-flatten-container;
          tailf:cli-compact-syntax;
          tailf:cli-hide-in-submode;
          choice id-choice {
            leaf null {
              type empty;
            }
            leaf string {
              type string;
            }
            leaf dns {
              type string;
            }
            leaf mac-address {
              type string;
            }
          }
        }
        list service {
          tailf:cli-compact-syntax;
          tailf:cli-sequence-commands;
          key "name";
          leaf name {
            type string;
          }
          choice service-type {
            container bridge {
              tailf:cli-hide-in-submode;
              tailf:cli-flatten-container;
              tailf:cli-compact-syntax;
              tailf:cli-sequence-commands;
              leaf group {
                type string;
              }
              leaf bridge-domain {
                type string;
              }
              container id {
                tailf:cli-flatten-container;
                tailf:cli-compact-syntax;
                choice id-choice {
                  container icc-based {
                    tailf:cli-flatten-container;
                    tailf:cli-compact-syntax;
                    tailf:cli-sequence-commands {
                      tailf:cli-reset-siblings;
                    }
                    leaf icc-string {
                      tailf:cli-drop-node-name;
                      type string;
                    }
                    leaf umc-string {
                      tailf:cli-drop-node-name;
                      type string;
                    }
                  }
                  leaf number {
                    type uint16;
                  }
                  leaf vlanid {
                    type uint16;
                  }
                  leaf vpn-id {
                    type string;
                  }
                }
              }
            }
            container xconnect {
              tailf:cli-hide-in-submode;
              tailf:cli-flatten-container;
              tailf:cli-compact-syntax;
              tailf:cli-sequence-commands;
              leaf group {
                type string;
              }
              leaf p2p {
                type string;
              }
              container id {
                tailf:cli-flatten-container;
                tailf:cli-compact-syntax;
                choice id-choice {
                  leaf number {
                    type uint16;
                  }
                  leaf string {
                    type string;
                  }
                  leaf vlanid {
                    type uint16;
                  }
                  container icc-based {
                    tailf:cli-flatten-container;
                    tailf:cli-compact-syntax;
                    tailf:cli-sequence-commands {
                      tailf:cli-reset-siblings;
                    }
                    leaf icc-string {
                      tailf:cli-drop-node-name;
                      type string;
                    }
                    leaf umc-string {
                      tailf:cli-drop-node-name;
                      type string;
                    }
                  }
                }
              }
            }
            container down-meps {
              tailf:cli-hide-in-submode;
              tailf:cli-flatten-container;
              tailf:cli-compact-syntax;
              presence "true";
              container id {
                tailf:cli-flatten-container;
                tailf:cli-compact-syntax;
                tailf:cli-hide-in-submode;
                choice id-choice {
                  leaf number {
                    type uint16;
                  }
                  leaf string {
                    type string;
                  }
                }
              }
            }
            container flexible-xconnect {
              tailf:cli-hide-in-submode;
              tailf:cli-flatten-container;
              container vlan-aware {
                tailf:cli-flatten-container;
                leaf evi {
                  type uint16;
                }
              }
            }
          }
          container continuity-check {
            tailf:cli-break-sequence-commands;
            container interval {
              tailf:cli-compact-syntax;
              tailf:cli-sequence-commands;
              leaf value {
                tailf:cli-drop-node-name;
                type string;
              }
              leaf loss-threshold {
                type uint8;
              }
            }
            container archive {
              leaf hold-time {
                type uint16;
              }
            }
            container loss {
              leaf auto-traceroute {
                type empty;
              }
            }
          }
          container log {
            container continuity-check {
              leaf errors {
                type empty;
              }
              container mep {
                leaf changes {
                  type empty;
                }
              }
            }
            leaf ais {
              type empty;
            }
            container crosscheck {
              leaf errors {
                type empty;
              }
            }
          }
          container mip {
            container auto-create {
              tailf:cli-compact-syntax;
              tailf:cli-sequence-commands {
                tailf:cli-reset-siblings;
              }
              choice create-choice {
                leaf all {
                  tailf:cli-optional-in-sequence;
                  type empty;
                }
                leaf lower-mep-only {
                  type empty;
                }
              }
              leaf ccm-learning {
                type empty;
              }
            }
          }
          container mep {
            container crosscheck {
              tailf:cli-add-mode;
              leaf auto {
                type empty;
              }
              list mep-id {
                tailf:cli-suppress-mode;
                tailf:cli-delete-when-empty;
                key "id";
                leaf id {
                  type uint16;
                }
                leaf mac-address {
                  type string;
                }
              }
            }
          }
          container ais {
            leaf transmission {
              type empty;
            }
          }
          container efd {
            tailf:cli-delete-when-empty;
            presence "true";
            leaf protection-switching {
              type empty;
            }
          }
        }
      }
    }
    container oam {
      list profile {
        key "name";
        leaf name {
          type string;
        }
        leaf mode {
          type enumeration {
            enum active;
            enum passive;
          }
        }
        container connection {
          leaf timeout {
            type uint8;
          }
        }
        leaf hello-interval {
          type enumeration {
            enum 100ms;
            enum 1s;
          }
        }
        container mib-retrieval {
          tailf:cli-delete-when-empty;
          presence "true";
          leaf disable {
            type empty;
          }
        }
        container uni-directional {
          container link-fault {
            container detection {
              tailf:cli-delete-when-empty;
              presence "true";
              leaf disable {
                type empty;
              }
            }
          }
        }
        container remote-loopback {
          tailf:cli-delete-when-empty;
          presence "true";
          leaf disable {
            type empty;
          }
        }
        container link-monitor {
          tailf:cli-add-mode;
          container frame {
            uses ethernet-oam-profile-link-monitor-frame-grouping;
          }
          container frame-period {
            uses ethernet-oam-profile-link-monitor-frame-grouping;
          }
          container frame-seconds {
            uses ethernet-oam-profile-link-monitor-frame-grouping;
          }
          container symbol-period {
            uses ethernet-oam-profile-link-monitor-frame-grouping;
          }
          container monitoring {
            tailf:cli-delete-when-empty;
            presence "true";
            leaf disable {
              type empty;
            }
          }
        }
        container require-remote {
          tailf:cli-add-mode;
          leaf link-monitoring {
            type empty;
          }
          container mib-retrieval {
            tailf:cli-delete-when-empty;
            presence "true";
            leaf disabled {
              type empty;
            }
          }
          leaf mode {
            type enumeration {
              enum active;
              enum disabled;
              enum passive;
            }
          }
        }
        container action {
          tailf:cli-add-mode;
          leaf critical-event {
            type enumeration {
              enum disable;
              enum log {
                value 2;
              }
              enum error-disable-interface {
                value 3;
              }
            }
          }
          leaf wiring-conflict {
            type if-eth-oam-action-type;
          }
          leaf discovery-timeout {
            type enumeration {
              enum disable;
              enum efd;
              enum error-disable-interface {
                value 3;
              }
            }
          }
          leaf high-threshold {
            type enumeration {
              enum log {
                value 2;
              }
              enum error-disable-interface {
                value 3;
              }
            }
          }
          leaf session-down {
            type enumeration {
              enum disable;
              enum efd;
              enum error-disable-interface {
                value 3;
              }
            }
          }
          leaf remote-loopback {
            type enumeration {
              enum disable;
            }
          }
          leaf capabilities-conflict {
            type if-eth-oam-action-type;
          }
        }
      }
    }
    container ring {
      container g8032 {
        list profile {
          key "name";
          leaf name {
            type string;
          }
          container timer {
            leaf wtr {
              type uint8;
            }
            leaf guard {
              type uint16;
            }
            leaf hold-off {
              type uint8;
            }
          }
        }
      }
    }
    container service-activation-test {
      tailf:cli-add-mode;
      list profile {
        key "name";
        leaf name {
          type string;
        }
        container cos {
          tailf:cli-drop-node-name;
          tailf:cli-compact-syntax;
          tailf:cli-sequence-commands {
            tailf:cli-reset-siblings;
          }
          leaf outer-cos {
            type uint8;
          }
          leaf inner-cos {
            type uint8;
          }
        }
        container mode {
          leaf two-way {
            type empty;
          }
        }
        container duration {
          tailf:cli-compact-syntax;
          tailf:cli-sequence-commands {
            tailf:cli-reset-siblings;
          }
          leaf value {
            tailf:cli-drop-node-name;
            type uint16;
          }
          leaf unit {
            tailf:cli-drop-node-name;
            type enumeration {
              enum hours;
              enum minutes;
            }
          }
          leaf per-step {
            type empty;
          }
        }
        container color-aware {
          tailf:cli-compact-syntax;
          tailf:cli-sequence-commands {
            tailf:cli-reset-siblings;
          }
          leaf cir {
            type uint32;
          }
          leaf unit {
            tailf:cli-drop-node-name;
            type enumeration {
              enum gbps;
              enum kbps;
              enum mbps;
            }
          }
          leaf eir-color {
            type empty;
          }
          leaf set-dei {
            tailf:cli-optional-in-sequence;
            type empty;
          }
          leaf cos {
            type uint8;
          }
        }
        container packet-size {
          tailf:cli-compact-syntax;
          tailf:cli-sequence-commands {
            tailf:cli-reset-siblings;
          }
          choice packet-size-choice {
            leaf emix {
              type empty;
            }
            leaf value {
              tailf:cli-drop-node-name;
              type uint16;
            }
          }
        }
        container information-rate {
          tailf:cli-compact-syntax;
          tailf:cli-sequence-commands {
            tailf:cli-reset-siblings;
          }
          leaf value {
            tailf:cli-drop-node-name;
            type uint32;
          }
          leaf unit {
            tailf:cli-drop-node-name;
            type enumeration {
              enum gbps;
              enum kbps;
              enum mbps;
            }
          }
        }
      }
    }
  }
  container rcc {
    container ipv4 {
      container unicast {
        leaf enable {
          type empty;
        }
        leaf period {
          type uint32;
        }
      }
    }
    container ipv6 {
      container unicast {
        leaf enable {
          type empty;
        }
        leaf period {
          type uint32;
        }
      }
    }
  }
  container pce {
    tailf:cli-add-mode;
    presence "true";
    container address {
      leaf ipv4 {
        type inet:ipv4-address;
      }
      leaf ipv6 {
        type inet:ipv6-address;
      }
    }
    container disjoint-path {
      tailf:cli-add-mode;
      presence "true";
      list group-id {
        key "id type";
        leaf id {
          tailf:cli-suppress-range;
          type uint16;
        }
        leaf type {
          type enumeration {
            enum link;
            enum node;
            enum srlg;
            enum srlg-node;
          }
        }
        uses pce-disjoint-path-group-id-grouping;
      }
      container group-sub-id {
        tailf:cli-drop-node-name;
        list group-id {
          key "id type sub-id";
          leaf id {
            tailf:cli-suppress-range;
            type uint16;
          }
          leaf type {
            type enumeration {
              enum link;
              enum node;
              enum srlg;
              enum srlg-node;
            }
          }
          leaf sub-id {
            type uint16;
          }
          uses pce-disjoint-path-group-id-grouping;
        }
      }
    }
    container logging {
      tailf:cli-add-mode;
      container pcep {
        leaf pcerr-received {
          type empty;
        }
      }
      leaf no-path {
        type empty;
      }
      leaf fallback {
        type empty;
      }
    }
    container timers {
      tailf:cli-add-mode;
      leaf reoptimization {
        type uint32;
      }
      leaf keepalive {
        type uint8;
      }
      leaf minimum-peer-keepalive {
        type uint8;
      }
    }
    container state-sync {
      list ipv4 {
        tailf:cli-suppress-mode;
        tailf:cli-delete-when-empty;
        key "address";
        leaf address {
          tailf:cli-suppress-range;
          type inet:ipv4-address;
        }
      }
    }
    container password {
      tailf:cli-compact-syntax;
      tailf:cli-sequence-commands;
      uses password-grouping {
        refine "secret";
      }
    }
    container backoff {
      tailf:cli-add-mode;
      leaf ratio {
        type uint8;
      }
      leaf difference {
        type uint8;
      }
      leaf threshold {
        type uint16;
      }
    }
    container segment-routing {
      tailf:cli-add-mode;
      container traffic-eng {
        tailf:cli-add-mode;
        presence "true";
        container p2mp {
          tailf:cli-add-mode;
          container label-range {
            tailf:cli-compact-syntax;
            tailf:cli-sequence-commands {
              tailf:cli-reset-siblings;
            }
            leaf min {
              type uint32;
            }
            leaf max {
              type uint32;
            }
          }
          list endpoint-set {
            key "name";
            leaf name {
              type string;
            }
            list ipv4 {
              tailf:cli-suppress-mode;
              tailf:cli-delete-when-empty;
              key "address";
              leaf address {
                type inet:ipv4-address;
              }
            }
          }
          list policy {
            key "name";
            leaf name {
              type string;
            }
            container source {
              leaf ipv4 {
                type inet:ipv4-address;
              }
            }
            container color {
              tailf:cli-compact-syntax;
              tailf:cli-sequence-commands {
                tailf:cli-reset-siblings;
              }
              leaf value {
                tailf:cli-drop-node-name;
                type uint32;
              }
              leaf endpoint-set {
                type string;
              }
            }
            container treesid {
              leaf mpls {
                type uint32;
              }
            }
            container candidate-paths {
              tailf:cli-add-mode;
              list preference {
                key "id";
                leaf id {
                  type enumeration {
                    enum 100;
                  }
                }
                container dynamic {
                  tailf:cli-add-mode;
                  presence "true";
                  container metric {
                    tailf:cli-add-mode;
                    leaf type {
                      type enumeration {
                        enum hopcount;
                        enum igp;
                        enum latency;
                        enum te;
                      }
                    }
                  }
                }
              }
            }
          }
        }
        list segment-list {
          key "name";
          leaf name {
            type string;
          }
          list index {
            tailf:cli-suppress-mode;
            tailf:cli-delete-when-empty;
            key "id";
            leaf id {
              type uint16;
            }
            choice config-choice {
              container mpls {
                choice mpls-choice {
                  leaf label {
                    type uint32;
                  }
                  leaf adjacency {
                    type union {
                      type inet:ipv4-address;
                      type inet:ipv6-address;
                    }
                  }
                }
              }
              container address {
                leaf ipv4 {
                  type inet:ipv4-address;
                }
              }
            }
          }
        }
        container peer {
          list ipv4 {
            key "address";
            leaf address {
              type inet:ipv4-address;
            }
            list policy {
              key "name";
              leaf name {
                type string;
              }
              container binding-sid {
                leaf mpls {
                  type uint32;
                }
              }
              container color {
                tailf:cli-compact-syntax;
                tailf:cli-sequence-commands;
                leaf value {
                  tailf:cli-drop-node-name;
                  type uint32;
                }
                container end-point {
                  tailf:cli-flatten-container;
                  tailf:cli-compact-syntax;
                  leaf ipv4 {
                    type inet:ipv4-address;
                  }
                }
              }
              leaf shutdown {
                type empty;
              }
              container candidate-paths {
                tailf:cli-add-mode;
                presence "true";
                list preference {
                  key "id";
                  leaf id {
                    type uint16;
                  }
                  container explicit {
                    list segment-list {
                      key "name";
                      leaf name {
                        type string;
                      }
                    }
                  }
                  container dynamic {
                    container mpls {
                      tailf:cli-add-mode;
                      presence "true";
                      container metric {
                        tailf:cli-add-mode;
                        presence "true";
                        leaf type {
                          type enumeration {
                            enum igp;
                            enum te;
                            enum hopcount;
                            enum latency;
                          }
                        }
                      }
                    }
                  }
                  container constraints {
                    tailf:cli-add-mode;
                    container segments {
                      tailf:cli-add-mode;
                      leaf sid-algorithm {
                        type uint8;
                      }
                    }
                  }
                }
                container affinity {
                  tailf:cli-add-mode;
                  list attribute-list {
                    tailf:cli-drop-node-name;
                    key "name";
                    leaf name {
                      type enumeration {
                        enum exclude;
                        enum include-all;
                        enum include-any;
                      }
                    }
                    list color {
                      tailf:cli-drop-node-name;
                      tailf:cli-suppress-mode;
                      tailf:cli-delete-when-empty;
                      key "name";
                      leaf name {
                        type string;
                      }
                    }
                  }
                }
              }
            }
          }
        }
        container affinity {
          container bit-map {
            tailf:cli-add-mode;
            list color {
              tailf:cli-drop-node-name;
              tailf:cli-suppress-mode;
              tailf:cli-delete-when-empty;
              key "name";
              leaf name {
                type string;
              }
              leaf bit-position {
                tailf:cli-drop-node-name;
                type uint8;
              }
            }
          }
        }
      }
      leaf strict-sid-only {
        type empty;
      }
      leaf te-latency {
        type empty;
      }
    }
    container rest {
      tailf:cli-add-mode;
      presence "true";
      list user {
        key "name";
        leaf name {
          type string;
        }
        container password {
          tailf:cli-compact-syntax;
          tailf:cli-sequence-commands;
          uses password-grouping {
            refine "secret";
          }
        }
      }
      leaf authentication {
        type enumeration {
          enum basic;
          enum digest;
        }
      }
    }
    container api {
      tailf:cli-add-mode;
      presence "true";
      list user {
        key "name";
        leaf name {
          type string;
        }
        container password {
          tailf:cli-compact-syntax;
          tailf:cli-sequence-commands;
          uses password-grouping {
            refine "secret";
          }
        }
      }
      leaf authentication {
        type enumeration {
          enum basic;
          enum digest;
        }
      }
      leaf vrf {
        type string;
      }
      container sibling {
        leaf ipv4 {
          type inet:ipv4-address;
        }
      }
    }
    container netconf {
      presence "true";
      tailf:cli-add-mode;
    }
    container tcp-ao {
      tailf:cli-compact-syntax;
      tailf:cli-sequence-commands {
        tailf:cli-reset-siblings;
      }
      leaf keychain {
        tailf:cli-drop-node-name;
        type string;
      }
      leaf accept-ao-mismatch-connection {
        tailf:cli-optional-in-sequence;
        type empty;
      }
      leaf include-tcp-options {
        type empty;
      }
    }
    container tcp-buffer {
      leaf size {
        type uint32;
      }
    }
  }
  container pppoe {
    container bba-group-list {
      tailf:cli-drop-node-name;
      list bba-group {
        key "name";
        leaf name {
          type string;
        }
        uses pppoe-bba-group-grouping;
      }
    }
    container bba-group {
      tailf:cli-add-mode;
      uses pppoe-bba-group-grouping;
    }
    leaf in-flight-window {
      type uint16;
    }
  }
  container rp {
    container mgmtethernet {
      leaf forwarding {
        type empty;
      }
    }
  }
  container logging {
    leaf disable {
      type empty;
    }
    container ipv4 {
      leaf dscp {
        type dscp-type;
      }
    }
    container ipv6 {
      leaf dscp {
        type dscp-type;
      }
    }
    leaf trap {
      type severity-type;
    }
    container events {
      leaf level {
        type severity-type;
      }
      leaf link-status {
        type enumeration {
          enum disable;
          enum software-interfaces;
        }
      }
      leaf threshold {
        type uint8;
      }
      leaf buffer-size {
        type uint32;
      }
      leaf display-location {
        type empty;
      }
      container filter {
        tailf:cli-add-mode;
        list match {
          tailf:cli-suppress-mode;
          tailf:cli-delete-when-empty;
          key "name";
          leaf name {
            type string;
          }
        }
      }
    }
    list file {
      tailf:cli-suppress-mode;
      tailf:cli-delete-when-empty;
      tailf:cli-compact-syntax;
      tailf:cli-sequence-commands {
        tailf:cli-reset-siblings;
      }
      key "name";
      leaf name {
        type string;
      }
      leaf path {
        type string;
      }
      leaf maxfilesize {
        tailf:cli-optional-in-sequence;
        type uint32;
      }
      leaf severity {
        type severity-type;
      }
      leaf local-accounting {
        type empty;
      }
      leaf send-to-remote {
        type empty;
      }
      leaf facility {
        type facility-type;
      }
    }
    container archive {
      tailf:cli-add-mode;
      leaf device {
        type string;
      }
      leaf severity {
        type severity-type;
      }
      leaf file-size {
        type uint32;
      }
      leaf frequency {
        type enumeration {
          enum daily;
          enum weekly;
        }
      }
      leaf archive-size {
        type uint32;
      }
      leaf archive-length {
        type uint32;
      }
    }
    leaf monitor {
      type union {
        type severity-type;
        type enumeration {
          enum disable {
            value -1;
          }
        }
      }
    }
    container monitor-conf {
      tailf:cli-drop-node-name;
      container monitor {
        container discriminator {
          tailf:cli-add-mode;
          uses logging-discriminator-grouping;
        }
      }
    }
    container buffered {
      leaf size {
        tailf:cli-drop-node-name;
        type uint32;
      }
      leaf type {
        tailf:cli-drop-node-name;
        type severity-type;
      }
      container discriminator {
        tailf:cli-add-mode;
        uses logging-discriminator-grouping;
      }
    }
    leaf facility {
      type facility-type;
    }
    list host {
      tailf:cli-drop-node-name;
      tailf:cli-suppress-mode;
      tailf:cli-delete-when-empty;
      tailf:cli-compact-syntax;
      key "address vrf";
      leaf address {
        type union {
          type inet:ipv4-address;
          type inet:ipv6-address;
        }
      }
      leaf vrf {
        type string;
      }
      leaf source-address {
        type inet:host;
      }
      leaf severity {
        type severity-type;
      }
      leaf port {
        type union {
          type enumeration {
            enum default;
          }
          type uint32;
        }
      }
    }
    leaf localfilesize {
      type uint32;
    }
    container source-interface {
      uses interface-name-grouping;
    }
    container source-interface-vrf {
      tailf:cli-drop-node-name;
      list source-interface {
        tailf:cli-suppress-mode;
        tailf:cli-delete-when-empty;
        tailf:cli-compact-syntax;
        tailf:cli-sequence-commands;
        key "vrf";
        leaf vrf {
          tailf:cli-suppress-range;
          type string;
        }
        leaf interface {
          tailf:cli-drop-node-name;
          tailf:cli-prefix-key;
          type string;
        }
      }
    }
    container cns-events {
      tailf:cli-delete-when-empty;
      presence "true";
      leaf severity {
        type severity-type;
      }
    }
    container format {
      leaf rfc5424 {
        type empty;
      }
    }
    leaf console {
      type union {
        type severity-type;
        type enumeration {
          enum disable {
            value -1;
          }
        }
      }
    }
    container console-conf {
      tailf:cli-drop-node-name;
      container console {
        container discriminator {
          tailf:cli-add-mode;
          uses logging-discriminator-grouping;
        }
      }
    }
    leaf count {
      type empty;
    }
    leaf history {
      type severity-type;
    }
    container history-conf {
      tailf:cli-drop-node-name;
      container history {
        leaf size {
          type uint16;
        }
      }
    }
    container suppress {
      leaf duplicates {
        type empty;
      }
      list rule {
        key "name";
        leaf name {
          type string;
        }
        list alarm {
          tailf:cli-suppress-mode;
          tailf:cli-delete-when-empty;
          key "msg-category group-name msg-code";
          leaf msg-category {
            type string;
          }
          leaf group-name {
            type string;
          }
          leaf msg-code {
            type string;
          }
        }
      }
      container apply {
        list rule {
          key "name";
          leaf name {
            type string;
          }
          uses apply-group-grouping;
          leaf all-of-router {
            type empty;
          }
          container source {
            leaf location {
              type string;
            }
          }
        }
      }
    }
    container correlator {
      container rule {
        list timeout-list {
          tailf:cli-drop-node-name;
          tailf:cli-suppress-mode;
          tailf:cli-delete-when-empty;
          tailf:cli-compact-syntax;
          tailf:cli-sequence-commands {
            tailf:cli-reset-siblings;
          }
          key "name";
          leaf name {
            type string;
          }
          leaf timeout {
            type uint32;
          }
          leaf msg-category {
            tailf:cli-drop-node-name;
            type string;
          }
          leaf group-name {
            tailf:cli-drop-node-name;
            type string;
          }
        }
        list list {
          tailf:cli-drop-node-name;
          key "name";
          leaf name {
            type string;
          }
          leaf type {
            tailf:cli-hide-in-submode;
            type enumeration {
              enum nonstateful;
              enum stateful;
            }
          }
          leaf timeout {
            type uint32;
          }
          container rootcause {
            tailf:cli-compact-syntax;
            tailf:cli-sequence-commands {
              tailf:cli-reset-siblings;
            }
            leaf msg-category {
              tailf:cli-drop-node-name;
              type string;
            }
            leaf group-name {
              tailf:cli-drop-node-name;
              type string;
            }
            leaf msg-code {
              tailf:cli-drop-node-name;
              type string;
            }
          }
          container nonrootcause {
            tailf:cli-add-mode;
            list alarm {
              tailf:cli-suppress-mode;
              tailf:cli-delete-when-empty;
              key "msg-category group-name msg-code";
              leaf msg-category {
                type string;
              }
              leaf group-name {
                type string;
              }
              leaf msg-code {
                type string;
              }
            }
          }
          leaf timeout-rootcause {
            type uint32;
          }
        }
      }
      container rule-timeout {
        tailf:cli-drop-node-name;
        list rule {
          tailf:cli-suppress-mode;
          tailf:cli-delete-when-empty;
          tailf:cli-compact-syntax;
          tailf:cli-sequence-commands {
            tailf:cli-reset-siblings;
          }
          key "name";
          leaf name {
            type string;
          }
          leaf timeout {
            type uint32;
          }
          leaf msg-category {
            tailf:cli-drop-node-name;
            type string;
          }
          leaf group-name {
            tailf:cli-drop-node-name;
            type string;
          }
          leaf msg-code {
            tailf:cli-drop-node-name;
            type string;
          }
        }
      }
      container apply {
        list rule {
          key "name";
          leaf name {
            type string;
          }
          leaf all-of-router {
            type empty;
          }
        }
      }
      list apply-rule {
        tailf:cli-suppress-mode;
        tailf:cli-delete-when-empty;
        key "name";
        leaf name {
          type string;
        }
        leaf-list location {
          tailf:cli-flat-list-syntax;
          type string;
        }
      }
      leaf buffer-size {
        type uint32;
      }
    }
    leaf hostnameprefix {
      type string;
    }
  }

  grouping logging-discriminator-grouping {
    leaf match1 {
      type string;
    }
    leaf nomatch1 {
      type string;
    }
    leaf match2 {
      type string;
    }
    leaf nomatch2 {
      type string;
    }
    leaf match3 {
      type string;
    }
    leaf nomatch3 {
      type string;
    }
  }

  container service {
    container alignment {
      leaf detection {
        type empty;
      }
      leaf logging {
        type empty;
      }
    }
    leaf call-home {
      type empty;
    }
    leaf compress-config {
      type empty;
    }
    container counters {
      container max {
        leaf age {
          type uint8;
        }
      }
    }
    leaf dhcp {
      type empty;
    }
    leaf disable-ip-fast-frag {
      type empty;
    }
    leaf exec-callback {
      type empty;
    }
    leaf exec-wait {
      type empty;
    }
    leaf finger {
      type empty;
    }
    container heartbeat {
      leaf fatal-count {
        type uint8;
      }
      leaf interrupt-interval {
        type uint8;
      }
      leaf interrupt-max {
        type uint8;
      }
      leaf transmit-interval {
        type uint8;
      }
      leaf warning-timeout {
        type uint8;
      }
    }
    leaf hide-telnet-addresses {
      type empty;
    }
    container ipv4 {
      uses tcp-small-servers-grouping;
      uses udp-small-servers-grouping;
    }
    container ipv6 {
      uses tcp-small-servers-grouping;
      uses udp-small-servers-grouping;
    }
    leaf linenumber {
      type empty;
    }
    leaf nagle {
      type empty;
    }
    leaf old-slip-prompts {
      type empty;
    }
    container pad {
      presence "true";
      leaf cmns {
        type empty;
      }
      leaf from-xot {
        type empty;
      }
      leaf to-xot {
        type empty;
      }
    }
    leaf password-encryption {
      type empty;
    }
    container prompt {
      leaf config {
        type empty;
      }
    }
    leaf pt-vty-logging {
      type empty;
    }
    leaf sequence-numbers {
      type empty;
    }
    leaf slave-log {
      type empty;
    }
    leaf tcp-keepalives-in {
      type empty;
    }
    leaf tcp-keepalives-out {
      type empty;
    }
    container tcp-small-servers {
      presence "true";
      leaf max-servers {
        type union {
          type uint32;
          type enumeration {
            enum no-limit;
          }
        }
      }
    }
    leaf telnet-zeroidle {
      type empty;
    }
    container timestamps {
      container debug {
        leaf uptime {
          type empty;
        }
        container datetime {
          tailf:cli-drop-node-name;
          tailf:cli-compact-syntax;
          tailf:cli-sequence-commands {
            tailf:cli-reset-siblings;
          }
          leaf datetime {
            type empty;
          }
          leaf localtime {
            tailf:cli-break-sequence-commands;
            type empty;
          }
          leaf msec {
            type empty;
          }
          leaf show-timezone {
            type empty;
          }
          leaf year {
            type empty;
          }
        }
      }
      container log {
        leaf uptime {
          type empty;
        }
        container datetime {
          tailf:cli-drop-node-name;
          tailf:cli-compact-syntax;
          tailf:cli-sequence-commands {
            tailf:cli-reset-siblings;
          }
          leaf datetime {
            type empty;
          }
          leaf localtime {
            tailf:cli-break-sequence-commands;
            type empty;
          }
          leaf msec {
            type empty;
          }
          leaf show-timezone {
            type empty;
          }
          leaf year {
            type empty;
          }
        }
      }
    }
    container udp-small-servers {
      presence "true";
      leaf max-servers {
        type union {
          type uint32;
        }
      }
    }
    leaf unsupported-transceiver {
      type empty;
    }
    container cli {
      container configuration {
        container disable {
          leaf usergroup {
            type string;
          }
        }
      }
      container history {
        leaf size {
          type uint16;
        }
      }
      container interactive {
        leaf disable {
          type empty;
        }
      }
    }
  }
  container event {
    container manager {
      list action {
        key "name";
        leaf name {
          type string;
        }
        leaf username {
          type string;
        }
        container type {
          container script {
            tailf:cli-compact-syntax;
            tailf:cli-sequence-commands {
              tailf:cli-reset-siblings;
            }
            leaf script-name {
              type string;
            }
            container maxrun {
              tailf:cli-flatten-container;
              tailf:cli-compact-syntax;
              tailf:cli-optional-in-sequence;
              leaf seconds {
                type uint32;
              }
            }
            container checksum {
              tailf:cli-flatten-container;
              tailf:cli-compact-syntax;
              leaf sha256 {
                type string;
              }
            }
          }
        }
      }
      container directory {
        container user {
          leaf policy {
            type string;
          }
          leaf library {
            type string;
          }
        }
      }
      leaf refresh-time {
        type uint32;
      }
      list policy {
        tailf:cli-suppress-mode;
        tailf:cli-delete-when-empty;
        tailf:cli-compact-syntax;
        tailf:cli-sequence-commands {
          tailf:cli-reset-all-siblings;
        }
        key "name";
        leaf name {
          type string;
        }
        leaf username {
          type string;
        }
        leaf persist-time {
          tailf:cli-break-sequence-commands;
          type union {
            type enumeration {
              enum infinite;
            }
            type uint32;
          }
        }
        leaf type {
          type enumeration {
            enum system;
            enum user;
          }
        }
      }
      list event-trigger {
        key "name";
        leaf name {
          type string;
        }
        container type {
          container syslog {
            leaf pattern {
              type string;
            }
          }
          container track {
            tailf:cli-compact-syntax;
            tailf:cli-sequence-commands {
              tailf:cli-reset-siblings;
            }
            leaf name {
              type string;
            }
            leaf status {
              type enumeration {
                enum any;
                enum down;
                enum up;
              }
            }
          }
        }
      }
      list policy-map {
        key "name";
        leaf name {
          type string;
        }
        container trigger {
          leaf event {
            type string;
          }
        }
        list action {
          tailf:cli-suppress-mode;
          tailf:cli-delete-when-empty;
          key "name";
          leaf name {
            type string;
          }
        }
      }
      list environment {
        tailf:cli-suppress-mode;
        tailf:cli-delete-when-empty;
        tailf:cli-compact-syntax;
        key "name";
        leaf name {
          type string;
        }
        leaf var-value {
          tailf:cli-drop-node-name;
          tailf:cli-multi-value;
          type string;
        }
      }
      container scheduler {
        leaf suspend {
          type empty;
        }
      }
    }
  }
  container domain {
    container ipv4 {
      list host {
        tailf:cli-suppress-mode;
        tailf:cli-delete-when-empty;
        key "host-name";
        leaf host-name {
          type string;
        }
        leaf-list address {
          tailf:cli-drop-node-name;
          tailf:cli-flat-list-syntax;
          ordered-by user;
          type string;
        }
      }
    }
    container ipv6 {
      list host {
        tailf:cli-suppress-mode;
        tailf:cli-delete-when-empty;
        key "host-name";
        leaf host-name {
          type string;
        }
        leaf-list address {
          tailf:cli-drop-node-name;
          tailf:cli-flat-list-syntax;
          ordered-by user;
          type string;
        }
      }
    }
    container lookup {
      leaf disable {
        type empty;
      }
      container source-interface {
        tailf:cli-flatten-container;
        tailf:cli-compact-syntax;
        uses interface-name-grouping;
      }
    }
    leaf name {
      type string;
    }
    leaf-list list {
      ordered-by user;
      type string;
    }
    list name-server {
      tailf:cli-suppress-mode;
      tailf:cli-delete-when-empty;
      ordered-by user;
      key "address";
      leaf address {
        type inet:host;
      }
    }
    list vrf {
      tailf:cli-suppress-mode;
      tailf:cli-delete-when-empty;
      key "id";
      leaf id {
        type string;
      }
      leaf name {
        type string;
      }
      leaf-list list {
        ordered-by user;
        type string;
      }
      list name-server {
        tailf:cli-suppress-mode;
        tailf:cli-delete-when-empty;
        ordered-by user;
        key "address";
        leaf address {
          type inet:host;
        }
      }
      container lookup {
        leaf disable {
          type empty;
        }
        container source-interface {
          uses interface-name-grouping;
        }
      }
      container ipv4 {
        list host {
          tailf:cli-suppress-mode;
          tailf:cli-delete-when-empty;
          key "name";
          leaf name {
            type string;
          }
          leaf-list address {
            tailf:cli-drop-node-name;
            tailf:cli-flat-list-syntax;
            ordered-by user;
            type string;
          }
        }
      }
      container ipv6 {
        list host {
          tailf:cli-suppress-mode;
          tailf:cli-delete-when-empty;
          key "host-name";
          leaf host-name {
            type string;
          }
          leaf-list address {
            tailf:cli-drop-node-name;
            tailf:cli-flat-list-syntax;
            ordered-by user;
            type string;
          }
        }
      }
    }
  }
  container forward-protocol {
    container udp {
      list port-list {
        tailf:cli-drop-node-name;
        tailf:cli-suppress-mode;
        tailf:cli-delete-when-empty;
        tailf:cli-compact-syntax;
        key "port";
        leaf port {
          type union {
            type uint16;
            type enumeration {
              enum domain {
                value 53;
              }
              enum nameserver {
                value 42;
              }
              enum netbios-dgm {
                value 138;
              }
              enum netbios-ns {
                value 137;
              }
              enum tacacs {
                value 49;
              }
              enum tftp {
                value 69;
              }
            }
          }
        }
        leaf disable {
          type empty;
        }
      }
    }
  }
  list taskgroup {
    key "name";
    leaf name {
      type string;
    }
    container task {
      list execute {
        tailf:cli-suppress-mode;
        tailf:cli-delete-when-empty;
        key "name";
        leaf name {
          type task-type;
        }
      }
      list read {
        tailf:cli-suppress-mode;
        tailf:cli-delete-when-empty;
        key "name";
        leaf name {
          type task-type;
        }
      }
      list write {
        tailf:cli-suppress-mode;
        tailf:cli-delete-when-empty;
        key "name";
        leaf name {
          type task-type;
        }
      }
      list debug {
        tailf:cli-suppress-mode;
        tailf:cli-delete-when-empty;
        key "name";
        leaf name {
          type task-type;
        }
      }
    }
    container inherit {
      list taskgroup {
        tailf:cli-suppress-mode;
        tailf:cli-delete-when-empty;
        key "name";
        leaf name {
          type string;
        }
      }
    }
    leaf description {
      tailf:cli-multi-value;
      type string;
    }
  }
  container diameter {
    container origin {
      leaf host {
        type string;
      }
      leaf realm {
        type string;
      }
    }
    leaf gx {
      type empty;
    }
    leaf gy {
      type empty;
    }
    container source-interface {
      uses interface-name-grouping;
    }
    container timer {
      leaf watchdog {
        type uint16;
      }
    }
    container gx-conf {
      tailf:cli-drop-node-name;
      container gx {
        leaf tx-timer {
          type uint16;
        }
        leaf retransmit {
          type uint8;
        }
      }
    }
    container vendor {
      container supported {
        leaf threegpp {
          type empty;
        }
        leaf cisco {
          type empty;
        }
        leaf vodafone {
          type empty;
        }
        leaf etsi {
          type empty;
        }
      }
    }
    list peer {
      key "name";
      leaf name {
        type string;
      }
      container destination {
        leaf host {
          type string;
        }
        leaf realm {
          type string;
        }
      }
      container transport {
        container tcp {
          leaf port {
            type uint16;
          }
        }
      }
      container address {
        leaf ipv4 {
          type inet:ipv4-address;
        }
      }
    }
  }
  container radius {
    list source-interface {
      tailf:cli-suppress-mode;
      tailf:cli-delete-when-empty;
      tailf:cli-compact-syntax;
      tailf:cli-sequence-commands;
      key "vrf";
      leaf vrf {
        tailf:cli-suppress-range;
        type string;
      }
      leaf interface {
        tailf:cli-drop-node-name;
        tailf:cli-prefix-key;
        type string;
      }
    }
  }
  container radius-server {
    container vsa {
      container attribute {
        container ignore {
          leaf unknown {
            type empty;
          }
        }
      }
    }
    list host {
      key "id";
      leaf id {
        type inet:host;
      }
      leaf auth-port {
        tailf:cli-hide-in-submode;
        type uint16;
      }
      leaf acct-port {
        tailf:cli-hide-in-submode;
        type uint16;
      }
      container key {
        tailf:cli-compact-syntax;
        tailf:cli-sequence-commands;
        uses key-grouping {
          refine "key";
        }
      }
      leaf timeout {
        type uint16;
      }
      leaf retransmit {
        type uint8;
      }
    }
    container ipv4 {
      leaf dscp {
        type dscp-type;
      }
    }
    container ipv6 {
      leaf dscp {
        type dscp-type;
      }
    }
    container key {
      tailf:cli-compact-syntax;
      tailf:cli-sequence-commands;
      uses key-grouping {
        refine "key";
      }
    }
    leaf timeout {
      type uint16;
    }
    leaf deadtime {
      type uint16;
    }
    container disallow {
      leaf null-username {
        type empty;
      }
    }
    container throttle {
      tailf:cli-compact-syntax;
      leaf access {
        type uint16;
      }
      leaf access-timeout {
        type uint8;
      }
      leaf accounting {
        type uint16;
      }
    }
    container load-balance {
      container method {
        container least-outstanding {
          tailf:cli-compact-syntax;
          leaf batch-size {
            type uint16;
          }
          leaf ignore-preferred-server {
            type empty;
          }
        }
      }
    }
    leaf retransmit {
      type union {
        type uint8;
        type enumeration {
          enum disable;
        }
      }
    }
    container attribute {
      list list {
        key "name";
        leaf name {
          type string;
        }
        container attribute {
          list vendor-id {
            key "id";
            leaf id {
              type uint32;
            }
          }
          leaf list {
            tailf:cli-drop-node-name;
            type string;
          }
        }
      }
    }
    container source-port {
      leaf extended {
        type empty;
      }
    }
    container dead-criteria {
      leaf time {
        type uint8;
      }
      leaf tries {
        type uint8;
      }
    }
  }
  list usergroup {
    key "name";
    leaf name {
      type string;
    }
    leaf-list taskgroup {
      type string;
    }
    leaf description {
      tailf:cli-multi-value;
      type string;
    }
  }
  container http {
    container client {
      leaf version {
        type enumeration {
          enum 1.0;
          enum 1.1;
          enum default;
        }
      }
      container ssl {
        leaf version {
          type enumeration {
            enum tls1.0;
            enum tls1.1;
            enum tls1.2;
          }
        }
      }
      container source-interface {
        tailf:cli-compact-syntax;
        tailf:cli-sequence-commands {
          tailf:cli-reset-siblings;
        }
        leaf af {
          tailf:cli-drop-node-name;
          type enumeration {
            enum ipv4;
            enum ipv6;
          }
        }
        uses interface-name-grouping;
      }
      container secure-verify-peer {
        leaf disable {
          type empty;
        }
      }
      leaf vrf {
        type string;
      }
    }
    container server {
      tailf:cli-delete-when-empty;
      presence "true";
      leaf ssl {
        type empty;
      }
    }
  }
  container xnetconf {
    tailf:alt-name "netconf";
    container agent {
      container tty {
        tailf:cli-add-mode;
        presence "true";
        container session {
          leaf timeout {
            type uint16;
          }
        }
        container throttle {
          leaf memory {
            type uint16;
          }
          leaf process-rate {
            type uint16;
          }
        }
      }
      leaf ssh {
        type empty;
      }
    }
  }
  container network-controller {
    tailf:cli-add-mode;
    presence "true";
    container anycast-gateway {
      leaf mac {
        type string;
      }
    }
    leaf standby {
      type empty;
    }
    leaf dhcp-server {
      type inet:ipv4-address;
    }
    list switch {
      tailf:cli-suppress-mode;
      tailf:cli-delete-when-empty;
      key "mac ip-address";
      leaf mac {
        type string;
      }
      leaf ip-address {
        type inet:ipv4-address;
      }
    }
  }
  container netconf-yang {
    container agent {
      tailf:cli-add-mode;
      presence "true";
      leaf ssh {
        type empty;
      }
      container exclude-item {
        leaf ssh {
          type empty;
        }
        container yfw {
          container idle-timeout {
            presence "true";
          }
        }
      }
      container yfw {
        leaf idle-timeout {
          type uint32;
        }
      }
      container session {
        leaf limit {
          type uint8;
        }
        leaf idle-timeout {
          type uint16;
        }
        leaf absolute-timeout {
          type uint16;
        }
      }
      leaf rate-limit {
        type uint32;
      }
      container with-defaults-support {
        leaf enable {
          type empty;
        }
      }
    }
  }
  container nsr {
    leaf process-failures {
      type enumeration {
        enum switchover;
      }
    }
  }
  container ftp {
    container client {
      leaf passive {
        type empty;
      }
      container password {
        tailf:cli-compact-syntax;
        tailf:cli-sequence-commands;
        uses password-grouping {
          refine "secret";
        }
      }
      leaf username {
        type string;
      }
      list vrf {
        tailf:cli-suppress-mode;
        tailf:cli-delete-when-empty;
        key "name";
        leaf name {
          type string;
        }
        leaf passive {
          type empty;
        }
        container source-interface {
          tailf:cli-flatten-container;
          tailf:cli-compact-syntax;
          uses interface-name-grouping;
        }
        container password {
          tailf:cli-compact-syntax;
          tailf:cli-sequence-commands;
          uses password-grouping {
            refine "secret";
          }
        }
        leaf username {
          type string;
        }
      }
      container source-interface {
        tailf:cli-flatten-container;
        tailf:cli-compact-syntax;
        uses interface-name-grouping;
      }
    }
  }
  container icmp {
    container ipv4 {
      container source {
        leaf rfc {
          type empty;
        }
        leaf vrf {
          type empty;
        }
      }
      container rate-limit {
        container unreachable {
          leaf DF {
            type union {
              type uint32;
              type enumeration {
                enum disable;
              }
            }
          }
          leaf milliseconds {
            tailf:cli-drop-node-name;
            type union {
              type uint32;
              type enumeration {
                enum disable;
              }
            }
          }
        }
      }
    }
  }
  container ntp {
    tailf:cli-add-mode;
    container ipv4 {
      choice ipv4-choice {
        leaf dscp {
          type dscp-type;
        }
        leaf precedence {
          type precedence-type;
        }
      }
    }
    container ipv6 {
      choice ipv6-choice {
        leaf dscp {
          type dscp-type;
        }
        leaf precedence {
          type precedence-type;
        }
      }
    }
    leaf max-associations {
      type uint32;
    }
    list peer {
      tailf:cli-suppress-mode;
      tailf:cli-delete-when-empty;
      key "address";
      leaf address {
        type inet:host;
      }
      leaf af {
        tailf:cli-drop-node-name;
        tailf:cli-prefix-key;
        type enumeration {
          enum ipv4;
          enum ipv6;
        }
      }
    }
    container peer-vrf {
      tailf:cli-drop-node-name;
      list peer {
        tailf:cli-suppress-mode;
        tailf:cli-delete-when-empty;
        tailf:cli-compact-syntax;
        tailf:cli-sequence-commands {
          tailf:cli-reset-siblings;
        }
        key "vrf address";
        leaf vrf {
          type string;
        }
        leaf address {
          type inet:host;
        }
        leaf af {
          tailf:cli-drop-node-name;
          tailf:cli-optional-in-sequence;
          tailf:cli-prefix-key {
            tailf:cli-before-key "2";
          }
          type enumeration {
            enum ipv4;
            enum ipv6;
          }
        }
        leaf source {
          type string;
        }
      }
    }
    container server {
      uses ntp-server-grouping;
      list vrf {
        tailf:cli-suppress-mode;
        tailf:cli-delete-when-empty;
        tailf:cli-compact-syntax;
        key "name";
        leaf name {
          type string;
        }
        uses ntp-server-grouping;
      }
    }
    list access-group {
      tailf:cli-suppress-mode;
      tailf:cli-delete-when-empty;
      tailf:cli-compact-syntax;
      tailf:cli-sequence-commands {
        tailf:cli-reset-siblings;
      }
      key "version type";
      leaf version {
        type enumeration {
          enum ipv4;
          enum ipv6;
        }
      }
      leaf type {
        type enumeration {
          enum peer;
          enum query-only;
          enum serve;
          enum serve-only;
        }
      }
      leaf name {
        tailf:cli-drop-node-name;
        type string;
      }
    }
    container access-group-vrf {
      tailf:cli-drop-node-name;
      list access-group {
        tailf:cli-suppress-mode;
        tailf:cli-delete-when-empty;
        tailf:cli-compact-syntax;
        tailf:cli-sequence-commands {
          tailf:cli-reset-siblings;
        }
        key "vrf version type";
        leaf vrf {
          type string;
        }
        leaf version {
          type enumeration {
            enum ipv4;
            enum ipv6;
          }
        }
        leaf type {
          type enumeration {
            enum peer;
            enum query-only;
            enum serve;
            enum serve-only;
          }
        }
        leaf name {
          tailf:cli-drop-node-name;
          type string;
        }
      }
    }
    grouping ntp-interface-grouping {
      container broadcast {
        tailf:cli-compact-syntax;
        tailf:cli-delete-when-empty;
        presence "true";
        leaf key {
          type uint16;
        }
        leaf version {
          type uint8;
        }
      }
      container multicast {
        tailf:cli-delete-when-empty;
        presence "true";
        leaf version {
          type uint8;
        }
      }
      leaf disable {
        type empty;
      }
    }

    list interface {
      key "name";
      leaf name {
        type string;
      }
      uses ntp-interface-grouping;
    }
    container vrf-interface {
      tailf:cli-drop-node-name;
      list interface {
        key "name vrf";
        leaf name {
          type string;
        }
        leaf vrf {
          type string;
        }
        uses ntp-interface-grouping;
      }
    }
    leaf master {
      type uint16;
    }
    container source {
      list vrf {
        tailf:cli-suppress-mode;
        tailf:cli-delete-when-empty;
        tailf:cli-compact-syntax;
        key "name";
        leaf name {
          type string;
        }
        uses interface-name-grouping;
      }
      uses interface-name-grouping;
    }
    leaf update-calendar {
      type empty;
    }
    leaf log-internal-sync {
      type empty;
    }
    list authentication-key {
      tailf:cli-suppress-mode;
      tailf:cli-delete-when-empty;
      key "id";
      leaf id {
        type uint16;
      }
      container md5 {
        tailf:cli-compact-syntax;
        tailf:cli-sequence-commands;
        uses password-grouping {
          refine "secret";
        }
      }
    }
    leaf authenticate {
      type empty;
    }
    leaf-list trusted-key {
      type uint16;
    }
  }
  container rcp {
    container client {
      leaf username {
        type string;
      }
      container source-interface {
        uses interface-name-grouping;
      }
    }
  }
  container telnet {
    container ipv4 {
      container client {
        container source-interface {
          uses interface-name-grouping;
        }
      }
    }
    container ipv6 {
      container client {
        container source-interface {
          uses interface-name-grouping;
        }
      }
    }
    uses telnet-server-grouping;
    list vrf {
      tailf:cli-suppress-mode;
      tailf:cli-delete-when-empty;
      tailf:cli-compact-syntax;
      key "name";
      leaf name {
        type vrf-type;
      }
      uses telnet-server-grouping;
    }
  }
  container bfd {
    tailf:cli-add-mode;
    list interface {
      key "name";
      leaf name {
        type string;
      }
      leaf echo {
        type empty;
      }
      container echo-conf {
        tailf:cli-drop-node-name;
        container echo {
          leaf disable {
            type empty;
          }
          container ipv4 {
            leaf source {
              type inet:ipv4-address;
            }
          }
        }
      }
      leaf local-address {
        type union {
          type inet:ipv4-address;
          type inet:ipv6-address;
        }
      }
      leaf multiplier {
        type uint8;
      }
      leaf rx-interval {
        type uint32;
      }
      leaf tx-interval {
        type uint32;
      }
    }
    container multihop {
      leaf ttl-drop-threshold {
        type uint8;
      }
    }
    container multipath {
      container include {
        list location {
          tailf:cli-suppress-mode;
          tailf:cli-delete-when-empty;
          key "name";
          leaf name {
            type string;
          }
        }
      }
    }
    container bundle {
      container coexistence {
        leaf bob-blb {
          type enumeration {
            enum inherit;
            enum logical;
          }
        }
      }
    }
    container echo {
      leaf disable {
        type empty;
      }
    }
    container trap {
      container singlehop {
        leaf pre-mapped {
          type empty;
        }
      }
    }
    container dampening {
      leaf disable {
        type empty;
      }
      container bundle-member {
        leaf l3-only-mode {
          type empty;
        }
        leaf secondary-wait {
          type uint32;
        }
        leaf initial-wait {
          type uint32;
        }
        leaf maximum-wait {
          type uint32;
        }
      }
      leaf secondary-wait {
        type uint32;
      }
      leaf initial-wait {
        type uint32;
      }
      leaf maximum-wait {
        type uint32;
      }
      leaf threshold {
        type uint32;
      }
      container extensions {
        leaf down-monitoring {
          type empty;
        }
      }
    }
  }
  container sbfd {
    tailf:cli-add-mode;
    container remote-target {
      list ipv4 {
        key "address";
        leaf address {
          type inet:ipv4-address;
        }
        leaf remote-discriminator {
          type uint32;
        }
      }
    }
    container local-discriminator {
      list address-list {
        tailf:cli-drop-node-name;
        tailf:cli-suppress-mode;
        tailf:cli-delete-when-empty;
        key "ipv4";
        leaf ipv4 {
          type inet:ipv4-address;
        }
      }
      list id-list {
        tailf:cli-drop-node-name;
        tailf:cli-suppress-mode;
        tailf:cli-delete-when-empty;
        key "id";
        leaf id {
          type uint32;
        }
      }
      leaf dynamic {
        type empty;
      }
      list interface {
        tailf:cli-suppress-mode;
        tailf:cli-delete-when-empty;
        key "name";
        leaf name {
          type ifname;
        }
      }
    }
  }
  container tftp {
    container client {
      list vrf {
        tailf:cli-suppress-mode;
        tailf:cli-delete-when-empty;
        tailf:cli-compact-syntax;
        tailf:cli-sequence-commands {
          tailf:cli-reset-siblings;
        }
        key "name";
        leaf name {
          type string;
        }
        container source-interface {
          tailf:cli-flatten-container;
          tailf:cli-compact-syntax;
          uses interface-name-grouping;
        }
      }
      container source-interface {
        uses interface-name-grouping;
      }
      leaf retries {
        type uint16;
      }
      leaf timeout {
        type uint16;
      }
      leaf dscp {
        type dscp-type;
      }
    }
    uses tftp-server-grouping;
    list vrf {
      tailf:cli-suppress-mode;
      tailf:cli-delete-when-empty;
      tailf:cli-compact-syntax;
      key "name";
      leaf name {
        type string;
      }
      uses tftp-server-grouping;
    }
  }
  container nv {
    tailf:cli-add-mode;
    container optical {
      tailf:cli-add-mode;
      list satellite {
        key "id";
        leaf id {
          type uint32;
        }
        container ipv6 {
          leaf address {
            type inet:ipv6-address;
          }
        }
        container username {
          tailf:cli-compact-syntax;
          leaf name {
            tailf:cli-drop-node-name;
            type string;
          }
          leaf password {
            type string;
          }
        }
        container trunk {
          list slot {
            key "id";
            leaf id {
              type uint32;
            }
            leaf port {
              tailf:cli-hide-in-submode;
              type uint32;
            }
            leaf local-port {
              tailf:cli-hide-in-submode;
              type string;
            }
          }
        }
      }
    }
    container controller {
      uses controller-dwdm-grouping;
      list HundredGigE {
        tailf:cli-allow-join-with-key;
        key "id";
        leaf id {
          type string;
        }
        leaf admin-state {
          type enumeration {
            enum in-service;
            enum maintenance;
            enum out-of-service;
            enum in-service-config-allowed;
          }
        }
      }
    }
    list satellite {
      key "id";
      leaf id {
        type uint16;
      }
      leaf type {
        type string;
      }
      container ip {
        leaf address {
          type union {
            type inet:ipv4-address;
            type inet:ipv6-address;
          }
        }
      }
      container ipv4 {
        leaf address {
          type inet:ipv4-address;
        }
      }
      leaf device-name {
        type string;
      }
      container redundancy {
        tailf:cli-add-mode;
        leaf host-priority {
          type uint8;
        }
      }
      leaf description {
        tailf:cli-multi-value;
        type string;
      }
      leaf serial-number {
        type string;
      }
      container upgrade {
        leaf on-connect {
          type empty;
        }
      }
      container secret {
        tailf:cli-compact-syntax;
        tailf:cli-sequence-commands;
        leaf type {
          tailf:cli-drop-node-name;
          type enumeration {
            enum 0;
            enum 5;
          }
        }
        leaf secret {
          tailf:cli-drop-node-name;
          type string;
        }
      }
    }
  }
  container enable {
    container password;
    container secret {
      tailf:cli-compact-syntax;
      tailf:cli-sequence-commands;
      leaf type {
        tailf:cli-drop-node-name;
        type enumeration {
          enum 0;
          enum 5;
        }
      }
      leaf secret {
        tailf:cli-drop-node-name;
        type string;
      }
    }
  }
  uses username-grouping;
  container tacacs-server {
    list host {
      ordered-by user;
      key "name port";
      leaf name {
        type inet:host;
      }
      leaf port {
        type uint16;
      }
      container key {
        tailf:cli-compact-syntax;
        tailf:cli-sequence-commands;
        uses key-grouping {
          refine "key";
        }
      }
      leaf timeout {
        type uint16;
      }
      leaf holddown-time {
        type uint16;
      }
      leaf single-connection {
        type empty;
      }
      leaf single-connection-idle-timeout {
        type uint16;
      }
    }
    container ipv4 {
      leaf dscp {
        type dscp-type;
      }
    }
    container ipv6 {
      leaf dscp {
        type dscp-type;
      }
    }
    container key {
      tailf:cli-compact-syntax;
      tailf:cli-sequence-commands;
      uses key-grouping {
        refine "key";
      }
    }
    leaf timeout {
      type uint16;
    }
  }
  container tacacs {
    container source-interface {
      uses interface-name-grouping;
    }
    container source-interface-vrf {
      tailf:cli-drop-node-name;
      list source-interface {
        tailf:cli-suppress-mode;
        tailf:cli-delete-when-empty;
        tailf:cli-compact-syntax;
        tailf:cli-sequence-commands;
        key "vrf";
        leaf vrf {
          tailf:cli-suppress-range;
          type string;
        }
        leaf interface {
          tailf:cli-drop-node-name;
          tailf:cli-prefix-key;
          type string;
        }
      }
    }
  }
  container tpa {
    tailf:cli-add-mode;
    list vrf {
      key "name";
      leaf name {
        type string;
      }
      container address-family {
        container ipv4 {
          tailf:cli-add-mode;
          uses tpa-af-grouping;
        }
        container ipv6 {
          tailf:cli-add-mode;
          uses tpa-af-grouping;
        }
      }
      list east-west {
        tailf:cli-suppress-mode;
        tailf:cli-delete-when-empty;
        key "name";
        leaf name {
          type string;
        }
      }
    }
  }
  container aaa {
    leaf new-model {
      type empty;
    }
    container server {
      container radius {
        container dynamic-author {
          tailf:cli-add-mode;
          leaf port {
            type uint16;
          }
          container ignore {
            leaf server-key {
              type empty;
            }
          }
          list client {
            key "address vrf";
            leaf address {
              type inet:host;
            }
            leaf vrf {
              type vrf-type;
            }
            container server-key {
              tailf:cli-compact-syntax;
              tailf:cli-sequence-commands;
              uses key-grouping {
                refine "key";
              }
            }
          }
        }
      }
    }
    container group {
      container server {
        list radius {
          key "name";
          leaf name {
            type string;
          }
          leaf vrf {
            type string;
          }
          container authorization {
            container reply {
              tailf:cli-compact-syntax;
              tailf:cli-sequence-commands {
                tailf:cli-reset-siblings;
              }
              leaf action {
                tailf:cli-drop-node-name;
                type enumeration {
                  enum accept;
                  enum reject;
                }
              }
              leaf attr-name {
                tailf:cli-drop-node-name;
                type string;
              }
            }
            container request {
              tailf:cli-compact-syntax;
              tailf:cli-sequence-commands {
                tailf:cli-reset-siblings;
              }
              leaf action {
                tailf:cli-drop-node-name;
                type enumeration {
                  enum accept;
                  enum reject;
                }
              }
              leaf attr-name {
                tailf:cli-drop-node-name;
                type string;
              }
            }
          }
          container server {
            list name {
              key "name";
              leaf name {
                type string;
              }
            }
            list direct {
              tailf:cli-drop-node-name;
              tailf:cli-suppress-mode;
              tailf:cli-delete-when-empty;
              tailf:cli-compact-syntax;
              ordered-by user;
              key "name";
              leaf name {
                type inet:host;
              }
              leaf auth-port {
                type uint16;
              }
              leaf acct-port {
                type uint16;
              }
            }
          }
          container ip {
            container vrf {
              leaf forwarding {
                type string;
              }
            }
          }
          leaf deadtime {
            type uint16;
          }
          container source-interface {
            uses interface-name-grouping;
          }
          container throttle {
            tailf:cli-compact-syntax;
            leaf access {
              type uint16;
            }
            leaf access-timeout {
              type uint8;
            }
            leaf accounting {
              type uint16;
            }
          }
          container load-balance {
            container method {
              container least-outstanding {
                tailf:cli-compact-syntax;
                leaf batch-size {
                  type uint16;
                }
                leaf ignore-preferred-server {
                  type empty;
                }
              }
            }
          }
          list server-private {
            key "address auth-port acct-port";
            leaf address {
              type inet:host;
            }
            leaf auth-port {
              type uint16;
            }
            leaf acct-port {
              type uint16;
            }
            container key {
              tailf:cli-compact-syntax;
              tailf:cli-sequence-commands;
              uses key-grouping {
                refine "key";
              }
            }
          }
        }
        list tacacs {
          tailf:alt-name "tacacs+";
          key "name";
          leaf name {
            type string;
          }
          leaf-list server {
            ordered-by user;
            type inet:host;
          }
          leaf vrf {
            type string;
          }
          leaf holddown-time {
            type uint16;
          }
          list server-private {
            key "address port";
            leaf address {
              type inet:host;
            }
            leaf port {
              type uint16;
            }
            container key {
              tailf:cli-compact-syntax;
              tailf:cli-sequence-commands;
              uses key-grouping {
                refine "key";
              }
            }
            leaf timeout {
              type uint16;
            }
            leaf holddown-time {
              type uint16;
            }
            leaf single-connection {
              type empty;
            }
          }
        }
      }
    }
    container authentication {
      list login {
        tailf:cli-suppress-mode;
        tailf:cli-delete-when-empty;
        key "name";
        leaf name {
          type string;
        }
        leaf methods {
          tailf:cli-drop-node-name;
          tailf:cli-multi-value;
          type string;
        }
      }
      list subscriber {
        tailf:cli-suppress-mode;
        tailf:cli-delete-when-empty;
        key "name";
        leaf name {
          type string;
        }
        leaf methods {
          tailf:cli-drop-node-name;
          tailf:cli-multi-value;
          type string;
        }
      }
      list dot1x {
        tailf:cli-suppress-mode;
        tailf:cli-delete-when-empty;
        key "name";
        leaf name {
          type string;
        }
        leaf methods {
          tailf:cli-drop-node-name;
          tailf:cli-multi-value;
          type string;
        }
      }
    }
    container authorization {
      list commands {
        tailf:cli-suppress-mode;
        tailf:cli-delete-when-empty;
        key "name";
        leaf name {
          type string;
        }
        leaf methods {
          tailf:cli-drop-node-name;
          tailf:cli-multi-value;
          type string;
        }
      }
      list exec {
        tailf:cli-suppress-mode;
        tailf:cli-delete-when-empty;
        key "name";
        leaf name {
          type string;
        }
        leaf methods {
          tailf:cli-drop-node-name;
          tailf:cli-multi-value;
          type string;
        }
      }
      list eventmanager {
        tailf:cli-suppress-mode;
        tailf:cli-delete-when-empty;
        key "name";
        leaf name {
          type string;
        }
        leaf methods {
          tailf:cli-drop-node-name;
          tailf:cli-multi-value;
          type string;
        }
      }
      list subscriber {
        tailf:cli-suppress-mode;
        tailf:cli-delete-when-empty;
        key "name";
        leaf name {
          type string;
        }
        leaf methods {
          tailf:cli-drop-node-name;
          tailf:cli-multi-value;
          type string;
        }
      }
      list network {
        tailf:cli-suppress-mode;
        tailf:cli-delete-when-empty;
        key "name";
        leaf name {
          type string;
        }
        leaf methods {
          tailf:cli-drop-node-name;
          tailf:cli-multi-value;
          type string;
        }
      }
    }
    container accounting {
      container update {
        choice update-choice {
          leaf newinfo {
            type empty;
          }
          leaf periodic {
            type uint32;
          }
        }
      }
      list exec {
        tailf:cli-suppress-mode;
        tailf:cli-delete-when-empty;
        tailf:cli-compact-syntax;
        tailf:cli-sequence-commands {
          tailf:cli-reset-siblings;
        }
        key "name";
        leaf name {
          type string;
        }
        uses aaa-accounting-grouping;
      }
      list system {
        tailf:cli-suppress-mode;
        tailf:cli-delete-when-empty;
        tailf:cli-compact-syntax;
        tailf:cli-sequence-commands {
          tailf:cli-reset-siblings;
        }
        key "name";
        leaf name {
          type string;
        }
        leaf start-stop {
          type empty;
        }
        leaf group {
          tailf:cli-optional-in-sequence;
          type union {
            type string;
            type enumeration {
              enum radius;
              enum tacacs+;
            }
          }
        }
        container group2 {
          tailf:cli-drop-node-name;
          tailf:cli-flatten-container;
          tailf:cli-compact-syntax;
          tailf:cli-optional-in-sequence;
          leaf group {
            type string;
          }
        }
        leaf none {
          type empty;
        }
      }
      list network {
        tailf:cli-suppress-mode;
        tailf:cli-delete-when-empty;
        tailf:cli-compact-syntax;
        tailf:cli-sequence-commands {
          tailf:cli-reset-siblings;
        }
        key "name";
        leaf name {
          type string;
        }
        uses aaa-accounting-grouping;
      }
      list commands {
        tailf:cli-suppress-mode;
        tailf:cli-delete-when-empty;
        tailf:cli-compact-syntax;
        tailf:cli-sequence-commands {
          tailf:cli-reset-siblings;
        }
        key "name";
        leaf name {
          type string;
        }
        uses aaa-accounting-grouping;
      }
      list subscriber {
        tailf:cli-suppress-mode;
        tailf:cli-delete-when-empty;
        tailf:cli-compact-syntax;
        tailf:cli-sequence-commands {
          tailf:cli-reset-siblings;
        }
        key "name";
        leaf name {
          type string;
        }
        leaf broadcast {
          tailf:cli-optional-in-sequence;
          type empty;
        }
        leaf group {
          type string;
        }
        container group2 {
          tailf:cli-drop-node-name;
          tailf:cli-flatten-container;
          tailf:cli-compact-syntax;
          tailf:cli-optional-in-sequence;
          leaf group {
            type string;
          }
        }
      }
      list service {
        tailf:cli-suppress-mode;
        tailf:cli-delete-when-empty;
        key "name";
        leaf name {
          type string;
        }
        leaf methods {
          tailf:cli-drop-node-name;
          tailf:cli-multi-value;
          type string;
        }
      }
    }
    leaf session-id {
      type enumeration {
        enum common;
        enum unique;
      }
    }
    leaf default-taskgroup {
      type string;
    }
    container attribute {
      list format {
        key "name";
        leaf name {
          type string;
        }
        choice format-choice {
          container format-string {
            tailf:cli-compact-syntax;
            tailf:cli-sequence-commands {
              tailf:cli-reset-siblings;
            }
            leaf length {
              tailf:cli-optional-in-sequence;
              type uint8;
            }
            leaf format {
              tailf:cli-drop-node-name;
              type string;
            }
            leaf arguments {
              tailf:cli-drop-node-name;
              tailf:cli-multi-value;
              type string;
            }
          }
          leaf-list format-list {
            tailf:cli-drop-node-name;
            tailf:cli-flat-list-syntax;
            ordered-by user;
            type enumeration {
              enum mac-address;
              enum circuit-id;
              enum remote-id;
            }
          }
        }
      }
    }
    container radius {
      container attribute {
        container nas-port-id {
          uses aaa-radius-attribute-grouping;
        }
        container calling-station-id {
          uses aaa-radius-attribute-grouping;
        }
      }
    }
    container intercept {
      presence "true";
    }
    list password-policy {
      key "name";
      leaf name {
        type string;
      }
      leaf numeric {
        type uint8;
      }
      container lifetime {
        leaf months {
          type uint8;
        }
      }
      leaf lower-case {
        type uint8;
      }
      leaf min-length {
        type uint8;
      }
      leaf max-length {
        type uint8;
      }
      leaf upper-case {
        type uint8;
      }
      leaf special-char {
        type uint8;
      }
      container lockout-time {
        leaf minutes {
          type uint8;
        }
        leaf days {
          type uint8;
        }
        leaf hours {
          type uint8;
        }
        leaf seconds {
          type uint8;
        }
      }
      leaf min-char-change {
        type uint32;
      }
      container warn-interval {
        leaf days {
          type uint8;
        }
      }
      leaf restrict-username {
        type empty;
      }
      leaf restrict-old-count {
        type uint8;
      }
      leaf authen-max-attempts {
        type uint8;
      }
      leaf max-char-repetition {
        type uint8;
      }
    }
  }
  container watchdog {
    container threshold {
      container disk {
        tailf:cli-compact-syntax;
        tailf:cli-sequence-commands {
          tailf:cli-reset-siblings;
        }
        uses watchdog-threshold-grouping;
      }
      container disk-location {
        tailf:cli-drop-node-name;
        container disk {
          list location {
            tailf:cli-suppress-mode;
            tailf:cli-delete-when-empty;
            tailf:cli-compact-syntax;
            tailf:cli-sequence-commands {
              tailf:cli-reset-siblings;
            }
            key "name";
            leaf name {
              type string;
            }
            uses watchdog-threshold-grouping;
          }
        }
      }
      container memory {
        tailf:cli-compact-syntax;
        tailf:cli-sequence-commands {
          tailf:cli-reset-siblings;
        }
        uses watchdog-threshold-grouping;
      }
    }
  }

  grouping watchdog-threshold-grouping {
    leaf minor {
      type uint8;
    }
    leaf severe {
      type uint8;
    }
    leaf critical {
      type uint8;
    }
  }

  container cdp {
    presence "true";
    leaf timer {
      type uint8;
    }
    container log {
      container adjacency {
        leaf changes {
          type empty;
        }
      }
    }
    container advertise {
      leaf v1 {
        type empty;
      }
    }
    leaf holdtime {
      type uint8;
    }
  }
  container grpc {
    tailf:cli-add-mode;
    presence "true";
    leaf local-connection {
      type empty;
    }
    container aaa {
      container authorization {
        leaf exec {
          type string;
        }
      }
      container authentication {
        leaf login {
          type string;
        }
      }
    }
    leaf port {
      type uint16;
    }
    leaf no-tls {
      type empty;
    }
    leaf address-family {
      type enumeration {
        enum ipv4;
        enum ipv6;
        enum dual;
      }
    }
    container service-layer {
      tailf:cli-add-mode;
      presence "true";
    }
    leaf dscp {
      type dscp-type;
    }
    leaf vrf {
      type string;
    }
  }
  container fabric {
    container enable {
      leaf mode {
        type enumeration {
          enum A99-highbandwidth;
          enum highbandwidth;
        }
      }
    }
  }
  container ptp {
    tailf:cli-add-mode;
    presence "true";
    container clock {
      tailf:cli-add-mode;
      leaf domain {
        type uint8;
      }
      container profile {
        tailf:cli-compact-syntax;
        tailf:cli-sequence-commands {
          tailf:cli-reset-siblings;
        }
        leaf name {
          tailf:cli-drop-node-name;
          type enumeration {
            enum g.8265.1;
            enum g.8275.1;
            enum g.8275.2;
          }
        }
        leaf clock-type {
          type enumeration {
            enum T-BC;
            enum T-GM;
            enum T-TSC;
            enum master;
            enum slave;
          }
        }
      }
      leaf clock-class {
        type uint8;
      }
      leaf timescale {
        type enumeration {
          enum ARB;
          enum PTP;
        }
      }
      leaf time-source {
        type enumeration {
          enum GPS;
          enum NTP;
          enum PTP;
          enum atomic-clock;
          enum hand-set;
          enum internal-oscillator;
          enum other;
          enum terrestrial-radio;
        }
      }
    }
    list profile {
      key "name";
      leaf name {
        type string;
      }
      uses ptp-profile-grouping;
    }
    container utc-offset {
      list list {
        tailf:cli-drop-node-name;
        tailf:cli-suppress-mode;
        tailf:cli-delete-when-empty;
        key "name";
        leaf name {
          type union {
            type enumeration {
              enum baseline;
            }
            type string;
          }
        }
        leaf offset-value {
          tailf:cli-drop-node-name;
          type uint16;
        }
      }
    }
    container frequency {
      leaf priority {
        type uint8;
      }
    }
    container time-of-day {
      leaf priority {
        type uint8;
      }
    }
    leaf physical-layer-frequency {
      type empty;
    }
    container log {
      tailf:cli-add-mode;
      container servo {
        leaf events {
          type empty;
        }
      }
      container best-master-clock {
        leaf changes {
          type empty;
        }
      }
    }
    container virtual-port {
      tailf:cli-add-mode;
      presence "true";
      leaf offset-scaled-log-variance {
        type uint16;
      }
      leaf clock-class {
        type uint8;
      }
      leaf clock-accuracy {
        type uint8;
      }
      leaf local-priority {
        type uint8;
      }
    }
    container uncalibrated-clock-class {
      tailf:cli-compact-syntax;
      tailf:cli-sequence-commands {
        tailf:cli-reset-siblings;
      }
      leaf class {
        tailf:cli-drop-node-name;
        type uint8;
      }
      leaf unless-from-holdover {
        type empty;
      }
    }
    leaf holdover-spec-duration {
      type uint32;
    }
    leaf holdover-spec-clock-class {
      type uint8;
    }
    leaf holdover-spec-traceable-override {
      type empty;
    }
  }
  container tcp {
    leaf mss {
      type uint16;
    }
    leaf selective-ack {
      type empty;
    }
    container path-mtu-discovery {
      tailf:cli-delete-when-empty;
      presence "true";
      leaf age-timer {
        type union {
          type uint8;
          type enumeration {
            enum infinite;
          }
        }
      }
    }
    leaf timestamp {
      type empty;
    }
    container directory {
      tailf:cli-compact-syntax;
      tailf:cli-sequence-commands {
        tailf:cli-reset-siblings;
      }
      leaf directory {
        tailf:cli-drop-node-name;
        type string;
      }
      leaf files {
        tailf:cli-break-sequence-commands;
        type uint16;
      }
      leaf size {
        type uint32;
      }
    }
    leaf window-size {
      type uint32;
    }
    leaf synwait-time {
      type uint8;
    }
    leaf accept-rate {
      type uint16;
    }
    container ao {
      tailf:cli-add-mode;
      presence "true";
      list keychain {
        key "name";
        leaf name {
          type string;
        }
        list key {
          tailf:cli-suppress-mode;
          tailf:cli-delete-when-empty;
          tailf:cli-compact-syntax;
          tailf:cli-sequence-commands {
            tailf:cli-reset-siblings;
          }
          key "id";
          leaf id {
            type string;
          }
          leaf SendID {
            type uint8;
          }
          leaf ReceiveID {
            type uint8;
          }
        }
      }
    }
    container num-thread {
      tailf:cli-compact-syntax;
      tailf:cli-sequence-commands {
        tailf:cli-reset-siblings;
      }
      leaf ingress-threads {
        tailf:cli-drop-node-name;
        type uint8;
      }
      leaf max-threads {
        tailf:cli-drop-node-name;
        type uint8;
      }
    }
    leaf receive-queue {
      type uint16;
    }
  }
  container line {
    container console {
      tailf:cli-add-mode;
      uses line-grouping;
    }
    container default {
      tailf:cli-add-mode;
      uses line-grouping;
    }
    list template {
      key "name";
      leaf name {
        type string;
      }
      uses line-grouping;
    }
  }
  container pool {
    list vrf {
      key "vrf ipv4";
      leaf vrf {
        type string;
      }
      leaf ipv4 {
        type string;
      }
      list network {
        tailf:cli-suppress-mode;
        tailf:cli-delete-when-empty;
        tailf:cli-compact-syntax;
        key "prefix";
        leaf prefix {
          type ipv4-prefix;
        }
        leaf default-router {
          type inet:ipv4-address;
        }
        leaf block {
          type empty;
        }
      }
      list address-range {
        tailf:cli-suppress-mode;
        tailf:cli-delete-when-empty;
        tailf:cli-compact-syntax;
        tailf:cli-sequence-commands {
          tailf:cli-reset-siblings;
        }
        key "first_range";
        leaf first_range {
          type inet:ipv4-address;
        }
        leaf last_range {
          tailf:cli-drop-node-name;
          type inet:ipv4-address;
        }
        leaf block {
          type empty;
        }
      }
      list exclude {
        tailf:cli-suppress-mode;
        tailf:cli-delete-when-empty;
        key "first";
        leaf first {
          tailf:cli-suppress-range;
          type inet:ipv4-address;
        }
        leaf last {
          tailf:cli-drop-node-name;
          type inet:ipv4-address;
        }
      }
      container utilization-mark {
        tailf:cli-compact-syntax;
        tailf:cli-sequence-commands;
        leaf high {
          type uint8;
        }
        leaf low {
          type uint8;
        }
      }
    }
    container pool-ipv6 {
      tailf:cli-drop-node-name;
      list vrf {
        key "vrf ipv6";
        leaf vrf {
          type string;
        }
        leaf ipv6 {
          type string;
        }
        list address-range {
          tailf:cli-suppress-mode;
          tailf:cli-delete-when-empty;
          tailf:cli-compact-syntax;
          tailf:cli-sequence-commands {
            tailf:cli-reset-siblings;
          }
          key "first_range";
          leaf first_range {
            tailf:cli-suppress-range;
            type inet:ipv6-address;
          }
          leaf last_range {
            tailf:cli-drop-node-name;
            type inet:ipv6-address;
          }
          leaf block {
            type empty;
          }
        }
        leaf prefix-length {
          type uint8;
        }
        list prefix-range {
          tailf:cli-suppress-mode;
          tailf:cli-delete-when-empty;
          key "first last";
          leaf first {
            tailf:cli-suppress-range;
            type inet:ipv6-address;
          }
          leaf last {
            tailf:cli-suppress-range;
            type inet:ipv6-address;
          }
        }
        leaf network {
          type tailf:ipv6-address-and-prefix-length;
        }
        container utilization-mark {
          tailf:cli-compact-syntax;
          tailf:cli-sequence-commands;
          leaf high {
            type uint8;
          }
          leaf low {
            type uint8;
          }
        }
      }
    }
  }
  container vty-pool {
    container default {
      tailf:cli-compact-syntax;
      tailf:cli-sequence-commands;
      uses vty-pool-grouping;
    }
    container eem {
      tailf:cli-compact-syntax;
      tailf:cli-sequence-commands;
      uses vty-pool-grouping;
    }
    list pool-name-list {
      tailf:cli-drop-node-name;
      tailf:cli-suppress-mode;
      tailf:cli-delete-when-empty;
      tailf:cli-compact-syntax;
      tailf:cli-sequence-commands;
      key "pool-name";
      leaf pool-name {
        type string;
      }
      uses vty-pool-grouping;
    }
  }
  container aps {
    list group {
      key "id";
      leaf id {
        type uint8;
      }
      leaf revert {
        type uint8;
      }
      container timers {
        tailf:cli-compact-syntax;
        tailf:cli-sequence-commands {
          tailf:cli-reset-siblings;
        }
        leaf hello {
          tailf:cli-drop-node-name;
          type uint8;
        }
        leaf hold {
          tailf:cli-drop-node-name;
          type uint8;
        }
      }
      list channel {
        tailf:cli-suppress-mode;
        tailf:cli-delete-when-empty;
        tailf:cli-compact-syntax;
        tailf:cli-sequence-commands {
          tailf:cli-reset-siblings;
        }
        key "id location";
        leaf id {
          type uint8;
        }
        leaf location {
          type enumeration {
            enum local;
            enum remote;
          }
        }
        leaf preconfigure {
          tailf:cli-optional-in-sequence;
          type empty;
        }
        leaf data {
          tailf:cli-drop-node-name;
          type union {
            type string;
            type inet:ipv4-address;
          }
        }
      }
    }
    leaf rprplus {
      type empty;
    }
  }
  container platform {
    container ip {
      container cef {
        leaf load-sharing {
          type enumeration {
            enum dst-only;
            enum full;
            enum ip-only;
          }
        }
      }
    }
    container qos {
      leaf qos-10g-only {
        tailf:alt-name "10g-only";
        type empty;
      }
      list protocol {
        tailf:cli-suppress-mode;
        tailf:cli-delete-when-empty;
        tailf:cli-compact-syntax;
        key "proto";
        leaf proto {
          type enumeration {
            enum isis;
            enum eigrp;
            enum ldp;
            enum ospf;
            enum rip;
            enum bgp;
            enum hsrp;
            enum bfd;
            enum ospfv3;
            enum bgpv2;
            enum ripng;
            enum neigh-discover;
            enum wlccp;
            enum rsvp;
            enum rsvpv6;
            enum arp;
            enum gre;
            enum mpls;
          }
        }
        choice proto-choice {
          leaf pass-through {
            type empty;
          }
          container police {
            tailf:cli-compact-syntax;
            tailf:cli-sequence-commands;
            leaf bit-rate {
              tailf:cli-drop-node-name;
              type uint64;
            }
            leaf burst {
              tailf:cli-drop-node-name;
              type uint32;
            }
          }
          container precedence {
            tailf:cli-compact-syntax;
            tailf:cli-sequence-commands;
            leaf cos {
              tailf:cli-drop-node-name;
              type uint8;
            }
            leaf bit-rate {
              tailf:cli-drop-node-name;
              type uint64;
            }
            leaf burst {
              tailf:cli-drop-node-name;
              type uint32;
            }
          }
        }
      }
    }
  }

  grouping control-plane-grouping {
    container control-plane {
      tailf:cli-add-mode;
      container management-plane {
        tailf:cli-add-mode;
        container inband {
          tailf:cli-add-mode;
          list interface {
            key "name";
            leaf name {
              type string;
            }
            list allow {
              tailf:cli-suppress-mode;
              tailf:cli-delete-when-empty;
              key "proto";
              leaf proto {
                type control-plane-proto;
              }
            }
            uses mpp-ioband-if-allow-peer-grouping;
          }
        }
        container out-of-band {
          tailf:cli-add-mode;
          leaf vrf {
            type string;
          }
          list interface {
            key "name";
            leaf name {
              type string;
            }
            list allow {
              tailf:cli-suppress-mode;
              tailf:cli-delete-when-empty;
              key "proto";
              leaf proto {
                type control-plane-proto;
              }
            }
            uses mpp-ioband-if-allow-peer-grouping;
          }
        }
      }
      container local {
        container control-packets {
          tailf:cli-add-mode;
          container copy {
            container precedence {
              leaf qos-group {
                type empty;
              }
            }
          }
        }
      }
    }
  }

  uses control-plane-grouping;

  typedef control-plane-proto {
    type enumeration {
      enum HTTP;
      enum NETCONF;
      enum SNMP;
      enum SSH;
      enum TFTP;
      enum Telnet;
      enum XML;
      enum all;
    }
  }

  grouping mpp-ioband-if-allow-peer-grouping {
    container allow-peer {
      tailf:cli-drop-node-name;
      container allow {
        container HTTP {
          uses mpp-ioband-if-allow-addr-grouping;
        }
        container NETCONF {
          uses mpp-ioband-if-allow-addr-grouping;
        }
        container SNMP {
          uses mpp-ioband-if-allow-addr-grouping;
        }
        container SSH {
          uses mpp-ioband-if-allow-addr-grouping;
        }
        container TFTP {
          uses mpp-ioband-if-allow-addr-grouping;
        }
        container Telnet {
          uses mpp-ioband-if-allow-addr-grouping;
        }
        container XXML {
          tailf:alt-name "XML";
          uses mpp-ioband-if-allow-addr-grouping;
        }
        container all {
          uses mpp-ioband-if-allow-addr-grouping;
        }
      }
    }
  }

  grouping mpp-ioband-if-allow-addr-grouping {
    container peer {
      tailf:cli-add-mode;
      container address {
        list ipv4 {
          tailf:cli-suppress-mode;
          tailf:cli-delete-when-empty;
          key "prefix";
          leaf prefix {
            type union {
              type inet:ipv4-address;
              type ipv4-prefix;
            }
          }
        }
        list ipv6 {
          tailf:cli-suppress-mode;
          tailf:cli-delete-when-empty;
          key "prefix";
          leaf prefix {
            type union {
              type inet:ipv6-address;
              type tailf:ipv6-address-and-prefix-length;
            }
          }
        }
      }
    }
  }

  container ip {
    container domain-lookup {
      leaf do-lookup {
        tailf:cli-drop-node-name;
        type boolean;
      }
      leaf nsap {
        type empty;
      }
    }
    leaf domain-name {
      type string;
    }
    container forward-protocol {
      leaf nd {
        type empty;
      }
      leaf sdns {
        type empty;
      }
      leaf spanning-tree {
        type empty;
      }
      leaf turbo-flood {
        type empty;
      }
      leaf udp {
        type empty;
      }
    }
    container http {
      leaf server {
        type boolean;
      }
      leaf secure-server {
        type boolean;
      }
    }
    container pim {
      container ssm {
        choice ssm-choice {
          leaf default {
            type empty;
          }
          leaf range {
            type union {
              type uint8;
              type string;
            }
          }
        }
      }
    }
    container route {
      container vrf {
        tailf:cli-compact-syntax;
        tailf:cli-sequence-commands;
        leaf name {
          tailf:cli-drop-node-name;
          type string;
        }
        leaf dest {
          tailf:cli-drop-node-name;
          type inet:ipv4-address;
        }
        leaf dest-mask {
          tailf:cli-drop-node-name;
          type inet:ipv4-address;
        }
        choice vrf-choice {
          leaf forwarding-address {
            tailf:cli-drop-node-name;
            type inet:ipv4-address;
          }
          leaf GigabitEthernet {
            tailf:cli-allow-join-with-value;
            type string;
          }
        }
      }
    }
    container multicast-routing {
      presence "true";
      leaf-list vrf {
        type string;
      }
    }
    container multicast {
      list vrf {
        tailf:cli-suppress-mode;
        tailf:cli-delete-when-empty;
        tailf:cli-compact-syntax;
        key "id";
        leaf id {
          type string;
        }
        container route-limit {
          tailf:cli-sequence-commands {
            tailf:cli-reset-siblings;
          }
          tailf:cli-compact-syntax;
          leaf nr-routes {
            tailf:cli-drop-node-name;
            type uint32;
          }
          leaf threshold {
            tailf:cli-drop-node-name;
            type uint32;
          }
        }
      }
    }
    container tftp {
      container source-interface {
        uses interface-name-grouping;
      }
    }
    container ssh {
      leaf logging {
        type enumeration {
          enum events;
        }
      }
      leaf version {
        type uint8;
      }
    }
  }
  container mirror {
    list location {
      tailf:cli-suppress-mode;
      tailf:cli-delete-when-empty;
      key "name";
      leaf name {
        tailf:cli-multi-word-key;
        type string;
      }
    }
  }
  container ipv4 {
    container netmask-format {
      leaf bit-count {
        type empty;
      }
    }
    container assembler {
      leaf max-packets {
        type uint8;
      }
      leaf timeout {
        type uint8;
      }
    }
    container access-list {
      container log-update {
        leaf rate {
          type uint16;
        }
        leaf threshold {
          type uint32;
        }
      }
      list named-acl {
        tailf:cli-drop-node-name;
        key "name";
        leaf name {
          type string;
        }
        uses apply-group-grouping;
        list rule {
          tailf:cli-drop-node-name;
          tailf:cli-suppress-mode;
          tailf:cli-delete-when-empty;
          key "id";
          leaf id {
            type uint32;
          }
          leaf line {
            tailf:cli-drop-node-name;
            tailf:cli-multi-value;
            type string;
          }
        }
      }
    }
    container unnumbered {
      container mpls {
        container traffic-eng {
          uses interface-name-grouping;
        }
      }
    }
    container virtual {
      container address {
        list address-list {
          tailf:cli-drop-node-name;
          tailf:cli-suppress-mode;
          tailf:cli-delete-when-empty;
          key "address mask";
          leaf address {
            type inet:ipv4-address;
          }
          leaf mask {
            type inet:ipv4-address;
          }
        }
        list cidr-address-list {
          tailf:cli-drop-node-name;
          tailf:cli-suppress-mode;
          tailf:cli-delete-when-empty;
          key "prefix";
          leaf prefix {
            type ipv4-prefix;
          }
        }
        leaf use-as-src-addr {
          type empty;
        }
        list vrf {
          tailf:cli-suppress-mode;
          tailf:cli-delete-when-empty;
          key "name";
          leaf name {
            type string;
          }
          list address-list {
            tailf:cli-drop-node-name;
            tailf:cli-suppress-mode;
            tailf:cli-delete-when-empty;
            key "address mask";
            leaf address {
              type inet:ipv4-address;
            }
            leaf mask {
              type inet:ipv4-address;
            }
          }
          list cidr-address-list {
            tailf:cli-drop-node-name;
            tailf:cli-suppress-mode;
            tailf:cli-delete-when-empty;
            key "prefix";
            leaf prefix {
              type ipv4-prefix;
            }
          }
        }
      }
    }
    uses ipv4-ipv6-common-grouping;
    leaf source-route {
      type empty;
    }
  }
  container ipv6 {
    container assembler {
      leaf max-packets {
        type uint8;
      }
      leaf timeout {
        type uint8;
      }
    }
    leaf unicast-routing {
      type empty;
    }
    container icmp {
      container error-interval {
        tailf:cli-compact-syntax;
        tailf:cli-sequence-commands {
          tailf:cli-reset-siblings;
        }
        leaf interval {
          tailf:cli-drop-node-name;
          type uint32;
        }
        leaf size {
          tailf:cli-drop-node-name;
          type uint16;
        }
      }
    }
    leaf hop-limit {
      type uint8;
    }
    container path-mtu {
      leaf enable {
        type empty;
      }
      leaf timeout {
        type uint8;
      }
    }
    container virtual {
      container address {
        leaf address {
          tailf:cli-drop-node-name;
          type tailf:ipv6-address-and-prefix-length;
        }
        leaf use-as-src-addr {
          type empty;
        }
        list vrf {
          tailf:cli-suppress-mode;
          tailf:cli-delete-when-empty;
          key "name";
          leaf name {
            type string;
          }
          leaf address {
            tailf:cli-drop-node-name;
            type tailf:ipv6-address-and-prefix-length;
          }
        }
      }
    }
    container access-list {
      container log-update {
        leaf rate {
          type uint16;
        }
        leaf threshold {
          type uint32;
        }
      }
      list named-acl {
        tailf:cli-drop-node-name;
        key "name";
        leaf name {
          type string;
        }
        list rule {
          tailf:cli-drop-node-name;
          tailf:cli-suppress-mode;
          tailf:cli-delete-when-empty;
          key "id";
          leaf id {
            type uint32;
          }
          leaf line {
            tailf:cli-drop-node-name;
            tailf:cli-multi-value;
            type string;
          }
        }
      }
    }
    container multicast {
      container rpf {
        container backoff {
          tailf:cli-compact-syntax;
          tailf:cli-sequence-commands {
            tailf:cli-reset-siblings;
          }
          leaf initial {
            tailf:cli-drop-node-name;
            type uint16;
          }
          leaf max-backoff-delay {
            tailf:cli-drop-node-name;
            type uint16;
          }
        }
        leaf use-bgp {
          type empty;
        }
      }
    }
    uses ipv4-ipv6-common-grouping;
    container mobile {
      list pmipv6-domain {
        key "name";
        leaf name {
          type string;
        }
        list nai {
          key "name";
          leaf name {
            type string;
          }
          leaf network {
            type string;
          }
          leaf service {
            type enumeration {
              enum dual;
              enum ipv4;
              enum ipv6;
            }
          }
          leaf customer {
            type string;
          }
        }
      }
      list pmipv6-lma {
        key "name domain";
        leaf name {
          type string;
        }
        leaf domain {
          type string;
        }
        uses ipv6-mobile-heartbeat-grouping;
        container aaa {
          container accounting {
            tailf:cli-delete-when-empty;
            presence "true";
            leaf interim {
              type uint32;
            }
          }
        }
        container bce {
          leaf maximum {
            type uint32;
          }
          leaf lifetime {
            type uint16;
          }
        }
        container dscp {
          tailf:cli-compact-syntax;
          tailf:cli-sequence-commands {
            tailf:cli-reset-siblings;
          }
          leaf control-plane {
            type uint8;
          }
          leaf force {
            type empty;
          }
        }
        container redistribute {
          leaf home-address {
            type enumeration {
              enum disable;
              enum host-prefix;
            }
          }
        }
        container dynamic {
          container mag {
            leaf learning {
              type empty;
            }
          }
        }
        container enforce {
          leaf heartbeat-to-mag {
            type empty;
          }
        }
        container mobility-service {
          container mobile-local-loop {
            tailf:cli-add-mode;
            presence "true";
            container ignore {
              leaf home-address {
                type empty;
              }
            }
            uses ipv6-mobile-mnp-grouping;
            list customer {
              key "name vrf";
              leaf name {
                type string;
              }
              leaf vrf {
                type vrf-type;
              }
              container bce {
                leaf lifetime {
                  type uint16;
                }
              }
              container gre-key {
                leaf symmetric {
                  type uint32;
                }
              }
              container bandwidth {
                leaf aggregate {
                  type uint32;
                }
              }
              uses ipv6-mobile-mnp-grouping;
              container network {
                list authorized {
                  key "name";
                  leaf name {
                    type string;
                  }
                  container pool {
                    container mobile-node {
                      container ipv4 {
                        tailf:cli-compact-syntax;
                        tailf:cli-sequence-commands;
                        leaf start-address {
                          type inet:ipv4-address;
                        }
                        leaf pool-prefix {
                          type uint8;
                        }
                      }
                      container ipv6 {
                        tailf:cli-compact-syntax;
                        tailf:cli-sequence-commands;
                        leaf start-address {
                          type inet:ipv6-address;
                        }
                        leaf pool-prefix {
                          type uint8;
                        }
                      }
                    }
                    container mobile-network {
                      container ipv4 {
                        tailf:cli-compact-syntax;
                        tailf:cli-sequence-commands;
                        leaf start-address {
                          type inet:ipv4-address;
                        }
                        leaf pool-prefix {
                          type uint8;
                        }
                        leaf network-prefix {
                          type uint8;
                        }
                      }
                      container ipv6 {
                        tailf:cli-compact-syntax;
                        tailf:cli-sequence-commands;
                        leaf start-address {
                          type inet:ipv6-address;
                        }
                        leaf pool-prefix {
                          type uint8;
                        }
                        leaf network-prefix {
                          type uint8;
                        }
                      }
                    }
                  }
                }
                leaf unauthorized {
                  type empty;
                }
              }
              container auth-option {
                tailf:cli-compact-syntax;
                tailf:cli-sequence-commands {
                  tailf:cli-reset-siblings;
                }
                leaf spi {
                  type string;
                }
                container key {
                  tailf:cli-flatten-container;
                  tailf:cli-compact-syntax;
                  leaf ascii {
                    type string;
                  }
                }
              }
              container mobile-route {
                leaf admin-distance {
                  type uint8;
                }
              }
              container transport {
                list vrf {
                  key "name";
                  leaf name {
                    type string;
                  }
                  container address {
                    leaf ipv4 {
                      type inet:ipv4-address;
                    }
                    leaf ipv6 {
                      type inet:ipv6-address;
                    }
                  }
                }
              }
              uses ipv6-mobile-heartbeat-grouping;
            }
          }
        }
        container pgw {
          container subscriber {
            leaf continuity {
              type empty;
            }
          }
        }
        container mobile-route {
          leaf admin-distance {
            type uint8;
          }
        }
      }
    }
  }
  container frequency {
    container synchronization {
      tailf:cli-add-mode;
      presence "true";
      container quality {
        container itu-t {
          tailf:cli-compact-syntax;
          tailf:cli-sequence-commands {
            tailf:cli-reset-siblings;
          }
          leaf option {
            type enumeration {
              enum 1;
              enum 2;
            }
          }
          leaf generation {
            type enumeration {
              enum 1;
              enum 2;
            }
          }
        }
      }
      container clock-interface {
        leaf timing-mode {
          type enumeration {
            enum independent;
            enum system;
          }
        }
      }
      container system {
        leaf timing-mode {
          type enumeration {
            enum clock-only;
            enum line-only;
          }
        }
      }
      container log {
        leaf selection {
          type enumeration {
            enum changes;
            enum errors;
          }
        }
      }
    }
  }
  container cem {
    list class {
      key "name";
      leaf name {
        type string;
      }
      leaf payload {
        type uint16;
      }
      leaf dejitter {
        type union {
          type uint32;
          type enumeration {
            enum best-match;
          }
        }
      }
    }
  }
  container error-disable {
    container recovery {
      container cause {
        container stp-bpdu-guard {
          presence "true";
        }
        container stp-legacy-bpdu {
          presence "true";
        }
        container link-oam-miswired {
          presence "true";
        }
        container link-oam-dying-gasp {
          presence "true";
        }
        container link-oam-link-fault {
          presence "true";
        }
        container link-oam-session-down {
          presence "true";
        }
        container link-oam-critical-event {
          presence "true";
        }
        container link-oam-discovery-timeout {
          presence "true";
        }
        container link-oam-threshold-breached {
          presence "true";
        }
        container link-oam-capabilities-conflict {
          presence "true";
        }
        container link-oam-dampening {
          presence "true";
        }
        container udld-timeout {
          tailf:cli-delete-when-empty;
          presence "true";
          leaf interval {
            type uint32;
          }
        }
      }
    }
  }
  container vtp {
    leaf mode {
      type enumeration {
        enum client;
        enum off;
        enum server;
        enum transparent;
      }
    }
  }
  container arp {
    leaf inner-cos {
      type uint8;
    }
    leaf outer-cos {
      type uint8;
    }
    uses arp-grouping;
    container redundancy {
      tailf:cli-add-mode;
      presence "true";
      list group {
        key "id";
        leaf id {
          type uint8;
        }
        leaf peer {
          type inet:ipv4-address;
        }
        container source-interface {
          uses interface-name-grouping;
        }
        container interface-list {
          tailf:cli-add-mode;
          presence "true";
          list interface {
            tailf:cli-suppress-mode;
            tailf:cli-delete-when-empty;
            key "name";
            leaf name {
              type string;
            }
            leaf id {
              type uint16;
            }
          }
        }
      }
    }
    leaf max-entries {
      type uint32;
    }
    list vrf {
      tailf:cli-suppress-mode;
      tailf:cli-delete-when-empty;
      tailf:cli-compact-syntax;
      key "name";
      leaf name {
        type string;
      }
      uses arp-grouping;
    }
  }
  container cinetd {
    leaf rate-limit {
      type uint8;
    }
  }
  container adt {
    leaf enable {
      type empty;
    }
  }
  container xxml {
    tailf:alt-name "xml";
    container tty-agent {
      tailf:cli-drop-node-name;
      container agent {
        container tty {
          tailf:cli-add-mode;
          presence "true";
          container iteration {
            leaf off {
              type empty;
            }
          }
          leaf ipv4 {
            type enumeration {
              enum enable;
              enum disable;
            }
          }
          leaf ipv6 {
            type enumeration {
              enum enable;
              enum disable;
            }
          }
          container session {
            leaf timeout {
              type uint16;
            }
          }
        }
      }
    }
    container ssl-agent {
      tailf:cli-drop-node-name;
      container agent {
        container ssl {
          tailf:cli-add-mode;
          presence "true";
          container session {
            leaf timeout {
              type uint16;
            }
          }
          container iteration {
            choice iteration-choice {
              leaf off {
                type empty;
              }
              container on {
                leaf size {
                  type uint32;
                }
              }
            }
          }
        }
      }
    }
    container other-agent {
      tailf:cli-drop-node-name;
      container agent {
        tailf:cli-add-mode;
        presence "true";
        leaf ipv4 {
          type enumeration {
            enum enable;
            enum disable;
          }
        }
        leaf ipv6 {
          type enumeration {
            enum enable;
            enum disable;
          }
        }
        container iteration {
          choice iteration-choice {
            container on {
              leaf size {
                type uint32;
              }
            }
            leaf off {
              type empty;
            }
          }
        }
      }
    }
  }
  container switch {
    container virtual {
      list domain {
        key "id";
        leaf id {
          type uint8;
        }
        leaf mac-address {
          type union {
            type string;
            type enumeration {
              enum use-virtual;
            }
          }
        }
        container switch {
          leaf mode {
            type enumeration {
              enum virtual;
            }
          }
          list nr {
            tailf:cli-drop-node-name;
            tailf:cli-suppress-mode;
            tailf:cli-delete-when-empty;
            key "id";
            leaf id {
              type uint8;
            }
            leaf location {
              type string;
            }
            leaf priority {
              type uint8;
            }
          }
        }
      }
    }
  }
  container password6 {
    container encryption {
      leaf aes {
        type empty;
      }
    }
  }
  container key {
    list chain {
      key "name";
      leaf name {
        tailf:cli-suppress-range;
        type string;
      }
      container macsec {
        tailf:cli-add-mode;
        presence "true";
        list key {
          key "id";
          leaf id {
            tailf:cli-suppress-range;
            type string;
          }
          container key-string {
            tailf:cli-compact-syntax;
            tailf:cli-sequence-commands;
            leaf type {
              tailf:cli-drop-node-name;
              tailf:cli-optional-in-sequence;
              type enumeration {
                enum clear;
                enum password;
                enum password6;
              }
            }
            leaf secret {
              tailf:cli-drop-node-name;
              type string;
            }
            leaf cryptographic-algorithm {
              type enumeration {
                enum aes-128-cmac;
                enum aes-256-cmac;
              }
            }
          }
          container lifetime {
            tailf:cli-compact-syntax;
            tailf:cli-sequence-commands {
              tailf:cli-reset-siblings;
            }
            uses key-duration-grouping;
          }
        }
      }
      list key {
        key "id";
        leaf id {
          tailf:cli-suppress-range;
          type uint32;
        }
        container accept-lifetime {
          tailf:cli-compact-syntax;
          tailf:cli-sequence-commands {
            tailf:cli-reset-siblings;
          }
          leaf local {
            tailf:cli-optional-in-sequence;
            type empty;
          }
          uses key-duration-grouping;
        }
        container key-string {
          tailf:cli-compact-syntax;
          tailf:cli-sequence-commands;
          leaf type {
            tailf:cli-drop-node-name;
            tailf:cli-optional-in-sequence;
            type enumeration {
              enum clear;
              enum password;
              enum password6;
            }
          }
          leaf password {
            tailf:cli-drop-node-name;
            type string;
          }
        }
        container send-lifetime {
          tailf:cli-compact-syntax;
          tailf:cli-sequence-commands {
            tailf:cli-reset-siblings;
          }
          leaf local {
            tailf:cli-optional-in-sequence;
            type empty;
          }
          uses key-duration-grouping;
        }
        leaf cryptographic-algorithm {
          type enumeration {
            enum HMAC-MD5;
            enum HMAC-SHA1-12;
            enum HMAC-SHA1-20;
            enum MD5;
            enum SHA-1;
            enum HMAC-SHA1-96;
            enum AES-128-CMAC-96;
            enum HMAC-SHA-256;
          }
        }
      }
      leaf accept-tolerance {
        type union {
          type uint32;
          type enumeration {
            enum infinite;
          }
        }
      }
    }
  }
  container dhcp {
    container ipv4 {
      tailf:cli-add-mode;
      presence "true";
      list vrf {
        tailf:cli-suppress-mode;
        tailf:cli-delete-when-empty;
        tailf:cli-compact-syntax;
        tailf:cli-sequence-commands;
        key "name";
        leaf name {
          type string;
        }
        leaf type {
          tailf:cli-drop-node-name;
          type enumeration {
            enum relay;
            enum proxy;
          }
        }
        leaf profile {
          type string;
        }
      }
      list profile {
        key "name type";
        leaf name {
          type string;
        }
        leaf type {
          type enumeration {
            enum proxy;
            enum relay;
            enum server;
            enum snoop;
            enum base;
            enum cnbng;
          }
        }
        leaf trusted {
          type empty;
        }
        leaf allow-move {
          type empty;
        }
        container aaa {
          container dhcp-option {
            leaf force-insert {
              type empty;
            }
          }
        }
        leaf pool {
          type string;
        }
        leaf-list dns-server {
          tailf:cli-flat-list-syntax;
          ordered-by user;
          type inet:ipv4-address;
        }
        leaf-list default-router {
          tailf:cli-flat-list-syntax;
          ordered-by user;
          type inet:ipv4-address;
        }
        container giaddr {
          leaf policy {
            type enumeration {
              enum drop;
              enum replace;
            }
          }
        }
        container broadcast-flag {
          container policy {
            choice policy-choice {
              leaf check {
                type empty;
              }
              leaf unicast-always {
                type empty;
              }
            }
          }
        }
        list helper-address {
          tailf:cli-suppress-mode;
          tailf:cli-delete-when-empty;
          tailf:cli-compact-syntax;
          key "vrf address";
          leaf vrf {
            type vrf-type;
          }
          leaf address {
            type inet:ipv4-address;
          }
          leaf giaddr {
            type inet:ipv4-address;
          }
        }
        container dhcp-to-aaa {
          container option {
            leaf list {
              tailf:cli-multi-value;
              type string;
            }
          }
        }
        container lease {
          tailf:cli-compact-syntax;
          tailf:cli-sequence-commands {
            tailf:cli-reset-siblings;
          }
          choice lease-choice {
            case infinite {
              leaf infinite {
                type empty;
              }
            }
            case duration {
              leaf days {
                tailf:cli-drop-node-name;
                type uint16;
              }
              leaf hours {
                tailf:cli-drop-node-name;
                tailf:cli-optional-in-sequence;
                type uint8;
              }
              leaf minutes {
                tailf:cli-drop-node-name;
                type uint8;
              }
            }
          }
        }
        container proxy {
          tailf:cli-drop-node-name;
          container lease {
            container proxy {
              leaf client-lease-time {
                type uint32;
              }
            }
          }
        }
        container relay {
          container information {
            leaf check {
              type empty;
            }
            container option {
              leaf vpn {
                type empty;
              }
              leaf vpn-mode {
                type enumeration {
                  enum cisco;
                  enum rfc;
                }
              }
              container remote-id {
                leaf suppress {
                  type empty;
                }
                leaf value {
                  tailf:cli-drop-node-name;
                  type string;
                }
                leaf enable {
                  type empty;
                }
                container format-type {
                  tailf:cli-compact-syntax;
                  tailf:cli-sequence-commands {
                    tailf:cli-reset-siblings;
                  }
                  leaf format {
                    tailf:cli-drop-node-name;
                    type enumeration {
                      enum ascii;
                      enum hex;
                    }
                  }
                  leaf value {
                    tailf:cli-drop-node-name;
                    type string;
                  }
                }
              }
              leaf allow-untrusted {
                type empty;
              }
            }
            container option-base {
              tailf:cli-drop-node-name;
              leaf option {
                type empty;
              }
            }
            leaf policy {
              type enumeration {
                enum drop;
                enum encapsulate;
                enum keep;
                enum replace;
              }
            }
          }
        }
        leaf subnet-mask {
          type inet:ipv4-address;
        }
        list class {
          key "name";
          leaf name {
            type string;
          }
          container match {
            leaf vrf {
              type string;
            }
            list option {
              tailf:cli-suppress-mode;
              tailf:cli-delete-when-empty;
              tailf:cli-compact-syntax;
              tailf:cli-sequence-commands {
                tailf:cli-reset-siblings;
              }
              key "id";
              leaf id {
                type enumeration {
                  enum 60;
                  enum 77;
                  enum 124;
                  enum 125;
                  enum circuitid;
                  enum remoteid;
                }
              }
              leaf hex {
                type string;
              }
              leaf mask {
                type string;
              }
            }
          }
          leaf pool {
            type string;
          }
          leaf subnet-mask {
            type inet:ipv4-address;
          }
          leaf-list default-router {
            tailf:cli-flat-list-syntax;
            ordered-by user;
            type inet:ipv4-address;
          }
          list helper-address {
            tailf:cli-suppress-mode;
            tailf:cli-delete-when-empty;
            tailf:cli-compact-syntax;
            key "vrf address";
            leaf vrf {
              type vrf-type;
            }
            leaf address {
              type inet:ipv4-address;
            }
            leaf giaddr {
              type inet:ipv4-address;
            }
          }
        }
        leaf domain-name {
          type string;
        }
        list option {
          tailf:cli-suppress-mode;
          tailf:cli-delete-when-empty;
          tailf:cli-compact-syntax;
          tailf:cli-sequence-commands {
            tailf:cli-reset-all-siblings;
          }
          key "code";
          leaf code {
            type uint8;
          }
          choice type-choice {
            leaf ascii {
              type string;
            }
            leaf hex {
              type string;
            }
            leaf-list ip {
              tailf:cli-flat-list-syntax;
              type inet:ipv4-address;
            }
          }
          leaf force-insert {
            type empty;
          }
        }
        container requested-ip-address-check {
          leaf disable {
            type empty;
          }
        }
      }
      container interface-option {
        tailf:cli-drop-node-name;
        list interface {
          tailf:cli-suppress-mode;
          tailf:cli-delete-when-empty;
          tailf:cli-compact-syntax;
          key "name type";
          leaf name {
            type string;
          }
          leaf type {
            type enumeration {
              enum proxy;
              enum relay;
              enum server;
              enum snoop;
              enum base;
              enum cnbng;
            }
          }
          container information {
            container option {
              container format-type {
                tailf:cli-compact-syntax;
                tailf:cli-sequence-commands {
                  tailf:cli-reset-siblings;
                }
                container circuit-id {
                  tailf:cli-flatten-container;
                  tailf:cli-compact-syntax;
                  choice format-choice {
                    leaf value {
                      tailf:cli-drop-node-name;
                      type string;
                    }
                    leaf format-string {
                      type string;
                    }
                  }
                }
                leaf-list args {
                  tailf:cli-drop-node-name;
                  tailf:cli-flat-list-syntax;
                  ordered-by user;
                  type enumeration {
                    enum inner-vlan-id;
                    enum outer-vlan-id;
                    enum physical-chassis;
                    enum physical-port;
                    enum physical-slot;
                    enum physical-subport;
                    enum physical-subslot;
                    enum l2-interface;
                    enum l3-interface;
                    enum hostname;
                  }
                }
              }
            }
          }
        }
      }
      list interface {
        tailf:cli-suppress-mode;
        tailf:cli-delete-when-empty;
        tailf:cli-compact-syntax;
        key "name type";
        leaf name {
          type string;
        }
        leaf type {
          type enumeration {
            enum proxy;
            enum relay;
            enum server;
            enum snoop;
            enum base;
            enum cnbng;
          }
        }
        leaf profile {
          type string;
        }
      }
      container duplicate-mac-allowed {
        tailf:cli-delete-when-empty;
        presence "true";
        leaf exclude-vlan {
          type empty;
        }
      }
      container database {
        tailf:cli-compact-syntax;
        tailf:cli-delete-when-empty;
        presence "true";
        leaf proxy {
          type empty;
        }
        leaf server {
          type empty;
        }
        leaf snoop {
          type empty;
        }
        leaf full-write-interval {
          type uint16;
        }
        leaf incremental-write-interval {
          type uint16;
        }
      }
      leaf inner-cos {
        type uint8;
      }
      leaf outer-cos {
        type uint8;
      }
      leaf allow-client-id-change {
        type empty;
      }
    }
    container ipv6 {
      tailf:cli-add-mode;
      presence "true";
      container database {
        tailf:cli-compact-syntax;
        tailf:cli-delete-when-empty;
        presence "true";
        leaf proxy {
          type empty;
        }
        leaf server {
          type empty;
        }
        leaf relay {
          type empty;
        }
        leaf full-write-interval {
          type uint16;
        }
        leaf incremental-write-interval {
          type uint16;
        }
      }
      list profile {
        key "name type";
        leaf name {
          type string;
        }
        leaf type {
          type enumeration {
            enum proxy;
            enum relay;
            enum server;
            enum snoop;
            enum base;
            enum cnbng;
          }
        }
        list interface {
          tailf:cli-suppress-mode;
          tailf:cli-delete-when-empty;
          key "name";
          leaf name {
            type ifname;
          }
          leaf interface-id {
            type string;
          }
        }
        list helper-address {
          tailf:cli-suppress-mode;
          tailf:cli-delete-when-empty;
          key "vrf address";
          leaf vrf {
            type vrf-type;
          }
          leaf address {
            type inet:ipv6-address;
          }
        }
        leaf link-address {
          type inet:ipv6-address;
        }
        leaf iana-route-add {
          type empty;
        }
        leaf route-add-disable {
          type empty;
        }
        container source-interface {
          uses interface-name-grouping;
        }
        container lease {
          tailf:cli-compact-syntax;
          tailf:cli-sequence-commands {
            tailf:cli-reset-siblings;
          }
          choice lease-choice {
            leaf infinite {
              type empty;
            }
            case duration {
              leaf days {
                tailf:cli-drop-node-name;
                type uint16;
              }
              leaf hours {
                tailf:cli-drop-node-name;
                tailf:cli-optional-in-sequence;
                type uint8;
              }
              leaf minutes {
                tailf:cli-drop-node-name;
                type uint8;
              }
            }
          }
        }
        container relay {
          container option {
            leaf remote-id {
              type string;
            }
            container interface-id {
              leaf insert {
                type enumeration {
                  enum local;
                  enum pppoe;
                  enum received;
                }
              }
            }
            container link-layer-addr {
              leaf set {
                type empty;
              }
            }
          }
        }
        leaf prefix-pool {
          type string;
        }
        leaf address-pool {
          type string;
        }
        leaf rapid-commit {
          type empty;
        }
        container option {
          tailf:cli-compact-syntax;
          tailf:cli-sequence-commands {
            tailf:cli-reset-siblings;
          }
          leaf options {
            tailf:cli-drop-node-name;
            type enumeration {
              enum 17;
            }
          }
          leaf hex {
            type string;
          }
        }
        list class {
          key "name";
          leaf name {
            type string;
          }
          list helper-address {
            tailf:cli-suppress-mode;
            tailf:cli-delete-when-empty;
            key "vrf address";
            leaf vrf {
              type vrf-type;
            }
            leaf address {
              type inet:ipv6-address;
            }
          }
          leaf link-address {
            type inet:ipv6-address;
          }
          leaf-list dns-server {
            tailf:cli-flat-list-syntax;
            ordered-by user;
            type inet:ipv6-address;
          }
          leaf preference {
            type uint8;
          }
          leaf prefix-pool {
            type string;
          }
          leaf address-pool {
            type string;
          }
        }
      }
      list interface {
        tailf:cli-suppress-mode;
        tailf:cli-delete-when-empty;
        tailf:cli-compact-syntax;
        tailf:cli-sequence-commands {
          tailf:cli-reset-siblings;
        }
        key "name";
        leaf name {
          type string;
        }
        leaf type {
          tailf:cli-drop-node-name;
          type enumeration {
            enum proxy;
            enum relay;
            enum server;
            enum snoop;
            enum base;
            enum cnbng;
          }
        }
        leaf profile {
          type string;
        }
      }
      container interface-ppoe {
        tailf:cli-drop-node-name;
        container interface {
          container subscriber-pppoe {
            leaf profile {
              type string;
            }
          }
        }
      }
      leaf inner-cos {
        type uint8;
      }
      leaf outer-cos {
        type uint8;
      }
    }
  }
  container lacp {
    container system {
      leaf mac {
        type string;
      }
      leaf priority {
        type uint16;
      }
    }
  }
  container object-group {
    container network {
      list ipv4 {
        key "name";
        leaf name {
          type string;
        }
        list prefix-list {
          tailf:cli-drop-node-name;
          tailf:cli-suppress-mode;
          tailf:cli-delete-when-empty;
          key "prefix";
          leaf prefix {
            type ipv4-prefix;
          }
        }
        list host {
          tailf:cli-suppress-mode;
          tailf:cli-delete-when-empty;
          key "address";
          leaf address {
            type inet:ipv4-address;
          }
        }
        uses description-grouping;
      }
      list ipv6 {
        key "name";
        leaf name {
          type string;
        }
        list prefix-list {
          tailf:cli-drop-node-name;
          tailf:cli-suppress-mode;
          tailf:cli-delete-when-empty;
          key "prefix";
          leaf prefix {
            type tailf:ipv6-address-and-prefix-length;
          }
        }
        list host {
          tailf:cli-suppress-mode;
          tailf:cli-delete-when-empty;
          key "address";
          leaf address {
            type inet:ipv6-address;
          }
        }
        uses description-grouping;
      }
    }
    list port {
      key "name";
      leaf name {
        type string;
      }
      leaf-list eq {
        type string;
      }
      list range {
        tailf:cli-suppress-mode;
        tailf:cli-delete-when-empty;
        key "start";
        leaf start {
          type string;
        }
        leaf end {
          tailf:cli-drop-node-name;
          type string;
        }
      }
    }
  }
  container as-format {
    leaf asdot {
      type empty;
    }
  }
  container udf {
    list udf-list {
      tailf:cli-drop-node-name;
      tailf:cli-suppress-mode;
      tailf:cli-delete-when-empty;
      tailf:cli-compact-syntax;
      tailf:cli-sequence-commands {
        tailf:cli-reset-siblings;
      }
      key "name";
      leaf name {
        type string;
      }
      leaf header {
        type empty;
      }
      leaf start {
        tailf:cli-drop-node-name;
        type enumeration {
          enum inner;
          enum outer;
        }
      }
      leaf layer {
        tailf:cli-drop-node-name;
        type enumeration {
          enum l2;
          enum l3;
          enum l4;
        }
      }
      leaf offset {
        type uint16;
      }
      leaf length {
        type uint16;
      }
    }
  }
  container onep {
    tailf:cli-add-mode;
    presence "true";
  }
  container install {
    tailf:cli-add-mode;
    list repository {
      key "name";
      leaf name {
        type string;
      }
      leaf url {
        type string;
      }
    }
  }
  container snmp-server {
    container ifmib {
      container ifalias {
        leaf long {
          type empty;
        }
      }
      container internal {
        container cache {
          leaf max-duration {
            type uint8;
          }
        }
      }
      container stats {
        leaf cache {
          type empty;
        }
      }
      leaf ipsubscriber {
        type empty;
      }
    }
    leaf packetsize {
      type uint32;
    }
    leaf ifindex {
      type enumeration {
        enum persist;
      }
    }
    container engineID {
      leaf local {
        type string;
      }
      list remote {
        tailf:cli-suppress-mode;
        tailf:cli-delete-when-empty;
        tailf:cli-compact-syntax;
        key "ip-address";
        leaf ip-address {
          type string;
        }
        leaf engine-id {
          tailf:cli-drop-node-name;
          type string;
        }
        leaf udp-port {
          type uint16;
        }
      }
    }
    uses snmp-server-host-grouping;
    container entityindex {
      leaf persist {
        type empty;
      }
    }
    list vrf {
      key "name";
      leaf name {
        type string;
      }
      uses snmp-server-host-grouping;
      list context {
        tailf:cli-suppress-mode;
        tailf:cli-delete-when-empty;
        key "name";
        leaf name {
          type string;
        }
      }
    }
    container ipv4 {
      choice ipv4-choice {
        leaf dscp {
          type dscp-type;
        }
        leaf precedence {
          type precedence-type;
        }
      }
    }
    container ipv6 {
      choice ipv6-choice {
        leaf dscp {
          type dscp-type;
        }
        leaf precedence {
          type precedence-type;
        }
      }
    }
    container context {
      list context-list {
        tailf:cli-drop-node-name;
        tailf:cli-suppress-mode;
        tailf:cli-delete-when-empty;
        key "name";
        leaf name {
          type string;
        }
      }
    }
    list community {
      tailf:cli-suppress-mode;
      tailf:cli-delete-when-empty;
      tailf:cli-compact-syntax;
      tailf:cli-sequence-commands {
        tailf:cli-reset-siblings;
      }
      key "name";
      leaf name {
        type string;
      }
      leaf type {
        tailf:cli-prefix-key;
        tailf:cli-drop-node-name;
        tailf:cli-optional-in-sequence;
        type enumeration {
          enum clear;
          enum encrypted;
        }
      }
      leaf encryption-aes {
        tailf:cli-optional-in-sequence;
        tailf:cli-prefix-key;
        type empty;
      }
      leaf view {
        tailf:cli-optional-in-sequence;
        type string;
      }
      choice access-choice {
        leaf RO {
          tailf:cli-optional-in-sequence;
          type empty;
        }
        leaf RW {
          tailf:cli-optional-in-sequence;
          type empty;
        }
      }
      choice owner-choice {
        leaf SDROwner {
          tailf:cli-optional-in-sequence;
          type empty;
        }
        leaf SystemOwner {
          tailf:cli-optional-in-sequence;
          type empty;
        }
      }
      leaf access-list-type {
        tailf:cli-drop-node-name;
        tailf:cli-optional-in-sequence;
        type enumeration {
          enum IPv4;
        }
      }
      leaf access-list {
        tailf:cli-drop-node-name;
        tailf:cli-optional-in-sequence;
        type string;
      }
      leaf IPv6 {
        type string;
      }
    }
    container community-map {
      list community-map-list {
        tailf:cli-drop-node-name;
        tailf:cli-suppress-mode;
        tailf:cli-delete-when-empty;
        key "name";
        leaf name {
          type string;
        }
        leaf context {
          type string;
        }
      }
    }
    leaf queue-length {
      type uint32;
    }
    leaf trap-timeout {
      type uint16;
    }
    leaf contact {
      type string;
    }
    leaf location {
      type string;
    }
    container logging {
      container threshold {
        leaf oid-processing {
          type uint16;
        }
        leaf pdu-processing {
          type uint16;
        }
      }
    }
    container trap-source {
      container IPv4 {
        uses interface-name-grouping;
      }
      container IPv6 {
        uses interface-name-grouping;
      }
      uses interface-name-grouping;
      leaf port {
        type uint16;
      }
    }
    leaf oid-poll-stats {
      type empty;
    }
    container overload-control {
      tailf:cli-compact-syntax;
      tailf:cli-sequence-commands;
      leaf drop-time {
        tailf:cli-drop-node-name;
        type uint16;
      }
      leaf throttle-rate {
        tailf:cli-drop-node-name;
        type uint16;
      }
    }
    container mroutemib {
      leaf send-all-vrf {
        type empty;
      }
    }
    container mibs {
      container cbqosmib {
        leaf persist {
          type empty;
        }
        container cache {
          tailf:cli-add-mode;
          presence "true";
          container refresh {
            leaf time {
              type uint16;
            }
          }
          container service-policy {
            leaf count {
              type uint16;
            }
          }
        }
        leaf member-stats {
          type empty;
        }
      }
      container eventmib {
        list packet-loss {
          tailf:cli-suppress-mode;
          tailf:cli-delete-when-empty;
          tailf:cli-compact-syntax;
          key "name";
          leaf name {
            type string;
          }
          leaf rising {
            type uint32;
          }
          leaf falling {
            type uint32;
          }
          leaf interval {
            type uint16;
          }
        }
      }
      container sensormib {
        leaf cache {
          type empty;
        }
      }
    }
    container trap {
      leaf link {
        type enumeration {
          enum ietf;
        }
      }
      leaf throttle-time {
        type uint16;
      }
      container authentication {
        container vrf {
          leaf disable {
            type empty;
          }
        }
      }
    }
    container drop {
      container report {
        container acl {
          tailf:cli-compact-syntax;
          tailf:cli-sequence-commands {
            tailf:cli-reset-siblings;
          }
          leaf access-list-type {
            tailf:cli-drop-node-name;
            type enumeration {
              enum IPv4;
              enum IPv6;
            }
          }
          leaf access-list {
            tailf:cli-drop-node-name;
            type string;
          }
        }
      }
      leaf unknown-user {
        type empty;
      }
    }
    list user {
      tailf:cli-suppress-mode;
      tailf:cli-delete-when-empty;
      tailf:cli-compact-syntax;
      tailf:cli-sequence-commands {
        tailf:cli-reset-siblings;
      }
      key "username";
      leaf username {
        type string;
      }
      leaf groupname {
        tailf:cli-drop-node-name;
        type string;
      }
      leaf remote {
        tailf:cli-optional-in-sequence;
        type inet:host;
      }
      leaf udp-port {
        tailf:cli-optional-in-sequence;
        type uint16;
      }
      leaf version {
        tailf:cli-drop-node-name;
        type enumeration {
          enum v1;
          enum v2c;
          enum v3;
        }
      }
      container auth {
        tailf:cli-optional-in-sequence;
        tailf:cli-flatten-container;
        tailf:cli-compact-syntax;
        tailf:cli-sequence-commands {
          tailf:cli-reset-siblings;
        }
        leaf level {
          tailf:cli-drop-node-name;
          type enumeration {
            enum md5;
            enum sha;
            enum sha-224;
            enum sha-256;
            enum sha-384;
            enum sha-512;
          }
        }
        choice password-choice {
          leaf auth-password {
            tailf:cli-drop-node-name;
            type string;
          }
          leaf clear {
            type string;
          }
          leaf encrypted {
            type string;
          }
          container auth-encrypted-aes {
            tailf:cli-drop-node-name;
            tailf:cli-flatten-container;
            tailf:cli-compact-syntax;
            container encrypted {
              tailf:cli-flatten-container;
              tailf:cli-compact-syntax;
              leaf encryption-aes {
                type string;
              }
            }
          }
          container auth-clear-aes {
            tailf:cli-drop-node-name;
            tailf:cli-flatten-container;
            tailf:cli-compact-syntax;
            container clear {
              tailf:cli-flatten-container;
              tailf:cli-compact-syntax;
              leaf encryption-aes {
                type string;
              }
            }
          }
        }
      }
      container priv {
        tailf:cli-optional-in-sequence;
        tailf:cli-flatten-container;
        tailf:cli-compact-syntax;
        tailf:cli-sequence-commands {
          tailf:cli-reset-siblings;
        }
        choice priv-level {
          leaf threedes {
            tailf:alt-name "3des";
            type empty;
          }
          leaf aes {
            type enumeration {
              enum 128;
              enum 192;
              enum 256;
            }
          }
          leaf des56 {
            type empty;
          }
        }
        choice password-choice {
          leaf priv-password {
            tailf:cli-drop-node-name;
            type string;
          }
          leaf clear {
            type string;
          }
          leaf encrypted {
            type string;
          }
          container priv-encrypted-aes {
            tailf:cli-drop-node-name;
            tailf:cli-flatten-container;
            tailf:cli-compact-syntax;
            container encrypted {
              tailf:cli-flatten-container;
              tailf:cli-compact-syntax;
              leaf encryption-aes {
                type string;
              }
            }
          }
          container priv-clear-aes {
            tailf:cli-drop-node-name;
            tailf:cli-flatten-container;
            tailf:cli-compact-syntax;
            container clear {
              tailf:cli-flatten-container;
              tailf:cli-compact-syntax;
              leaf encryption-aes {
                type string;
              }
            }
          }
        }
      }
      leaf access-list-type {
        tailf:cli-drop-node-name;
        tailf:cli-optional-in-sequence;
        type enumeration {
          enum IPv4;
          enum IPv6;
        }
      }
      leaf access-list {
        tailf:cli-drop-node-name;
        tailf:cli-optional-in-sequence;
        type string;
      }
      choice owner-choice {
        leaf SDROwner {
          type empty;
        }
        leaf SystemOwner {
          type empty;
        }
      }
    }
    list view {
      tailf:cli-suppress-mode;
      tailf:cli-compact-syntax;
      tailf:cli-delete-when-empty;
      key "view-name";
      leaf view-name {
        type string;
      }
      list oid-list {
        tailf:cli-suppress-mode;
        tailf:cli-drop-node-name;
        tailf:cli-compact-syntax;
        tailf:cli-delete-when-empty;
        key "oid-tree";
        leaf oid-tree {
          type string;
        }
        leaf viewmode {
          tailf:cli-drop-node-name;
          type enumeration {
            enum excluded;
            enum included;
          }
        }
      }
    }
    list group {
      tailf:cli-suppress-mode;
      tailf:cli-delete-when-empty;
      tailf:cli-compact-syntax;
      tailf:cli-sequence-commands {
        tailf:cli-reset-all-siblings;
      }
      key "name";
      leaf name {
        type string;
      }
      choice version-choice {
        leaf v1 {
          type empty;
        }
        leaf v2c {
          type empty;
        }
        leaf v3 {
          type enumeration {
            enum auth;
            enum noauth;
            enum priv;
          }
        }
      }
      leaf read {
        tailf:cli-break-sequence-commands;
        type string;
      }
      leaf write {
        type string;
      }
      leaf notify {
        type string;
      }
      leaf context {
        type string;
      }
      leaf access-list-type {
        tailf:cli-drop-node-name;
        type enumeration {
          enum IPv4;
        }
      }
      leaf access-list {
        tailf:cli-drop-node-name;
        type string;
      }
      leaf IPv6 {
        type string;
      }
    }
    container interface {
      list subset {
        tailf:cli-sequence-commands;
        key "id";
        leaf id {
          type uint8;
        }
        leaf regular-expression {
          tailf:cli-hide-in-submode;
          type string;
        }
        container notification {
          tailf:cli-break-sequence-commands;
          container linkupdown {
            tailf:cli-delete-when-empty;
            presence "true";
            leaf disable {
              type empty;
            }
          }
        }
      }
      list interface-name {
        tailf:cli-drop-node-name;
        key "ifname";
        leaf ifname {
          type ifname;
        }
        container index {
          leaf persistence {
            type empty;
          }
        }
        container notification {
          container linkupdown {
            tailf:cli-delete-when-empty;
            presence "true";
            leaf disable {
              type empty;
            }
          }
        }
      }
    }
    leaf chassis-id {
      tailf:cli-multi-value;
      type string;
    }
    container traps {
      list traps-list {
        tailf:cli-drop-node-name;
        tailf:cli-suppress-mode;
        tailf:cli-delete-when-empty;
        key "name";
        leaf name {
          tailf:cli-multi-word-key;
          type string;
        }
      }
      leaf all-traps {
        type empty;
      }
    }
    container timeouts {
      leaf duplicate {
        type uint8;
      }
      leaf subagent {
        type uint8;
      }
      leaf inQdrop {
        type uint8;
      }
      leaf threshold {
        type uint32;
      }
    }
    container notification-log-mib {
      leaf default {
        type empty;
      }
    }
  }
  container appmgr {
    tailf:cli-add-mode;
    list application {
      key "name";
      leaf name {
        type string;
      }
      container activate {
        tailf:cli-compact-syntax;
        tailf:cli-sequence-commands {
          tailf:cli-reset-all-siblings;
        }
        leaf type {
          type enumeration {
            enum docker;
          }
        }
        leaf source {
          type string;
        }
        leaf svault {
          tailf:cli-break-sequence-commands;
          type string;
        }
        leaf docker-run-opts {
          type string;
        }
        leaf docker-run-cmd {
          type string;
        }
      }
    }
  }
  container linux {
    container networking {
      tailf:cli-add-mode;
      list vrf {
        key "name";
        leaf name {
          type string;
        }
        container address-family {
          container ipv4 {
            tailf:cli-add-mode;
            container protection {
              tailf:cli-add-mode;
              list protocol {
                key "protocol local-port";
                leaf protocol {
                  type enumeration {
                    enum tcp;
                    enum udp;
                  }
                }
                leaf local-port {
                  type union {
                    type uint16;
                    type enumeration {
                      enum all;
                    }
                  }
                }
                leaf default-action {
                  tailf:cli-hide-in-submode;
                  type enumeration {
                    enum deny;
                    enum permit;
                  }
                }
                container permit {
                  list remote-address {
                    tailf:cli-suppress-mode;
                    tailf:cli-delete-when-empty;
                    key "address";
                    leaf address {
                      type ipv4-prefix;
                    }
                  }
                  container remote-address-list2 {
                    tailf:cli-drop-node-name;
                    list remote-address {
                      tailf:cli-suppress-mode;
                      tailf:cli-delete-when-empty;
                      key "address local-address";
                      leaf address {
                        type ipv4-prefix;
                      }
                      leaf local-address {
                        type ipv4-prefix;
                      }
                    }
                  }
                  container remote-address-list3 {
                    tailf:cli-drop-node-name;
                    list remote-address {
                      tailf:cli-suppress-mode;
                      tailf:cli-delete-when-empty;
                      key "address local-address interface";
                      leaf address {
                        type ipv4-prefix;
                      }
                      leaf local-address {
                        type ipv4-prefix;
                      }
                      leaf interface {
                        type string;
                      }
                    }
                  }
                }
              }
            }
            container source-hint {
              container default-route {
                choice source-hint-choice {
                  leaf active-management {
                    type empty;
                  }
                  leaf interface {
                    type string;
                  }
                }
              }
              container management-route {
                leaf interface {
                  type string;
                }
              }
            }
          }
        }
      }
    }
  }
  container virtual-service {
    leaf enable {
      type empty;
    }
    list virtual-service-list {
      tailf:cli-drop-node-name;
      key "name";
      leaf name {
        type string;
      }
    }
  }
  container srlg {
    tailf:cli-add-mode;
    presence "true";
    grouping value-list-grouping {
      list value-list {
        tailf:cli-drop-node-name;
        tailf:cli-suppress-mode;
        tailf:cli-delete-when-empty;
        tailf:cli-compact-syntax;
        tailf:cli-sequence-commands {
          tailf:cli-reset-siblings;
        }
        key "id";
        leaf id {
          type uint16;
        }
        leaf value {
          type uint32;
        }
        leaf priority {
          type enumeration {
            enum verylow;
            enum low;
            enum high;
            enum critical;
          }
        }
      }
    }

    list interface {
      key "id";
      leaf id {
        type string;
      }
      uses value-list-grouping;
      list name-list {
        tailf:cli-drop-node-name;
        tailf:cli-suppress-mode;
        tailf:cli-delete-when-empty;
        key "name";
        leaf name {
          type string;
        }
      }
      container group {
        tailf:cli-add-mode;
        presence "true";
        list index-list {
          tailf:cli-suppress-mode;
          tailf:cli-delete-when-empty;
          tailf:cli-drop-node-name;
          tailf:cli-sequence-commands {
            tailf:cli-reset-siblings;
          }
          tailf:cli-compact-syntax;
          key "index";
          leaf index {
            type uint8;
          }
          leaf name {
            tailf:cli-drop-node-name;
            mandatory true;
            type string;
          }
        }
      }
      container include-optical {
        tailf:cli-add-mode;
        presence "true";
      }
    }
    list name {
      tailf:cli-suppress-mode;
      tailf:cli-delete-when-empty;
      key "name";
      leaf name {
        type string;
      }
      leaf value {
        type uint32;
      }
    }
    list group {
      key "name";
      leaf name {
        type string;
      }
      uses value-list-grouping;
    }
  }
  list monitor-session {
    key "name";
    leaf name {
      type string;
    }
    choice type-choice {
      leaf ethernet {
        tailf:cli-hide-in-submode;
        type empty;
      }
      leaf ipv4 {
        tailf:cli-hide-in-submode;
        type empty;
      }
      leaf ipv6 {
        tailf:cli-hide-in-submode;
        type empty;
      }
    }
    container destination {
      choice destination-choice {
        leaf pseudowire {
          type empty;
        }
        container interface {
          uses interface-name-grouping;
        }
        leaf next-hop {
          type inet:ipv4-address;
        }
        container file {
          tailf:cli-compact-syntax;
          tailf:cli-delete-when-empty;
          presence "true";
          leaf size {
            type uint32;
          }
          leaf format {
            type enumeration {
              enum pcapng;
            }
          }
        }
      }
    }
  }
  container spanning-tree {
    container extend {
      leaf system-id {
        type empty;
      }
    }
    leaf mode {
      type enumeration {
        enum mst;
        enum rapid-pvst;
      }
    }
    container mst {
      list range {
        tailf:cli-drop-node-name;
        tailf:cli-suppress-mode;
        tailf:cli-delete-when-empty;
        tailf:cli-range-list-syntax;
        key "id";
        leaf id {
          type uint8;
        }
        leaf priority {
          type uint16;
        }
      }
      list protocol-instance {
        tailf:cli-drop-node-name;
        key "id";
        leaf id {
          type string;
        }
        leaf name {
          type string;
        }
        container maximum {
          leaf age {
            type uint8;
          }
          leaf hops {
            type uint8;
          }
        }
        leaf revision {
          type uint16;
        }
        leaf allow-legacy-bpdu {
          type empty;
        }
        container bringup {
          container delay {
            tailf:cli-compact-syntax;
            tailf:cli-sequence-commands;
            leaf for {
              type uint16;
            }
            leaf unit {
              tailf:cli-drop-node-name;
              type enumeration {
                enum seconds;
                enum minutes;
                enum hours;
              }
            }
          }
        }
        leaf forward-delay {
          type uint8;
        }
        container transmit {
          leaf hold-count {
            type uint8;
          }
        }
        leaf provider-bridge {
          type empty;
        }
        list instance {
          key "id";
          leaf id {
            type uint16;
          }
          leaf priority {
            type uint16;
          }
          leaf-list vlan-ids {
            tailf:cli-range-list-syntax;
            type uint16;
          }
        }
        list interface {
          key "ifname";
          leaf ifname {
            type ifname;
          }
          container portfast {
            presence "true";
          }
          list instance {
            tailf:cli-suppress-mode;
            tailf:cli-delete-when-empty;
            tailf:cli-compact-syntax;
            key "id";
            leaf id {
              type uint16;
            }
            leaf cost {
              type uint32;
            }
          }
          leaf link-type {
            type enumeration {
              enum multipoint;
              enum point-to-point;
            }
          }
          container guard {
            leaf root {
              type empty;
            }
            leaf topology-change {
              type empty;
            }
          }
          leaf hello-time {
            type uint8;
          }
          leaf external-cost {
            type uint32;
          }
        }
      }
    }
    leaf portfast {
      type enumeration {
        enum disable;
        enum edge;
        enum network;
      }
    }
    list mstag {
      key "name";
      leaf name {
        type string;
      }
      list interface {
        key "ifname";
        leaf ifname {
          type ifname;
        }
        leaf name {
          type string;
        }
        leaf revision {
          type uint16;
        }
        leaf port-id {
          type uint16;
        }
        leaf bridge-id {
          type string;
        }
        list instance {
          key "id";
          leaf id {
            type uint16;
          }
          container cost {
            tailf:cli-compact-syntax;
            tailf:cli-sequence-commands {
              tailf:cli-reset-siblings;
            }
            leaf cost-value {
              tailf:cli-drop-node-name;
              type uint32;
            }
            leaf startup-value {
              type uint32;
            }
          }
          leaf-list vlan-ids {
            tailf:cli-range-list-syntax;
            type uint16;
          }
          container root-id {
            tailf:cli-compact-syntax;
            tailf:cli-sequence-commands {
              tailf:cli-reset-siblings;
            }
            leaf root-id-value {
              tailf:cli-drop-node-name;
              type string;
            }
            leaf startup-value {
              type string;
            }
          }
          leaf edge-mode {
            type empty;
          }
          container priority {
            tailf:cli-compact-syntax;
            tailf:cli-sequence-commands {
              tailf:cli-reset-siblings;
            }
            leaf priority-value {
              tailf:cli-drop-node-name;
              type uint16;
            }
            leaf startup-value {
              type uint16;
            }
          }
          container root-priority {
            tailf:cli-compact-syntax;
            tailf:cli-sequence-commands {
              tailf:cli-reset-siblings;
            }
            leaf priority-value {
              tailf:cli-drop-node-name;
              type uint16;
            }
            leaf startup-value {
              type uint16;
            }
          }
        }
        leaf hello-time {
          type uint8;
        }
      }
    }
    list pvstag {
      key "name";
      leaf name {
        type string;
      }
      list interface {
        key "ifname";
        leaf ifname {
          type ifname;
        }
        list vlan {
          key "id";
          leaf id {
            type uint16;
          }
          container root-priority {
            tailf:cli-compact-syntax;
            tailf:cli-sequence-commands {
              tailf:cli-reset-siblings;
            }
            leaf value {
              tailf:cli-drop-node-name;
              type uint16;
            }
            leaf startup-value {
              type uint16;
            }
          }
          container root-id {
            tailf:cli-compact-syntax;
            tailf:cli-sequence-commands {
              tailf:cli-reset-siblings;
            }
            leaf value {
              tailf:cli-drop-node-name;
              type string;
            }
            leaf startup-value {
              type string;
            }
          }
          container root-cost {
            tailf:cli-compact-syntax;
            tailf:cli-sequence-commands {
              tailf:cli-reset-siblings;
            }
            leaf value {
              tailf:cli-drop-node-name;
              type uint32;
            }
            leaf startup-value {
              type uint32;
            }
          }
          container priority {
            tailf:cli-compact-syntax;
            tailf:cli-sequence-commands {
              tailf:cli-reset-siblings;
            }
            leaf value {
              tailf:cli-drop-node-name;
              type uint16;
            }
            leaf startup-value {
              type uint16;
            }
          }
          container bridge-id {
            tailf:cli-compact-syntax;
            tailf:cli-sequence-commands {
              tailf:cli-reset-siblings;
            }
            leaf value {
              tailf:cli-drop-node-name;
              type string;
            }
            leaf startup-value {
              type string;
            }
          }
          container port-priority {
            tailf:cli-compact-syntax;
            tailf:cli-sequence-commands {
              tailf:cli-reset-siblings;
            }
            leaf value {
              tailf:cli-drop-node-name;
              type uint8;
            }
            leaf startup-value {
              type uint8;
            }
          }
          container port-id {
            tailf:cli-compact-syntax;
            tailf:cli-sequence-commands {
              tailf:cli-reset-siblings;
            }
            leaf value {
              tailf:cli-drop-node-name;
              type uint8;
            }
            leaf startup-value {
              type uint8;
            }
          }
          container max {
            leaf age {
              type uint8;
            }
          }
          leaf hello-time {
            type uint8;
          }
        }
      }
    }
    list repag {
      key "name";
      leaf name {
        type string;
      }
      list interface {
        key "ifname";
        leaf ifname {
          type ifname;
        }
      }
    }
    list pvrst {
      key "name";
      leaf name {
        type string;
      }
      list vlan {
        key "id";
        leaf id {
          type uint16;
        }
        leaf priority {
          type uint16;
        }
      }
      list interface {
        key "name";
        leaf name {
          type string;
        }
        list vlan {
          tailf:cli-suppress-mode;
          tailf:cli-delete-when-empty;
          key "id";
          leaf id {
            type uint16;
          }
          leaf cost {
            type uint32;
          }
        }
      }
    }
  }
  container isolation {
    leaf enable {
      type empty;
    }
    leaf multiple {
      type empty;
    }
  }
  container redundancy {
    tailf:cli-add-mode;
    container iccp {
      tailf:cli-add-mode;
      list group {
        key "id";
        leaf id {
          type uint32;
        }
        container mlacp {
          leaf node {
            type uint8;
          }
          container system {
            leaf mac {
              type string;
            }
            leaf priority {
              type uint16;
            }
          }
          container connect {
            leaf timeout {
              type uint16;
            }
          }
        }
        container member {
          tailf:cli-add-mode;
          leaf neighbor {
            type inet:ipv4-address;
          }
        }
        container mode {
          leaf singleton {
            type empty;
          }
        }
        container backbone {
          tailf:cli-add-mode;
          list interface {
            tailf:cli-suppress-mode;
            tailf:cli-delete-when-empty;
            key "name";
            leaf name {
              type string;
            }
          }
        }
        container isolation {
          leaf recovery-delay {
            type uint16;
          }
        }
        container nv {
          container satellite {
            tailf:cli-add-mode;
            leaf system-mac {
              type string;
            }
          }
        }
      }
    }
  }
  container ssh {
    container client {
      leaf v2 {
        type empty;
      }
      leaf vrf {
        type string;
      }
      container source-interface {
        uses interface-name-grouping;
      }
      container disable {
        list hmac {
          tailf:cli-suppress-mode;
          tailf:cli-delete-when-empty;
          key "name";
          leaf name {
            type enumeration {
              enum hmac-sha1;
              enum hmac-sha2-256;
              enum hmac-sha2-512;
            }
          }
        }
      }
      leaf dscp {
        type uint8;
      }
      leaf knownhost {
        type string;
      }
      leaf tcp-window-scale {
        type uint8;
      }
      container enable {
        leaf-list cipher {
          tailf:cli-flat-list-syntax;
          type enumeration {
            enum 3des-cbc;
            enum aes-cbc;
          }
        }
      }
      container algorithms {
        leaf-list cipher {
          tailf:cli-flat-list-syntax;
          ordered-by user;
          type enumeration {
            enum aes128-ctr;
            enum aes192-ctr;
            enum aes256-ctr;
            enum aes128-gcm@openssh.com;
            enum aes256-gcm@openssh.com;
            enum aes128-cbc;
            enum aes192-cbc;
            enum aes256-cbc;
            enum 3des-cbc;
            enum chacha20-poly1305@openssh.com;
          }
        }
        leaf-list key-exchange {
          tailf:cli-flat-list-syntax;
          ordered-by user;
          type enumeration {
            enum ecdh-sha2-nistp521;
            enum ecdh-sha2-nistp384;
            enum ecdh-sha2-nistp256;
            enum diffie-hellman-group14-sha1;
            enum diffie-hellman-group1-sha1;
            enum curve25519-sha256;
            enum diffie-hellman-group14-sha256;
            enum diffie-hellman-group16-sha512;
            enum curve25519-sha256@libssh.org;
          }
        }
      }
    }
    container server {
      container enable {
        leaf-list cipher {
          tailf:cli-flat-list-syntax;
          ordered-by user;
          type enumeration {
            enum 3des-cbc;
            enum aes-cbc;
          }
        }
      }
      container disable {
        list hmac {
          tailf:cli-suppress-mode;
          tailf:cli-delete-when-empty;
          key "name";
          leaf name {
            type enumeration {
              enum hmac-sha1;
              enum hmac-sha2-256;
              enum hmac-sha2-512;
            }
          }
        }
      }
      leaf dscp {
        type uint8;
      }
      leaf logging {
        type empty;
      }
      container netconf {
        tailf:cli-delete-when-empty;
        presence "true";
        leaf port {
          type uint16;
        }
        uses ssh-server-vrf-grouping;
      }
      container capability {
        leaf netconf-xml {
          type empty;
        }
      }
      container algorithms {
        leaf-list key-exchange {
          tailf:cli-flat-list-syntax;
          ordered-by user;
          type enumeration {
            enum diffie-hellman-group1-sha1;
            enum diffie-hellman-group14-sha1;
            enum ecdh-sha2-nistp521;
            enum ecdh-sha2-nistp384;
            enum ecdh-sha2-nistp256;
            enum curve25519-sha256;
            enum diffie-hellman-group14-sha256;
            enum diffie-hellman-group16-sha512;
            enum curve25519-sha256@libssh.org;
          }
        }
        leaf-list cipher {
          tailf:cli-flat-list-syntax;
          ordered-by user;
          type enumeration {
            enum aes128-ctr;
            enum aes192-ctr;
            enum aes256-ctr;
            enum aes128-gcm@openssh.com;
            enum aes256-gcm@openssh.com;
            enum aes128-cbc;
            enum aes192-cbc;
            enum aes256-cbc;
            enum 3des-cbc;
            enum chacha20-poly1305@openssh.com;
          }
        }
        leaf-list host-key {
          tailf:cli-flat-list-syntax;
          type enumeration {
            enum dsa;
            enum ecdsa-nistp256;
            enum ecdsa-nistp384;
            enum ecdsa-nistp521;
            enum ed25519;
            enum rsa;
            enum x509v3-ssh-rsa;
            enum rsa-sha256;
            enum rsa-sha512;
            enum ssh-rsa;
            enum ssh-rsa-cert-v01;
          }
        }
      }
      leaf rate-limit {
        type uint32;
      }
      leaf max-auth-limit {
        type uint8;
      }
      leaf session-limit {
        type uint32;
      }
      leaf tcp-window-scale {
        type uint8;
      }
      leaf v2 {
        type empty;
      }
      leaf rekey-time {
        type uint16;
      }
      leaf rekey-volume {
        type uint16;
      }
      uses ssh-server-vrf-grouping;
    }
    leaf timeout {
      type uint8;
    }
  }
  container performance-measurement {
    tailf:cli-add-mode;
    presence "true";
    list interface {
      key "name";
      leaf name {
        type string;
      }
      container next-hop {
        choice ipv4-or-ipv6 {
          leaf ipv4 {
            type inet:ipv4-address;
          }
          leaf ipv6 {
            type inet:ipv6-address;
          }
        }
      }
      container delay-measurement {
        tailf:cli-add-mode;
        presence "true";
        leaf advertise-delay {
          type uint32;
        }
        container delay-profile {
          leaf name {
            type string;
          }
        }
      }
    }
    container protocol {
      container twamp-light {
        tailf:cli-add-mode;
        container measurement {
          container delay {
            tailf:cli-add-mode;
            container unauthenticated {
              tailf:cli-add-mode;
              grouping ip-ts-grouping {
                container timestamp1 {
                  leaf label {
                    type uint16;
                  }
                }
                container timestamp2 {
                  leaf label {
                    type uint16;
                  }
                }
              }

              container ipv4 {
                uses ip-ts-grouping;
              }
              container ipv6 {
                uses ip-ts-grouping;
              }
              leaf querier-dst-port {
                type uint16;
              }
              leaf querier-src-port {
                type uint16;
              }
            }
          }
        }
      }
    }
    container delay-profile {
      container sr-policy-name {
        tailf:cli-drop-node-name;
        list sr-policy {
          key "name";
          leaf name {
            type string;
          }
          uses pm-dm-grouping;
        }
      }
      container sr-policy-default {
        tailf:cli-drop-node-name;
        container sr-policy {
          container default {
            tailf:cli-add-mode;
            presence "true";
            uses pm-dm-grouping;
          }
        }
      }
      container sr-policy {
        tailf:cli-add-mode;
        presence "true";
        uses pm-dm-grouping;
      }
      container interfaces-name {
        tailf:cli-drop-node-name;
        list interfaces {
          key "name";
          leaf name {
            type string;
          }
          uses pm-dm-grouping;
        }
      }
      container interfaces-default {
        tailf:cli-drop-node-name;
        container interfaces {
          container default {
            tailf:cli-add-mode;
            presence "true";
            uses pm-dm-grouping;
          }
        }
      }
      container interfaces {
        tailf:cli-add-mode;
        presence "true";
        uses pm-dm-grouping;
      }
      container rsvp-te {
        container default {
          tailf:cli-add-mode;
          uses pm-dm-grouping;
        }
      }
      container endpoint {
        container default {
          tailf:cli-add-mode;
          uses pm-dm-grouping;
        }
        list name {
          key "name";
          leaf name {
            type string;
          }
          uses pm-dm-grouping;
        }
      }
      list name {
        key "name";
        leaf name {
          type string;
        }
        uses pm-dm-grouping;
      }
    }
    container endpoint {
      list ipv4 {
        key "address";
        leaf address {
          type inet:ipv4-address;
        }
        uses pm-ep-grouping;
      }
      container ipv4-vrf {
        tailf:cli-drop-node-name;
        list ipv4 {
          key "address vrf";
          leaf address {
            type inet:ipv4-address;
          }
          leaf vrf {
            type string;
          }
          uses pm-ep-grouping;
        }
      }
      list ipv6 {
        key "address";
        leaf address {
          type inet:ipv6-address;
        }
        uses pm-ep-grouping;
      }
      container ipv6-vrf {
        tailf:cli-drop-node-name;
        list ipv6 {
          key "address vrf";
          leaf address {
            type inet:ipv6-address;
          }
          leaf vrf {
            type string;
          }
          uses pm-ep-grouping;
        }
      }
    }
    container liveness-profile {
      container endpoint {
        container default {
          tailf:cli-add-mode;
          uses pm-ld-grouping;
        }
        list name {
          key "name";
          leaf name {
            type string;
          }
          uses pm-ld-grouping;
        }
      }
      container sr-policy {
        container default {
          tailf:cli-add-mode;
          uses pm-ld-grouping;
        }
        list name {
          key "name";
          leaf name {
            type string;
          }
          uses pm-ld-grouping;
        }
      }
      list name {
        key "name";
        leaf name {
          type string;
        }
        uses pm-ld-grouping;
      }
    }
  }

  grouping pm-dm-grouping {
    container advertisement {
      tailf:cli-add-mode;
      container accelerated {
        tailf:cli-add-mode;
        presence "true";
        leaf minimum-change {
          type uint32;
        }
        leaf threshold {
          type uint8;
        }
      }
      container anomaly-check {
        tailf:cli-add-mode;
        presence "true";
        container bound {
          tailf:cli-drop-node-name;
          tailf:cli-compact-syntax;
          tailf:cli-sequence-commands;
          leaf upper-bound {
            type uint32;
          }
          leaf lower-bound {
            type uint32;
          }
        }
      }
      container logging {
        tailf:cli-add-mode;
        leaf delay-exceeded {
          type empty;
        }
      }
      container periodic {
        tailf:cli-add-mode;
        leaf disabled {
          type empty;
        }
        leaf minimum-change {
          type uint32;
        }
        leaf interval {
          type uint16;
        }
        leaf threshold {
          type uint8;
        }
      }
      container threshold-check {
        tailf:cli-add-mode;
        leaf average-delay {
          type empty;
        }
        leaf maximum-delay {
          type empty;
        }
        leaf minimum-delay {
          type empty;
        }
      }
    }
    container probe {
      tailf:cli-add-mode;
      container tos {
        tailf:cli-add-mode;
        leaf dscp {
          type uint8;
        }
        leaf traffic-class {
          type uint8;
        }
      }
      container sweep {
        tailf:cli-add-mode;
        container destination {
          tailf:cli-compact-syntax;
          tailf:cli-sequence-commands {
            tailf:cli-reset-siblings;
          }
          leaf ipv4 {
            type inet:ipv4-address;
          }
          leaf range {
            type uint8;
          }
        }
      }
      leaf tx-interval {
        type uint32;
      }
      leaf measurement-mode {
        type enumeration {
          enum loopback;
          enum one-way;
          enum two-way;
        }
      }
      leaf protocol {
        type enumeration {
          enum pm-mpls;
          enum twamp-light;
        }
      }
      leaf computation-interval {
        type uint16;
      }
      leaf burst-interval {
        type uint16;
      }
    }
  }

  grouping pm-ep-grouping {
    container segment-list {
      list name {
        key "id";
        leaf id {
          type string;
        }
      }
    }
    leaf description {
      tailf:cli-multi-value;
      type string;
    }
    container source-address {
      leaf ipv4 {
        type inet:ipv4-address;
      }
      leaf ipv6 {
        type inet:ipv6-address;
      }
    }
    container delay-measurement {
      tailf:cli-add-mode;
      presence "true";
      container delay-profile {
        leaf name {
          type string;
        }
      }
    }
    container liveness-detection {
      tailf:cli-add-mode;
      presence "true";
      container liveness-profile {
        leaf name {
          type string;
        }
      }
    }
  }

  grouping pm-ld-grouping {
    container liveness-detection {
      tailf:cli-add-mode;
      container logging {
        leaf state-change {
          type empty;
        }
      }
      leaf multiplier {
        type uint8;
      }
    }
    container probe {
      tailf:cli-add-mode;
      container tos {
        leaf dscp {
          type uint8;
        }
      }
      container sweep {
        tailf:cli-add-mode;
        container destination {
          tailf:cli-compact-syntax;
          tailf:cli-sequence-commands {
            tailf:cli-reset-siblings;
          }
          leaf ipv4 {
            type inet:ipv4-address;
          }
          leaf range {
            type uint8;
          }
        }
      }
      leaf tx-interval {
        type uint32;
      }
      leaf measurement-mode {
        type enumeration {
          enum loopback;
        }
      }
      leaf burst-interval {
        type uint16;
      }
    }
    container npu-offload {
      tailf:cli-add-mode;
      leaf enable {
        type empty;
      }
    }
  }

  container eap {
    list profile {
      key "name";
      leaf name {
        type string;
      }
      container method {
        container tls {
          tailf:cli-add-mode;
          leaf pki-trustpoint {
            type string;
          }
        }
      }
      leaf identity {
        type string;
      }
    }
  }
  container dot1x {
    list profile {
      key "name";
      leaf name {
        type string;
      }
      leaf pae {
        type enumeration {
          enum authenticator;
          enum supplicant;
          enum both;
        }
      }
      container authenticator {
        tailf:cli-add-mode;
        container timer {
          container reauth-time {
            leaf seconds {
              tailf:cli-drop-node-name;
              type uint32;
            }
            leaf server {
              type empty;
            }
          }
        }
      }
      container supplicant {
        tailf:cli-add-mode;
        container eap {
          leaf profile {
            type string;
          }
        }
      }
    }
  }
  list macsec-policy {
    key "name";
    leaf name {
      type string;
    }
    leaf conf-offset {
      type enumeration {
        enum CONF-OFFSET-0;
        enum CONF-OFFSET-30;
        enum CONF-OFFSET-50;
      }
    }
    leaf security-policy {
      type enumeration {
        enum must-secure;
        enum should-secure;
      }
    }
    leaf window-size {
      type uint16;
    }
    leaf cipher-suite {
      type enumeration {
        enum GCM-AES-128;
        enum GCM-AES-256;
        enum GCM-AES-XPN-128;
        enum GCM-AES-XPN-256;
      }
    }
    leaf include-icv-indicator {
      type empty;
    }
    leaf delay-protection {
      type empty;
    }
    leaf key-server-priority {
      type uint8;
    }
    container sak-rekey-interval {
      leaf seconds {
        type uint32;
      }
    }
    container policy-exception {
      leaf lacp-in-clear {
        type empty;
      }
    }
    leaf enable-legacy-fallback {
      type empty;
    }
    leaf vlan-tags-in-clear {
      type uint8;
    }
  }
  list track {
    key "name";
    leaf name {
      tailf:cli-suppress-range;
      type string;
    }
    container type {
      container rtr {
        tailf:cli-compact-syntax;
        tailf:cli-sequence-commands;
        leaf ipsla-no {
          tailf:cli-drop-node-name;
          type uint16;
        }
        leaf reachability {
          type empty;
        }
      }
      container list {
        container boolean {
          container and {
            tailf:cli-add-mode;
            presence "true";
            list object {
              tailf:cli-suppress-mode;
              tailf:cli-delete-when-empty;
              key "name";
              leaf name {
                type string;
              }
              leaf not {
                type empty;
              }
            }
          }
          container or {
            tailf:cli-add-mode;
            presence "true";
            list object {
              tailf:cli-suppress-mode;
              tailf:cli-delete-when-empty;
              key "name";
              leaf name {
                type string;
              }
              leaf not {
                type empty;
              }
            }
          }
        }
      }
      container line-protocol {
        container state {
          tailf:cli-add-mode;
          presence "true";
          container interface {
            uses interface-name-grouping;
          }
        }
      }
      container route {
        container reachability {
          tailf:cli-add-mode;
          presence "true";
          leaf vrf {
            type string;
          }
          container route {
            choice addr-choice {
              leaf ipv4 {
                type inet:ipv4-prefix;
              }
              leaf address {
                tailf:cli-drop-node-name;
                type union {
                  type tailf:ipv4-address-and-prefix-length;
                  type tailf:ipv6-address-and-prefix-length;
                }
              }
            }
          }
        }
      }
      container bgp {
        container neighbor {
          container address-family {
            container state {
              tailf:cli-add-mode;
              presence "true";
              container address-family {
                container l2vpn {
                  container evpn {
                    tailf:cli-add-mode;
                    presence "true";
                    container neighbor {
                      tailf:cli-compact-syntax;
                      tailf:cli-sequence-commands {
                        tailf:cli-reset-siblings;
                      }
                      leaf address {
                        tailf:cli-drop-node-name;
                        type inet:host;
                      }
                      leaf disable {
                        type enumeration {
                          enum fib-check;
                        }
                      }
                    }
                  }
                }
              }
            }
          }
        }
      }
    }
    container action {
      tailf:cli-add-mode;
      container track-down {
        container error-disable {
          list interface {
            tailf:cli-suppress-mode;
            tailf:cli-delete-when-empty;
            tailf:cli-compact-syntax;
            tailf:cli-sequence-commands {
              tailf:cli-reset-siblings;
            }
            key "name";
            leaf name {
              type ifname;
            }
            leaf auto-recover {
              type empty;
            }
          }
        }
      }
    }
    container delay {
      leaf up {
        type uint16;
      }
      leaf down {
        type uint16;
      }
    }
  }
  container ipsla {
    tailf:cli-add-mode;
    container hw-timestamp {
      leaf disable {
        type empty;
      }
    }
    list operation {
      key "id";
      leaf id {
        type uint16;
      }
      uses apply-group-grouping;
      container type {
        list udp {
          key "name";
          leaf name {
            type enumeration {
              enum echo;
              enum jitter;
            }
          }
          uses ipsla-operation-type-grouping;
        }
        list icmp {
          key "name";
          leaf name {
            type enumeration {
              enum echo;
              enum path-echo;
              enum path-jitter;
            }
          }
          uses ipsla-operation-type-grouping;
        }
        container mpls {
          list lsp {
            key "name";
            leaf name {
              type enumeration {
                enum ping;
                enum trace;
              }
            }
            uses ipsla-operation-type-grouping;
          }
        }
      }
    }
    container reaction {
      list operation {
        key "id";
        leaf id {
          type uint16;
        }
        uses apply-group-grouping;
        container react {
          container connection-loss {
            tailf:cli-add-mode;
            uses ipsla-reaction-operation-react-grouping;
          }
          container jitter-average {
            tailf:cli-add-mode;
            uses ipsla-reaction-operation-react-grouping;
          }
          container packet-loss {
            container dest-to-source {
              tailf:cli-add-mode;
              uses ipsla-reaction-operation-react-grouping;
            }
            container source-to-dest {
              tailf:cli-add-mode;
              uses ipsla-reaction-operation-react-grouping;
            }
          }
          container timeout {
            tailf:cli-add-mode;
            container action {
              leaf logging {
                type empty;
              }
              leaf trigger {
                type empty;
              }
            }
            container threshold {
              container type {
                choice type-choice {
                  leaf consecutive {
                    type uint8;
                  }
                  leaf immediate {
                    type empty;
                  }
                  container xofy {
                    tailf:cli-compact-syntax;
                    tailf:cli-sequence-commands {
                      tailf:cli-reset-siblings;
                    }
                    leaf x-value {
                      tailf:cli-drop-node-name;
                      type uint8;
                    }
                    leaf y-value {
                      tailf:cli-drop-node-name;
                      type uint8;
                    }
                  }
                }
              }
            }
          }
          container rtt {
            tailf:cli-add-mode;
            uses ipsla-reaction-operation-react-grouping;
          }
        }
      }
    }
    container schedule {
      list operation {
        key "id";
        leaf id {
          type uint16;
        }
        uses apply-group-grouping;
        container start-time {
          tailf:cli-flatten-container;
          tailf:cli-compact-syntax;
          choice start-time-choice {
            leaf after {
              type string;
            }
            leaf now {
              type empty;
            }
            leaf pending {
              type empty;
            }
            leaf time {
              tailf:cli-drop-node-name;
              type string;
            }
          }
        }
        leaf life {
          type union {
            type enumeration {
              enum forever;
            }
            type uint32;
          }
        }
        leaf ageout {
          type uint32;
        }
      }
    }
    leaf key-chain {
      type string;
    }
    container responder {
      tailf:cli-add-mode;
      presence "true";
      container type {
        container udp {
          list ipv4 {
            tailf:cli-suppress-mode;
            tailf:cli-delete-when-empty;
            key "address port";
            leaf address {
              type inet:ipv4-address;
            }
            leaf port {
              type uint16;
            }
          }
        }
      }
      container twamp {
        tailf:cli-add-mode;
        presence "true";
        leaf timeout {
          type uint32;
        }
      }
      container twamp-light {
        list test-session {
          key "id";
          leaf id {
            type uint8;
          }
          list local-ip {
            tailf:cli-suppress-mode;
            tailf:cli-delete-when-empty;
            tailf:cli-compact-syntax;
            tailf:cli-sequence-commands {
              tailf:cli-reset-siblings;
            }
            key "local-ip local-port remote-ip remote-port vrf";
            leaf local-ip {
              type union {
                type inet:ipv4-address;
                type inet:ipv6-address;
                type enumeration {
                  enum any;
                }
              }
            }
            leaf local-port {
              type uint16;
            }
            leaf remote-ip {
              type union {
                type inet:ipv4-address;
                type inet:ipv6-address;
                type enumeration {
                  enum any;
                }
              }
            }
            leaf af {
              tailf:cli-drop-node-name;
              tailf:cli-optional-in-sequence;
              tailf:cli-prefix-key {
                tailf:cli-before-key "4";
              }
              type enumeration {
                enum ipv4;
                enum ipv6;
              }
            }
            leaf remote-port {
              type union {
                type uint16;
                type enumeration {
                  enum any;
                }
              }
            }
            leaf vrf {
              type string;
            }
          }
          leaf timeout {
            type uint32;
          }
        }
      }
    }
    container server {
      container twamp {
        tailf:cli-add-mode;
        presence "true";
        leaf port {
          type uint16;
        }
        container timer {
          leaf inactivity {
            type uint16;
          }
        }
      }
    }
  }
  container performance-mgmt {
    container statistics {
      container interface {
        container basic-counters {
          uses performance-mgmt-template-grouping;
        }
        container data-rates {
          uses performance-mgmt-template-grouping;
        }
        container generic-counters {
          uses performance-mgmt-template-grouping;
        }
      }
      container bgp {
        uses performance-mgmt-template-grouping;
      }
    }
    container thresholds {
      container node {
        container cpu {
          list template {
            key "name";
            leaf name {
              type string;
            }
            uses performance-mgmt-grouping;
          }
        }
        container process {
          list template {
            key "name";
            leaf name {
              type string;
            }
            uses performance-mgmt-grouping;
          }
        }
      }
    }
    container resources {
      leaf dump {
        type enumeration {
          enum local;
        }
      }
      container memory {
        tailf:cli-compact-syntax;
        tailf:cli-sequence-commands {
          tailf:cli-reset-siblings;
        }
        leaf max-limit {
          type uint32;
        }
        leaf min-reserved {
          type uint32;
        }
      }
      container tftp-server {
        tailf:cli-compact-syntax;
        tailf:cli-sequence-commands {
          tailf:cli-reset-siblings;
        }
        leaf host {
          tailf:cli-drop-node-name;
          type string;
        }
        leaf vrf {
          tailf:cli-optional-in-sequence;
          type string;
        }
        leaf directory {
          type string;
        }
      }
    }
    list apply {
      tailf:cli-suppress-mode;
      tailf:cli-delete-when-empty;
      key "name";
      leaf name {
        tailf:cli-multi-word-key;
        type string;
      }
    }
  }
  container vlan {
    container internal {
      container allocation {
        leaf policy {
          type enumeration {
            enum ascending;
            enum descending;
          }
        }
      }
    }
    container access-log {
      leaf maxflow {
        type uint16;
      }
      leaf ratelimit {
        type uint16;
      }
      leaf threshold {
        type uint32;
      }
    }
    list vlan-list {
      tailf:cli-drop-node-name;
      tailf:cli-range-list-syntax;
      key "id";
      leaf id {
        type uint16;
      }
      leaf name {
        tailf:cli-multi-value;
        type string;
      }
      leaf uni-vlan {
        type enumeration {
          enum community;
          enum isolated;
        }
      }
    }
  }
  container lldp {
    tailf:cli-add-mode;
    presence "true";
    container subinterfaces {
      leaf enable {
        type empty;
      }
    }
    leaf holdtime {
      type uint16;
    }
    leaf reinit {
      type uint8;
    }
    leaf run {
      type empty;
    }
    leaf timer {
      type uint16;
    }
    container extended-show-width {
      leaf enable {
        type empty;
      }
    }
    container tlv-select {
      tailf:cli-add-mode;
      leaf port-description {
        type enumeration {
          enum disable;
        }
      }
      leaf management-address {
        type enumeration {
          enum disable;
        }
      }
      leaf system-capabilities {
        type enumeration {
          enum disable;
        }
      }
      leaf system-description {
        type enumeration {
          enum disable;
        }
      }
    }
    container management {
      leaf enable {
        type empty;
      }
    }
  }
  container mld {
    container snooping {
      list profile {
        key "name";
        leaf name {
          type string;
        }
        leaf router-guard {
          type empty;
        }
        leaf minimum-version {
          type uint8;
        }
        container mrouter-enable {
          tailf:cli-drop-node-name;
          leaf mrouter {
            type empty;
          }
        }
        container mrouter {
          container forwarding {
            leaf disable {
              type empty;
            }
          }
        }
        container router-alert-check {
          leaf disable {
            type empty;
          }
        }
      }
    }
  }
  container igmp {
    container snooping {
      list profile {
        key "name";
        leaf name {
          type string;
        }
        container mrouter {
          presence "true";
        }
        leaf system-ip-address {
          type inet:ipv4-address;
        }
        leaf minimum-version {
          type uint8;
        }
        container internal-querier {
          presence "true";
        }
        container internal-querier-conf {
          tailf:cli-drop-node-name;
          container internal-querier {
            leaf version {
              type uint8;
            }
          }
        }
        container tcn {
          container query {
            leaf solicit {
              type empty;
            }
          }
          container flood {
            container query {
              leaf count {
                type uint8;
              }
            }
          }
        }
        container report-suppression {
          leaf disable {
            type empty;
          }
        }
        leaf router-guard {
          type empty;
        }
        container router-alert-check {
          leaf disable {
            type empty;
          }
        }
      }
    }
  }
  container switch-fabric {
    tailf:cli-add-mode;
    list service-policy {
      tailf:cli-suppress-mode;
      tailf:cli-delete-when-empty;
      key "name";
      leaf name {
        type string;
      }
    }
  }
  container lpts {
    container pifib {
      container hardware {
        container police {
          tailf:cli-add-mode;
          presence "true";
          uses lpts-flow-grouping;
        }
        container police-location {
          tailf:cli-drop-node-name;
          container police {
            list location {
              key "id";
              leaf id {
                type string;
              }
              leaf preconfigure {
                tailf:cli-prefix-key;
                type empty;
              }
              uses lpts-flow-grouping;
            }
          }
        }
        container dynamic-flows {
          list location {
            key "id";
            leaf id {
              type string;
            }
            leaf preconfigure {
              tailf:cli-prefix-key;
              type empty;
            }
            list flow {
              tailf:cli-suppress-mode;
              tailf:cli-delete-when-empty;
              key "name";
              leaf name {
                tailf:cli-multi-word-key;
                type string;
              }
              container known {
                leaf max {
                  type uint32;
                }
              }
              container configured {
                leaf max {
                  type uint32;
                }
              }
              leaf max {
                type uint32;
              }
            }
          }
        }
      }
    }
    container punt {
      container excessive-flow-trap {
        tailf:cli-add-mode;
        list penalty-rate {
          tailf:cli-suppress-mode;
          tailf:cli-delete-when-empty;
          key "protocol";
          leaf protocol {
            type enumeration {
              enum arp;
              enum dhcp;
              enum icmp;
              enum igmp;
              enum ip;
              enum l2tp;
              enum ppp;
              enum pppoe;
              enum unclassified;
              enum default;
            }
          }
          leaf rate {
            tailf:cli-drop-node-name;
            type uint8;
          }
        }
        list penalty-timeout {
          tailf:cli-suppress-mode;
          tailf:cli-delete-when-empty;
          key "protocol";
          leaf protocol {
            type enumeration {
              enum arp;
              enum dhcp;
              enum icmp;
              enum igmp;
              enum ip;
              enum l2tp;
              enum ppp;
              enum pppoe;
              enum unclassified;
              enum default;
            }
          }
          leaf value {
            tailf:cli-drop-node-name;
            type uint16;
          }
        }
        container exclude {
          list interface {
            tailf:cli-suppress-mode;
            tailf:cli-delete-when-empty;
            key "name";
            leaf name {
              type ifname;
            }
          }
        }
        container dampening {
          tailf:cli-delete-when-empty;
          presence "true";
          leaf time {
            tailf:cli-drop-node-name;
            type uint16;
          }
        }
        leaf subscriber-interfaces {
          type empty;
        }
        container non-subscriber-interfaces {
          tailf:cli-delete-when-empty;
          presence "true";
          leaf mac {
            type empty;
          }
        }
        leaf trap-size {
          type uint8;
        }
        leaf sample-prob {
          type string;
        }
        leaf report-threshold {
          type uint16;
        }
        leaf interface-based-flow {
          type empty;
        }
      }
      container police {
        list location {
          key "name";
          leaf name {
            type string;
          }
          leaf preconfigure {
            tailf:cli-prefix-key;
            type empty;
          }
          list protocol {
            tailf:cli-suppress-mode;
            tailf:cli-delete-when-empty;
            key "name";
            leaf name {
              tailf:cli-multi-word-key;
              type string;
            }
            leaf rate {
              type uint32;
            }
          }
          container exception {
            grouping rate-leaf {
              leaf rate {
                type uint32;
              }
            }

            container ipv4 {
              container fragment {
                uses rate-leaf;
              }
              container ttl-error {
                uses rate-leaf;
              }
            }
            container ipv6 {
              container fragment {
                uses rate-leaf;
              }
              container ttl-error {
                uses rate-leaf;
              }
            }
            container ttl-expiry {
              uses rate-leaf;
            }
            container mpls {
              container fragment {
                uses rate-leaf;
              }
              container ttl-error {
                uses rate-leaf;
              }
              container ttl-expiry {
                uses rate-leaf;
              }
            }
          }
        }
      }
    }
  }
  container cnbng-nal {
    list location {
      key "name";
      leaf name {
        type string;
      }
      leaf preconfigure {
        tailf:cli-prefix-key;
        type empty;
      }
      uses description-grouping;
      leaf hostidentifier {
        type string;
      }
      container up-server {
        choice up-server-choice {
          container ipv4 {
            tailf:cli-compact-syntax;
            tailf:cli-sequence-commands {
              tailf:cli-reset-siblings;
            }
            leaf address {
              tailf:cli-drop-node-name;
              type inet:ipv4-address;
            }
            leaf gtp-port {
              tailf:cli-optional-in-sequence;
              type uint16;
            }
            leaf pfcp-port {
              tailf:cli-optional-in-sequence;
              type uint16;
            }
            leaf vrf {
              type string;
            }
          }
          container interface {
            tailf:cli-compact-syntax;
            tailf:cli-sequence-commands {
              tailf:cli-reset-siblings;
            }
            leaf Loopback {
              tailf:cli-allow-join-with-value;
              type uint32;
            }
            leaf gtp-port {
              tailf:cli-optional-in-sequence;
              type uint16;
            }
            leaf pfcp-port {
              tailf:cli-optional-in-sequence;
              type uint16;
            }
            leaf vrf {
              type string;
            }
          }
        }
      }
      container cp-server {
        container primary {
          leaf ipv4 {
            type inet:ipv4-address;
          }
        }
      }
      container auto-loopback {
        list vrf {
          key "name";
          leaf name {
            type string;
          }
          uses description-grouping;
          list interface {
            key "name";
            leaf name {
              type string;
            }
            leaf primary-address {
              type inet:ipv4-address;
            }
          }
        }
      }
      container route-summary {
        leaf tag {
          type uint32;
        }
      }
      container disconnect-history {
        leaf file-logging-enable {
          type empty;
        }
      }
      container spa-req-resp-history {
        leaf file-logging-enable {
          type empty;
        }
      }
      leaf disable-secondary-address-notification {
        type empty;
      }
      container cp-association {
        leaf retry-count {
          type uint8;
        }
      }
      container ipoe {
        leaf fsol-flow-control {
          type uint16;
        }
      }
      container pppoe {
        leaf fsol-flow-control {
          type uint16;
        }
      }
      container trace {
        leaf level {
          type enumeration {
            enum low;
            enum high;
            enum default;
            enum verbose;
            enum critical;
            enum all;
          }
        }
      }
      container up-cp-notification {
        leaf flow-control {
          type uint16;
        }
      }
      container up-cp-stats {
        leaf flow-control {
          type uint16;
        }
      }
      container l2tp {
        leaf enable {
          type empty;
        }
      }
      leaf enable-tr459-mode {
        type empty;
      }
      leaf l2tp-tcp-mss-adjust {
        type uint16;
      }
      container subscriber-redundancy {
        tailf:cli-add-mode;
        list group {
          key "name";
          leaf name {
            type string;
          }
          leaf route-tag {
            type uint32;
          }
          leaf core-tracking {
            type string;
          }
          leaf damping-timer-val {
            type uint16;
          }
          leaf virtual-mac {
            type string;
          }
          leaf access-tracking {
            type string;
          }
          container access-interface-list {
            tailf:cli-add-mode;
            list interface {
              tailf:cli-suppress-mode;
              tailf:cli-delete-when-empty;
              tailf:cli-compact-syntax;
              tailf:cli-sequence-commands {
                tailf:cli-reset-siblings;
              }
              key "name";
              leaf name {
                type string;
              }
              container sub-intf-range {
                tailf:cli-flatten-container;
                tailf:cli-compact-syntax;
                tailf:cli-sequence-commands {
                  tailf:cli-reset-siblings;
                }
                leaf start {
                  tailf:cli-drop-node-name;
                  type uint32;
                }
                leaf end {
                  tailf:cli-drop-node-name;
                  type uint32;
                }
              }
            }
          }
          leaf fast-switchover-disable {
            type empty;
          }
          uses description-grouping;
        }
        leaf damping-timer-val {
          type uint16;
        }
        leaf stats-request-rate {
          type uint16;
        }
        leaf stats-request-svm-timeout {
          type uint16;
        }
        leaf stats-request-rate-timeout {
          type uint16;
        }
      }
      leaf max-create-in-progress {
        type uint16;
      }
      leaf max-delete-in-progress {
        type uint16;
      }
      leaf max-update-in-progress {
        type uint16;
      }
      leaf delete-batch-size {
        type uint16;
      }
      leaf delete-batch-timer {
        type uint16;
      }
      leaf enable-test-server {
        type empty;
      }
      container secondary-address-update {
        leaf enable {
          type empty;
        }
      }
    }
  }

  grouping interface-cnbng-nal-grouping {
    container cnbng-nal {
      container ipv6 {
        container nd {
          tailf:cli-add-mode;
          leaf nud-enable {
            type empty;
          }
          container ra-initial {
            tailf:cli-compact-syntax;
            tailf:cli-sequence-commands {
              tailf:cli-reset-siblings;
            }
            leaf count {
              tailf:cli-drop-node-name;
              type uint8;
            }
            leaf interval {
              tailf:cli-drop-node-name;
              type uint16;
            }
          }
          leaf ra-unicast {
            type empty;
          }
          leaf ns-interval {
            type uint32;
          }
          container ra-interval {
            tailf:cli-compact-syntax;
            tailf:cli-sequence-commands {
              tailf:cli-reset-siblings;
            }
            leaf maximum {
              tailf:cli-drop-node-name;
              type uint16;
            }
            leaf minimum {
              tailf:cli-drop-node-name;
              type uint16;
            }
          }
          leaf ra-lifetime {
            type uint16;
          }
          leaf suppress-ra {
            type empty;
          }
          leaf slaac-enable {
            type empty;
          }
          container mtu {
            leaf suppress {
              type empty;
            }
          }
          leaf other-config-flag {
            type empty;
          }
          leaf managed-config-flag {
            type empty;
          }
          leaf reachable-time {
            type uint32;
          }
          leaf router-preference {
            type enumeration {
              enum low;
              enum medium;
              enum high;
            }
          }
          container hop-limit {
            leaf unspecified {
              type empty;
            }
          }
          leaf start-ra-on-ipv6-enable {
            type empty;
          }
          leaf suppress-cache-learning {
            type empty;
          }
        }
      }
    }
  }

  container healthcheck {
    tailf:cli-add-mode;
    leaf cadence {
      type uint16;
    }
    container use-case {
      container asic-reset {
        leaf disable {
          type empty;
        }
      }
      container packet-drop {
        leaf disable {
          type empty;
        }
      }
    }
    leaf enable {
      type empty;
    }
  }
  container hw-module {
    container shut {
      list location {
        tailf:cli-suppress-mode;
        tailf:cli-delete-when-empty;
        key "name";
        leaf name {
          type string;
        }
      }
    }
    container unshut {
      list location {
        tailf:cli-suppress-mode;
        tailf:cli-delete-when-empty;
        key "name";
        leaf name {
          type string;
        }
      }
    }
    container ejector {
      container close {
        leaf wait {
          type empty;
        }
      }
    }
    container fib {
      container ipv4 {
        leaf scale {
          type enumeration {
            enum host-optimized-disable;
            enum internet-optimized;
          }
        }
      }
      container ipv6 {
        leaf scale {
          type enumeration {
            enum internet-optimized-disable;
            enum internet-optimized;
          }
        }
      }
      container mpls {
        container label {
          leaf lsr-optimized {
            type empty;
          }
        }
        container ldp {
          leaf lsr-optimized {
            type empty;
          }
        }
      }
    }
    container qos {
      container pol-gran {
        tailf:cli-compact-syntax;
        tailf:cli-sequence-commands {
          tailf:cli-reset-siblings;
        }
        leaf granularity {
          tailf:cli-drop-node-name;
          type uint8;
        }
        leaf location {
          type string;
        }
      }
      container queue-auto-defrag {
        container disable {
          list location {
            key "id";
            leaf id {
              type string;
            }
          }
        }
      }
      container account {
        container layer2 {
          container encapsulation {
            tailf:cli-compact-syntax;
            tailf:cli-sequence-commands {
              tailf:cli-reset-siblings;
            }
            choice encapsulation-choice {
              leaf arpa {
                type empty;
              }
              leaf dot1q {
                type empty;
              }
              leaf length {
                type uint8;
              }
            }
            leaf location {
              type string;
            }
          }
        }
      }
      container multicast {
        tailf:cli-compact-syntax;
        leaf location {
          type string;
        }
        container priorityq {
          container disable {
            leaf location {
              type string;
            }
          }
        }
      }
    }
    container pse {
      container allocate {
        container tcam {
          list location {
            key "id";
            leaf id {
              type string;
            }
            list region {
              key "name num";
              leaf name {
                type string;
              }
              leaf num {
                type uint32;
              }
            }
          }
        }
      }
    }
    container mac-move {
      leaf police-mode {
        type enumeration {
          enum on;
          enum off;
        }
      }
    }
    container linecard {
      list throughput {
        tailf:cli-suppress-mode;
        tailf:cli-delete-when-empty;
        tailf:cli-compact-syntax;
        tailf:cli-sequence-commands;
        key "name";
        leaf name {
          type string;
        }
        leaf throughput {
          tailf:cli-drop-node-name;
          tailf:cli-prefix-key;
          type enumeration {
            enum 20G;
            enum 40G;
          }
        }
      }
    }
    container location {
      uses hw-module-location-list-grouping;
      container preconfigure {
        uses hw-module-location-list-grouping;
      }
    }
    list subslot {
      tailf:cli-suppress-mode;
      tailf:cli-delete-when-empty;
      key "name";
      leaf name {
        type string;
      }
      leaf cardtype {
        type enumeration {
          enum e1;
          enum e3;
          enum sdh;
          enum sonet;
          enum t1;
          enum t3;
        }
      }
      container shutdown {
        tailf:cli-delete-when-empty;
        presence "true";
        leaf option {
          tailf:cli-drop-node-name;
          type enumeration {
            enum powered;
            enum unpowered;
          }
        }
      }
    }
    list port {
      tailf:cli-suppress-mode;
      tailf:cli-delete-when-empty;
      key "id";
      leaf id {
        type uint8;
      }
      list srp {
        tailf:cli-suppress-mode;
        tailf:cli-delete-when-empty;
        key "location";
        leaf location {
          type string;
        }
        leaf spa-bay {
          type uint8;
        }
      }
    }
    list port-range {
      tailf:cli-suppress-mode;
      tailf:cli-delete-when-empty;
      tailf:cli-compact-syntax;
      tailf:cli-sequence-commands;
      key "start end instance";
      leaf start {
        type uint8;
      }
      leaf end {
        type uint8;
      }
      leaf instance {
        type uint8;
      }
      leaf location {
        type string;
      }
      leaf mode {
        type string;
      }
    }
    container profile {
      container acl {
        container ingress {
          container compress {
            container enable {
              list location {
                tailf:cli-suppress-mode;
                tailf:cli-delete-when-empty;
                key "name";
                leaf name {
                  type string;
                }
              }
            }
          }
        }
        container egress {
          container layer3 {
            leaf interface-based {
              type empty;
            }
          }
        }
      }
      container qos {
        leaf hqos-enable {
          type empty;
        }
        leaf physical-hqos-enable {
          type empty;
        }
        leaf-list qosg-dscp-mark-enable {
          tailf:cli-flat-list-syntax;
          ordered-by user;
          type uint8;
        }
        container max-classmap-size {
          leaf value {
            tailf:cli-drop-node-name;
            type enumeration {
              enum 4;
              enum 8;
              enum 16;
              enum 32;
            }
          }
          list location-list {
            tailf:cli-drop-node-name;
            tailf:cli-suppress-mode;
            tailf:cli-delete-when-empty;
            tailf:cli-compact-syntax;
            tailf:cli-sequence-commands;
            leaf value {
              tailf:cli-drop-node-name;
              tailf:cli-prefix-key;
              type enumeration {
                enum 4;
                enum 8;
                enum 16;
                enum 32;
              }
            }
            key "location";
            leaf location {
              type string;
            }
          }
        }
        container ingress-model {
          leaf peering {
            type empty;
          }
          container peering-location {
            tailf:cli-drop-node-name;
            container peering {
              list location {
                tailf:cli-suppress-mode;
                tailf:cli-delete-when-empty;
                key "name";
                leaf name {
                  type string;
                }
              }
            }
          }
        }
        leaf conform-aware-policer {
          type empty;
        }
        leaf egress-compensation-setting-force {
          type empty;
        }
        container ipv6 {
          leaf short {
            type empty;
          }
        }
        list bundle {
          tailf:cli-suppress-mode;
          tailf:cli-delete-when-empty;
          key "location";
          leaf scale {
            tailf:cli-drop-node-name;
            tailf:cli-prefix-key;
            type enumeration {
              enum low-scale;
              enum medium-scale;
              enum high-scale;
            }
          }
          leaf location {
            type string;
          }
        }
      }
      container segment-routing {
        container srv6 {
          tailf:cli-delete-when-empty;
          presence "true";
          container encapsulation {
            leaf traffic-class {
              type union {
                type enumeration {
                  enum propagate;
                }
                type string;
              }
            }
          }
          container mode {
            container micro-segment {
              container format {
                container f3216 {
                  container encapsulation {
                    leaf traffic-class {
                      type union {
                        type enumeration {
                          enum propagate;
                        }
                        type string;
                      }
                    }
                  }
                }
              }
            }
          }
        }
      }
      container stats {
        choice stats-choice {
          leaf acl-permit {
            type empty;
          }
          leaf enh-sr-policy {
            type empty;
          }
          leaf ingress-sr {
            type empty;
          }
          leaf qos-enhanced {
            type empty;
          }
          leaf tx-scale-enhanced {
            type empty;
          }
        }
      }
      container flowspec {
        leaf v6-enable {
          type empty;
        }
        container v6-enable-location {
          tailf:cli-drop-node-name;
          container v6-enable {
            list location {
              tailf:cli-suppress-mode;
              tailf:cli-delete-when-empty;
              key "name";
              leaf name {
                type string;
              }
            }
          }
        }
      }
      container tcam {
        container acl-prefix {
          leaf percent {
            type uint8;
          }
        }
        container fib {
          container ipv4 {
            container unicast {
              leaf percent {
                type uint8;
              }
            }
          }
        }
        container format {
          list access-list {
            tailf:cli-suppress-mode;
            tailf:cli-delete-when-empty;
            key "af";
            leaf af {
              type enumeration {
                enum ipv4;
                enum ipv6;
              }
            }
            leaf acl-qualifiers {
              tailf:cli-drop-node-name;
              tailf:cli-multi-value;
              type string;
            }
          }
        }
      }
      container mpls-ext-dscp-preserve {
        leaf v4uc-enable {
          type empty;
        }
      }
      container load-balance {
        container algorithm {
          choice alg-choice {
            leaf gtp-mpls {
              type empty;
            }
            leaf gtp {
              type empty;
            }
            leaf L3-only {
              type empty;
            }
          }
        }
      }
      leaf bundle-scale {
        type enumeration {
          enum 256;
          enum 512;
          enum 1024;
        }
      }
      container cef {
        container bgplu {
          leaf enable {
            type empty;
          }
        }
        container cbf {
          leaf enable {
            type empty;
          }
        }
        container dark-bw {
          leaf enable {
            type empty;
          }
        }
        container ip-redirect {
          leaf enable {
            type empty;
          }
        }
        container ipv6 {
          container hop-limit {
            leaf punt {
              type empty;
            }
          }
        }
        container lpts {
          leaf acl {
            type empty;
          }
          leaf pifib-entry-counters {
            type uint16;
          }
        }
        container stats {
          container label {
            container app-default {
              leaf dynamic {
                type empty;
              }
            }
          }
        }
        container te-tunnel {
          leaf highscale-no-ldp-over-te {
            type empty;
          }
        }
        container ttl {
          container tunnel-ip {
            container decrement {
              leaf disable {
                type empty;
              }
            }
          }
        }
      }
      container npu {
        leaf native-mode-enable {
          type empty;
        }
      }
      container otn {
        leaf twohundredg-slot-otn-only {
          tailf:alt-name "200g-slot-otn-only";
          type empty;
        }
      }
      leaf scale {
        type enumeration {
          enum bng-max;
          enum default;
          enum evpn-convergence;
          enum l2;
          enum l3xl;
        }
      }
      leaf mdb {
        type enumeration {
          enum l2max;
          enum l2max-se;
          enum l3max;
          enum l3max-se;
        }
      }
    }
    container tcam {
      container fib {
        container ipv4 {
          leaf scaledisable {
            type empty;
          }
        }
      }
    }
    container all {
      container qos-mode {
        container pwhe-aggregate-shaper {
          container sub-interface {
            leaf egress {
              type enumeration {
                enum non-queuing;
                enum queuing;
              }
            }
            leaf ingress {
              type enumeration {
                enum non-queuing;
                enum queuing;
              }
            }
          }
        }
        leaf aggregate-bundle-mode {
          type empty;
        }
        leaf ingress-queue-enable {
          type empty;
        }
      }
    }
    container service {
      container offline {
        list location {
          tailf:cli-suppress-mode;
          tailf:cli-delete-when-empty;
          key "name";
          leaf name {
            type string;
          }
        }
      }
    }
    list quad {
      key "id location";
      leaf id {
        tailf:cli-suppress-range;
        type uint8;
      }
      leaf location {
        type string;
      }
      leaf mode {
        type string;
      }
    }
    container quad-instance {
      tailf:cli-drop-node-name;
      list quad {
        key "id location instance";
        leaf id {
          tailf:cli-suppress-range;
          type uint8;
        }
        leaf location {
          type string;
        }
        leaf instance {
          type uint8;
        }
        leaf mode {
          type string;
        }
      }
    }
    container route-stats {
      container l3mcast {
        container l3mcast-ingress {
          tailf:cli-drop-node-name;
          tailf:cli-compact-syntax;
          leaf vrf {
            type string;
          }
          choice l3mcast-ingress-choice {
            container ipv4 {
              tailf:cli-compact-syntax;
              tailf:cli-flatten-container;
              leaf ingress {
                type string;
              }
            }
            container ipv6 {
              tailf:cli-compact-syntax;
              tailf:cli-flatten-container;
              leaf ingress {
                type string;
              }
            }
          }
        }
        container l3mcast-egress {
          tailf:cli-drop-node-name;
          tailf:cli-compact-syntax;
          leaf vrf {
            type string;
          }
          choice l3mcast-egress-choice {
            container ipv4 {
              tailf:cli-compact-syntax;
              tailf:cli-flatten-container;
              leaf egress {
                type string;
              }
            }
            container ipv6 {
              tailf:cli-compact-syntax;
              tailf:cli-flatten-container;
              leaf egress {
                type string;
              }
            }
          }
        }
      }
    }
    container bfd-hw-offload {
      container enable {
        leaf location {
          type string;
        }
      }
    }
    container vrrpscale {
      leaf enable {
        type empty;
      }
    }
    container fia-intf-policer {
      leaf disable {
        type empty;
      }
    }
    container storm-control-combine-policer-bw {
      leaf enable {
        type empty;
      }
    }
    container olr {
      list plane {
        tailf:cli-suppress-mode;
        tailf:cli-delete-when-empty;
        tailf:cli-compact-syntax;
        tailf:cli-sequence-commands {
          tailf:cli-reset-siblings;
        }
        key "name rack";
        leaf name {
          type enumeration {
            enum A;
            enum B;
          }
        }
        leaf rack {
          type uint8;
        }
        leaf nodes {
          type string;
        }
      }
    }
    container npu-power-profile {
      leaf power {
        tailf:cli-drop-node-name;
        type enumeration {
          enum low;
          enum medium;
          enum high;
        }
      }
      container card-type {
        container FC {
          leaf power {
            tailf:cli-drop-node-name;
            type enumeration {
              enum low;
              enum medium;
              enum high;
            }
          }
        }
        list LC {
          tailf:cli-suppress-mode;
          tailf:cli-delete-when-empty;
          tailf:cli-compact-syntax;
          tailf:cli-sequence-commands;
          key "location";
          leaf power {
            tailf:cli-drop-node-name;
            tailf:cli-prefix-key;
            type enumeration {
              enum low;
              enum medium;
              enum high;
            }
          }
          leaf location {
            type string;
          }
        }
      }
    }
  }
  container fpd {
    leaf auto-reload {
      type enumeration {
        enum disable;
        enum enable;
      }
    }
    leaf auto-upgrade {
      type enumeration {
        enum disable;
        enum enable;
      }
    }
    container auto-upgrade-conf {
      tailf:cli-drop-node-name;
      container auto-upgrade {
        tailf:cli-compact-syntax;
        tailf:cli-sequence-commands;
        leaf configuration {
          tailf:cli-drop-node-name;
          type enumeration {
            enum exclude;
            enum include;
          }
        }
        leaf pm {
          type empty;
        }
      }
    }
  }
  list class-map {
    key "name";
    leaf name {
      type string;
    }
    leaf type {
      tailf:cli-prefix-key;
      type enumeration {
        enum traffic;
      }
    }
    leaf prematch {
      tailf:cli-drop-node-name;
      tailf:cli-prefix-key;
      type enumeration {
        enum match-all;
        enum match-any;
      }
    }
    leaf description {
      tailf:cli-multi-value;
      type string;
    }
    container match {
      uses class-map-match-grouping;
      container not {
        uses class-map-match-grouping;
      }
    }
  }
  container class-map-filter-control {
    tailf:cli-drop-node-name;
    list class-map {
      tailf:cli-suppress-list-no;
      tailf:cli-compact-syntax;
      tailf:cli-sequence-commands;
      key "name";
      leaf name {
        type string;
      }
      leaf type {
        tailf:cli-prefix-key;
        type enumeration {
          enum control;
        }
      }
      leaf domain {
        tailf:cli-drop-node-name;
        tailf:cli-prefix-key;
        type enumeration {
          enum subscriber;
        }
      }
      leaf prematch {
        tailf:cli-drop-node-name;
        tailf:cli-prefix-key;
        type enumeration {
          enum match-all;
          enum match-any;
        }
      }
      container match {
        uses class-map-filter-control-match-grouping;
        container not {
          uses class-map-filter-control-match-grouping;
        }
      }
    }
  }
  list policy-map {
    key "name";
    leaf name {
      type string;
    }
    leaf type {
      tailf:cli-prefix-key;
      type enumeration {
        enum pbr;
        enum performance-traffic;
        enum redirect;
        enum traffic;
      }
    }
    leaf description {
      tailf:cli-multi-value;
      type string;
    }
    container class {
      list class-ref {
        tailf:cli-drop-node-name;
        ordered-by user;
        key "map";
        leaf map {
          type string;
        }
        uses policy-map-class-grouping;
      }
      list class-default {
        tailf:cli-drop-node-name;
        key "map";
        leaf map {
          type enumeration {
            enum class-default;
          }
        }
        uses policy-map-class-grouping;
      }
    }
  }
  container policy-map-event-control {
    tailf:cli-drop-node-name;
    list policy-map {
      tailf:cli-sequence-commands;
      key "name";
      leaf name {
        type string;
      }
      leaf type {
        tailf:cli-prefix-key;
        type enumeration {
          enum control;
        }
      }
      leaf domain {
        tailf:cli-drop-node-name;
        tailf:cli-prefix-key;
        type enumeration {
          enum subscriber;
        }
      }
      list event {
        ordered-by user;
        key "name match";
        leaf name {
          tailf:cli-suppress-range;
          type enumeration {
            enum account-logoff;
            enum account-logon;
            enum authentication-failure;
            enum authentication-no-response;
            enum authorization-failure;
            enum authorization-no-response;
            enum credit-exhausted;
            enum exception;
            enum idle-timeout;
            enum quota-depleted;
            enum service-start;
            enum service-stop;
            enum session-activate;
            enum session-identity-change;
            enum session-start;
            enum session-stop;
            enum timer-expiry;
          }
        }
        leaf match {
          type enumeration {
            enum match-all;
            enum match-first;
          }
        }
        list class {
          key "name";
          leaf name {
            type string;
          }
          leaf type {
            tailf:cli-prefix-key;
            type enumeration {
              enum control;
            }
          }
          leaf domain {
            tailf:cli-drop-node-name;
            tailf:cli-prefix-key;
            type enumeration {
              enum subscriber;
            }
          }
          leaf execute {
            tailf:cli-drop-node-name;
            tailf:cli-hide-in-submode;
            type enumeration {
              enum do-all;
              enum do-until-failure;
              enum do-until-success;
            }
          }
          list action-list {
            tailf:cli-drop-node-name;
            tailf:cli-suppress-mode;
            tailf:cli-delete-when-empty;
            tailf:cli-compact-syntax;
            tailf:cli-sequence-commands {
              tailf:cli-reset-siblings;
            }
            key "id";
            leaf id {
              type uint16;
            }
            leaf action {
              tailf:cli-drop-node-name;
              type enumeration {
                enum activate;
                enum authenticate;
                enum authorize;
                enum deactivate;
                enum disconnect;
                enum monitor;
                enum set-timer;
                enum stop-timer;
              }
            }
            leaf action-string {
              tailf:cli-drop-node-name;
              tailf:cli-multi-value;
              type string;
            }
          }
        }
      }
    }
  }
  container crypto {
    list keyring {
      key "name";
      leaf name {
        type string;
      }
      leaf vrf {
        tailf:cli-hide-in-submode;
        type string;
      }
      uses description-grouping;
      container rsa-pubkey {
        list name {
          key "name type";
          leaf name {
            type string;
          }
          leaf type {
            type enumeration {
              enum encryption;
              enum signature;
            }
          }
        }
      }
    }
    uses crypto-ca-grouping;
    container gdoi {
      list group {
        key "name";
        leaf name {
          type string;
        }
        container client {
          container registration {
            container interface {
              uses interface-name-grouping;
            }
          }
        }
        container identity {
          leaf number {
            type uint32;
          }
        }
        list server {
          tailf:cli-drop-node-name;
          tailf:cli-suppress-mode;
          tailf:cli-delete-when-empty;
          key "id";
          leaf id {
            type uint16;
          }
          container server {
            container address {
              leaf ipv4 {
                type inet:ipv4-address;
              }
            }
          }
        }
      }
    }
    container ipsec {
      list profile {
        key "name";
        leaf name {
          type string;
        }
        container set {
          leaf-list transform-set {
            tailf:cli-flat-list-syntax;
            ordered-by user;
            type string;
          }
          leaf pfs {
            type enumeration {
              enum group1;
              enum group14;
              enum group15;
              enum group16;
              enum group17;
              enum group18;
              enum group2;
              enum group5;
            }
          }
          leaf isakmp-profile {
            type string;
          }
          container security-association {
            container lifetime {
              choice lifetime-choice {
                leaf days {
                  type uint8;
                }
                leaf seconds {
                  type uint32;
                }
              }
            }
            container replay {
              leaf disable {
                type empty;
              }
            }
          }
        }
      }
      list transform-set {
        key "name";
        leaf name {
          type string;
        }
        choice esp-choice {
          leaf esp-aes {
            tailf:cli-hide-in-submode;
            type enumeration {
              enum 128;
              enum 192;
              enum 256;
            }
          }
          leaf esp-3des {
            tailf:cli-hide-in-submode;
            type empty;
          }
        }
        leaf transform {
          tailf:cli-drop-node-name;
          tailf:cli-hide-in-submode;
          type enumeration {
            enum esp-md5-hmac;
            enum esp-sha-hmac;
            enum esp-sha256-hmac;
            enum esp-sha384-hmac;
            enum esp-sha512-hmac;
          }
        }
        leaf mode {
          type enumeration {
            enum transport;
            enum tunnel;
          }
        }
      }
    }
    list ipsec-node {
      key "name";
      leaf name {
        type string;
      }
      leaf admin {
        type inet:ipv4-address;
      }
      leaf data {
        type inet:ipv4-address;
      }
    }
    container isakmp {
      list keyring {
        key "name";
        leaf name {
          type string;
        }
        leaf vrf {
          tailf:cli-hide-in-submode;
          type string;
        }
        uses description-grouping;
        list pre-shared-key {
          tailf:cli-suppress-mode;
          tailf:cli-delete-when-empty;
          tailf:cli-compact-syntax;
          tailf:cli-sequence-commands {
            tailf:cli-reset-siblings;
          }
          key "address";
          leaf address {
            type inet:ipv4-address;
          }
          leaf netmask {
            tailf:cli-drop-node-name;
            tailf:cli-optional-in-sequence;
            type inet:ipv4-address;
          }
          container key {
            tailf:cli-flatten-container;
            tailf:cli-compact-syntax;
            tailf:cli-sequence-commands;
            leaf type {
              tailf:cli-drop-node-name;
              tailf:cli-optional-in-sequence;
              type enumeration {
                enum encrypted;
              }
            }
            leaf secret {
              tailf:cli-drop-node-name;
              type string;
            }
          }
        }
      }
      list policy {
        key "policy-id";
        leaf policy-id {
          type uint16;
        }
        leaf hash {
          type enumeration {
            enum md5;
            enum sha;
            enum sha256;
            enum sha384;
            enum sha512;
          }
        }
        leaf group {
          type enumeration {
            enum 1;
            enum 14;
            enum 15;
            enum 16;
            enum 17;
            enum 18;
            enum 2;
            enum 5;
          }
        }
        container encryption {
          choice enc-choice {
            leaf aes {
              type enumeration {
                enum 128;
                enum 192;
                enum 256;
              }
            }
            leaf a3des {
              tailf:alt-name "3des";
              type empty;
            }
          }
        }
        leaf lifetime {
          type uint32;
        }
        leaf authentication {
          type enumeration {
            enum pre-share;
          }
        }
      }
      list profile {
        key "name";
        leaf name {
          type string;
        }
        container match {
          container identity {
            list address {
              tailf:cli-suppress-mode;
              tailf:cli-delete-when-empty;
              key "ipv4-address netmask";
              leaf ipv4-address {
                type inet:ipv4-address;
              }
              leaf netmask {
                type inet:ipv4-address;
              }
            }
          }
        }
        container match-vrf {
          tailf:cli-drop-node-name;
          container match {
            container identity {
              list address {
                tailf:cli-suppress-mode;
                tailf:cli-delete-when-empty;
                key "ipv4-address netmask vrf";
                leaf ipv4-address {
                  type inet:ipv4-address;
                }
                leaf netmask {
                  type inet:ipv4-address;
                }
                leaf vrf {
                  type string;
                }
              }
            }
          }
        }
        list keyring {
          tailf:cli-suppress-mode;
          tailf:cli-delete-when-empty;
          key "name";
          leaf name {
            type union {
              type enumeration {
                enum default;
              }
              type string;
            }
          }
        }
      }
    }
    list map {
      key "name id";
      leaf name {
        type string;
      }
      leaf id {
        type uint16;
      }
      leaf gdoi {
        tailf:cli-hide-in-submode;
        type empty;
      }
      container set {
        leaf group {
          type string;
        }
      }
      container match {
        leaf address {
          type string;
        }
      }
      container fail-close {
        tailf:cli-compact-syntax;
        tailf:cli-sequence-commands {
          tailf:cli-reset-siblings;
        }
        leaf acl {
          tailf:cli-drop-node-name;
          type string;
        }
        leaf revert {
          type empty;
        }
      }
      leaf ipsec-node {
        type string;
      }
      list interface {
        tailf:cli-suppress-mode;
        tailf:cli-delete-when-empty;
        key "name";
        leaf name {
          type string;
        }
        leaf auto-shut {
          type empty;
        }
      }
    }
    leaf fips-mode {
      type empty;
    }
  }

  grouping crypto-ca-grouping {
    container ca {
      list trustpoint {
        key "name";
        leaf name {
          type string;
        }
        container keypair {
          tailf:cli-compact-syntax;
          tailf:cli-sequence-commands {
            tailf:cli-reset-siblings;
          }
          leaf name {
            tailf:cli-drop-node-name;
            type enumeration {
              enum dsa;
              enum ecdsanistp256;
              enum ecdsanistp384;
              enum ecdsanistp521;
              enum rsa;
            }
          }
          leaf label {
            tailf:cli-drop-node-name;
            type string;
          }
        }
        container ca-keypair {
          tailf:cli-compact-syntax;
          tailf:cli-sequence-commands {
            tailf:cli-reset-siblings;
          }
          leaf name {
            tailf:cli-drop-node-name;
            type enumeration {
              enum dsa;
              enum ecdsanistp256;
              enum ecdsanistp384;
              enum ecdsanistp521;
              enum rsa;
            }
          }
          leaf label {
            tailf:cli-drop-node-name;
            type string;
          }
        }
        leaf ip-address {
          type union {
            type inet:ipv4-address;
            type enumeration {
              enum none;
            }
          }
        }
        container crl {
          leaf optional {
            type empty;
          }
        }
        leaf subject-name {
          tailf:cli-multi-value;
          type string;
        }
        container enrollment {
          leaf url {
            type union {
              type enumeration {
                enum terminal;
              }
              type string;
            }
          }
        }
        leaf rsakeypair {
          type string;
        }
        leaf message-digest {
          type enumeration {
            enum md5;
            enum sha1;
            enum sha256;
            enum sha384;
            enum sha512;
          }
        }
        leaf vrf {
          type string;
        }
        container lifetime {
          leaf certificate {
            type uint16;
          }
          leaf ca-certificate {
            type uint16;
          }
        }
      }
      container http-proxy {
        tailf:cli-compact-syntax;
        tailf:cli-sequence-commands {
          tailf:cli-reset-siblings;
        }
        leaf server {
          tailf:cli-drop-node-name;
          type string;
        }
        leaf port {
          type uint16;
        }
      }
      container source-interface {
        tailf:cli-compact-syntax;
        tailf:cli-sequence-commands {
          tailf:cli-reset-siblings;
        }
        leaf address-type {
          tailf:cli-drop-node-name;
          type enumeration {
            enum ipv4;
            enum ipv6;
          }
        }
        uses interface-name-grouping;
      }
      container fqdn-check {
        container ip-address {
          leaf allow {
            type empty;
          }
        }
      }
    }
  }

  container flow {
    list exporter-map {
      key "name";
      leaf name {
        type string;
      }
      container version {
        container v9 {
          tailf:cli-add-mode;
          presence "true";
          container options {
            container interface-table {
              tailf:cli-delete-when-empty;
              presence "true";
              leaf timeout {
                type uint32;
              }
            }
            container sampler-table {
              tailf:cli-delete-when-empty;
              presence "true";
              leaf timeout {
                type uint32;
              }
            }
            container vrf-table {
              tailf:cli-delete-when-empty;
              presence "true";
              leaf timeout {
                type uint32;
              }
            }
          }
          container template {
            leaf timeout {
              type uint32;
            }
            container data {
              leaf timeout {
                type uint32;
              }
            }
            container options {
              leaf timeout {
                type uint32;
              }
            }
          }
        }
        container ipfix {
          tailf:cli-add-mode;
          presence "true";
          container options {
            grouping timeout-grouping {
              leaf timeout {
                type uint32;
              }
            }

            container interface-table {
              presence "true";
              uses timeout-grouping;
            }
            container sampler-table {
              presence "true";
              uses timeout-grouping;
            }
            container vrf-table {
              presence "true";
              uses timeout-grouping;
            }
          }
          container template {
            grouping timeout-grouping {
              leaf timeout {
                type uint32;
              }
            }

            container data {
              uses timeout-grouping;
            }
            container options {
              uses timeout-grouping;
            }
            uses timeout-grouping;
          }
        }
      }
      leaf dscp {
        type uint8;
      }
      container transport {
        leaf udp {
          type uint16;
        }
      }
      container source {
        uses interface-name-grouping;
      }
      container destination {
        tailf:cli-compact-syntax;
        tailf:cli-sequence-commands {
          tailf:cli-reset-siblings;
        }
        leaf address {
          tailf:cli-drop-node-name;
          type inet:host;
        }
        leaf vrf {
          type vrf-type;
        }
      }
    }
    list monitor-map {
      key "name";
      leaf name {
        type string;
      }
      container record {
        choice record-choice {
          container ipv4 {
            presence "true";
            choice record-ipv4-choice {
              leaf peer-as {
                type empty;
              }
              leaf destination-tos {
                type empty;
              }
            }
          }
          container ipv6 {
            presence "true";
            leaf peer-as {
              type empty;
            }
          }
          container mpls {
            tailf:cli-compact-syntax;
            tailf:cli-sequence-commands;
            presence "true";
            leaf fields-fmt {
              tailf:cli-drop-node-name;
              tailf:cli-optional-in-sequence;
              type enumeration {
                enum ipv4-fields;
                enum ipv4-ipv6-fields;
                enum ipv6-fields;
              }
            }
            leaf labels {
              type uint8;
            }
          }
          leaf datalinksectiondump {
            type empty;
          }
        }
      }
      leaf-list option {
        type enumeration {
          enum bgpattr;
          enum filtered;
          enum outphysint;
          enum outbundlemember;
        }
      }
      leaf-list exporter {
        type string;
      }
      container cache {
        choice cache-choice {
          leaf immediate {
            type empty;
          }
          leaf permanent {
            type empty;
          }
        }
        leaf entries {
          type uint32;
        }
        container timeout {
          leaf active {
            type uint32;
          }
          leaf inactive {
            type uint32;
          }
          leaf rate-limit {
            type uint32;
          }
          leaf update {
            type uint32;
          }
        }
      }
    }
  }
  list sampler-map {
    key "name";
    leaf name {
      type string;
    }
    container random {
      tailf:cli-compact-syntax;
      tailf:cli-sequence-commands {
        tailf:cli-reset-siblings;
      }
      leaf number-of-packets {
        tailf:cli-drop-node-name;
        type enumeration {
          enum 1;
        }
      }
      leaf out-of {
        type empty;
      }
      leaf sampling-interval {
        tailf:cli-drop-node-name;
        type uint32;
      }
    }
  }
  container clock-interface {
    list list {
      tailf:cli-drop-node-name;
      key "name";
      leaf name {
        type string;
      }
      uses clock-interface-grouping;
    }
    list sync {
      key "id location";
      leaf id {
        type uint32;
      }
      leaf location {
        type string;
      }
      uses clock-interface-grouping;
    }
  }

  grouping clock-interface-grouping {
    leaf shutdown {
      type empty;
    }
    container port-parameters {
      tailf:cli-add-mode;
      uses clock-interface-port-params-grouping;
      container ansi {
        uses clock-interface-port-params-grouping;
      }
    }
    container frequency {
      container synchronization {
        tailf:cli-add-mode;
        container selection {
          leaf input {
            type empty;
          }
        }
        leaf priority {
          type uint8;
        }
        leaf time-of-day-priority {
          type uint8;
        }
        leaf wait-to-restore {
          type uint8;
        }
        container ssm {
          leaf disable {
            type empty;
          }
        }
        container quality {
          container receive {
            tailf:cli-compact-syntax;
            tailf:cli-sequence-commands {
              tailf:cli-reset-siblings;
            }
            uses freqsync-quality-grouping;
          }
        }
      }
    }
  }

  grouping clock-interface-port-params-grouping {
    container bits-input {
      tailf:cli-compact-syntax;
      tailf:cli-sequence-commands {
        tailf:cli-reset-siblings;
      }
      leaf mode {
        tailf:cli-drop-node-name;
        type enumeration {
          enum 2m;
          enum 64k-input-only;
          enum e1;
          enum t1;
        }
      }
      leaf mode1 {
        tailf:cli-drop-node-name;
        type enumeration {
          enum d4;
          enum esf;
          enum crc-4;
          enum non-crc-4;
        }
      }
      leaf sa {
        tailf:cli-drop-node-name;
        tailf:cli-optional-in-sequence;
        type enumeration {
          enum sa4;
          enum sa5;
          enum sa6;
          enum sa7;
          enum sa8;
        }
      }
      leaf mode2 {
        tailf:cli-drop-node-name;
        type union {
          type enumeration {
            enum ami;
            enum b8zs;
            enum hdb3;
          }
          type string;
        }
      }
    }
    container bits-output {
      tailf:cli-compact-syntax;
      tailf:cli-sequence-commands {
        tailf:cli-reset-siblings;
      }
      leaf mode {
        tailf:cli-drop-node-name;
        type enumeration {
          enum 2m;
          enum 6m-output-only;
          enum e1;
          enum t1;
        }
      }
      leaf mode1 {
        tailf:cli-drop-node-name;
        type enumeration {
          enum d4;
          enum esf;
          enum crc-4;
          enum non-crc-4;
        }
      }
      leaf sa {
        tailf:cli-drop-node-name;
        tailf:cli-optional-in-sequence;
        type enumeration {
          enum sa4;
          enum sa5;
          enum sa6;
          enum sa7;
          enum sa8;
        }
      }
      leaf mode2 {
        tailf:cli-drop-node-name;
        type enumeration {
          enum ami;
          enum b8zs;
          enum hdb3;
        }
      }
      leaf buildout {
        tailf:cli-drop-node-name;
        type enumeration {
          enum 0;
          enum 1;
          enum 2;
          enum 3;
          enum 4;
        }
      }
    }
  }

  container l2 {
    list vfi {
      key "name";
      leaf name {
        type string;
      }
      leaf mode {
        tailf:cli-drop-node-name;
        tailf:cli-hide-in-submode;
        type enumeration {
          enum manual;
          enum autodiscovery;
        }
      }
      container vpn {
        leaf id {
          type uint32;
        }
      }
    }
  }
  container auto {
    leaf qos {
      type enumeration {
        enum default;
      }
    }
  }
  container ethernet-services {
    list access-list {
      key "name";
      leaf name {
        type string;
      }
      list rule {
        tailf:cli-drop-node-name;
        tailf:cli-suppress-mode;
        tailf:cli-delete-when-empty;
        key "id";
        leaf id {
          type uint32;
        }
        leaf line {
          tailf:cli-drop-node-name;
          tailf:cli-multi-value;
          type string;
        }
      }
    }
  }
  container interface {
    uses interface-grouping;
    container preconfigure {
      uses interface-grouping;
    }
  }
  container controller {
    uses controller-grouping;
    container preconfigure {
      uses controller-grouping;
    }
  }
  container dynamic-template {
    tailf:cli-add-mode;
    container type {
      list ppp {
        key "name";
        leaf name {
          type string;
        }
        container ppp {
          leaf max-configure {
            type uint8;
          }
          container timeout {
            leaf retry {
              type uint8;
            }
            leaf authentication {
              type uint8;
            }
            leaf absolute {
              type uint32;
            }
          }
          leaf-list authentication {
            tailf:cli-flat-list-syntax;
            ordered-by user;
            type enumeration {
              enum chap;
              enum ms-chap;
              enum pap;
            }
          }
          container ipcp {
            leaf passive {
              type empty;
            }
            container dns {
              tailf:cli-compact-syntax;
              tailf:cli-sequence-commands {
                tailf:cli-reset-siblings;
              }
              leaf primary {
                tailf:cli-drop-node-name;
                type inet:ipv4-address;
              }
              leaf secondary {
                tailf:cli-drop-node-name;
                type inet:ipv4-address;
              }
            }
            container peer-address {
              leaf pool {
                type string;
              }
            }
          }
          container ipv6cp {
            leaf passive {
              type empty;
            }
            leaf peer-interface-id {
              type string;
            }
          }
        }
        container keepalive {
          tailf:cli-compact-syntax;
          tailf:cli-sequence-commands {
            tailf:cli-reset-siblings;
          }
          choice keepalive-choice {
            case values-case {
              leaf interval {
                tailf:cli-drop-node-name;
                type uint8;
              }
              leaf retry {
                tailf:cli-drop-node-name;
                type uint8;
              }
            }
            leaf disable {
              type empty;
            }
          }
        }
        uses dynamic-template-service-policy-grouping;
        container accounting {
          container aaa {
            list list {
              tailf:cli-suppress-mode;
              tailf:cli-delete-when-empty;
              tailf:cli-compact-syntax;
              tailf:cli-sequence-commands {
                tailf:cli-reset-siblings;
              }
              key "name";
              leaf name {
                type string;
              }
              leaf type {
                type enumeration {
                  enum session;
                }
              }
              leaf periodic-interval {
                tailf:cli-optional-in-sequence;
                type uint16;
              }
              leaf dual-stack-delay {
                type uint8;
              }
            }
          }
        }
        leaf vrf {
          type string;
        }
        container ipv4 {
          leaf mtu {
            type uint16;
          }
          container verify {
            container unicast {
              container source {
                leaf reachable-via {
                  type enumeration {
                    enum rx;
                  }
                }
              }
            }
          }
          container unnumbered {
            uses interface-name-grouping;
          }
          container unreachables {
            leaf disable {
              type empty;
            }
          }
          list access-group {
            tailf:cli-suppress-mode;
            tailf:cli-delete-when-empty;
            tailf:cli-compact-syntax;
            key "direction";
            leaf direction {
              type enumeration {
                enum egress;
                enum ingress;
              }
            }
            leaf name {
              tailf:cli-drop-node-name;
              tailf:cli-prefix-key;
              type string;
            }
          }
        }
        container ipv6 {
          container nd {
            leaf nud-enable {
              type empty;
            }
            leaf ra-unicast {
              type empty;
            }
            container ra-interval {
              tailf:cli-compact-syntax;
              tailf:cli-sequence-commands {
                tailf:cli-reset-siblings;
              }
              leaf maximum {
                tailf:cli-drop-node-name;
                type uint16;
              }
              leaf minimum {
                tailf:cli-drop-node-name;
                type uint16;
              }
            }
            leaf ra-lifetime {
              type uint16;
            }
            leaf reachable-time {
              type uint32;
            }
            leaf other-config-flag {
              type empty;
            }
            leaf framed-prefix-pool {
              type string;
            }
            leaf managed-config-flag {
              type empty;
            }
          }
          leaf mtu {
            type uint16;
          }
          container verify {
            container unicast {
              container source {
                container reachable-via {
                  leaf rx {
                    type empty;
                  }
                }
              }
            }
          }
          leaf enable {
            type empty;
          }
        }
        container dhcpv6 {
          leaf address-pool {
            type string;
          }
          leaf delegated-prefix-pool {
            type string;
          }
        }
        container multicast {
          container ipv4 {
            choice functionality-choice {
              leaf qos-correlation {
                type empty;
              }
              leaf passive {
                type empty;
              }
            }
          }
        }
      }
      list service {
        key "name";
        leaf name {
          type string;
        }
        uses dynamic-template-service-policy-grouping;
        container accounting {
          container aaa {
            list list {
              tailf:cli-suppress-mode;
              tailf:cli-delete-when-empty;
              tailf:cli-compact-syntax;
              tailf:cli-sequence-commands {
                tailf:cli-reset-siblings;
              }
              key "name";
              leaf name {
                type string;
              }
              leaf type {
                type enumeration {
                  enum session;
                  enum service;
                }
              }
              leaf periodic-interval {
                tailf:cli-optional-in-sequence;
                type uint16;
              }
              leaf dual-stack-delay {
                type uint8;
              }
            }
          }
        }
        container ipv4 {
          list access-group {
            tailf:cli-suppress-mode;
            tailf:cli-delete-when-empty;
            key "direction";
            leaf direction {
              type enumeration {
                enum egress;
                enum ingress;
              }
            }
            leaf name {
              tailf:cli-drop-node-name;
              tailf:cli-prefix-key;
              type string;
            }
          }
          container unnumbered {
            uses interface-name-grouping;
          }
        }
        container ipv6 {
          list access-group {
            tailf:cli-suppress-mode;
            tailf:cli-delete-when-empty;
            key "direction";
            leaf direction {
              type enumeration {
                enum egress;
                enum ingress;
              }
            }
            leaf name {
              tailf:cli-drop-node-name;
              tailf:cli-prefix-key;
              type string;
            }
          }
          leaf enable {
            type empty;
          }
        }
      }
      list ipsubscriber {
        key "name";
        leaf name {
          type string;
        }
        uses interface-service-policy-grouping;
        leaf vrf {
          type string;
        }
        container timeout {
          tailf:cli-compact-syntax;
          tailf:cli-sequence-commands {
            tailf:cli-reset-siblings;
          }
          leaf idle {
            type uint32;
          }
          leaf threshold {
            tailf:cli-optional-in-sequence;
            type uint16;
          }
          leaf traffic {
            type enumeration {
              enum both;
              enum inbound;
              enum outbound;
            }
          }
        }
        container accounting {
          container aaa {
            list list {
              tailf:cli-suppress-mode;
              tailf:cli-delete-when-empty;
              tailf:cli-compact-syntax;
              tailf:cli-sequence-commands {
                tailf:cli-reset-siblings;
              }
              key "name";
              leaf name {
                type string;
              }
              leaf type {
                type enumeration {
                  enum session;
                }
              }
              leaf periodic-interval {
                tailf:cli-optional-in-sequence;
                type uint16;
              }
              leaf dual-stack-delay {
                type uint8;
              }
            }
          }
        }
        container ipv4 {
          container verify {
            container unicast {
              container source {
                container reachable-via {
                  leaf rx {
                    type empty;
                  }
                }
              }
            }
          }
          container unnumbered {
            uses interface-name-grouping;
          }
          container unreachables {
            leaf disable {
              type empty;
            }
          }
          list access-group {
            tailf:cli-suppress-mode;
            tailf:cli-delete-when-empty;
            key "direction";
            leaf direction {
              type enumeration {
                enum egress;
                enum ingress;
              }
            }
            leaf name {
              tailf:cli-drop-node-name;
              tailf:cli-prefix-key;
              type string;
            }
          }
        }
        container ipv6 {
          leaf enable {
            type empty;
          }
          container nd {
            leaf nud-enable {
              type empty;
            }
            container ra-initial {
              tailf:cli-compact-syntax;
              tailf:cli-sequence-commands {
                tailf:cli-reset-siblings;
              }
              leaf count {
                tailf:cli-drop-node-name;
                type uint8;
              }
              leaf interval {
                tailf:cli-drop-node-name;
                type uint16;
              }
            }
            leaf ra-unicast {
              type empty;
            }
            container ra-interval {
              tailf:cli-compact-syntax;
              tailf:cli-sequence-commands {
                tailf:cli-reset-siblings;
              }
              leaf maximum {
                tailf:cli-drop-node-name;
                type uint16;
              }
              leaf minimum {
                tailf:cli-drop-node-name;
                type uint16;
              }
            }
            leaf ra-lifetime {
              type uint16;
            }
            container dad {
              leaf attempts {
                type uint16;
              }
            }
            leaf other-config-flag {
              type empty;
            }
            leaf managed-config-flag {
              type empty;
            }
          }
          container unreachables {
            leaf disable {
              type empty;
            }
          }
          container verify {
            container unicast {
              container source {
                container reachable-via {
                  leaf rx {
                    type empty;
                  }
                }
              }
            }
          }
          list access-group {
            tailf:cli-suppress-mode;
            tailf:cli-delete-when-empty;
            key "direction";
            leaf direction {
              type enumeration {
                enum egress;
                enum ingress;
              }
            }
            leaf name {
              tailf:cli-drop-node-name;
              tailf:cli-prefix-key;
              type string;
            }
          }
        }
        container multicast {
          container ipv4 {
            leaf qos-correlation {
              type empty;
            }
          }
        }
      }
    }
  }
  container lawful-intercept {
    leaf disable {
      type empty;
    }
  }
  uses evpn-config-grouping;

  grouping evpn-config-grouping {
    container evpn {
      tailf:cli-add-mode;
      presence "true";
      uses apply-group-grouping;
      container bgp {
        tailf:cli-add-mode;
        presence "true";
        leaf rd {
          type string;
        }
      }
      container ethernet-segment {
        tailf:cli-add-mode;
        presence "true";
        container type {
          container one {
            tailf:alt-name "1";
            leaf auto-generation-disable {
              type empty;
            }
          }
        }
      }
      list vni {
        key "id";
        leaf id {
          type uint32;
        }
        leaf stitching {
          tailf:cli-hide-in-submode;
          type empty;
        }
        container bgp {
          tailf:cli-add-mode;
          presence "true";
          uses evpn-bgp-grouping;
        }
        container advertise-mac {
          tailf:cli-add-mode;
          presence "true";
          leaf bvi-mac {
            type empty;
          }
        }
      }
      list evi {
        key "id";
        leaf id {
          type uint16;
        }
        leaf stitching {
          tailf:cli-hide-in-submode;
          type empty;
        }
        leaf segment-routing {
          tailf:cli-hide-in-submode;
          type enumeration {
            enum srv6;
          }
        }
        container bgp {
          tailf:cli-add-mode;
          presence "true";
          uses evpn-bgp-grouping;
          container route-policy {
            leaf export {
              type string;
            }
            leaf import {
              type string;
            }
          }
        }
        container multicast {
          tailf:cli-add-mode;
          presence "true";
        }
        uses description-grouping;
        leaf ignore-mtu-mismatch {
          type empty;
        }
        leaf vpws-single-active-backup-suppression {
          type empty;
        }
        container etree {
          tailf:cli-add-mode;
          presence "true";
          leaf leaf {
            type empty;
          }
          leaf rt-leaf {
            type empty;
          }
        }
        leaf control-word-disable {
          type empty;
        }
        container load-balancing {
          tailf:cli-add-mode;
          presence "true";
          container flow-label {
            leaf static {
              type empty;
            }
          }
        }
        container ecmp-disable {
          tailf:cli-delete-when-empty;
          presence "true";
          leaf nexthop-preference {
            type enumeration {
              enum lowest-ip;
              enum highest-ip;
            }
          }
        }
        container advertise-mac {
          tailf:cli-add-mode;
          presence "true";
          leaf bvi-mac {
            type empty;
          }
        }
        leaf unknown-unicast-suppression {
          type empty;
        }
        container network-controller {
          tailf:cli-add-mode;
          leaf vni {
            type uint16;
          }
          list host {
            key "mac";
            leaf mac {
              type string;
            }
            leaf ip-address {
              tailf:cli-hide-in-submode;
              type inet:ipv4-address;
            }
            container ipv4 {
              leaf address {
                type inet:ipv4-address;
              }
            }
            leaf switch {
              type inet:ipv4-address;
            }
            container gateway {
              tailf:cli-compact-syntax;
              tailf:cli-sequence-commands {
                tailf:cli-reset-siblings;
              }
              leaf ip-address {
                tailf:cli-drop-node-name;
                type union {
                  type inet:ipv4-address;
                  type inet:ipv4-prefix;
                }
              }
              leaf netmask {
                tailf:cli-drop-node-name;
                type inet:ipv4-address;
              }
            }
            leaf vlan {
              type uint16;
            }
          }
        }
        leaf bvi-coupled-mode {
          type empty;
        }
        leaf preferred-nexthop {
          type enumeration {
            enum highest-ip;
            enum lowest-ip;
            enum modulo;
          }
        }
        leaf locator {
          type string;
        }
        leaf enforce-mtu-match {
          type empty;
        }
        container transmit-mtu-zero {
          tailf:cli-delete-when-empty;
          presence "true";
          leaf disable-deprecated {
            type empty;
          }
        }
        leaf transmit-l2-mtu {
          type empty;
        }
      }
      list group {
        key "id";
        leaf id {
          type uint32;
        }
        container core {
          list interface {
            tailf:cli-suppress-mode;
            tailf:cli-delete-when-empty;
            key "name";
            leaf name {
              type string;
            }
          }
        }
      }
      container logging {
        tailf:cli-add-mode;
        presence "true";
        leaf df-election {
          type empty;
        }
      }
      uses evpn-timers-grouping;
      list interface {
        key "name";
        leaf name {
          type string;
        }
        container ethernet-segment {
          tailf:cli-add-mode;
          container identifier {
            list type {
              tailf:cli-suppress-mode;
              tailf:cli-delete-when-empty;
              key "esi-type";
              leaf esi-type {
                type enumeration {
                  enum 0;
                }
              }
              leaf esi-identifier {
                tailf:cli-drop-node-name;
                type string;
              }
            }
          }
          container service-carving {
            container manual {
              tailf:cli-add-mode;
              presence "true";
              container services-lists {
                tailf:cli-drop-node-name;
                tailf:cli-compact-syntax;
                tailf:cli-sequence-commands {
                  tailf:cli-reset-siblings;
                }
                leaf primary {
                  type string;
                }
                leaf secondary {
                  type string;
                }
              }
            }
            container preference-based {
              tailf:cli-add-mode;
              presence "true";
              leaf weight {
                type uint16;
              }
              leaf srg-driven {
                type empty;
              }
            }
          }
          container bgp {
            leaf route-target {
              type string;
            }
          }
          container load-balancing-mode {
            choice mode-choice {
              leaf single-active {
                type empty;
              }
              leaf port-active {
                type empty;
              }
              leaf single-flow-active {
                type empty;
              }
            }
          }
          container convergence {
            tailf:cli-add-mode;
            presence "true";
            leaf nexthop-tracking {
              type empty;
            }
            leaf reroute {
              type empty;
            }
          }
        }
        leaf access-signal {
          type enumeration {
            enum bundle-down;
            enum out-of-service;
          }
        }
        leaf core-isolation-group {
          type uint32;
        }
        uses evpn-timers-grouping;
      }
      container virtual {
        list neighbor {
          key "address pw-id";
          leaf address {
            type inet:ipv4-address;
          }
          leaf pw-id {
            type uint32;
          }
          uses evpn-virtual-grouping;
        }
        list vfi {
          key "name";
          leaf name {
            type string;
          }
          uses evpn-virtual-grouping;
        }
      }
      container source {
        container interface {
          leaf Loopback {
            tailf:cli-allow-join-with-value;
            type uint32;
          }
        }
      }
      container segment-routing {
        container srv6 {
          tailf:cli-add-mode;
          presence "true";
          list locator {
            key "name";
            leaf name {
              type string;
            }
          }
        }
      }
    }
  }

  container l2vpn {
    tailf:cli-add-mode;
    presence "true";
    uses apply-group-grouping;
    leaf router-id {
      type inet:ipv4-address;
    }
    leaf description {
      type string;
    }
    leaf nsr {
      type empty;
    }
    leaf pw-grouping {
      type empty;
    }
    container pw-status {
      tailf:cli-delete-when-empty;
      presence "true";
      leaf disable {
        type empty;
      }
    }
    container autodiscovery {
      container bgp {
        tailf:cli-add-mode;
        container signaling-protocol {
          container bgp {
            tailf:cli-add-mode;
            container mtu {
              container mismatch {
                leaf ignore {
                  type empty;
                }
              }
            }
          }
        }
      }
    }
    container logging {
      tailf:cli-add-mode;
      tailf:cli-delete-when-empty;
      presence "true";
      leaf nsr {
        type empty;
      }
      container pseudowire {
        tailf:cli-delete-when-empty;
        presence "true";
        leaf status {
          type empty;
        }
      }
      leaf bridge-domain {
        type empty;
      }
      leaf vfi {
        type empty;
      }
    }
    container load-balancing {
      leaf flow {
        type enumeration {
          enum src-dst-ip;
          enum src-dst-mac;
        }
      }
    }
    leaf capability {
      type enumeration {
        enum high-mode;
        enum single-mode;
      }
    }
    leaf ignore-mtu-mismatch {
      type empty;
    }
    leaf ignore-mtu-mismatch-ad {
      type empty;
    }
    container redundancy {
      tailf:cli-add-mode;
      presence "true";
      container iccp {
        list group {
          key "id";
          leaf id {
            type uint32;
          }
          container multi-homing {
            leaf node-id {
              type uint8;
            }
          }
          list interface {
            key "name";
            leaf name {
              type string;
            }
            container primary {
              leaf-list vlan {
                tailf:cli-range-list-syntax;
                type uint16;
              }
            }
            container secondary {
              leaf-list vlan {
                tailf:cli-range-list-syntax;
                type uint16;
              }
            }
            container recovery {
              leaf delay {
                type uint16;
              }
            }
          }
        }
      }
    }
    container ethernet {
      container ring {
        list g8032 {
          key "name";
          leaf name {
            type string;
          }
          container port0 {
            list interface {
              key "name";
              leaf name {
                type string;
              }
              container monitor {
                container interface {
                  uses interface-name-grouping;
                }
              }
            }
          }
          container port1 {
            list interface {
              key "name";
              leaf name {
                type string;
              }
              container monitor {
                container interface {
                  uses interface-name-grouping;
                }
              }
            }
            leaf none {
              type empty;
            }
          }
          leaf open-ring {
            type empty;
          }
          container exclusion-list {
            leaf vlan-ids {
              type string;
            }
          }
          list instance {
            key "id";
            leaf id {
              type uint8;
            }
            uses description-grouping;
            leaf profile {
              type string;
            }
            container inclusion-list {
              leaf vlan-ids {
                type string;
              }
            }
            container aps-channel {
              tailf:cli-add-mode;
              presence "true";
              leaf level {
                type uint8;
              }
              container port0 {
                container interface {
                  uses interface-name-grouping;
                }
              }
              container port1 {
                container interface {
                  uses interface-name-grouping;
                }
                leaf none {
                  type empty;
                }
              }
            }
            container rpl {
              tailf:cli-compact-syntax;
              tailf:cli-sequence-commands;
              leaf port {
                tailf:cli-drop-node-name;
                type enumeration {
                  enum port0;
                  enum port1;
                }
              }
              leaf mode {
                tailf:cli-drop-node-name;
                type enumeration {
                  enum neighbor;
                  enum next-neighbor;
                  enum owner;
                }
              }
            }
          }
        }
      }
    }
    list pw-class {
      key "name";
      leaf name {
        type string;
      }
      container encapsulation {
        container l2tpv3 {
          tailf:cli-add-mode;
          presence "true";
          leaf protocol {
            type enumeration {
              enum l2tpv3;
            }
          }
          leaf ttl {
            type uint8;
          }
        }
        container mpls {
          tailf:cli-add-mode;
          presence "true";
          container protocol {
            leaf ldp {
              type empty;
            }
          }
          container tag-rewrite {
            container ingress {
              leaf vlan {
                type uint16;
              }
            }
          }
          leaf control-word {
            type empty;
          }
          container vccv {
            container verification-type {
              leaf none {
                type empty;
              }
            }
          }
          container transport-mode {
            choice transport-mode-choice {
              leaf ethernet {
                type empty;
              }
              container vlan {
                tailf:cli-delete-when-empty;
                presence "true";
                leaf passthrough {
                  type empty;
                }
              }
            }
          }
          container load-balancing {
            tailf:cli-add-mode;
            leaf pw-label {
              type empty;
            }
            container flow-label {
              choice direction-choice {
                container both {
                  tailf:cli-delete-when-empty;
                  presence "true";
                  leaf static {
                    type empty;
                  }
                }
                container receive {
                  tailf:cli-delete-when-empty;
                  presence "true";
                  leaf static {
                    type empty;
                  }
                }
                container transmit {
                  tailf:cli-delete-when-empty;
                  presence "true";
                  leaf static {
                    type empty;
                  }
                }
              }
              container code {
                tailf:cli-compact-syntax;
                tailf:cli-sequence-commands {
                  tailf:cli-reset-siblings;
                }
                leaf value {
                  tailf:cli-drop-node-name;
                  type enumeration {
                    enum 17;
                  }
                }
                leaf disable {
                  type empty;
                }
              }
            }
          }
          container preferred-path {
            tailf:cli-compact-syntax;
            tailf:cli-sequence-commands {
              tailf:cli-reset-siblings;
            }
            choice preferred-path-choice {
              case interface {
                leaf interface {
                  type enumeration {
                    enum tunnel-ip;
                    enum tunnel-te;
                    enum tunnel-tp;
                  }
                }
                leaf id {
                  tailf:cli-drop-node-name;
                  type uint16;
                }
                leaf fallback {
                  type enumeration {
                    enum disable;
                  }
                }
              }
              container sr-te {
                tailf:cli-flatten-container;
                tailf:cli-compact-syntax;
                tailf:cli-sequence-commands {
                  tailf:cli-reset-siblings;
                }
                leaf policy {
                  type string;
                }
                leaf fallback {
                  type enumeration {
                    enum disable;
                  }
                }
              }
            }
          }
          container ipv4 {
            leaf source {
              type inet:ipv4-address;
            }
          }
          container redundancy {
            tailf:cli-add-mode;
            leaf one-way {
              type empty;
            }
            leaf initial-delay {
              type uint8;
            }
          }
        }
      }
      container backup {
        container disable {
          choice disable-choice {
            leaf delay {
              type uint8;
            }
            leaf never {
              type empty;
            }
          }
        }
      }
    }
    container flexible-xconnect-service {
      list vlan-aware {
        key "evi";
        leaf evi {
          type uint16;
        }
        list interface {
          tailf:cli-suppress-mode;
          tailf:cli-delete-when-empty;
          key "name";
          leaf name {
            type string;
          }
        }
      }
      list vlan-unaware {
        key "name";
        leaf name {
          type string;
        }
        list interface {
          tailf:cli-suppress-mode;
          key "name";
          leaf name {
            type string;
          }
        }
        container neighbor {
          container evpn {
            tailf:cli-compact-syntax;
            tailf:cli-sequence-commands {
              tailf:cli-reset-siblings;
            }
            leaf evi {
              type uint16;
            }
            leaf target {
              type uint32;
            }
          }
        }
      }
    }
    container xconnect {
      list group {
        key "name";
        leaf name {
          type string;
        }
        list mp2mp {
          key "name";
          leaf name {
            type string;
          }
          leaf vpn-id {
            type uint32;
          }
          leaf mtu {
            type uint32;
          }
          leaf l2-encapsulation {
            type enumeration {
              enum ethernet;
              enum vlan;
            }
          }
          container control-word {
            leaf disable {
              type empty;
            }
          }
          container autodiscovery {
            container bgp {
              tailf:cli-add-mode;
              presence "true";
              leaf rd {
                type string;
              }
              uses route-target-import-export-grouping;
              container signaling-protocol {
                container bgp {
                  tailf:cli-add-mode;
                  presence "true";
                  list ce-id {
                    key "id";
                    leaf id {
                      type uint16;
                    }
                    list interface {
                      tailf:cli-suppress-mode;
                      tailf:cli-delete-when-empty;
                      key "name";
                      leaf name {
                        type string;
                      }
                      leaf remote-ce-id {
                        type uint16;
                      }
                    }
                  }
                }
              }
            }
          }
        }
        list p2p {
          key "name";
          leaf name {
            type string;
          }
          list interface {
            tailf:cli-suppress-mode;
            tailf:cli-delete-when-empty;
            key "name";
            leaf name {
              type string;
            }
          }
          leaf monitor-session {
            type string;
          }
          list neighbor {
            key "address pw-id";
            leaf address {
              type string;
            }
            leaf pw-id {
              type uint32;
            }
            leaf ip-version {
              tailf:cli-drop-node-name;
              tailf:cli-prefix-key;
              type enumeration {
                enum ipv4;
                enum ipv6;
              }
            }
            container mpls {
              container static {
                container label {
                  tailf:cli-compact-syntax;
                  tailf:cli-sequence-commands {
                    tailf:cli-reset-siblings;
                  }
                  leaf local {
                    type uint32;
                  }
                  leaf remote {
                    type uint32;
                  }
                }
              }
            }
            leaf pw-class {
              type string;
            }
            container tag-impose {
              leaf vlan {
                type uint16;
              }
            }
            container l2tp {
              container static {
                tailf:cli-add-mode;
                presence "true";
                container local {
                  container cookie {
                    tailf:cli-flatten-container;
                    tailf:cli-compact-syntax;
                    tailf:cli-sequence-commands {
                      tailf:cli-reset-siblings;
                    }
                    leaf size {
                      type enumeration {
                        enum 0;
                        enum 4;
                        enum 8;
                      }
                    }
                    container value {
                      tailf:cli-flatten-container;
                      tailf:cli-compact-syntax;
                      tailf:cli-sequence-commands;
                      leaf value-1 {
                        tailf:cli-drop-node-name;
                        type string;
                      }
                      leaf value-2 {
                        tailf:cli-drop-node-name;
                        type string;
                      }
                    }
                  }
                }
                container remote {
                  container cookie {
                    tailf:cli-flatten-container;
                    tailf:cli-compact-syntax;
                    tailf:cli-sequence-commands {
                      tailf:cli-reset-siblings;
                    }
                    leaf size {
                      type enumeration {
                        enum 0;
                        enum 4;
                        enum 8;
                      }
                    }
                    container value {
                      tailf:cli-flatten-container;
                      tailf:cli-compact-syntax;
                      tailf:cli-sequence-commands;
                      leaf value-1 {
                        tailf:cli-drop-node-name;
                        type string;
                      }
                      leaf value-2 {
                        tailf:cli-drop-node-name;
                        type string;
                      }
                    }
                  }
                }
              }
            }
            leaf source {
              type inet:ipv6-address;
            }
            container backup {
              list neighbor {
                key "address pw-id";
                leaf address {
                  type string;
                }
                leaf pw-id {
                  type uint32;
                }
                leaf pw-class {
                  type string;
                }
              }
            }
          }
          container neighbor-routed {
            tailf:cli-drop-node-name;
            list neighbor {
              key "routed source";
              leaf routed {
                type string;
              }
              leaf source {
                type uint32;
              }
              leaf pw-class {
                type string;
              }
              container tag-impose {
                leaf vlan {
                  type uint16;
                }
              }
            }
          }
          container neighbor-evpn {
            tailf:cli-drop-node-name;
            container neighbor {
              list evpn {
                key "evi target source";
                leaf evi {
                  type uint16;
                }
                leaf target {
                  type uint32;
                }
                leaf source {
                  type uint32;
                }
                leaf pw-class {
                  type string;
                }
              }
            }
          }
          container neighbor-evpn-service {
            tailf:cli-drop-node-name;
            container neighbor {
              container evpn {
                tailf:cli-add-mode;
                tailf:cli-sequence-commands {
                  tailf:cli-reset-siblings;
                }
                leaf evi {
                  tailf:cli-hide-in-submode;
                  type uint16;
                }
                leaf service {
                  tailf:cli-break-sequence-commands;
                  tailf:cli-hide-in-submode;
                  type union {
                    type uint32;
                    type enumeration {
                      enum vlan-aware;
                    }
                  }
                }
                container segment-routing {
                  tailf:cli-flatten-container;
                  tailf:cli-hide-in-submode;
                  leaf srv6 {
                    type empty;
                  }
                }
                leaf pw-class {
                  tailf:cli-optional-in-sequence;
                  type string;
                }
                leaf locator {
                  type string;
                }
              }
            }
          }
          leaf interworking {
            type enumeration {
              enum ethernet;
              enum ipv4;
            }
          }
          leaf description {
            tailf:cli-multi-value;
            type string;
          }
        }
      }
    }
    container bridge {
      list group {
        key "group-name";
        leaf group-name {
          type string;
        }
        uses apply-group-grouping;
        list bridge-domain {
          key "bridge-domain-name";
          leaf bridge-domain-name {
            type string;
          }
          uses apply-group-grouping;
          uses description-grouping;
          leaf multicast-source {
            type enumeration {
              enum ipv4;
              enum ipv6;
              enum ipv4-ipv6;
            }
          }
          leaf mtu {
            type uint16;
          }
          container nv {
            container satellite {
              tailf:cli-add-mode;
              presence "true";
            }
          }
          container flood {
            leaf mode {
              type enumeration {
                enum convergence-optimized;
                enum resilience-optimized;
                enum ac-ingress-replication;
              }
            }
          }
          uses l2vpn-bridge-domain-grouping;
          leaf shutdown {
            type empty;
          }
          list interface {
            key "name";
            leaf name {
              type string;
            }
            container mac {
              tailf:cli-add-mode;
              uses l2vpn-bridge-domain-mac-grouping;
            }
            list static-mac-address {
              tailf:cli-suppress-mode;
              tailf:cli-delete-when-empty;
              key "address";
              leaf address {
                type string;
              }
            }
            uses storm-control-grouping;
            container igmp {
              container snooping {
                leaf profile {
                  type string;
                }
              }
            }
            container split-horizon {
              leaf group {
                type empty;
              }
            }
            container flooding {
              leaf disable {
                type empty;
              }
              container unknown-unicast {
                leaf disable {
                  type empty;
                }
              }
            }
            container etree {
              tailf:cli-add-mode;
              presence "true";
              leaf leaf {
                type empty;
              }
            }
          }
          list neighbor {
            key "address pw-id";
            leaf address {
              type inet:ipv4-address;
            }
            leaf pw-id {
              type uint32;
            }
            leaf pw-class {
              type string;
            }
            list static-mac-address {
              tailf:cli-suppress-mode;
              tailf:cli-delete-when-empty;
              key "address";
              leaf address {
                type string;
              }
            }
            container mpls {
              container static {
                container label {
                  tailf:cli-compact-syntax;
                  tailf:cli-sequence-commands {
                    tailf:cli-reset-siblings;
                  }
                  leaf local {
                    type uint32;
                  }
                  leaf remote {
                    type uint32;
                  }
                }
              }
            }
            uses l2vpn-bridge-domain-grouping;
            container backup {
              list neighbor {
                key "address pw-id";
                leaf address {
                  type string;
                }
                leaf pw-id {
                  type uint32;
                }
                leaf pw-class {
                  type string;
                }
              }
            }
            container split-horizon {
              leaf group {
                type empty;
              }
            }
          }
          container neighbor-evpn {
            tailf:cli-drop-node-name;
            container neighbor {
              list evpn {
                tailf:cli-suppress-mode;
                tailf:cli-delete-when-empty;
                key "evi target";
                leaf evi {
                  type uint16;
                }
                leaf target {
                  type uint32;
                }
              }
            }
          }
          list access-vfi {
            key "name";
            leaf name {
              type string;
            }
            list neighbor {
              key "address pw-id";
              leaf address {
                type inet:ipv4-address;
              }
              leaf pw-id {
                type uint32;
              }
            }
          }
          container routed {
            list interface {
              key "name";
              leaf name {
                type string;
              }
              container split-horizon {
                container group {
                  leaf core {
                    type empty;
                  }
                }
              }
            }
          }
          list vfi {
            key "name";
            leaf name {
              type string;
            }
            leaf vpn-id {
              type uint32;
            }
            container autodiscovery {
              container bgp {
                tailf:cli-add-mode;
                presence "true";
                leaf rd {
                  type string;
                }
                uses route-target-import-export-grouping;
                container signaling-protocol {
                  container bgp {
                    tailf:cli-add-mode;
                    presence "true";
                    leaf ve-id {
                      type uint16;
                    }
                    leaf ve-range {
                      type uint16;
                    }
                    container load-balancing {
                      tailf:cli-compact-syntax;
                      tailf:cli-sequence-commands {
                        tailf:cli-reset-siblings;
                      }
                      leaf flow-label {
                        type enumeration {
                          enum both;
                          enum receive;
                          enum transmit;
                        }
                      }
                      leaf static {
                        type empty;
                      }
                    }
                  }
                  container ldp {
                    tailf:cli-add-mode;
                    presence "true";
                    leaf vpls-id {
                      type union {
                        type string;
                        type inet:ipv4-address;
                      }
                    }
                    container load-balancing {
                      tailf:cli-compact-syntax;
                      tailf:cli-sequence-commands {
                        tailf:cli-reset-siblings;
                      }
                      leaf flow-label {
                        type enumeration {
                          enum both;
                          enum receive;
                          enum transmit;
                        }
                      }
                      leaf static {
                        type empty;
                      }
                    }
                  }
                }
                leaf control-word {
                  type empty;
                }
              }
            }
            list neighbor {
              key "address pw-id";
              leaf address {
                type string;
              }
              leaf pw-id {
                type uint32;
              }
              leaf pw-class {
                type string;
              }
              list static-mac-address {
                tailf:cli-suppress-mode;
                tailf:cli-delete-when-empty;
                key "address";
                leaf address {
                  type string;
                }
              }
              container igmp {
                container snooping {
                  leaf profile {
                    type string;
                  }
                }
              }
            }
          }
          container pbb {
            list edge {
              key "i-sid core-bridge";
              leaf i-sid {
                type uint32;
              }
              leaf core-bridge {
                type string;
              }
              leaf unknown-unicast-bmac {
                type string;
              }
            }
            container core {
              tailf:cli-add-mode;
              presence "true";
              leaf evi {
                type uint16;
              }
              container evpn {
                leaf evi {
                  type uint16;
                }
              }
            }
          }
          container evpn {
            leaf evi {
              type uint16;
            }
          }
          list evi {
            key "id";
            leaf id {
              type uint16;
            }
            leaf segment-routing {
              tailf:cli-hide-in-submode;
              type enumeration {
                enum srv6;
              }
            }
          }
          container member {
            list vni {
              key "id";
              leaf id {
                type uint32;
              }
            }
          }
          container dhcp {
            container ipv4 {
              container snoop {
                leaf profile {
                  type string;
                }
              }
            }
          }
          container etree {
            tailf:cli-add-mode;
            presence "true";
            leaf leaf {
              type empty;
            }
          }
        }
      }
    }
    container pbb {
      tailf:cli-add-mode;
      leaf backbone-source-mac {
        type string;
      }
    }
  }
  container policy-global {
    tailf:cli-add-mode;
    presence "true";
    list set {
      tailf:cli-drop-node-name;
      tailf:cli-suppress-mode;
      tailf:cli-delete-when-empty;
      ordered-by user;
      key "value";
      leaf value {
        tailf:cli-multi-word-key;
        type string;
      }
    }
  }
  container extcommunity-set {
    list rt {
      key "name";
      leaf name {
        type string;
      }
      uses set-list-grouping;
    }
    list soo {
      key "name";
      leaf name {
        type string;
      }
      uses set-list-grouping;
    }
    list opaque {
      key "name";
      leaf name {
        type string;
      }
      uses set-list-grouping;
    }
  }
  list rd-set {
    key "name";
    leaf name {
      type string;
    }
    uses set-list-grouping;
  }
  list tag-set {
    key "name";
    leaf name {
      type string;
    }
    uses set-list-grouping;
  }
  list prefix-set {
    key "name";
    leaf name {
      type string;
    }
    uses set-list-grouping;
  }
  list as-set {
    key "name";
    leaf name {
      type string;
    }
    uses set-list-grouping;
  }
  list as-path-set {
    key "name";
    leaf name {
      type string;
    }
    uses set-list-grouping;
  }
  list community-set {
    key "name";
    leaf name {
      type string;
    }
    uses set-list-grouping;
  }
  list large-community-set {
    key "name";
    leaf name {
      type string;
    }
    uses set-list-grouping;
  }
  container rpl {
    leaf editor {
      type enumeration {
        enum emacs;
        enum nano;
        enum vim;
      }
    }
    leaf set-exit-as-abort {
      type empty;
    }
    container maximum {
      leaf policies {
        type uint16;
      }
    }
  }
  list route-policy {
    key "name";
    leaf name {
      tailf:cli-suppress-range;
      type string;
    }
    leaf value {
      tailf:cli-drop-node-name;
      type string;
    }
  }
  container route-policy-edit {
    tailf:cli-drop-node-name;
    list route-policy {
      key "name";
      leaf name {
        tailf:cli-suppress-range;
        type string;
      }
      list line {
        tailf:cli-drop-node-name;
        tailf:cli-suppress-mode;
        tailf:cli-delete-when-empty;
        key "id";
        leaf id {
          tailf:cli-suppress-range;
          type uint32;
        }
        leaf value {
          tailf:cli-drop-node-name;
          tailf:cli-multi-value;
          type string;
        }
      }
    }
  }
  list generic-interface-list {
    key "name";
    leaf name {
      type string;
    }
    list interface {
      tailf:cli-suppress-mode;
      tailf:cli-delete-when-empty;
      key "name";
      leaf name {
        type ifname;
      }
    }
  }
  list gnss-receiver {
    key "number location";
    leaf number {
      type uint32;
    }
    leaf location {
      type string;
    }
    container onepps {
      tailf:alt-name "1pps";
      leaf polarity {
        type enumeration {
          enum negative;
          enum positive;
        }
      }
    }
    container anti-jam {
      leaf disable {
        type empty;
      }
    }
    leaf band-width {
      type uint16;
    }
    container cable-delay {
      leaf compensation {
        type int32;
      }
    }
    leaf constellation {
      type enumeration {
        enum auto;
        enum beidou;
        enum galileo;
        enum glonass;
        enum gps;
        enum irnss;
        enum qzss;
        enum sbas;
      }
    }
    container elevation {
      leaf threshold {
        type uint8;
      }
    }
    container frequency {
      container synchronization {
        tailf:cli-add-mode;
        leaf priority {
          type uint8;
        }
        container quality {
          grouping quality-grouping {
            leaf type {
              tailf:cli-drop-node-name;
              type enumeration {
                enum exact;
                enum highest;
                enum lowest;
              }
            }
            leaf itu-t {
              type empty;
            }
            leaf option {
              type enumeration {
                enum 1;
                enum 2;
              }
            }
            leaf generation {
              type enumeration {
                enum 1;
                enum 2;
              }
            }
            leaf value-opt1 {
              tailf:cli-drop-node-name;
              type enumeration {
                enum DNU;
                enum EEC1;
                enum PRC;
                enum PRTC;
                enum SEC;
                enum SSU-A;
                enum SSU-B;
                enum eEEC;
                enum ePRTC;
              }
            }
            leaf value-opt2 {
              tailf:cli-drop-node-name;
              type enumeration {
                enum DUS;
                enum EEC2;
                enum PROV;
                enum PRS;
                enum PRTC;
                enum RES;
                enum SMC;
                enum ST2;
                enum ST3;
                enum ST3E;
                enum ST4;
                enum STU;
                enum TNC;
                enum eEEC;
                enum ePRTC;
              }
            }
          }

          container receive {
            tailf:cli-sequence-commands {
              tailf:cli-reset-siblings;
            }
            tailf:cli-compact-syntax;
            uses quality-grouping;
          }
          container transmit {
            tailf:cli-sequence-commands {
              tailf:cli-reset-siblings;
            }
            tailf:cli-compact-syntax;
            uses quality-grouping;
          }
        }
        container selection {
          leaf input {
            type empty;
          }
        }
        container ssm {
          leaf disable {
            type empty;
          }
        }
        leaf time-of-day-priority {
          type uint8;
        }
        leaf wait-to-restore {
          type uint8;
        }
      }
    }
    container pdop {
      leaf threshold {
        type uint8;
      }
    }
    leaf shutdown {
      type empty;
    }
    container snr {
      leaf threshold {
        type uint8;
      }
    }
    container traim {
      leaf threshold {
        type uint8;
      }
    }
  }
  container ospf {
    leaf name-lookup {
      type empty;
    }
  }
  container router-convergence {
    tailf:cli-add-mode;
    presence "true";
    list collect-diagnostics {
      tailf:cli-suppress-mode;
      tailf:cli-delete-when-empty;
      key "name";
      leaf name {
        type string;
      }
    }
  }
  container router {
    container static {
      tailf:cli-add-mode;
      uses router-static-grouping;
      list vrf {
        key "name";
        leaf name {
          type string;
        }
        uses router-static-grouping;
      }
    }
    container igmp {
      tailf:cli-add-mode;
      presence "true";
      uses router-igmp-grouping;
      container nsf {
        leaf lifetime {
          type uint16;
        }
      }
      list vrf {
        key "name";
        leaf name {
          type string;
        }
        uses router-igmp-grouping;
      }
    }
    container isis {
      list tag {
        tailf:cli-drop-node-name;
        key "name";
        leaf name {
          type string;
        }
        uses apply-group-grouping;
        leaf vrf-context {
          type string;
        }
        leaf instance-id {
          type uint16;
        }
        list affinity-map {
          tailf:cli-suppress-mode;
          tailf:cli-delete-when-empty;
          tailf:cli-compact-syntax;
          tailf:cli-sequence-commands {
            tailf:cli-reset-siblings;
          }
          key "name";
          leaf name {
            tailf:cli-suppress-range;
            type string;
          }
          leaf bit-position {
            type uint8;
          }
        }
        list flex-algo {
          key "id";
          leaf id {
            type uint8;
          }
          container address-family {
            container ipv4 {
              container unicast {
                tailf:cli-add-mode;
                leaf maximum-paths {
                  type uint8;
                }
              }
            }
            container ipv6 {
              container unicast {
                tailf:cli-add-mode;
                leaf maximum-paths {
                  type uint8;
                }
              }
            }
          }
          leaf priority {
            type uint8;
          }
          container metric-type {
            choice metric-type-choice {
              leaf delay {
                type empty;
              }
              leaf te {
                type empty;
              }
            }
          }
          leaf advertise-definition {
            type empty;
          }
          container affinity {
            leaf-list include-all {
              tailf:cli-flat-list-syntax;
              type string;
            }
            leaf-list include-any {
              tailf:cli-flat-list-syntax;
              type string;
            }
            leaf-list exclude-any {
              tailf:cli-flat-list-syntax;
              type string;
            }
          }
          leaf prefix-metric {
            type empty;
          }
        }
        container adjacency {
          container stagger {
            tailf:cli-compact-syntax;
            tailf:cli-sequence-commands {
              tailf:cli-reset-siblings;
            }
            tailf:cli-delete-when-empty;
            presence "true";
            leaf initial-num-nbr {
              tailf:cli-drop-node-name;
              type uint16;
            }
            leaf max-num-nbr {
              tailf:cli-drop-node-name;
              type uint16;
            }
          }
        }
        container set-overload-bit-level {
          tailf:cli-drop-node-name;
          list set-overload-bit {
            tailf:cli-suppress-mode;
            tailf:cli-delete-when-empty;
            tailf:cli-compact-syntax;
            tailf:cli-sequence-commands {
              tailf:cli-reset-siblings;
            }
            key "level";
            leaf level {
              type uint8;
            }
            leaf on-startup {
              tailf:cli-prefix-key;
              tailf:cli-optional-in-sequence;
              type union {
                type uint32;
                type enumeration {
                  enum wait-for-bgp;
                }
              }
            }
            container advertise {
              tailf:cli-flatten-container;
              tailf:cli-compact-syntax;
              leaf external {
                type empty;
              }
              leaf interlevel {
                type empty;
              }
            }
          }
        }
        container set-overload-bit {
          tailf:cli-delete-when-empty;
          tailf:cli-compact-syntax;
          presence "true";
          leaf on-startup {
            tailf:cli-optional-in-sequence;
            type union {
              type uint32;
              type enumeration {
                enum wait-for-bgp;
              }
            }
          }
          container advertise {
            tailf:cli-flatten-container;
            tailf:cli-compact-syntax;
            leaf external {
              type empty;
            }
            leaf interlevel {
              type empty;
            }
          }
        }
        container max-metric {
          list level {
            tailf:cli-suppress-mode;
            tailf:cli-delete-when-empty;
            key "id";
            leaf id {
              type uint8;
            }
          }
          container on-startup {
            tailf:cli-compact-syntax;
            choice on-startup-choice {
              leaf time {
                tailf:cli-drop-node-name;
                type uint32;
              }
              leaf wait-for-bgp {
                type empty;
              }
            }
            leaf external {
              type empty;
            }
            leaf interlevel {
              type empty;
            }
            leaf default-route {
              type empty;
            }
            leaf srv6-locator {
              type empty;
            }
            leaf te {
              type empty;
            }
            leaf delay {
              type empty;
            }
          }
        }
        leaf max-link-metric {
          type empty;
        }
        container max-link-metric-level {
          tailf:cli-drop-node-name;
          container max-link-metric {
            list level {
              tailf:cli-suppress-mode;
              tailf:cli-delete-when-empty;
              key "id";
              leaf id {
                type uint8;
              }
            }
          }
        }
        container hostname {
          container dynamic {
            leaf disable {
              type empty;
            }
          }
        }
        leaf is-type {
          type enumeration {
            enum level-1;
            enum level-1-2;
            enum level-2-only;
          }
        }
        list net {
          tailf:cli-suppress-mode;
          tailf:cli-delete-when-empty;
          key "id";
          leaf id {
            type string;
          }
        }
        container segment-routing {
          container global-block {
            tailf:cli-compact-syntax;
            tailf:cli-sequence-commands {
              tailf:cli-reset-siblings;
            }
            leaf lower-bound {
              tailf:cli-drop-node-name;
              type uint32;
            }
            leaf upper-bound {
              tailf:cli-drop-node-name;
              type uint32;
            }
          }
        }
        container nsf {
          choice nsf-choice {
            container advertise {
              leaf holdtime {
                type uint16;
              }
            }
            leaf cisco {
              type empty;
            }
            leaf ietf {
              type empty;
            }
            container interface {
              leaf wait {
                type uint8;
              }
            }
            leaf interval {
              type uint16;
            }
            container t3 {
              choice t3-choice {
                leaf adjacency {
                  type empty;
                }
                leaf manual {
                  type uint16;
                }
              }
            }
          }
          leaf lifetime {
            type uint16;
          }
          leaf interface-timer {
            type uint8;
          }
          leaf interface-expires {
            type uint8;
          }
        }
        leaf nsr {
          type empty;
        }
        container distribute {
          container link-state {
            tailf:cli-compact-syntax;
            tailf:cli-sequence-commands {
              tailf:cli-reset-siblings;
            }
            tailf:cli-delete-when-empty;
            presence "true";
            leaf instance-id {
              tailf:cli-optional-in-sequence;
              type uint16;
            }
            leaf level {
              tailf:cli-optional-in-sequence;
              type uint8;
            }
            leaf throttle {
              type uint8;
            }
          }
          container bgp-ls {
            tailf:cli-compact-syntax;
            leaf instance-id {
              type uint32;
            }
            leaf level {
              type uint8;
            }
            leaf throttle {
              type uint8;
            }
          }
        }
        container log {
          container adjacency {
            leaf changes {
              type empty;
            }
          }
          container pdu {
            leaf drops {
              type empty;
            }
          }
        }
        container trace {
          leaf mode {
            type enumeration {
              enum off;
              enum basic;
              enum enhanced;
            }
          }
        }
        container lsp-gen-interval-1 {
          tailf:cli-drop-node-name;
          container lsp-gen-interval {
            tailf:cli-compact-syntax;
            tailf:cli-sequence-commands {
              tailf:cli-reset-siblings;
            }
            uses router-isis-lsp-gen-interval-level-grouping;
            leaf level {
              type enumeration {
                enum 1;
              }
            }
          }
        }
        container lsp-gen-interval-2 {
          tailf:cli-drop-node-name;
          container lsp-gen-interval {
            tailf:cli-compact-syntax;
            tailf:cli-sequence-commands {
              tailf:cli-reset-siblings;
            }
            uses router-isis-lsp-gen-interval-level-grouping;
            leaf level {
              type enumeration {
                enum 2;
              }
            }
          }
        }
        container lsp-gen-interval {
          tailf:cli-compact-syntax;
          leaf maximum-wait {
            type uint32;
          }
          leaf initial-wait {
            type uint32;
          }
          leaf secondary-wait {
            type uint32;
          }
        }
        leaf lsp-check-interval {
          type uint16;
        }
        leaf lsp-refresh-interval {
          type uint16;
        }
        leaf lsp-mtu {
          type uint16;
        }
        container lsp-password {
          tailf:cli-compact-syntax;
          tailf:cli-sequence-commands {
            tailf:cli-reset-all-siblings;
          }
          leaf auth-type {
            tailf:cli-drop-node-name;
            tailf:cli-optional-in-sequence;
            type enumeration {
              enum hmac-md5;
              enum text;
            }
          }
          leaf enc-type {
            tailf:cli-drop-node-name;
            tailf:cli-optional-in-sequence;
            type enumeration {
              enum clear;
              enum encrypted;
            }
          }
          choice password-choice {
            leaf password {
              tailf:cli-drop-node-name;
              type string;
            }
            leaf keychain {
              type string;
            }
          }
          leaf level {
            tailf:cli-break-sequence-commands;
            type uint8;
          }
          leaf snp {
            type empty;
          }
          leaf send-only {
            type empty;
          }
        }
        leaf max-lsp-lifetime {
          type uint16;
        }
        container purge-transmit {
          container strict {
            tailf:cli-delete-when-empty;
            presence "true";
            leaf level {
              tailf:cli-drop-node-name;
              type enumeration {
                enum level-1;
                enum level-2;
              }
            }
          }
        }
        container receive {
          container application {
            container flex-algo {
              container delay {
                leaf app-only {
                  type empty;
                }
              }
            }
          }
        }
        container address-family {
          container ipv4 {
            container unicast {
              tailf:cli-add-mode;
              presence "true";
              uses router-isis-common-grouping;
              uses router-isis-common-af-grouping;
              uses router-isis-af4-grouping;
            }
            container multicast {
              tailf:cli-add-mode;
              presence "true";
              uses router-isis-common-grouping;
              uses router-isis-common-af-grouping;
              uses router-isis-af4-grouping;
            }
          }
          container ipv6 {
            container unicast {
              tailf:cli-add-mode;
              presence "true";
              uses router-isis-common-grouping;
              uses router-isis-common-af-grouping;
              uses router-isis-af6-grouping;
            }
            container multicast {
              tailf:cli-add-mode;
              presence "true";
              uses router-isis-common-grouping;
              uses router-isis-common-af-grouping;
              uses router-isis-af6-grouping;
            }
          }
        }
        list interface {
          key "name";
          leaf name {
            type string;
          }
          uses apply-group-grouping;
          leaf interface-type {
            tailf:cli-drop-node-name;
            type enumeration {
              enum active;
              enum passive;
              enum suppressed;
              enum shutdown;
            }
          }
          leaf circuit-type {
            type enumeration {
              enum level-1;
              enum level-1-2;
              enum level-2-only;
            }
          }
          container bfd {
            leaf minimum-interval {
              type uint16;
            }
            leaf multiplier {
              type uint16;
            }
            container fast-detect {
              leaf ipv4 {
                type empty;
              }
              leaf ipv6 {
                type empty;
              }
            }
          }
          leaf priority {
            type uint8;
          }
          leaf mesh-group {
            type union {
              type enumeration {
                enum blocked;
              }
              type uint32;
            }
          }
          leaf point-to-point {
            type empty;
          }
          container lsp-interval {
            leaf milliseconds {
              tailf:cli-drop-node-name;
              type uint32;
            }
            list lsp-number-level {
              tailf:cli-drop-node-name;
              tailf:cli-suppress-mode;
              tailf:cli-delete-when-empty;
              tailf:cli-compact-syntax;
              tailf:cli-sequence-commands;
              key "level";
              leaf level {
                type uint8;
              }
              leaf milliseconds {
                tailf:cli-drop-node-name;
                tailf:cli-prefix-key;
                type uint32;
              }
            }
          }
          container csnp-interval {
            leaf csnp-number {
              tailf:cli-drop-node-name;
              type uint16;
            }
            list csnp-number-level {
              tailf:cli-drop-node-name;
              tailf:cli-suppress-mode;
              tailf:cli-delete-when-empty;
              tailf:cli-compact-syntax;
              tailf:cli-sequence-commands;
              key "level";
              leaf level {
                type uint8;
              }
              leaf csnp-number {
                tailf:cli-drop-node-name;
                tailf:cli-prefix-key;
                type uint16;
              }
            }
          }
          leaf hello-interval {
            type uint16;
          }
          leaf hello-padding {
            type enumeration {
              enum disable;
              enum enable;
              enum sometimes;
            }
          }
          container hello-password {
            tailf:cli-compact-syntax;
            tailf:cli-sequence-commands {
              tailf:cli-reset-siblings;
            }
            choice authentication-choice {
              leaf keychain {
                tailf:cli-optional-in-sequence;
                type string;
              }
              leaf accept {
                tailf:cli-optional-in-sequence;
                type empty;
              }
              leaf hmac-md5 {
                tailf:cli-optional-in-sequence;
                type empty;
              }
              leaf text {
                tailf:cli-optional-in-sequence;
                type empty;
              }
            }
            choice password-choice {
              leaf clear {
                tailf:cli-optional-in-sequence;
                type string;
              }
              leaf encrypted {
                tailf:cli-optional-in-sequence;
                type string;
              }
              leaf password {
                tailf:cli-drop-node-name;
                tailf:cli-optional-in-sequence;
                type string;
              }
            }
            leaf level {
              tailf:cli-optional-in-sequence;
              type uint8;
            }
            leaf send-only {
              type empty;
            }
          }
          container hello-multiplier {
            leaf value {
              tailf:cli-drop-node-name;
              type uint16;
            }
          }
          container lsp {
            container fast-flood {
              container threshold {
                leaf lsp-number {
                  tailf:cli-drop-node-name;
                  type uint32;
                }
                list lsp-number-level {
                  tailf:cli-drop-node-name;
                  tailf:cli-suppress-mode;
                  tailf:cli-delete-when-empty;
                  tailf:cli-compact-syntax;
                  tailf:cli-sequence-commands;
                  key "level";
                  leaf level {
                    type uint8;
                  }
                  leaf lsp-number {
                    tailf:cli-drop-node-name;
                    tailf:cli-prefix-key;
                    type uint32;
                  }
                }
              }
            }
          }
          container link-down {
            leaf fast-detect {
              type empty;
            }
          }
          container retransmit-interval {
            leaf milliseconds {
              tailf:cli-drop-node-name;
              type uint16;
            }
          }
          container retransmit-throttle-interval {
            leaf milliseconds {
              tailf:cli-drop-node-name;
              type uint16;
            }
          }
          container affinity {
            leaf-list flex-algo {
              tailf:cli-flat-list-syntax;
              type string;
            }
          }
          container delay {
            container normalize {
              tailf:cli-compact-syntax;
              tailf:cli-sequence-commands {
                tailf:cli-reset-siblings;
              }
              leaf interval {
                type uint32;
              }
              leaf offset {
                type uint32;
              }
            }
          }
          container address-family {
            container ipv4 {
              container unicast {
                tailf:cli-add-mode;
                presence "true";
                uses router-isis-common-af-grouping;
                uses router-isis-if-af-grouping;
              }
              container multicast {
                tailf:cli-add-mode;
                presence "true";
                uses router-isis-common-af-grouping;
                uses router-isis-if-af-grouping;
              }
            }
            container ipv6 {
              container unicast {
                tailf:cli-add-mode;
                presence "true";
                uses router-isis-common-af-grouping;
                uses router-isis-if-af-grouping;
              }
              container multicast {
                tailf:cli-add-mode;
                presence "true";
                uses router-isis-common-af-grouping;
                uses router-isis-if-af-grouping;
              }
            }
          }
        }
        container authentication {
          container key-chain {
            tailf:cli-compact-syntax;
            tailf:cli-sequence-commands;
            leaf ref {
              tailf:cli-drop-node-name;
              type string;
            }
            leaf level {
              tailf:cli-drop-node-name;
              type enumeration {
                enum level-1;
                enum level-2;
              }
            }
          }
          container mode {
            choice mode-choice {
              container md5 {
                presence "true";
                leaf level {
                  tailf:cli-drop-node-name;
                  type enumeration {
                    enum level-1;
                    enum level-2;
                  }
                }
              }
              container text {
                presence "true";
                leaf level {
                  tailf:cli-drop-node-name;
                  type enumeration {
                    enum level-1;
                    enum level-2;
                  }
                }
              }
            }
          }
        }
        container bfd {
          leaf all-interfaces {
            type empty;
          }
          leaf check-ctrl-plane-failure {
            type empty;
          }
        }
        container mpls {
          leaf ldp {
            type enumeration {
              enum sync;
            }
          }
          container traffic-eng {
            leaf level-1 {
              type empty;
            }
            leaf level-2 {
              type empty;
            }
            leaf multicast-intact {
              type empty;
            }
            leaf router-id {
              type empty;
            }
            leaf scanner {
              type empty;
            }
          }
        }
        container srlg {
          tailf:cli-add-mode;
          presence "true";
          leaf admin-weight {
            type uint32;
          }
          list name {
            key "name";
            leaf name {
              type string;
            }
            leaf admin-weight {
              type uint32;
            }
          }
        }
        uses router-isis-common-grouping;
      }
    }
    list ospf {
      key "name";
      leaf name {
        type string;
      }
      container protocol {
        leaf shutdown {
          type empty;
        }
      }
      uses router-ospf-authentication-grouping;
      uses router-ospf-grouping;
      container mpls {
        container traffic-eng {
          choice router-id-choice {
            container router-id {
              uses interface-name-grouping;
            }
            container router-id-address {
              tailf:cli-drop-node-name;
              leaf router-id {
                type inet:ipv4-address;
              }
            }
          }
          leaf multicast-intact {
            type empty;
          }
          leaf igp-intact {
            type empty;
          }
          container autoroute-exclude {
            leaf route-policy {
              type string;
            }
          }
        }
        container ldp {
          leaf sync {
            type empty;
          }
          leaf auto-config {
            type empty;
          }
          leaf sync-igp-shortcuts {
            type empty;
          }
        }
      }
      list flex-algo {
        key "id";
        leaf id {
          type uint8;
        }
        leaf priority {
          type uint8;
        }
        leaf metric-type {
          type enumeration {
            enum delay;
            enum te-metric;
          }
        }
        leaf advertise-definition {
          type empty;
        }
      }
      list vrf {
        key "name";
        leaf name {
          type string;
        }
        uses router-ospf-authentication-grouping;
        uses router-ospf-grouping {
          augment "capability" {
            leaf vrf-lite {
              type empty;
            }
          }
          augment "area" {
            list sham-link {
              key "local remote";
              leaf local {
                type inet:ipv4-address;
              }
              leaf remote {
                type inet:ipv4-address;
              }
              leaf cost {
                type uint16;
              }
            }
          }
        }
        leaf domain-tag {
          type uint32;
        }
      }
    }
    list ospfv3 {
      key "name";
      leaf name {
        type string;
      }
      container protocol {
        leaf shutdown {
          type empty;
        }
      }
      uses router-ospfv3-grouping;
      container stub-router {
        list router-lsa {
          key "mode";
          leaf mode {
            type enumeration {
              enum max-metric;
              enum r-bit;
              enum v6-bit;
            }
          }
        }
      }
      list vrf {
        key "name";
        leaf name {
          type string;
        }
        uses router-ospfv3-grouping {
          augment "capability" {
            leaf vrf-lite {
              type empty;
            }
          }
          augment "area" {
            list sham-link {
              key "local remote";
              leaf local {
                type inet:ipv6-address;
              }
              leaf remote {
                type inet:ipv6-address;
              }
              leaf cost {
                type uint16;
              }
            }
          }
        }
      }
    }
    container bgp {
      list bgp-no-instance {
        tailf:cli-drop-node-name;
        key "id";
        leaf id {
          tailf:cli-suppress-range;
          type union {
            type uint32;
            type string;
          }
        }
        uses router-bgp-grouping;
      }
      list bgp-instance {
        tailf:cli-drop-node-name;
        key "id instance";
        leaf id {
          tailf:cli-suppress-range;
          type union {
            type uint32;
            type string;
          }
        }
        leaf instance {
          type string;
        }
        uses router-bgp-grouping;
      }
    }
    container mld {
      tailf:cli-add-mode;
      presence "true";
      uses router-mld-grouping;
      list vrf {
        key "name";
        leaf name {
          type string;
        }
        uses router-mld-grouping;
      }
    }
    container pim {
      tailf:cli-add-mode;
      presence "true";
      uses router-pim-grouping;
      list vrf {
        key "name";
        leaf name {
          type string;
        }
        uses router-pim-grouping;
      }
    }
    container rip {
      tailf:cli-add-mode;
      presence "true";
      uses router-rip-grouping;
      list vrf {
        key "name";
        leaf name {
          type string;
        }
        uses router-rip-grouping;
      }
    }
    list eigrp {
      key "name";
      leaf name {
        type string;
      }
      uses router-eigrp-grouping;
      list vrf {
        key "name";
        leaf name {
          type string;
        }
        uses router-eigrp-grouping;
      }
    }
    container vrrp {
      tailf:cli-add-mode;
      uses apply-group-grouping;
      list interface {
        key "name";
        leaf name {
          type string;
        }
        container delay {
          tailf:cli-compact-syntax;
          tailf:cli-sequence-commands {
            tailf:cli-reset-siblings;
          }
          leaf minimum {
            type uint16;
          }
          leaf reload {
            type uint16;
          }
        }
        container bfd {
          leaf minimum-interval {
            type uint16;
          }
          leaf multiplier {
            type uint8;
          }
        }
        container address-family {
          container ipv4 {
            tailf:cli-add-mode;
            list vrrp {
              key "id";
              leaf id {
                type uint8;
              }
              leaf slave {
                tailf:cli-hide-in-submode;
                type empty;
              }
              leaf follow {
                type string;
              }
              uses router-vrrp-if-af4-vrrp-grouping;
            }
            container vrrp-version {
              tailf:cli-drop-node-name;
              list vrrp {
                key "id";
                leaf id {
                  type uint8;
                }
                leaf version {
                  tailf:cli-hide-in-submode;
                  type uint8;
                }
                uses router-vrrp-if-af4-vrrp-grouping;
              }
            }
          }
          container ipv6 {
            tailf:cli-add-mode;
            list vrrp {
              key "id";
              leaf id {
                type uint8;
              }
              leaf slave {
                tailf:cli-hide-in-submode;
                type empty;
              }
              leaf follow {
                type string;
              }
              uses router-vrrp-if-af-vrrp-grouping;
              container bfd {
                container fast-detect {
                  container peer {
                    leaf ipv6 {
                      type inet:ipv6-address;
                    }
                  }
                }
              }
              container address {
                list global {
                  tailf:cli-suppress-mode;
                  tailf:cli-delete-when-empty;
                  tailf:cli-compact-syntax;
                  key "ip";
                  leaf ip {
                    type inet:ipv6-address;
                  }
                }
                leaf linklocal {
                  type union {
                    type inet:ipv6-address;
                    type enumeration {
                      enum autoconfig;
                    }
                  }
                }
              }
            }
          }
        }
      }
    }
    container hsrp {
      tailf:cli-add-mode;
      list interface {
        key "name";
        leaf name {
          type string;
        }
        container hsrp {
          uses router-hsrp-old-group-grouping;
          container delay {
            tailf:cli-compact-syntax;
            tailf:cli-sequence-commands {
              tailf:cli-reset-siblings;
            }
            leaf minimum {
              type uint16;
            }
            leaf reload {
              type uint16;
            }
          }
          leaf use-bia {
            type empty;
          }
          container redirects {
            leaf disable {
              type empty;
            }
          }
          leaf mac-refresh {
            type uint16;
          }
          list group {
            tailf:cli-drop-node-name;
            tailf:cli-suppress-mode;
            tailf:cli-delete-when-empty;
            tailf:cli-compact-syntax;
            key "id";
            leaf id {
              type uint8;
            }
            uses router-hsrp-old-group-grouping;
          }
        }
        container address-family {
          container ipv4 {
            tailf:cli-add-mode;
            container hsrp {
              tailf:cli-add-mode;
              presence "true";
              uses router-hsrp-ipv4-group-grouping;
            }
            container hsrp-version1-list {
              tailf:cli-drop-node-name;
              list hsrp {
                key "id";
                leaf id {
                  type uint16;
                }
                uses router-hsrp-ipv4-group-grouping;
              }
            }
            container hsrp-slave-list {
              tailf:cli-drop-node-name;
              list hsrp {
                key "id slave";
                leaf id {
                  type uint16;
                }
                leaf slave {
                  type enumeration {
                    enum slave;
                  }
                }
                uses router-hsrp-ipv4-slave-group-grouping;
              }
            }
            container hsrp-version2 {
              tailf:cli-drop-node-name;
              container hsrp {
                list version {
                  key "version";
                  leaf version {
                    type enumeration {
                      enum 1;
                      enum 2;
                    }
                  }
                  uses router-hsrp-ipv4-group-grouping;
                }
              }
            }
            container hsrp-version2-list {
              tailf:cli-drop-node-name;
              list hsrp {
                key "id";
                leaf id {
                  type uint16;
                }
                leaf version {
                  tailf:cli-hide-in-submode;
                  type uint8;
                }
                uses router-hsrp-ipv4-group-grouping;
              }
            }
          }
          container ipv6 {
            tailf:cli-add-mode;
            container hsrp {
              tailf:cli-add-mode;
              presence "true";
              uses router-hsrp-ipv6-group-grouping;
            }
            container hsrp-version1-list {
              tailf:cli-drop-node-name;
              list hsrp {
                key "id";
                leaf id {
                  type uint16;
                }
                uses router-hsrp-ipv6-group-grouping;
              }
            }
            container hsrp-slave-list {
              tailf:cli-drop-node-name;
              list hsrp {
                key "id slave";
                leaf id {
                  type uint16;
                }
                leaf slave {
                  type enumeration {
                    enum slave;
                  }
                }
                uses router-hsrp-ipv6-slave-group-grouping;
              }
            }
            container hsrp-version2 {
              tailf:cli-drop-node-name;
              container hsrp {
                list version {
                  key "version";
                  leaf version {
                    type enumeration {
                      enum 2;
                    }
                  }
                  uses router-hsrp-ipv6-group-grouping;
                }
              }
            }
            container hsrp-version2-list {
              tailf:cli-drop-node-name;
              list hsrp {
                key "id version";
                leaf id {
                  type uint16;
                }
                leaf version {
                  type uint8;
                }
                uses router-hsrp-ipv6-group-grouping;
              }
            }
          }
        }
      }
    }
    container msdp {
      tailf:cli-add-mode;
      uses router-msdp-grouping;
      list vrf {
        key "name";
        leaf name {
          type string;
        }
        uses router-msdp-grouping;
      }
    }
    container rib {
      tailf:cli-add-mode;
      container address-family {
        container ipv4 {
          tailf:cli-add-mode;
          container rump {
            leaf always-replicate {
              type empty;
            }
          }
        }
      }
    }
  }
  container accounting {
    tailf:cli-add-mode;
    presence "true";
    container interfaces {
      tailf:cli-add-mode;
      presence "true";
      container segment-routing {
        container mpls {
          tailf:cli-add-mode;
          presence "true";
          leaf ipv4 {
            type empty;
          }
          leaf ipv6 {
            type empty;
          }
        }
      }
      container mpls {
        tailf:cli-add-mode;
        presence "true";
        container ipv4 {
          leaf rsvp-te {
            type empty;
          }
        }
      }
    }
  }
  container service-policy {
    leaf-list apply-order {
      tailf:cli-flat-list-syntax;
      ordered-by user;
      type enumeration {
        enum pbr;
        enum qos;
      }
    }
  }
  container service-function-chaining {
    tailf:cli-add-mode;
    list sf {
      key "name";
      leaf name {
        type string;
      }
      list locator {
        key "id";
        leaf id {
          type uint8;
        }
        container transport {
          container vxlan-gpe {
            tailf:cli-add-mode;
            tailf:cli-compact-syntax;
            container source-address {
              tailf:cli-flatten-container;
              leaf ipv4 {
                type inet:ipv4-address;
              }
            }
            container destination-address {
              tailf:cli-flatten-container;
              leaf ipv4 {
                type inet:ipv4-address;
              }
            }
            leaf source-port {
              type uint16;
            }
            leaf vni {
              type uint16;
            }
          }
        }
      }
    }
    list sff {
      key "name";
      leaf name {
        type string;
      }
      list locator {
        key "id";
        leaf id {
          type uint8;
        }
        container transport {
          container vxlan-gpe {
            tailf:cli-add-mode;
            tailf:cli-compact-syntax;
            container source-address {
              tailf:cli-flatten-container;
              leaf ipv4 {
                type inet:ipv4-address;
              }
            }
            container destination-address {
              tailf:cli-flatten-container;
              leaf ipv4 {
                type inet:ipv4-address;
              }
            }
            leaf source-port {
              type uint16;
            }
            leaf vni {
              type uint16;
            }
          }
        }
      }
    }
    list metadata {
      key "name";
      leaf name {
        type string;
      }
      list type {
        key "id";
        leaf id {
          type enumeration {
            enum 1;
          }
        }
        leaf format {
          tailf:cli-hide-in-submode;
          type enumeration {
            enum dc-allocation;
          }
        }
        leaf tenant-id {
          type uint32;
        }
      }
    }
    list path {
      key "id";
      leaf id {
        type uint32;
      }
      list terminate-list {
        tailf:cli-drop-node-name;
        tailf:cli-suppress-mode;
        tailf:cli-delete-when-empty;
        tailf:cli-compact-syntax;
        key "id";
        leaf id {
          type uint8;
        }
        leaf terminate {
          type empty;
        }
        leaf metadata-disposition {
          type string;
        }
        container default-action {
          tailf:cli-flatten-container;
          tailf:cli-compact-syntax;
          container redirect {
            tailf:cli-flatten-container;
            tailf:cli-compact-syntax;
            container ipv4 {
              tailf:cli-flatten-container;
              tailf:cli-compact-syntax;
              container nexthop {
                tailf:cli-flatten-container;
                tailf:cli-compact-syntax;
                choice nexthop-choice {
                  leaf address {
                    tailf:cli-drop-node-name;
                    type inet:ipv4-address;
                  }
                  leaf vrf {
                    type string;
                  }
                }
              }
            }
          }
        }
      }
      list sf-list {
        tailf:cli-drop-node-name;
        tailf:cli-suppress-mode;
        tailf:cli-delete-when-empty;
        key "id sf";
        leaf id {
          type uint8;
        }
        leaf sf {
          type string;
        }
      }
      list sff-list {
        tailf:cli-drop-node-name;
        tailf:cli-suppress-mode;
        tailf:cli-delete-when-empty;
        key "id sff";
        leaf id {
          type uint8;
        }
        leaf sff {
          type string;
        }
      }
    }
    list metadata-disposition {
      key "name";
      leaf name {
        type string;
      }
      list type {
        key "id";
        leaf id {
          type enumeration {
            enum 1;
          }
        }
        leaf format {
          tailf:cli-hide-in-submode;
          type enumeration {
            enum dc-allocation;
          }
        }
        list match-entry {
          key "name";
          leaf name {
            type string;
          }
          container tenant-id {
            tailf:cli-add-mode;
            leaf id {
              tailf:cli-drop-node-name;
              tailf:cli-hide-in-submode;
              type uint32;
            }
            container redirect {
              container ipv4 {
                container nexthop {
                  choice nexthop-choice {
                    leaf address {
                      tailf:cli-drop-node-name;
                      type inet:ipv4-address;
                    }
                    leaf vrf {
                      type string;
                    }
                  }
                }
              }
            }
          }
        }
      }
    }
  }
  container bundle-offload {
    presence "true";
  }
  container subscriber {
    tailf:cli-add-mode;
    container arp {
      leaf scale-mode-enable {
        type empty;
      }
      leaf uncond-proxy-arp-enable {
        type empty;
      }
    }
    container redundancy {
      tailf:cli-add-mode;
      presence "true";
      container source-interface {
        uses interface-name-grouping;
      }
      container revertive-timer {
        tailf:cli-compact-syntax;
        tailf:cli-sequence-commands {
          tailf:cli-reset-siblings;
        }
        leaf value {
          tailf:cli-drop-node-name;
          type uint16;
        }
        leaf maximum {
          type uint16;
        }
      }
      list group {
        key "id";
        leaf id {
          type uint16;
        }
        uses description-grouping;
        leaf preferred-role {
          type enumeration {
            enum master;
            enum slave;
          }
        }
        leaf virtual-mac {
          type string;
        }
        leaf slave-mode {
          type enumeration {
            enum hot;
            enum warm;
          }
        }
        leaf hold-timer {
          type uint16;
        }
        container peer {
          leaf address {
            tailf:cli-drop-node-name;
            type union {
              type inet:ipv4-address;
              type inet:ipv6-address;
            }
          }
          leaf route-disable {
            type empty;
          }
        }
        leaf core-tracking {
          type string;
        }
        leaf access-tracking {
          type string;
        }
        container state-control-route {
          list ipv4 {
            tailf:cli-suppress-mode;
            tailf:cli-delete-when-empty;
            tailf:cli-compact-syntax;
            tailf:cli-sequence-commands {
              tailf:cli-reset-siblings;
            }
            key "prefix vrf";
            leaf prefix {
              type ipv4-prefix;
            }
            leaf vrf {
              type string;
            }
            leaf tag {
              type uint32;
            }
          }
          container ipv6 {
            container iapd {
              tailf:cli-compact-syntax;
              tailf:cli-sequence-commands {
                tailf:cli-reset-siblings;
              }
              leaf prefix {
                tailf:cli-drop-node-name;
                type tailf:ipv6-address-and-prefix-length;
              }
              leaf vrf {
                tailf:cli-optional-in-sequence;
                type string;
              }
              leaf tag {
                type uint32;
              }
            }
          }
        }
        container revertive-timer {
          tailf:cli-compact-syntax;
          tailf:cli-sequence-commands {
            tailf:cli-reset-siblings;
          }
          leaf value {
            tailf:cli-drop-node-name;
            type uint16;
          }
          leaf maximum {
            type uint16;
          }
        }
        container interface-list {
          tailf:cli-add-mode;
          presence "true";
          list interface {
            tailf:cli-suppress-mode;
            tailf:cli-delete-when-empty;
            key "name";
            leaf name {
              type ifname;
            }
            leaf id {
              type uint16;
            }
          }
        }
      }
    }
    container session {
      leaf limit {
        type uint32;
      }
    }
    container pta {
      container tcp {
        leaf mss-adjust {
          type uint16;
        }
      }
    }
    container database {
      leaf backpressure-level {
        type uint8;
      }
    }
  }
  container traffic-collector {
    tailf:cli-add-mode;
    presence "true";
    list interface {
      key "name";
      leaf name {
        type string;
      }
    }
    container statistics {
      tailf:cli-add-mode;
      presence "true";
      leaf history-size {
        type uint8;
      }
      leaf collection-interval {
        type uint8;
      }
      leaf history-timeout {
        type uint16;
      }
    }
  }
  container flowspec {
    tailf:cli-add-mode;
    presence "true";
    container local-install {
      leaf interface-all {
        type empty;
      }
    }
    uses flowspec-af-grouping;
    list vrf {
      key "name";
      leaf name {
        type string;
      }
      uses flowspec-af-grouping;
    }
  }

  grouping flowspec-af-grouping {
    container address-family {
      container ipv4 {
        tailf:cli-add-mode;
        container local-install {
          leaf interface-all {
            type empty;
          }
        }
        list service-policy {
          tailf:cli-suppress-mode;
          tailf:cli-delete-when-empty;
          key "name";
          leaf name {
            type string;
          }
          leaf type {
            tailf:cli-prefix-key;
            type enumeration {
              enum pbr;
            }
          }
        }
      }
      container ipv6 {
        tailf:cli-add-mode;
        container local-install {
          leaf interface-all {
            type empty;
          }
        }
      }
    }
  }

  container rsvp {
    tailf:cli-add-mode;
    uses apply-group-grouping;
    container bandwidth {
      container rdm {
        container percentage {
          tailf:cli-compact-syntax;
          tailf:cli-sequence-commands {
            tailf:cli-reset-siblings;
          }
          leaf max-reservable-bc0 {
            type uint16;
          }
          leaf bc1 {
            type uint16;
          }
        }
      }
    }
    uses rsvp-authentication-grouping;
    list interface {
      key "name";
      leaf name {
        type string;
      }
      uses rsvp-authentication-grouping;
      container bandwidth {
        tailf:cli-compact-syntax;
        tailf:cli-sequence-commands {
          tailf:cli-reset-siblings;
        }
        tailf:cli-delete-when-empty;
        presence "true";
        choice bandwidth-choice {
          case percentage-case {
            leaf percentage {
              type empty;
            }
            leaf total-reservable-percent {
              tailf:cli-drop-node-name;
              type uint16;
            }
            leaf largest-reservable-flow {
              tailf:cli-drop-node-name;
              type uint16;
            }
          }
          case rsvp-case {
            leaf global-pool {
              tailf:cli-optional-in-sequence;
              type empty;
            }
            leaf total-reservable {
              tailf:cli-drop-node-name;
              type uint32;
            }
            leaf total-reservable-unit {
              tailf:cli-drop-node-name;
              tailf:cli-optional-in-sequence;
              type enumeration {
                enum Gbps;
                enum Kbps;
                enum Mbps;
              }
            }
            leaf largest-reservable {
              tailf:cli-drop-node-name;
              tailf:cli-optional-in-sequence;
              type uint32;
            }
            leaf largest-reservable-unit {
              tailf:cli-drop-node-name;
              tailf:cli-optional-in-sequence;
              type enumeration {
                enum Gbps;
                enum Kbps;
                enum Mbps;
              }
            }
            leaf sub-pool {
              type uint32;
            }
          }
          case rdm-case {
            container rdm {
              tailf:cli-compact-syntax;
              tailf:cli-sequence-commands {
                tailf:cli-reset-siblings;
              }
              leaf bc0 {
                type uint32;
              }
              leaf largest-reservable-flow {
                tailf:cli-drop-node-name;
                tailf:cli-optional-in-sequence;
                type uint32;
              }
              leaf bc1 {
                type uint32;
              }
            }
          }
        }
      }
      container signalling {
        leaf dscp {
          type uint8;
        }
        container hello {
          container graceful-restart {
            leaf interface-based {
              type empty;
            }
          }
        }
        container refresh {
          leaf interval {
            type uint8;
          }
          container reduction {
            leaf disable {
              type empty;
            }
            container reliable {
              leaf summary-refresh {
                type empty;
              }
              leaf ack-max-size {
                type uint16;
              }
              leaf ack-hold-time {
                type uint16;
              }
              leaf retransmit-time {
                type uint16;
              }
            }
          }
        }
        container rate-limit {
          tailf:cli-compact-syntax;
          tailf:cli-sequence-commands {
            tailf:cli-reset-siblings;
          }
          tailf:cli-delete-when-empty;
          presence "true";
          leaf rate {
            type uint16;
          }
          leaf interval {
            type uint16;
          }
        }
      }
    }
    container logging {
      container events {
        leaf issu {
          type empty;
        }
        leaf nsr {
          type empty;
        }
      }
    }
    list neighbor {
      key "address";
      leaf address {
        type inet:ipv4-address;
      }
      uses rsvp-authentication-grouping;
    }
    list controller {
      key "name";
      leaf name {
        type string;
      }
      container signalling {
        container refresh {
          container out-of-band {
            leaf interval {
              type uint32;
            }
            leaf missed {
              type uint32;
            }
          }
        }
      }
    }
    container signalling {
      leaf graceful-restart {
        type empty;
      }
      container graceful-restart-conf {
        tailf:cli-drop-node-name;
        container graceful-restart {
          leaf restart-time {
            type uint16;
          }
          leaf recovery-time {
            type uint16;
          }
        }
      }
      container hello {
        container graceful-restart {
          container refresh {
            leaf misses {
              type uint8;
            }
            leaf interval {
              type uint16;
            }
          }
        }
      }
      container message-bundle {
        leaf disable {
          type empty;
        }
      }
    }
  }
  list xconnect {
    tailf:cli-suppress-mode;
    tailf:cli-delete-when-empty;
    tailf:cli-compact-syntax;
    tailf:cli-sequence-commands {
      tailf:cli-reset-siblings;
    }
    key "id";
    leaf id {
      type uint16;
    }
    leaf endpoint-1 {
      type string;
    }
    leaf endpoint-2 {
      type string;
    }
    leaf name {
      tailf:cli-drop-node-name;
      tailf:cli-multi-value;
      type string;
    }
  }
  container lmp {
    tailf:cli-add-mode;
    presence "true";
    container gmpls {
      container optical-uni {
        tailf:cli-add-mode;
        list controller {
          key "name";
          leaf name {
            type string;
          }
          container neighbor {
            leaf name {
              tailf:cli-drop-node-name;
              type string;
            }
            container link-id {
              container ipv4 {
                leaf unicast {
                  type inet:ipv4-address;
                }
              }
            }
            container interface-id {
              leaf unnumbered {
                type uint32;
              }
            }
          }
          container link-id {
            container ipv4 {
              choice ipv4-choice {
                leaf unicast {
                  type inet:ipv4-address;
                }
                leaf unnumbered {
                  type empty;
                }
              }
            }
          }
        }
        list neighbor {
          key "name";
          leaf name {
            type string;
          }
          container ipcc {
            leaf routed {
              type empty;
            }
          }
          container router-id {
            container ipv4 {
              leaf unicast {
                type inet:ipv4-address;
              }
            }
          }
        }
        container router-id {
          container ipv4 {
            leaf unicast {
              type inet:ipv4-address;
            }
          }
        }
      }
    }
  }
  list l2tp-class {
    key "name";
    leaf name {
      type string;
    }
    container password {
      tailf:cli-compact-syntax;
      tailf:cli-sequence-commands;
      leaf encryption {
        tailf:cli-drop-node-name;
        type enumeration {
          enum 0;
          enum 7;
        }
      }
      leaf password {
        tailf:cli-drop-node-name;
        type string;
      }
    }
    leaf hello-interval {
      type uint16;
    }
  }
  container mpls {
    container label {
      leaf protocol {
        type enumeration {
          enum ldp;
          enum tdp;
        }
      }
      container range {
        tailf:cli-compact-syntax;
        tailf:cli-sequence-commands {
          tailf:cli-reset-siblings;
        }
        leaf table {
          tailf:cli-optional-in-sequence;
          type uint8;
        }
        leaf min {
          tailf:cli-drop-node-name;
          type uint32;
        }
        leaf max {
          tailf:cli-drop-node-name;
          type uint32;
        }
      }
      container blocks {
        tailf:cli-add-mode;
        container block {
          list name {
            tailf:cli-suppress-mode;
            tailf:cli-delete-when-empty;
            tailf:cli-compact-syntax;
            tailf:cli-sequence-commands {
              tailf:cli-reset-siblings;
            }
            key "name";
            leaf name {
              type string;
            }
            leaf type {
              type enumeration {
                enum cbf;
                enum pfp;
              }
            }
            leaf start {
              type uint32;
            }
            choice end-or-size {
              leaf end {
                type uint32;
              }
              leaf size {
                type uint32;
              }
            }
            leaf client {
              type string;
            }
          }
        }
      }
    }
    container traffic-eng {
      tailf:cli-add-mode;
      presence "true";
      uses apply-group-grouping;
      container auto-tunnel {
        container p2p {
          tailf:cli-add-mode;
          container tunnel-id {
            tailf:cli-compact-syntax;
            tailf:cli-sequence-commands;
            leaf min {
              type uint16;
            }
            leaf max {
              type uint16;
            }
          }
        }
        container pcc {
          tailf:cli-add-mode;
          container tunnel-id {
            tailf:cli-compact-syntax;
            tailf:cli-sequence-commands;
            leaf min {
              type uint16;
            }
            leaf max {
              type uint16;
            }
          }
        }
        container backup {
          tailf:cli-add-mode;
          container timers {
            container removal {
              leaf unused {
                type uint16;
              }
            }
          }
          container tunnel-id {
            tailf:cli-compact-syntax;
            tailf:cli-sequence-commands;
            leaf min {
              type uint16;
            }
            leaf max {
              type uint16;
            }
          }
          container affinity {
            leaf ignore {
              type empty;
            }
          }
        }
        container mesh {
          tailf:cli-add-mode;
          list group {
            key "id";
            leaf id {
              type uint32;
            }
            leaf onehop {
              type empty;
            }
            leaf attribute-set {
              type string;
            }
            leaf destination-list {
              type string;
            }
          }
          container timers {
            container removal {
              leaf unused {
                type uint16;
              }
            }
          }
          container tunnel-id {
            tailf:cli-compact-syntax;
            tailf:cli-sequence-commands;
            leaf min {
              type uint16;
            }
            leaf max {
              type uint16;
            }
          }
        }
      }
      container bandwidth-accounting {
        tailf:cli-add-mode;
        presence "true";
        leaf adjustment-factor {
          type uint8;
        }
        container application {
          tailf:cli-add-mode;
          leaf interval {
            type uint16;
          }
        }
        container collection {
          leaf rsvp-te {
            type empty;
          }
        }
        container flooding {
          container threshold {
            tailf:cli-sequence-commands {
              tailf:cli-reset-siblings;
            }
            tailf:cli-compact-syntax;
            leaf up {
              type uint8;
            }
            leaf down {
              type uint8;
            }
          }
        }
        leaf sampling-interval {
          type uint16;
        }
      }
      list interface {
        key "name";
        leaf name {
          type string;
        }
        uses apply-group-grouping;
        container bfd {
          leaf fast-detect {
            type empty;
          }
        }
        container auto-tunnel {
          container backup {
            tailf:cli-add-mode;
            presence "true";
            container exclude {
              container srlg {
                tailf:cli-delete-when-empty;
                presence "true";
                leaf preferred {
                  type empty;
                }
              }
            }
            leaf nhop-only {
              type empty;
            }
            leaf attribute-set {
              type string;
            }
          }
        }
        leaf attribute-flags {
          type string;
        }
        container attribute-names {
          leaf name {
            tailf:cli-drop-node-name;
            tailf:cli-multi-value;
            type string;
          }
          list index {
            tailf:cli-suppress-mode;
            tailf:cli-delete-when-empty;
            key "id";
            leaf id {
              type uint8;
            }
            leaf name {
              tailf:cli-drop-node-name;
              tailf:cli-multi-value;
              type string;
            }
          }
        }
        leaf admin-weight {
          type uint32;
        }
        container backup-path {
          leaf-list tunnel-te {
            type union {
              type uint16;
              type string;
            }
          }
        }
        container fault-oam {
          leaf lockout {
            type empty;
          }
        }
      }
      container pce {
        tailf:cli-add-mode;
        leaf deadtimer {
          type uint8;
        }
        container peer {
          container source {
            leaf ipv4 {
              type inet:ipv4-address;
            }
          }
          list ipv4 {
            key "address";
            leaf address {
              type inet:ipv4-address;
            }
            container password {
              tailf:cli-compact-syntax;
              tailf:cli-sequence-commands;
              uses password-grouping {
                refine "secret";
              }
            }
            leaf precedence {
              type uint8;
            }
          }
        }
        leaf reoptimize {
          type uint32;
        }
        container logging {
          container events {
            leaf peer-status {
              type empty;
            }
          }
        }
        leaf segment-routing {
          type empty;
        }
        container stateful-client {
          tailf:cli-add-mode;
          presence "true";
          leaf instantiation {
            type empty;
          }
          leaf cisco-extension {
            type empty;
          }
          leaf report {
            type empty;
          }
          container timers {
            leaf redelegation-timeout {
              type uint32;
            }
            leaf state-timeout {
              type uint16;
            }
          }
          leaf fast-repair {
            type empty;
          }
          container redundancy {
            leaf pcc-centric {
              type empty;
            }
          }
          leaf autoroute-announce {
            type empty;
          }
        }
        container tolerance {
          leaf keepalive {
            type uint8;
          }
        }
      }
      container logging {
        container events {
          leaf all {
            type empty;
          }
          container role {
            leaf mid {
              type empty;
            }
            leaf head {
              type empty;
            }
            leaf tail {
              type empty;
            }
          }
          leaf nsr {
            type empty;
          }
          container frr-protection {
            tailf:cli-delete-when-empty;
            presence "true";
            leaf primary-lsp {
              type enumeration {
                enum ready-state;
                enum active-state;
              }
            }
          }
          leaf preemption {
            type empty;
          }
        }
      }
      list affinity-map {
        tailf:cli-suppress-mode;
        tailf:cli-delete-when-empty;
        key "name";
        leaf name {
          type string;
        }
        leaf value {
          tailf:cli-drop-node-name;
          type string;
        }
        leaf bit-position {
          type uint8;
        }
      }
      list attribute-set {
        key "type pathname";
        leaf type {
          type enumeration {
            enum path-option;
            enum auto-backup;
            enum auto-mesh;
            enum p2mp-te;
            enum path-protection-aps;
            enum xro;
            enum p2p-te;
          }
        }
        leaf pathname {
          type string;
        }
        uses affinity-grouping;
        container logging {
          container events {
            uses logging-events-lsp-status-grouping;
          }
        }
        leaf bandwidth {
          type uint32;
        }
        container priority {
          tailf:cli-compact-syntax;
          tailf:cli-sequence-commands;
          leaf setup {
            tailf:cli-drop-node-name;
            type uint8;
          }
          leaf hold {
            tailf:cli-drop-node-name;
            type uint8;
          }
        }
        container signalled-bandwidth {
          tailf:cli-compact-syntax;
          tailf:cli-sequence-commands;
          leaf bw-req {
            tailf:cli-drop-node-name;
            type uint32;
          }
          leaf class-type {
            type uint8;
          }
        }
        container auto-bw {
          leaf collect-bw-only {
            type empty;
          }
        }
        container autoroute {
          leaf announce {
            type empty;
          }
        }
        container fast-reroute {
          tailf:cli-delete-when-empty;
          presence "true";
          leaf-list protect {
            tailf:cli-flat-list-syntax;
            type enumeration {
              enum node;
              enum bandwidth;
            }
          }
        }
        container policy-class {
          tailf:cli-delete-when-empty;
          presence "true";
          leaf value {
            tailf:cli-drop-node-name;
            type uint8;
          }
        }
        leaf record-route {
          type empty;
        }
        leaf forward-class {
          type uint8;
        }
        list exclude {
          tailf:cli-suppress-mode;
          tailf:cli-delete-when-empty;
          tailf:cli-compact-syntax;
          tailf:cli-sequence-commands {
            tailf:cli-reset-siblings;
          }
          key "source destination tunnel-id extended-tunnel-id";
          leaf mode {
            tailf:cli-drop-node-name;
            tailf:cli-prefix-key;
            type enumeration {
              enum best-effort;
              enum strict;
            }
          }
          leaf lsp {
            tailf:cli-prefix-key;
            type empty;
          }
          leaf source {
            type inet:ipv4-address;
          }
          leaf destination {
            type inet:ipv4-address;
          }
          leaf tunnel-id {
            type uint16;
          }
          leaf extended-tunnel-id {
            type inet:ipv4-address;
          }
          leaf lsp-id {
            type uint16;
          }
        }
        container pce {
          tailf:cli-add-mode;
          presence "true";
          container disjoint-path {
            tailf:cli-compact-syntax;
            tailf:cli-sequence-commands {
              tailf:cli-reset-siblings;
            }
            leaf source {
              type inet:ipv4-address;
            }
            leaf type {
              type enumeration {
                enum link;
                enum node;
                enum srlg;
              }
            }
            leaf group-id {
              type uint32;
            }
          }
        }
        container path-selection {
          tailf:cli-add-mode;
          presence "true";
          leaf cost-limit {
            type uint32;
          }
          leaf delay-limit {
            type uint32;
          }
          leaf metric {
            type enumeration {
              enum igp;
              enum te;
            }
          }
          container segment-routing {
            container prepend {
              tailf:cli-add-mode;
              presence "true";
              list index {
                tailf:cli-suppress-mode;
                tailf:cli-delete-when-empty;
                key "id";
                leaf id {
                  type uint8;
                }
                leaf next-label {
                  type uint32;
                }
                leaf bgp-nhop {
                  type empty;
                }
              }
            }
          }
        }
        container biased-to {
          leaf explicit-path {
            type string;
          }
        }
      }
      container path-selection {
        tailf:cli-add-mode;
        leaf cost-limit {
          type uint32;
        }
        container metric {
          leaf metric-type {
            tailf:cli-drop-node-name;
            type enumeration {
              enum igp;
              enum te;
            }
          }
        }
        container ignore {
          leaf-list overload {
            tailf:cli-flat-list-syntax;
            type enumeration {
              enum head;
              enum mid;
              enum tail;
            }
          }
        }
        container loose-expansion {
          list metric {
            tailf:cli-suppress-mode;
            tailf:cli-delete-when-empty;
            key "class-type";
            leaf class-type {
              type uint8;
            }
            leaf metric-type {
              tailf:cli-drop-node-name;
              tailf:cli-prefix-key;
              type enumeration {
                enum delay;
                enum igp;
                enum te;
              }
            }
          }
          list affinity {
            tailf:cli-suppress-mode;
            tailf:cli-delete-when-empty;
            tailf:cli-compact-syntax;
            tailf:cli-sequence-commands {
              tailf:cli-reset-siblings;
            }
            key "class-type";
            leaf value {
              tailf:cli-drop-node-name;
              tailf:cli-prefix-key;
              type string;
            }
            leaf mask {
              tailf:cli-prefix-key;
              type string;
            }
            leaf class-type {
              type uint8;
            }
          }
          leaf domain-match {
            type empty;
          }
        }
      }
      container ds-te {
        container mode {
          leaf ietf {
            type empty;
          }
        }
        container te-classes {
          tailf:cli-add-mode;
          list te-class {
            tailf:cli-suppress-mode;
            tailf:cli-delete-when-empty;
            tailf:cli-compact-syntax;
            tailf:cli-sequence-commands;
            key "id";
            leaf id {
              type uint8;
            }
            choice te-class-choice {
              leaf unused {
                type empty;
              }
              case used {
                leaf class-type {
                  type uint8;
                }
                leaf priority {
                  type uint8;
                }
              }
            }
          }
        }
      }
      container soft-preemption {
        tailf:cli-add-mode;
        presence "true";
        leaf timeout {
          type uint32;
        }
      }
      container auto-bw {
        container collect {
          leaf frequency {
            type uint16;
          }
        }
      }
      container reoptimize {
        leaf value {
          tailf:cli-drop-node-name;
          type uint32;
        }
        leaf load-balance {
          type empty;
        }
        container timers {
          container delay {
            leaf cleanup {
              type uint16;
            }
            leaf installation {
              type uint16;
            }
            leaf after-frr {
              type uint8;
            }
            leaf path-protection {
              type uint32;
            }
          }
        }
      }
      container bfd {
        container lsp {
          container head {
            container down-action {
              leaf resetup {
                type empty;
              }
              container reoptimize {
                leaf timeout {
                  type uint32;
                }
              }
            }
          }
          container tail {
            leaf minimum-interval {
              type uint16;
            }
            leaf multiplier {
              type uint8;
            }
          }
        }
        leaf multiplier {
          type uint8;
        }
        leaf minimum-interval {
          type uint16;
        }
      }
      container router-id {
        list secondary {
          tailf:cli-suppress-mode;
          tailf:cli-delete-when-empty;
          key "address";
          leaf address {
            type inet:ipv4-address;
          }
        }
      }
      container fast-reroute {
        container timers {
          leaf promotion {
            type uint32;
          }
        }
      }
      container link-management {
        container timers {
          leaf periodic-flooding {
            type uint16;
          }
          container preemption-delay {
            leaf bundle-capacity {
              type uint16;
            }
          }
        }
      }
      container signalling {
        container advertise {
          leaf explicit-null {
            type empty;
          }
        }
      }
      container gmpls {
        container optical-nni {
          tailf:cli-add-mode;
          container topology {
            container instance {
              list ospf {
                key "name area";
                leaf name {
                  type string;
                }
                leaf area {
                  type ospf-area-type;
                }
                list controller {
                  key "name";
                  leaf name {
                    type string;
                  }
                  container tti-mode {
                    choice tti-mode-choice {
                      leaf odu-pm {
                        type empty;
                      }
                      leaf odu-tcm {
                        type uint8;
                      }
                      leaf otu-sm {
                        type empty;
                      }
                    }
                  }
                  leaf admin-weight {
                    type uint16;
                  }
                }
              }
            }
          }
          container controller {
            list Odu-Group-Te {
              key "id";
              leaf id {
                type uint16;
              }
              leaf signalled-name {
                type string;
              }
              container logging {
                container events {
                  container lsp-status {
                    leaf state {
                      type empty;
                    }
                    leaf signalling-state {
                      type empty;
                    }
                    leaf homepath-state {
                      type empty;
                    }
                    leaf switch-over {
                      type empty;
                    }
                    leaf cross-connect {
                      type empty;
                    }
                    leaf insufficient-bandwidth {
                      type empty;
                    }
                    leaf path-change {
                      type empty;
                    }
                  }
                }
              }
              leaf signalled-bandwidth {
                type string;
              }
              container static-uni {
                tailf:cli-compact-syntax;
                tailf:cli-sequence-commands {
                  tailf:cli-reset-siblings;
                }
                choice ingress-choice {
                  leaf ingress-port {
                    type empty;
                  }
                  leaf local-termination {
                    type empty;
                  }
                }
                leaf controller {
                  type string;
                }
                choice egress-choice {
                  leaf egress-port {
                    type empty;
                  }
                  leaf remote-termination {
                    type empty;
                  }
                }
                leaf unnumbered {
                  type uint32;
                }
              }
              container destination {
                container ipv4 {
                  tailf:cli-compact-syntax;
                  tailf:cli-sequence-commands {
                    tailf:cli-reset-siblings;
                  }
                  choice destination-choice {
                    leaf unicast {
                      type inet:ipv4-address;
                    }
                    case unnumbered {
                      leaf unnumbered {
                        type inet:ipv4-address;
                      }
                      leaf interface-ifindex {
                        type uint32;
                      }
                    }
                  }
                }
              }
              leaf announce-srlg {
                type empty;
              }
              leaf record-route {
                type empty;
              }
              uses mpls-traffic-eng-controller-path-option-grouping;
            }
          }
        }
        container optical-uni {
          tailf:cli-add-mode;
          list controller {
            key "name";
            leaf name {
              type string;
            }
            container logging {
              leaf discovered-srlgs {
                type empty;
              }
            }
            container announce {
              leaf srlgs {
                type empty;
              }
            }
            container tunnel-properties {
              tailf:cli-add-mode;
              presence "true";
              leaf signalled-name {
                type string;
              }
              container logging {
                container events {
                  container lsp-status {
                    leaf state {
                      type empty;
                    }
                  }
                }
              }
              leaf tunnel-id {
                type uint16;
              }
              container record {
                leaf srlg {
                  type empty;
                }
              }
              container destination {
                container ipv4 {
                  leaf unicast {
                    type inet:ipv4-address;
                  }
                }
              }
              uses mpls-traffic-eng-controller-path-option-grouping;
              leaf record-route {
                type empty;
              }
            }
          }
        }
      }
      container load-share {
        leaf unequal {
          type empty;
        }
      }
      container timers {
        container loose-path {
          leaf retry-period {
            type uint16;
          }
        }
      }
    }
    container ldp {
      tailf:cli-add-mode;
      presence "true";
      leaf nsr {
        type empty;
      }
      container log {
        tailf:cli-add-mode;
        leaf adjacency {
          type empty;
        }
        leaf hello-adjacency {
          type empty;
        }
        leaf neighbor {
          type empty;
        }
        leaf graceful-restart {
          type empty;
        }
        leaf session-protection {
          type empty;
        }
        leaf nsr {
          type empty;
        }
      }
      leaf graceful-restart {
        type empty;
      }
      container graceful-restart-conf {
        tailf:cli-drop-node-name;
        container graceful-restart {
          leaf reconnect-timeout {
            type uint16;
          }
          leaf forwarding-state-holdtime {
            type uint16;
          }
          container helper-peer {
            container maintain-on-local-reset {
              leaf for {
                type string;
              }
            }
          }
        }
      }
      leaf holdtime {
        type uint16;
      }
      container session {
        container backoff {
          tailf:cli-compact-syntax;
          tailf:cli-sequence-commands {
            tailf:cli-reset-siblings;
          }
          leaf initial {
            tailf:cli-drop-node-name;
            type uint32;
          }
          leaf maximum {
            tailf:cli-drop-node-name;
            type uint32;
          }
        }
        leaf holdtime {
          type uint16;
        }
        container protection {
          tailf:cli-delete-when-empty;
          presence "true";
          choice protection-choice {
            leaf duration {
              type union {
                type uint32;
                type enumeration {
                  enum infinite;
                }
              }
            }
            leaf for {
              type string;
            }
          }
        }
      }
      container signalling {
        leaf dscp {
          type uint8;
        }
      }
      container igp {
        container sync {
          container delay-on-proc-restart {
            tailf:cli-drop-node-name;
            container delay {
              leaf on-proc-restart {
                type uint16;
              }
            }
          }
          container delay {
            tailf:cli-compact-syntax;
            leaf on-session-up {
              type empty;
            }
            leaf delay-value {
              tailf:cli-drop-node-name;
              type uint16;
            }
          }
        }
      }
      leaf entropy-label {
        type empty;
      }
      container mldp {
        tailf:cli-add-mode;
        presence "true";
        container logging {
          leaf notifications {
            type empty;
          }
          leaf internal {
            type empty;
          }
        }
        container address-family {
          container ipv4 {
            tailf:cli-add-mode;
            presence "true";
            container make-before-break {
              container delay {
                tailf:cli-compact-syntax;
                tailf:cli-sequence-commands {
                  tailf:cli-reset-siblings;
                }
                leaf seconds {
                  tailf:cli-drop-node-name;
                  type uint16;
                }
                leaf delete-seconds {
                  tailf:cli-drop-node-name;
                  type uint8;
                }
              }
            }
            container forwarding {
              leaf recursive {
                type empty;
              }
            }
            container recursive-fec {
              presence "true";
            }
          }
        }
      }
      container discovery {
        tailf:cli-add-mode;
        container instance-tlv {
          leaf disable {
            type empty;
          }
        }
        container hello {
          leaf holdtime {
            type uint16;
          }
          leaf interval {
            type uint16;
          }
        }
        container targeted-hello {
          container accept {
            tailf:cli-delete-when-empty;
            presence "true";
            leaf from {
              type string;
            }
          }
          leaf holdtime {
            type uint16;
          }
          leaf interval {
            type uint16;
          }
        }
      }
      leaf router-id {
        type union {
          type inet:ipv4-address;
          type ifname;
        }
      }
      container neighbor {
        tailf:cli-add-mode;
        container password {
          tailf:cli-compact-syntax;
          tailf:cli-sequence-commands;
          leaf type {
            tailf:cli-drop-node-name;
            type enumeration {
              enum clear;
              enum encrypted;
            }
          }
          leaf password {
            tailf:cli-drop-node-name;
            type string;
          }
        }
        list neighbor-list {
          tailf:cli-drop-node-name;
          tailf:cli-suppress-mode;
          tailf:cli-delete-when-empty;
          tailf:cli-compact-syntax;
          key "id";
          leaf id {
            type union {
              type inet:ipv4-address;
              type string;
            }
          }
          container password {
            choice password-choice {
              leaf disable {
                type empty;
              }
              leaf clear {
                type string;
              }
              leaf encrypted {
                type string;
              }
            }
          }
        }
      }
      container password {
        container option {
          tailf:cli-compact-syntax;
          tailf:cli-sequence-commands;
          leaf sequence-nr {
            tailf:cli-drop-node-name;
            type uint16;
          }
          leaf for {
            type string;
          }
          leaf enc-type {
            tailf:cli-drop-node-name;
            type enumeration {
              enum 0;
              enum 7;
            }
          }
          leaf password {
            tailf:cli-drop-node-name;
            type string;
          }
        }
        container required {
          presence "true";
          leaf for {
            type string;
          }
        }
      }
      container label {
        tailf:cli-add-mode;
        container allocate {
          leaf for {
            type string;
          }
        }
        container accept {
          tailf:cli-add-mode;
          list from {
            tailf:cli-suppress-mode;
            tailf:cli-delete-when-empty;
            key "id";
            leaf id {
              type string;
            }
            leaf for {
              type string;
            }
          }
        }
        container advertise {
          tailf:cli-add-mode;
          leaf disable {
            type empty;
          }
          leaf for {
            type string;
          }
        }
      }
      container address-family {
        container ipv4 {
          tailf:cli-add-mode;
          presence "true";
          list neighbor {
            tailf:cli-suppress-mode;
            tailf:cli-delete-when-empty;
            key "address";
            leaf address {
              type inet:ipv4-address;
            }
            leaf targeted {
              type empty;
            }
          }
          container discovery {
            container targeted-hello {
              container accept {
                tailf:cli-delete-when-empty;
                presence "true";
                leaf from {
                  type string;
                }
              }
            }
          }
          container label {
            tailf:cli-add-mode;
            container local {
              tailf:cli-add-mode;
              container allocate {
                leaf for {
                  type union {
                    type string;
                    type enumeration {
                      enum host-routes;
                    }
                  }
                }
              }
              container advertise {
                tailf:cli-add-mode;
                list interface {
                  key "name";
                  tailf:cli-suppress-mode;
                  tailf:cli-delete-when-empty;
                  leaf name {
                    type ifname;
                  }
                }
                container explicit-null {
                  tailf:cli-compact-syntax;
                  tailf:cli-delete-when-empty;
                  presence "true";
                  leaf for {
                    type string;
                  }
                  leaf to {
                    type string;
                  }
                }
                leaf disable {
                  type empty;
                }
                list for {
                  tailf:cli-suppress-mode;
                  tailf:cli-delete-when-empty;
                  tailf:cli-compact-syntax;
                  tailf:cli-sequence-commands {
                    tailf:cli-reset-siblings;
                  }
                  key "acl";
                  leaf acl {
                    type string;
                  }
                  leaf to {
                    type string;
                  }
                }
                list to {
                  tailf:cli-suppress-mode;
                  tailf:cli-delete-when-empty;
                  tailf:cli-compact-syntax;
                  tailf:cli-sequence-commands {
                    tailf:cli-reset-siblings;
                  }
                  key "acl";
                  leaf acl {
                    type string;
                  }
                  leaf for {
                    type string;
                  }
                }
              }
            }
            container remote {
              tailf:cli-add-mode;
              container accept {
                tailf:cli-add-mode;
                list from {
                  tailf:cli-suppress-mode;
                  tailf:cli-delete-when-empty;
                  key "id";
                  leaf id {
                    type string;
                  }
                  leaf for {
                    type string;
                  }
                }
              }
            }
          }
          container traffic-eng {
            tailf:cli-add-mode;
            container auto-tunnel {
              container mesh {
                tailf:cli-add-mode;
                list group {
                  tailf:cli-suppress-mode;
                  tailf:cli-delete-when-empty;
                  key "id";
                  leaf id {
                    type union {
                      type enumeration {
                        enum all;
                      }
                      type uint32;
                    }
                  }
                }
              }
            }
          }
          container redistribute {
            tailf:cli-add-mode;
            container bgp {
              tailf:cli-add-mode;
              leaf as {
                type string;
              }
            }
          }
        }
      }
      container capabilities {
        choice sac-choice {
          leaf-list sac {
            tailf:cli-flat-list-syntax;
            type enumeration {
              enum fec128-disable;
              enum fec129-disable;
              enum ipv4-disable;
              enum ipv6-disable;
            }
          }
          container sac-mldp-only {
            tailf:cli-drop-node-name;
            container sac {
              leaf mldp-only {
                type empty;
              }
            }
          }
        }
      }
      list interface {
        key "name";
        leaf name {
          type string;
        }
        uses apply-group-grouping;
        container igp {
          container sync {
            container delay {
              leaf on-session-up {
                type union {
                  type uint16;
                  type enumeration {
                    enum disable;
                  }
                }
              }
            }
          }
        }
        container discovery {
          container hello {
            leaf holdtime {
              type uint16;
            }
            leaf interval {
              type uint16;
            }
          }
        }
        container address-family {
          container ipv4 {
            tailf:cli-add-mode;
            presence "true";
            container mldp {
              leaf disable {
                type empty;
              }
            }
            container discovery {
              leaf transport-address {
                type union {
                  type inet:ipv4-address;
                  type enumeration {
                    enum interface;
                  }
                }
              }
            }
          }
        }
      }
    }
    container oam {
      tailf:cli-add-mode;
      presence "true";
      container echo {
        leaf revision {
          type enumeration {
            enum 1;
            enum 2;
            enum 3;
            enum 4;
          }
        }
        leaf disable-vendor-extension {
          type empty;
        }
      }
      container dpm {
        tailf:cli-add-mode;
        presence "true";
        leaf pps {
          type uint8;
        }
        leaf interval {
          type uint16;
        }
      }
    }
    container static {
      tailf:cli-add-mode;
      presence "true";
      list ipv4 {
        tailf:cli-suppress-mode;
        tailf:cli-delete-when-empty;
        tailf:cli-compact-syntax;
        tailf:cli-sequence-commands {
          tailf:cli-reset-all-siblings;
        }
        key "address mask interface";
        leaf address {
          type inet:ipv4-address;
        }
        leaf mask {
          type inet:ipv4-address;
        }
        leaf interface {
          type string;
        }
        leaf nexthop {
          tailf:cli-drop-node-name;
          tailf:cli-optional-in-sequence;
          type inet:ipv4-address;
        }
        choice label-choice {
          leaf label {
            tailf:cli-drop-node-name;
            type uint32;
          }
          leaf ipv4-explicit-null {
            type empty;
          }
          leaf ipv6-explicit-null {
            type empty;
          }
          container pop {
            tailf:cli-compact-syntax;
            presence "true";
            choice pop-choice {
              leaf labelled {
                type empty;
              }
              leaf unlabelled {
                type empty;
              }
            }
          }
        }
      }
      list interface {
        key "name";
        tailf:cli-suppress-mode;
        tailf:cli-delete-when-empty;
        leaf name {
          type ifname;
        }
      }
      container address-family {
        list ipv4 {
          key "af-modifier";
          leaf af-modifier {
            type enumeration {
              enum unicast {
                tailf:code-name "ipv4_unicast";
              }
            }
          }
          list local-label {
            tailf:cli-sequence-commands {
              tailf:cli-reset-siblings;
            }
            key "id";
            leaf id {
              type uint32;
            }
            leaf allocate {
              tailf:cli-hide-in-submode;
              type empty;
            }
            leaf per-prefix {
              tailf:cli-hide-in-submode;
              tailf:cli-optional-in-sequence;
              type ipv4-prefix;
            }
            container forward {
              tailf:cli-break-sequence-commands;
              tailf:cli-add-mode;
              list path {
                tailf:cli-suppress-mode;
                tailf:cli-delete-when-empty;
                tailf:cli-compact-syntax;
                tailf:cli-sequence-commands {
                  tailf:cli-reset-siblings;
                }
                key "id";
                leaf id {
                  type uint16;
                }
                leaf nexthop {
                  type ifname;
                }
                leaf nexthop-address {
                  tailf:cli-optional-in-sequence;
                  tailf:cli-drop-node-name;
                  type inet:ipv4-address;
                }
                leaf out-label {
                  type union {
                    type uint32;
                    type enumeration {
                      enum exp-null;
                      enum pop;
                    }
                  }
                }
              }
            }
          }
        }
      }
      list vrf {
        key "name";
        leaf name {
          type string;
        }
        container address-family {
          list ipv4 {
            key "af-modifier";
            leaf af-modifier {
              type enumeration {
                enum unicast {
                  tailf:code-name "mpls_static_vrf_ipv4_unicast";
                }
              }
            }
            list local-label {
              tailf:cli-sequence-commands {
                tailf:cli-reset-siblings;
              }
              key "id";
              leaf id {
                tailf:cli-suppress-range;
                type uint32;
              }
              leaf allocate {
                tailf:cli-hide-in-submode;
                type empty;
              }
              choice allocate-choice {
                leaf per-prefix {
                  tailf:cli-hide-in-submode;
                  tailf:cli-optional-in-sequence;
                  type ipv4-prefix;
                }
                leaf per-vrf {
                  tailf:cli-hide-in-submode;
                  type empty;
                }
              }
              container forward {
                tailf:cli-break-sequence-commands;
                tailf:cli-add-mode;
                list path {
                  tailf:cli-suppress-mode;
                  tailf:cli-delete-when-empty;
                  key "id";
                  leaf id {
                    tailf:cli-suppress-range;
                    type uint8;
                  }
                  leaf pop-and-lookup {
                    type empty;
                  }
                }
              }
            }
          }
        }
      }
    }
    container ip-ttl-propagate {
      container disable {
        tailf:cli-delete-when-empty;
        presence "true";
        leaf disable-type {
          tailf:cli-drop-node-name;
          type enumeration {
            enum forwarded;
            enum local;
          }
        }
      }
    }
    leaf ip-ttl-expiration-pop {
      type uint8;
    }
    container lsd {
      container app-reg-delay {
        leaf disable {
          type empty;
        }
      }
      container ltrace-buffer {
        leaf multiplier {
          type uint8;
        }
      }
    }
    container ipv4 {
      leaf ttl-expiration-pop {
        type uint8;
      }
    }
    container ipv6 {
      leaf ttl-expiration-pop {
        type uint8;
      }
    }
  }
  container bmp {
    container server {
      container all {
        tailf:cli-add-mode;
        leaf max-buffer-size {
          type uint32;
        }
        container route-monitoring {
          container inbound {
            container post-policy {
              tailf:cli-add-mode;
              presence "true";
            }
            container pre-policy {
              tailf:cli-add-mode;
              presence "true";
            }
          }
          container local-rib {
            tailf:cli-add-mode;
            presence "true";
          }
        }
      }
      list server-list {
        tailf:cli-drop-node-name;
        key "id";
        leaf id {
          type uint8;
        }
        container host {
          tailf:cli-compact-syntax;
          tailf:cli-sequence-commands {
            tailf:cli-reset-siblings;
          }
          leaf name {
            tailf:cli-drop-node-name;
            type inet:host;
          }
          leaf port {
            type uint16;
          }
        }
        leaf dscp {
          type dscp-type;
        }
        uses description-grouping;
        leaf vrf {
          type string;
        }
        container update-source {
          uses interface-name-grouping;
        }
        leaf shutdown {
          type empty;
        }
        leaf flapping-delay {
          type uint16;
        }
        leaf initial-delay {
          type uint16;
        }
        leaf stats-reporting-period {
          type uint16;
        }
        container initial-refresh {
          tailf:cli-compact-syntax;
          tailf:cli-sequence-commands {
            tailf:cli-reset-siblings;
          }
          choice refresh-choice {
            leaf skip {
              tailf:cli-optional-in-sequence;
              type empty;
            }
            case delay {
              leaf delay {
                type uint16;
              }
              leaf spread {
                type uint16;
              }
            }
          }
        }
      }
    }
  }
  uses segment-routing-grouping;

  grouping segment-routing-grouping {
    container segment-routing {
      tailf:cli-add-mode;
      presence "true";
      container global-block {
        tailf:cli-compact-syntax;
        tailf:cli-sequence-commands {
          tailf:cli-reset-siblings;
        }
        leaf lower-bound {
          tailf:cli-drop-node-name;
          type uint32;
        }
        leaf upper-bound {
          tailf:cli-drop-node-name;
          type uint32;
        }
      }
      container local-block {
        tailf:cli-sequence-commands {
          tailf:cli-reset-siblings;
        }
        tailf:cli-compact-syntax;
        leaf lower {
          tailf:cli-drop-node-name;
          type uint32;
        }
        leaf upper {
          tailf:cli-drop-node-name;
          type uint32;
        }
      }
      container mapping-server {
        tailf:cli-add-mode;
        container prefix-sid-map {
          tailf:cli-add-mode;
          container address-family {
            container ipv4 {
              tailf:cli-add-mode;
              list prefix {
                tailf:cli-drop-node-name;
                tailf:cli-suppress-mode;
                tailf:cli-delete-when-empty;
                tailf:cli-compact-syntax;
                tailf:cli-sequence-commands {
                  tailf:cli-reset-siblings;
                }
                key "prefix";
                leaf prefix {
                  type inet:ipv4-prefix;
                }
                leaf SID-interval {
                  tailf:cli-drop-node-name;
                  type uint32;
                }
                leaf range {
                  type uint32;
                }
              }
            }
            container ipv6 {
              tailf:cli-add-mode;
              list prefix {
                tailf:cli-drop-node-name;
                tailf:cli-suppress-mode;
                tailf:cli-delete-when-empty;
                tailf:cli-compact-syntax;
                tailf:cli-sequence-commands {
                  tailf:cli-reset-siblings;
                }
                key "prefix";
                leaf prefix {
                  type tailf:ipv6-address-and-prefix-length;
                }
                leaf SID-interval {
                  tailf:cli-drop-node-name;
                  type uint32;
                }
                leaf range {
                  type uint32;
                }
              }
            }
          }
        }
      }
      container traffic-eng {
        tailf:cli-add-mode;
        presence "true";
        uses apply-group-grouping;
        uses segment-routing-te-srv6-grouping;
        container segment-lists {
          tailf:cli-add-mode;
          presence "true";
          container srv6 {
            tailf:cli-add-mode;
            presence "true";
            container sid-format {
              leaf usid-f3216 {
                type empty;
              }
            }
            leaf topology-check {
              type empty;
            }
          }
          list segment-list {
            key "name";
            leaf name {
              type string;
            }
            container srv6 {
              tailf:cli-add-mode;
              presence "true";
              list index {
                tailf:cli-suppress-mode;
                tailf:cli-delete-when-empty;
                key "id";
                leaf id {
                  type uint16;
                }
                leaf sid {
                  type string;
                }
              }
              leaf topology-check {
                type empty;
              }
            }
          }
        }
        container candidate-paths {
          tailf:cli-add-mode;
          presence "true";
          container all {
            tailf:cli-add-mode;
            presence "true";
            container source-address {
              choice address-choice {
                leaf ipv4 {
                  type inet:ipv4-address;
                }
                leaf ipv6 {
                  type inet:ipv6-address;
                }
              }
            }
          }
        }
        list interface {
          key "name";
          leaf name {
            type string;
          }
          container affinity {
            tailf:cli-add-mode;
            list color {
              tailf:cli-suppress-mode;
              tailf:cli-delete-when-empty;
              key "name";
              leaf name {
                type string;
              }
            }
            list name {
              tailf:cli-suppress-mode;
              tailf:cli-delete-when-empty;
              key "name";
              leaf name {
                type string;
              }
            }
          }
          leaf metric {
            type uint32;
          }
        }
        container logging {
          tailf:cli-add-mode;
          container policy {
            leaf status {
              type empty;
            }
          }
          container pcep {
            leaf peer-status {
              type empty;
            }
          }
        }
        list segment-list {
          key "name";
          leaf name {
            tailf:cli-suppress-range;
            type string;
          }
          leaf prefix {
            tailf:cli-drop-node-name;
            tailf:cli-prefix-key;
            type enumeration {
              enum name;
            }
          }
          list index {
            tailf:cli-suppress-mode;
            tailf:cli-delete-when-empty;
            key "id";
            leaf id {
              tailf:cli-suppress-range;
              type uint16;
            }
            choice config-choice {
              container mpls {
                choice mpls-choice {
                  leaf label {
                    type uint32;
                  }
                  leaf adjacency {
                    type union {
                      type inet:ipv4-address;
                      type inet:ipv6-address;
                    }
                  }
                }
              }
              container address {
                leaf ipv4 {
                  type inet:ipv4-address;
                }
              }
            }
          }
        }
        container on-demand {
          list color {
            key "id";
            leaf id {
              type uint32;
            }
            container srv6 {
              tailf:cli-add-mode;
              presence "true";
              container locator {
                tailf:cli-compact-syntax;
                tailf:cli-sequence-commands {
                  tailf:cli-reset-siblings;
                }
                leaf name {
                  tailf:cli-drop-node-name;
                  type string;
                }
                container binding-sid {
                  tailf:cli-flatten-container;
                  tailf:cli-compact-syntax;
                  container dynamic {
                    tailf:cli-flatten-container;
                    tailf:cli-compact-syntax;
                    container behavior {
                      tailf:cli-flatten-container;
                      tailf:cli-compact-syntax;
                      leaf ub6-insert-reduced {
                        type empty;
                      }
                    }
                  }
                }
              }
            }
            container source-address {
              choice address-source {
                leaf ipv4 {
                  type inet:ipv4-address;
                }
                leaf ipv6 {
                  type inet:ipv6-address;
                }
              }
            }
            leaf bandwidth {
              type uint32;
            }
            container dynamic {
              tailf:cli-add-mode;
              presence "true";
              leaf mpls {
                tailf:cli-hide-in-submode;
                type empty;
              }
              container pcep {
                tailf:cli-add-mode;
                presence "true";
              }
              container metric {
                tailf:cli-add-mode;
                presence "true";
                leaf type {
                  type enumeration {
                    enum igp;
                    enum te;
                    enum latency;
                    enum hopcount;
                  }
                }
                container margin {
                  choice margin-choice {
                    leaf absolute {
                      type uint32;
                    }
                    leaf relative {
                      type uint32;
                    }
                  }
                }
              }
              container disjoint-path {
                tailf:cli-compact-syntax;
                tailf:cli-sequence-commands {
                  tailf:cli-reset-siblings;
                }
                leaf group-id {
                  type uint16;
                }
                leaf type {
                  type enumeration {
                    enum link;
                    enum node;
                    enum srlg;
                    enum srlg-node;
                  }
                }
                leaf sub-id {
                  type uint16;
                }
              }
              leaf flex-alg {
                type uint16;
              }
              container anycast-sid-inclusion {
                tailf:cli-add-mode;
                presence "true";
              }
              leaf sid-algorithm {
                type uint8;
              }
              uses segment-routing-te-color-dyn-bounds-grouping;
              list affinity {
                key "name";
                leaf name {
                  type enumeration {
                    enum include-all;
                    enum include-any {
                      value 2;
                    }
                    enum exclude-any {
                      value 3;
                    }
                  }
                }
                list name-list {
                  tailf:cli-drop-node-name;
                  tailf:cli-suppress-mode;
                  tailf:cli-delete-when-empty;
                  leaf name {
                    tailf:cli-prefix-key;
                    type empty;
                  }
                  key "color";
                  leaf color {
                    type string;
                  }
                }
              }
              container affinity-mode {
                tailf:cli-drop-node-name;
                container affinity {
                  tailf:cli-add-mode;
                  grouping name-list-grouping {
                    list name {
                      tailf:cli-suppress-mode;
                      tailf:cli-delete-when-empty;
                      key "color";
                      leaf color {
                        type string;
                      }
                    }
                  }

                  container exclude-any {
                    tailf:cli-add-mode;
                    uses name-list-grouping;
                  }
                  container include-all {
                    tailf:cli-add-mode;
                    uses name-list-grouping;
                  }
                  container include-any {
                    tailf:cli-add-mode;
                    uses name-list-grouping;
                  }
                }
              }
            }
            leaf maximum-sid-depth {
              type uint8;
            }
            leaf pce-group {
              type string;
            }
            container per-flow {
              tailf:cli-add-mode;
              presence "true";
              list forward-class {
                tailf:cli-suppress-mode;
                tailf:cli-delete-when-empty;
                tailf:cli-compact-syntax;
                key "id";
                leaf id {
                  type union {
                    type uint8;
                    type enumeration {
                      enum default;
                    }
                  }
                }
                choice color-or-value {
                  leaf color {
                    type uint32;
                  }
                  leaf value {
                    tailf:cli-drop-node-name;
                    type uint8;
                  }
                }
              }
            }
            container steering {
              tailf:cli-add-mode;
              container path-invalidation {
                leaf drop {
                  type empty;
                }
              }
            }
            container constraints {
              tailf:cli-add-mode;
              container segments {
                tailf:cli-add-mode;
                leaf sid-algorithm {
                  type uint8;
                }
                leaf protection {
                  type enumeration {
                    enum protected-only;
                    enum protected-preferred;
                    enum unprotected-only;
                    enum unprotected-preferred;
                  }
                }
              }
            }
            container performance-measurement {
              tailf:cli-add-mode;
              presence "true";
              container liveness-detection {
                tailf:cli-add-mode;
                presence "true";
                container logging {
                  tailf:cli-add-mode;
                  presence "true";
                  leaf session-state-change {
                    type empty;
                  }
                }
                container liveness-profile {
                  container backup {
                    leaf name {
                      type string;
                    }
                  }
                  leaf name {
                    type string;
                  }
                }
                leaf invalidation-action {
                  type enumeration {
                    enum none;
                    enum down;
                  }
                }
              }
              container reverse-path {
                tailf:cli-add-mode;
                leaf label {
                  type uint32;
                }
              }
              container delay-measurement {
                tailf:cli-add-mode;
                presence "true";
                container logging {
                  tailf:cli-add-mode;
                  presence "true";
                  leaf delay-exceeded {
                    type empty;
                  }
                }
                container delay-profile {
                  leaf name {
                    type string;
                  }
                }
              }
            }
          }
        }
        leaf te-latency {
          type empty;
        }
        leaf maximum-sid-depth {
          type uint8;
        }
        list policy {
          key "name";
          leaf name {
            type string;
          }
          uses segment-routing-te-srv6-grouping;
          leaf bandwidth {
            type uint32;
          }
          container binding-sid {
            leaf mpls {
              type uint32;
            }
          }
          container source-address {
            choice address-source {
              leaf ipv4 {
                type inet:ipv4-address;
              }
              leaf ipv6 {
                type inet:ipv6-address;
              }
            }
          }
          container color {
            tailf:cli-compact-syntax;
            tailf:cli-sequence-commands;
            leaf value {
              tailf:cli-drop-node-name;
              type uint32;
            }
            container end-point {
              tailf:cli-flatten-container;
              tailf:cli-compact-syntax;
              choice af-choice {
                leaf ipv4 {
                  type inet:ipv4-address;
                }
                leaf ipv6 {
                  type inet:ipv6-address;
                }
              }
            }
          }
          leaf path-protection {
            type empty;
          }
          container autoroute {
            tailf:cli-add-mode;
            presence "true";
            container metric {
              choice metric-choice {
                leaf constant {
                  type uint32;
                }
                leaf relative {
                  type int8;
                }
              }
            }
            leaf force-sr-include {
              type empty;
            }
            container include {
              list ipv4 {
                tailf:cli-suppress-mode;
                tailf:cli-delete-when-empty;
                key "prefix";
                leaf prefix {
                  type union {
                    type ipv4-prefix;
                    type enumeration {
                      enum all;
                    }
                  }
                }
              }
              leaf all {
                type empty;
              }
            }
            leaf forward-class {
              type uint8;
            }
          }
          leaf shutdown {
            type empty;
          }
          container candidate-paths {
            tailf:cli-add-mode;
            presence "true";
            list preference {
              key "id";
              leaf id {
                type uint16;
              }
              container dynamic {
                tailf:cli-add-mode;
                presence "true";
                leaf mpls {
                  tailf:cli-hide-in-submode;
                  type empty;
                }
                container pcep {
                  tailf:cli-add-mode;
                  presence "true";
                  container address {
                    leaf ipv4 {
                      type inet:ipv4-address;
                    }
                  }
                }
                leaf weight {
                  type uint32;
                }
                container metric {
                  tailf:cli-add-mode;
                  presence "true";
                  leaf sid-limit {
                    type uint8;
                  }
                  leaf type {
                    type enumeration {
                      enum igp;
                      enum te;
                      enum latency;
                      enum hopcount;
                    }
                  }
                  container margin {
                    choice margin-choice {
                      leaf absolute {
                        type uint32;
                      }
                      leaf relative {
                        type uint32;
                      }
                    }
                  }
                }
                container anycast-sid-inclusion {
                  tailf:cli-add-mode;
                  presence "true";
                }
              }
              container explicit {
                list segment-list {
                  key "name";
                  leaf name {
                    type string;
                  }
                  leaf weight {
                    type uint32;
                  }
                  container reverse-path {
                    leaf segment-list {
                      type string;
                    }
                  }
                }
              }
              container lock {
                tailf:cli-add-mode;
                presence "true";
                leaf duration {
                  type uint16;
                }
              }
              container constraints {
                tailf:cli-add-mode;
                container segments {
                  tailf:cli-add-mode;
                  leaf sid-algorithm {
                    type uint8;
                  }
                  leaf protection {
                    type enumeration {
                      enum protected-only;
                      enum protected-preferred;
                      enum unprotected;
                      enum unprotected-only;
                      enum unprotected-preferred;
                    }
                  }
                  leaf adjacency-sid-only {
                    type empty;
                  }
                }
                container affinity {
                  tailf:cli-add-mode;
                  list rule {
                    tailf:cli-drop-node-name;
                    key "name";
                    leaf name {
                      type enumeration {
                        enum include-all;
                        enum exclude;
                        enum include-any;
                        enum exclude-any;
                      }
                    }
                    list color {
                      tailf:cli-suppress-mode;
                      tailf:cli-delete-when-empty;
                      key "name";
                      leaf name {
                        type string;
                      }
                    }
                    list name-list {
                      tailf:cli-drop-node-name;
                      tailf:cli-suppress-mode;
                      tailf:cli-delete-when-empty;
                      tailf:cli-sequence-commands;
                      leaf name {
                        tailf:cli-prefix-key;
                        type empty;
                      }
                      key "color";
                      leaf color {
                        type string;
                      }
                    }
                  }
                }
                container disjoint-path {
                  tailf:cli-compact-syntax;
                  tailf:cli-sequence-commands {
                    tailf:cli-reset-siblings;
                  }
                  leaf group-id {
                    type uint16;
                  }
                  leaf type {
                    type enumeration {
                      enum link;
                      enum node;
                      enum srlg;
                      enum srlg-node;
                    }
                  }
                  leaf sub-id {
                    type uint16;
                  }
                }
                uses segment-routing-te-color-dyn-bounds-grouping;
              }
              container bidirectional {
                tailf:cli-add-mode;
                leaf co-routed {
                  type empty;
                }
                leaf association-id {
                  type uint16;
                }
              }
              container backup-ineligible {
                tailf:cli-add-mode;
                presence "true";
              }
            }
          }
          container performance-measurement {
            tailf:cli-add-mode;
            container delay-measurement {
              tailf:cli-add-mode;
              presence "true";
              container logging {
                tailf:cli-add-mode;
                presence "true";
                leaf delay-exceeded {
                  type empty;
                }
              }
              container liveness-detection {
                tailf:cli-add-mode;
                presence "true";
                container logging {
                  tailf:cli-add-mode;
                  presence "true";
                  leaf session-state-change {
                    type empty;
                  }
                }
                leaf invalidation-action {
                  type enumeration {
                    enum none;
                    enum down;
                  }
                }
              }
              container reverse-path {
                tailf:cli-add-mode;
                leaf label {
                  type uint32;
                }
              }
              container delay-profile {
                leaf name {
                  type string;
                }
              }
            }
            container liveness-detection {
              tailf:cli-add-mode;
              presence "true";
              container liveness-profile {
                container backup {
                  leaf name {
                    type string;
                  }
                }
                leaf name {
                  type string;
                }
              }
              leaf invalidation-action {
                type enumeration {
                  enum none;
                  enum down;
                }
              }
              container logging {
                tailf:cli-add-mode;
                presence "true";
                leaf session-state-change {
                  type empty;
                }
              }
            }
            container reverse-path {
              tailf:cli-add-mode;
              leaf label {
                type uint32;
              }
            }
          }
          container steering {
            tailf:cli-add-mode;
            container bgp {
              leaf disable {
                type empty;
              }
            }
            container path-invalidation {
              leaf drop {
                type empty;
              }
            }
          }
          container per-flow {
            tailf:cli-add-mode;
            list forward-class {
              tailf:cli-suppress-mode;
              tailf:cli-delete-when-empty;
              key "id";
              leaf id {
                type uint8;
              }
              leaf color {
                type uint32;
              }
            }
          }
        }
        container affinity-map {
          tailf:cli-add-mode;
          leaf bit-map {
            tailf:cli-hide-in-submode;
            type empty;
          }
          list color {
            tailf:cli-drop-node-name;
            tailf:cli-suppress-mode;
            tailf:cli-delete-when-empty;
            tailf:cli-compact-syntax;
            tailf:cli-sequence-commands {
              tailf:cli-reset-siblings;
            }
            key "name";
            leaf prefix {
              tailf:cli-prefix-key;
              tailf:cli-drop-node-name;
              tailf:cli-optional-in-sequence;
              type enumeration {
                enum color;
                enum name;
              }
            }
            leaf name {
              tailf:cli-suppress-range;
              type string;
            }
            leaf bit-position {
              type uint8;
            }
          }
        }
        container pcc {
          tailf:cli-add-mode;
          presence "true";
          container source-address {
            leaf ipv4 {
              type inet:ipv4-address;
            }
          }
          container pce {
            container address {
              list ipv4 {
                key "address";
                leaf address {
                  tailf:cli-suppress-range;
                  type inet:ipv4-address;
                }
                leaf precedence {
                  type uint8;
                }
                container password {
                  tailf:cli-compact-syntax;
                  tailf:cli-sequence-commands;
                  uses password-grouping {
                    refine "secret";
                  }
                }
                container tcp-ao {
                  tailf:cli-compact-syntax;
                  tailf:cli-sequence-commands {
                    tailf:cli-reset-siblings;
                  }
                  leaf name {
                    tailf:cli-drop-node-name;
                    type string;
                  }
                  leaf include-tcp-options {
                    type empty;
                  }
                }
              }
            }
          }
          leaf report-all {
            type empty;
          }
          leaf maximum-sid-depth {
            type uint8;
          }
          container redundancy {
            leaf pcc-centric {
              type empty;
            }
          }
          list profile {
            key "id";
            leaf id {
              type uint16;
            }
            container autoroute {
              tailf:cli-add-mode;
              container include {
                leaf all {
                  type empty;
                }
                container ipv4 {
                  leaf all {
                    type empty;
                  }
                }
                container ipv6 {
                  leaf all {
                    type empty;
                  }
                }
              }
              leaf force-sr-include {
                type empty;
              }
            }
          }
          container timers {
            leaf delegation-timeout {
              type uint32;
            }
            leaf keepalive {
              type uint8;
            }
            leaf deadtimer {
              type uint8;
            }
            container initiated {
              leaf orphan {
                type uint8;
              }
              leaf state {
                type uint32;
              }
            }
          }
        }
        list explicit-path {
          key "name";
          leaf name {
            type string;
          }
          list index {
            tailf:cli-suppress-mode;
            tailf:cli-delete-when-empty;
            key "id";
            leaf id {
              type uint16;
            }
            choice config-choice {
              container address {
                leaf ipv4 {
                  type inet:ipv4-address;
                }
              }
              container mpls {
                leaf label {
                  type uint32;
                }
              }
            }
          }
          list policy {
            key "name";
            leaf name {
              type string;
            }
            container end-point {
              choice address-choice {
                leaf ipv4 {
                  type inet:ipv4-address;
                }
                leaf ipv6 {
                  type inet:ipv6-address;
                }
              }
            }
            leaf color {
              type uint32;
            }
            container binding-sid {
              leaf mpls {
                type uint32;
              }
            }
            container path {
              tailf:cli-add-mode;
              list preference {
                key "id";
                leaf id {
                  type uint16;
                }
                list explicit {
                  key "name";
                  leaf name {
                    type string;
                  }
                  leaf weight {
                    type uint32;
                  }
                }
              }
            }
            leaf shutdown {
              type empty;
            }
          }
        }
        container steering {
          tailf:cli-add-mode;
          presence "true";
        }
        container timers {
          tailf:cli-add-mode;
          container candidate-path {
            leaf cleanup-delay {
              type uint32;
            }
          }
          leaf cleanup-delay {
            type uint16;
          }
          leaf install-delay {
            type uint16;
          }
          leaf periodic-reoptimization {
            type uint32;
          }
          container exclude-item {
            container candidate-path {
              leaf cleanup-delay {
                type empty;
              }
            }
            leaf cleanup-delay {
              type empty;
            }
            leaf install-delay {
              type empty;
            }
            leaf periodic-reoptimization {
              type empty;
            }
          }
          leaf init-verify-restart {
            type uint16;
          }
          leaf init-verify-startup {
            type uint16;
          }
          leaf init-verify-switchover {
            type uint16;
          }
        }
      }
      container adjacency-sid {
        tailf:cli-add-mode;
        list interface {
          key "name";
          leaf name {
            type string;
          }
          container address-family {
            container ipv4 {
              container unicast {
                tailf:cli-add-mode;
                container l2-adjacency-sid {
                  choice sid-choice {
                    leaf absolute {
                      type uint32;
                    }
                    leaf index {
                      type uint32;
                    }
                  }
                }
              }
            }
          }
        }
      }
      container srv6 {
        tailf:cli-add-mode;
        presence "true";
        container logging {
          container locator {
            leaf status {
              type empty;
            }
          }
        }
        container encapsulation {
          tailf:cli-add-mode;
          leaf source-address {
            type inet:ipv6-address;
          }
          container traffic-class {
            choice traffic-class-choice {
              leaf value {
                tailf:cli-drop-node-name;
                type string;
              }
              container propagate {
                tailf:cli-delete-when-empty;
                presence "true";
                leaf disable {
                  type empty;
                }
              }
            }
          }
        }
        container locators {
          tailf:cli-add-mode;
          list locator {
            key "name";
            leaf name {
              type string;
            }
            container micro-segment {
              container behavior {
                leaf unode {
                  type enumeration {
                    enum psp-usd;
                    enum shift-only;
                  }
                }
              }
            }
            leaf prefix {
              type tailf:ipv6-address-and-prefix-length;
            }
            leaf algorithm {
              type uint8;
            }
          }
        }
      }
    }
  }

  grouping segment-routing-te-srv6-grouping {
    container srv6 {
      tailf:cli-add-mode;
      presence "true";
      container locator {
        tailf:cli-compact-syntax;
        tailf:cli-sequence-commands;
        leaf name {
          tailf:cli-drop-node-name;
          type string;
        }
        container binding-sid {
          tailf:cli-flatten-container;
          tailf:cli-compact-syntax;
          container dynamic {
            tailf:cli-flatten-container;
            tailf:cli-compact-syntax;
            container behavior {
              tailf:cli-flatten-container;
              tailf:cli-compact-syntax;
              leaf ub6-insert-reduced {
                type empty;
              }
            }
          }
        }
      }
    }
  }

  grouping segment-routing-te-color-dyn-bounds-grouping {
    container bounds {
      tailf:cli-add-mode;
      container cumulative {
        tailf:cli-add-mode;
        list type {
          tailf:cli-suppress-mode;
          tailf:cli-delete-when-empty;
          key "name";
          leaf name {
            type enumeration {
              enum hopcount;
              enum igp;
              enum latency;
              enum te;
            }
          }
          leaf value {
            tailf:cli-drop-node-name;
            type uint32;
          }
        }
      }
    }
  }

  container telemetry {
    container model-driven {
      tailf:cli-add-mode;
      presence "true";
      leaf strict-timer {
        type empty;
      }
      leaf max-sensor-paths {
        type uint16;
      }
      leaf max-containers-per-path {
        type uint16;
      }
      list destination-group {
        key "id";
        leaf id {
          type string;
        }
        leaf vrf {
          type string;
        }
        container address-family {
          list ipv4 {
            key "address port";
            leaf address {
              type inet:ipv4-address;
            }
            leaf port {
              type uint16;
            }
            uses telemetry-model-driven-dest-addr-grouping;
          }
          list ipv6 {
            key "address port";
            leaf address {
              type inet:ipv6-address;
            }
            leaf port {
              type uint16;
            }
            uses telemetry-model-driven-dest-addr-grouping;
          }
        }
      }
      list sensor-group {
        key "id";
        leaf id {
          type string;
        }
        list sensor-path {
          tailf:cli-suppress-mode;
          tailf:cli-delete-when-empty;
          key "name";
          leaf name {
            type string;
          }
        }
      }
      list subscription {
        key "id";
        leaf id {
          type string;
        }
        list sensor-group-id {
          tailf:cli-suppress-mode;
          tailf:cli-delete-when-empty;
          key "name";
          leaf name {
            type string;
          }
          leaf strict-timer {
            type empty;
          }
          leaf sample-interval {
            type uint32;
          }
        }
        list destination-id {
          tailf:cli-suppress-mode;
          tailf:cli-delete-when-empty;
          key "name";
          leaf name {
            type string;
          }
        }
        container source-interface {
          uses interface-name-grouping;
        }
        leaf source-qos-marking {
          type enumeration {
            enum af11;
            enum af12;
            enum af13;
            enum af21;
            enum af22;
            enum af23;
            enum af31;
            enum af32;
            enum af33;
            enum af41;
            enum af42;
            enum af43;
            enum cs1;
            enum cs2;
            enum cs3;
            enum cs4;
            enum cs5;
            enum cs6;
            enum cs7;
            enum default;
            enum ef;
          }
        }
      }
    }
    container policy-driven {
      tailf:cli-add-mode;
      container encoder {
        container gpb {
          tailf:cli-add-mode;
          uses telemetry-policy-driven-encoder-grouping;
        }
        container json {
          tailf:cli-add-mode;
          uses telemetry-policy-driven-encoder-grouping;
        }
      }
    }
  }
  container multicast-routing {
    tailf:cli-add-mode;
    presence "true";
    uses multicast-routing-grouping;
    list vrf {
      key "name";
      leaf name {
        type string;
      }
      uses multicast-routing-grouping;
    }
  }
  container alias {
    list alias-list {
      tailf:cli-drop-node-name;
      tailf:cli-suppress-mode;
      tailf:cli-delete-when-empty;
      key "name";
      leaf name {
        type string;
      }
      leaf line {
        tailf:cli-drop-node-name;
        tailf:cli-multi-value;
        type string;
      }
    }
    list exec {
      tailf:cli-suppress-mode;
      tailf:cli-delete-when-empty;
      key "name";
      leaf name {
        type string;
      }
      leaf line {
        tailf:cli-drop-node-name;
        tailf:cli-multi-value;
        type string;
      }
    }
    list config {
      tailf:cli-suppress-mode;
      tailf:cli-delete-when-empty;
      key "name";
      leaf name {
        type string;
      }
      leaf line {
        tailf:cli-drop-node-name;
        tailf:cli-multi-value;
        type string;
      }
    }
  }
  container process {
    container mandatory {
      list location {
        tailf:cli-suppress-mode;
        tailf:cli-delete-when-empty;
        key "name executable";
        leaf name {
          type string;
        }
        leaf executable {
          type string;
        }
      }
    }
  }
  list ltrace {
    tailf:cli-suppress-mode;
    tailf:cli-delete-when-empty;
    tailf:cli-compact-syntax;
    tailf:cli-sequence-commands {
      tailf:cli-reset-siblings;
    }
    key "name";
    leaf name {
      type string;
    }
    leaf mode {
      tailf:cli-prefix-key;
      type enumeration {
        enum static;
        enum dynamic;
      }
    }
    leaf scale-factor {
      tailf:cli-prefix-key;
      type enumeration {
        enum 0;
        enum 1;
        enum 2;
        enum 4;
        enum 8;
        enum 16;
      }
    }
    leaf location {
      tailf:cli-prefix-key;
      type empty;
    }
    leaf preconfigure {
      tailf:cli-prefix-key;
      tailf:cli-optional-in-sequence;
      type empty;
    }
  }
  container call-home {
    tailf:cli-add-mode;
    leaf vrf {
      type string;
    }
    container service {
      leaf active {
        type empty;
      }
    }
    leaf site-id {
      type string;
    }
    container sender {
      leaf from {
        type string;
      }
      leaf reply-to {
        type string;
      }
    }
    container contact {
      leaf smart-licensing {
        type empty;
      }
    }
    leaf contract-id {
      type string;
    }
    leaf customer-id {
      type string;
    }
    list mail-server {
      tailf:cli-suppress-mode;
      tailf:cli-delete-when-empty;
      key "address";
      leaf address {
        type string;
      }
      leaf priority {
        type uint8;
      }
    }
    leaf contact-email-addr {
      type string;
    }
    container http-proxy {
      tailf:cli-compact-syntax;
      tailf:cli-sequence-commands {
        tailf:cli-reset-siblings;
      }
      leaf address {
        tailf:cli-drop-node-name;
        type inet:host;
      }
      leaf port {
        type uint16;
      }
    }
    leaf phone-number {
      type string;
    }
    leaf rate-limit {
      type uint8;
    }
    container data-privacy {
      leaf level {
        type enumeration {
          enum normal;
          enum high;
        }
      }
      leaf hostname {
        type empty;
      }
    }
    leaf syslog-throttling {
      type empty;
    }
    container source-interface {
      uses interface-name-grouping;
    }
    container alert-group {
      leaf configuration {
        type empty;
      }
      leaf syslog {
        type empty;
      }
    }
    container alert-group-config {
      container snapshot {
        tailf:cli-add-mode;
        list add-command {
          tailf:cli-suppress-mode;
          tailf:cli-delete-when-empty;
          key "name";
          leaf name {
            type string;
          }
        }
      }
    }
    list profile {
      key "name";
      leaf name {
        type string;
      }
      leaf active {
        type empty;
      }
      container destination {
        container address {
          leaf email {
            type string;
          }
          list http {
            tailf:cli-suppress-mode;
            tailf:cli-delete-when-empty;
            tailf:cli-compact-syntax;
            tailf:cli-sequence-commands {
              tailf:cli-reset-siblings;
            }
            key "name";
            leaf name {
              type string;
            }
            leaf disabled {
              type empty;
            }
          }
        }
        container transport-method {
          choice transport-method-email-choice {
            leaf email {
              type empty;
            }
            container email-disable {
              tailf:cli-drop-node-name;
              container email {
                leaf disable {
                  type empty;
                }
              }
            }
          }
          leaf http {
            type empty;
          }
        }
        leaf message-size-limit {
          type uint32;
        }
      }
      container reporting {
        container smart-call-home-data {
          tailf:cli-delete-when-empty;
          presence "true";
          leaf disable {
            type empty;
          }
        }
        container smart-licensing-data {
          tailf:cli-delete-when-empty;
          presence "true";
          leaf disable {
            type empty;
          }
        }
      }
      container subscribe-to-alert-group {
        container snapshot {
          tailf:cli-delete-when-empty;
          tailf:cli-compact-syntax;
          tailf:cli-sequence-commands {
            tailf:cli-reset-siblings;
          }
          presence "true";
          uses call-home-profile-subscribe-to-alert-group-grouping;
        }
        container inventory {
          tailf:cli-delete-when-empty;
          tailf:cli-compact-syntax;
          tailf:cli-sequence-commands {
            tailf:cli-reset-siblings;
          }
          presence "true";
          uses call-home-profile-subscribe-to-alert-group-grouping;
        }
        container configuration {
          tailf:cli-delete-when-empty;
          tailf:cli-compact-syntax;
          tailf:cli-sequence-commands {
            tailf:cli-reset-siblings;
          }
          presence "true";
          uses call-home-profile-subscribe-to-alert-group-grouping;
        }
      }
    }
  }
  container cached-show {
    container version {
      leaf version {
        type string;
      }
      leaf model {
        type string;
      }
      leaf serial-number {
        type string;
      }
    }
  }
  container EXEC {
    tailf:cli-drop-node-name;
  }
  leaf bad-config {
    type empty;
  }
  leaf xyzexit {
    type uint8;
  }
  leaf xyzroot {
    type uint16;
  }
}
